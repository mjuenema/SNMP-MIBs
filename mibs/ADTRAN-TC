ADTRAN-TC    DEFINITIONS ::= BEGIN

    -- TITLE:       ADTRAN Textual Convention Definitions
    -- FILENAME:    adtrantc.mib
    -- AUTHOR:      Phil Bergstresser
    -- DATE:        00/03/29
    --
    -- PROCESS: END email requests to Heath Williams w/ product # & name
    --          CND email requests to Phil Bergstresser w/ product # & name
    --          Each backup for the other
    --
    -- MODIFICATIONS:
    --   2000/03/30 pnb Generate adProductID enumeration
    --   2000/04/12 pnb add alarm severity enumeration
    --   2000/04/24 pnb update productIds and adShared types from Source Safe doc
    --   2000/04/26 pnb same
    --   2000/05/03 pnb same, plus reorder some types
    --   2000/05/19 pnb same, reorder some comments
    --   2000/05/24 pnb correct 270 double comment flaw
    --   2000/06/19 pnb update adShared
    --   2000/07/31 pnb update from adtmib doc for options cards and additions.
    --                correct case typo in alarm severity.
    --   2000/08/04 pnb align comments for ease of reading, and
    --                update from latest adtmib.doc changes.
    --   2000/08/09 sls added TA1500 Dual FXO/DPT product ID
    --   2000/08/22 sls added TA3000 cards & MX2800STS1 (#s 286-288)
    --   2000/08/25 sls added TA1500 cards (#s 289-291)
    --   2000/09/15 sls added nodes to adShared
    --   2000/09/21 sls aded Lucent, TA1500, & Stratum card entries
    --   2000/10/02 sls added adTA1500LucentSCU
    --   2000/10/11 sls added adTA3000qADSL
    --   2000/10/23 sls added adATLAS890
    --   2000/10/26 sls added adTA1500FT1dp, adLucentLIU 2.4.1, adGenLIU &
    --                adDSX1Common
    --   2000/11/07 sls added adTA3000OctIMA
    --   2001/01/08 sls added adMgmt.303 - adMgmt.309 & adTSU1500SCUCommon
    --   2001/01/10 sls added adTA3000qHDSL2 & adTAGSHDSL
    --   2001/01/17 sls added adMX2810
    --   2001/02/16 sls corrected entries for enum 218,220, & 295
    --   2001/02/19 sls ATLAS 550 Packet Voice Rsrc Module
    --
    --   02/27/2001 sls added TA1500 Multi 4-Wire
    --   03/01/2001 sls added adTSULTX
    --   03/22/2001 sls added 316-321
    --   03/27/2001 sls consolidated 316-321 to 316-317 & added TA3000 G.SHDSL multi-ports
    --   04/05/2001 sls added 320-331 (TA 1500 access cards)
    --   04/10/2001 sls added adPSUcommon
    --   04/18/2001 sls added adTA1500DDSdp
    --   04/23/2001 sls added TA 3000 DS3 TSI E1 MUX (trap extension) place holders
    --   04/26/2001 sls added adGenSHDSL
    --   05/01/2001 sls added adTA3000CES
    --   05/03/2001 sls added adTARouterTraps
    --   05/09/2001 sls added adIQ710, its interface modules & adTA1500LcntUBR1TE
    --   05/18/2001 sls added adTA3000VCP
    --   05/23/2001 pnb added adExp6530SHDSL
    --   05/24/2001 pnb added adTA3000quadE1NTU
    --   05/29/2001 sls added ATLAS 810
    --   05/30/2001 sls added adTracerCommon
    --   05/31/2001 sls added adExp653x
    --   06/15/2001   sls added adTA608, adTA3000LTU8 & adTANTU8
    --   06/19/2001   sls added adTA3000DS1FR
    --   06/26/2001 sls added adTASHDSLbnc & adTASHDSLv35
    --   06/28/2001 sls added adTA3000ALEc
    --   06/29/2001 sls added Total Access 2nd Gen H2TUC  cards
    --   07/09/2001 sls added adTASHDSLSP
    --   07/31/2001 sls added adTA3000HTUCg6 & adTA3000HTUCg6HLSS
    --   08/13/2001 sls added adTADS3TSIE3
    --   08/22/2001 sls added several Total Access 1000 cards
    --   09/10/2001 sls added adXprs6503
    --   09/13/2001 sls added 3 HTUC cards
    --   09/21/2001 sls added adTA300DS3LM(371) & adTA300H2TURsprint(372)
    --   10/04/2001 sls added adTA1500MCU(373), adTA3000BATS(374) & adTA1500DDSdpQwest(375)
    --   10/19/2001 sls added adTA3000qSHDSL
    --   10/23/2001 sls added adTA3000T1OR
    --   10/25/2001 sls added adTA3000OC3CSM
    --   10/29/2001 sls added reserved14
    --   11/07/2001 sls added adTA1500DualCoinCot & adTA1500DualCoinRt
    --   11/12/2001 pnb added adDSX1CommonTraps (trap extender)
    --   11/16/2001 sls added adATLAS550NxT1hssi
    --   11/26/2001 sls added adNV1800
    --   11/28/2001 sls added adTASHDSLprot
    --   12/05/2001 pnb added adTA1500qFXOMLT(385)
    --   12/07/2001 pnb added adTAOC3L3(386) plus two trap extension IDs
    --   12/17/2001 pnb added EBS C & R phone cards
    --   01/07/2002 sls added 2nd Gen IQ710
    --   01/08/2002 pnb added quad E1
    --   01/11/2002 pnb added TA 1500 4 wire single DX cards
    --   01/23/2002 pnb added TA4303 PS
    --   01/24/2002 sls added Atlas 550 cards & corrected PNs on others
    --   01/24/2002 pnb added TA4303 STS1
    --   01/25/2002 sls added adunit
    --   01/25/2002 pnb added TA 3000 DS0 TSI Mux
    --   01/28/2002 pnb added TA4303 oBRI & adH4TUCcommon
    --   01/29/2002 pnb changed comment on product ID 3 (reserved00) to reflect usage
    --   01/30/2002 pnb added TA 3000 IVD
    --   02/01/2002 sls added TA550 modules
    --   02/05/2002 pnb added MX2810 STS1 card
    --   02/05/2002 pnb added TA3000 H4TUC
    --   02/07/2002 sls added added adTA850RCU
    --   02/14/2002 pnb added TA 3000 SHDSL 1.5 Gen LTUs
    --   02/20/2002 sls added ATLAS 800 modules & edited several existing ATLAS
    --                      entries to make more consistent
    --   02/24/2002 sls added ATLAS 830
    --   03/08/2002 pnb added TA 3000 H2TUC-HKT
    --   04/01/2002 pnb added TA 3000 octal ADSL
    --   04/02/2002 pnb added TA 3K HTUC cards
    --   04/03/2002 pnb added LTU4/NTU4
    --   04/05/2002 pnb added TA4303SNMP
    --   04/08/2002 pnb add TA3000 octal ADSL w/ POTS splitters
    --   04/19/2002 pnb add trap extension for MX28xx
    --   05/13/2002 sls add IAD entries in adShared
    --   05/16/2002 pnb add 28 slot DS3 TSI & mod description of 22 slot (264) for 3010
    --   05/17/2002 sls revise adTADSX1 comment
    --   05/22/2002 pnb change 445 to 455 and mark gap
    --   06/10/2002 pnb add H2TUC HLSS
    --   06/11/2002 pnb add H4TUC G2 (3)
    --   06/21/2002 pnb add 128 port CSM
    --   06/27/2002 pnb add comment to 319 for 2nd gen equivalence
    --   06/28/2002 sls add ATLAS 550 Dual Video
    --   07/02/2002 sls add ATLAS 800 Octal FXS
    --   07/10/2002 pnb add T200 SHDSL NTU
    --   07/11/2002 pnb add TA T1/E1 SHDSL LTU
    --   07/22/2002 pnb add shared GenOPTI3
    --   07/23/2002 pnb add OPTI3L2, and "Unknown" non-responsive generic
    --   07/30/2002 pnb add shared adGenAtm, & TA1500 4w cards
    --   08/02/2002 pnb add ta100 E1/T1 LIU
    --   08/05/2002 pnb add 3 1500 common nodes
    --   08/08/2002 pnb add TA3k DS3CSM cr
    --   08/08/2002 sls add adATLAS550EtherSwitch
    --   08/09/2002 sls add NetVanta 3xxx update/additions
    --   08/12/2002 sls add TA 6xx entries
    --   08/13/2002 pnb add E1FR and 1500 TO & FXS/GT cards
    --   08/27/2002 pnb add trap extension for generic OPTI3
    --   09/12/2002 pnb add shared DSx1FR
    --   09/18/2002 pnb add quad IMA cards
    --   09/27/2002 pnb add MX2820 19" shelf & cards
    --   10/16/2002 pnb add SHDSL4 LTU
    --   10/24/2002 pnb add TA1500 Single 4-Wire ETO
    --   10/29/2002 sls add adTa6xx & adIadIwf
    --   11/01/2002 sls add TA604, TA612, TA616
    --   11/13/2002 pnb add adGen654x to adShared
    --   12/12/2002 pnb add MX2820 23" shelf
    --   12/17/2002 pnb add OPTI-MX shelf & cards
    --   12/23/2002 sls add NV2xxx VPN products
    --   01/06/2003 pnb add OPTI-MX SCM controller
    --   02/03/2003 pnb add TA12xx shelves & cards
    --   02/04/2003 pnb add 512-520 TA3k variety
    --   02/06/2003 pnb adjust name/descr of SCU(517)
    --   02/06/2003 pnb add eSCU L3
    --   02/11/2003 pnb add & correct TA1500 ETO cards
    --   02/17/2003 pnb add new shared node for SHDSL4 products
    --   02/18/2003 pnb add 1500 Ubrite
    --   02/28/2003 pnb add adMCUcommon
    --   03/07/2003 sls add TA604, TA612, TA616: redundant
    --   03/11/2003 pnb add oADSL-c w/ ETA, remove redundant 6xx
    --   03/20/2003 sls add NetVanta 1224 & 1224ST
    --   04/02/2003 pnb add 1500FT1 shared
    --   04/08/2003 sls add ATLAS 550 NX
    --   04/09/2003 sls add ATLAS 550 Dual FXO
    --   04/18/2003 pnb add 1500 FXO GT
    --   04/22/2003 pnb add OMM12 shared and product, and 1500 4W TDM
    --   04/23/2003 pnb add OptiSMXshelf
    --   05/02/2003 pnb add 1200 ADSL IDs (same Product# as shelf)
    --   05/02/2003 pnb add adOptical shared node for Phoenix (JV)
    --   05/07/2003 pnb add DS3Mux L3, L4
    --   05/14/2003 pnb add SAM/DSLAM equivalents for TA3xxx shelf types
    --   05/28/2003 sls add adTAH4TUCmg
    --   05/29/2003 sls add OptiMX VT1.5 & TA300 Quad DS1/Mux to/from Fiber
    --   06/11/2003 pnb change symbol for adShared(51) HDSL group (BS, BT, JT)
    --   06/16/2003 pnb Added adShared node for adRFC2955, & ProdID for TA3k QFrAtm line card
    --   07/11/2003 sls add adGenAOS node to adShared
    --   07/28/2003 pnb add OC3Q mux IDs
    --   07/29/2003 pnb add IAD 6xx 3rd gen
    --   08/08/2003 pnb add MX2820 M13L10
    --   09/03/2003 pnb add H4TUCL2
    --   09/18/2003 pnb add OptiMux cards
    --   09/24/2003 sls add adSmart16eGen2
    --   09/24/2003 pnb modify descr & label on H2TUCG3(434), & add MX2820 STS1
    --   09/30/2003 pnb Add TA4303Plus codes + MTC
    --   10/03/2003 pnb Add Exp6531
    --   10/08/2003 sls Add IQ790 & NetVanta 5305
    --   10/09/2003 pnb Add 1124/1125
    --   10/10/2003 sls Add assorted NetVanta units & modules
    --   10/16/2003 pnb Add H2TUC HLSS dual circuit models
    --                  and make all date formats Y2K compliant (CCYY)
    --   10/21/2003 pnb Add TA1124 internal cards
    --   10/22/2003 dhw Add adTracer6420
    --   10/31/2003 pnb Add ETHM
    --   11/04/2003 pnb Add adShared Accessories
    --   11/13/2003 dhw Add adTSUNvRouter
    --   11/17/2003 dhw Add adIQ7xxT1Probe
    --   11/18/2003 pnb Add 1500 quad 232, ETOcommon, 4wTDMcommon, CN1200, OPT-MX GB Eth,
    --                  H2TUC sp dc HLSS, TA900R ac/dc
    --   12/05/2003 pnb Add 3000 QDFC
    --   12/10/2003 pnb Add TA110x models
    --   12/15/2003 pnb Add TA30x0 Accessory shelves & modules
    --   12/29/2003 pnb Add TA1500 TRI-C DP
    --   01/09/2004 pnb Add TA3000 LPU
    --   01/16/2004 pnb Add Opti-MX line cards
    --   01/27/2004 dhw Add adIQ310
    --   01/28/2004 pnb Add TA3000 RMM, 16 port IMA SHDSL, quad SHDSL E1/CES
    --   02/04/2004 dhw Add adNV5xxxT3
    --   02/05/2004 pnb Add shared node for future TA1500 branches (KW)
    --   02/25/2004 pnb Add shared node for trap extension for OPTI-MX
    --   03/10/2004 dhw Add adNV950, adNV3350, adNVxx50ESM, adNVxx50FXS, adNVxx50FXO, adNV3350DSS, adNV950T1V35
    --   03/11/2004 pnb Add 1500 FXS singles
    --   04/14/2004 pnb add 1500 cards and IAD ATM family
    --   04/20/2004 pnb add OPTI-MX ethernet card
    --   04/22/2004 pnb add TA3000 ADSL2+ Line Card
    --   05/07/2004 pnb add Spirent ITH  & SM2
    --   05/07/2004 pnb correct 1500 names & descriptions (237/294)
    --   05/17/2004 pnb Add shared node for future SHDSL branches
    --   05/27/2004 pnb Add TA3000 DS1 Cut-thru
    --   06/18/2004 pnb Add MX3yyy
    --   06/28/2004 pnb Add Opti-Mx DS1VME
    --   06/29/2004 pnb Add 1124/48, 1224/48 family
    --   07/07/2004 pnb Add OPTI-MX ETHM8E
    --   07/08/2004 pnb Add Express 654x remotes
    --   07/23/2004 pnb Add Opti-6100 VT Cross Coneect Mux
    --   07/27/2004 pnb Add 11xx/12xx products
    --   07/29/2004 pnb Add 11xx/12xx component cards
    --   08/11/2004 pnb add 11xx/12xx Verizon products
    --   08/16/2004 pnb add TA3000 OC3LM & Hex SHDSL cards
    --   08/19/2004 dhw change NV3350 descriptions to NV970
    --   08/27/2004 dhw add adNV1224RPWR, adNV1224STRPWR, adNV1224PWR, adNV1224STPWR
    --   09/01/2004 pnb add CND Rem Rep shared branch (KE, BT)
    --   09/02/2004 dhw add adNV340
    --   09/09/2004 pnb correct 734-739
    --   09/15/2004 pnb Add TA5000 products
    --   10/06/2004 dhw Add NV1524ST
    --   10/06/2004 pnb Add Opti-MX DS3M3E
    --   10/11/2004 pnb Add TA3k Hex POTS cards
    --   10/12/2004 dhw Add adNV344 and corrected descriptions for 1224 POE's
    --   10/15/2004 pnb add TA3000 quad VDSL
    --   11/05/2004 pnb Add TA1240
    --   11/15/2004 pnb Add LTU8cr
    --   11/15/2004 pnb Add octal ADSL2+
    --   11/15/2004 dhw Add NV3xxx Dual T1 Card
    --   12/17/2004 pnb Add MX3 RMM, TA3k 19" fans
    --   01/13/2005 pnb Add IMA Gen3
    --   01/25/2005 pnb Add 3050 splitters
    --   02/02/2005 pnb Add shared MiniDSLAM node
    --   02/15/2005 dhw Add TA908,TA912,TA916,TA908e,TA912e,TA916e
    --   02/25/2005 pnb Add TAEMS
    --   02/28/2005 pnb Add OptiO3TME and TA3k 2g CSM128
    --   03/01/2005 pnb Add TA4303 SCU+ L2
    --   03/03/2005 pnb Add Opti-6100 OMM-12 SDH
    --   03/08/2005 pnb Add SCM international
    --   03/23/2005 dhw Changed part numbers for TA912, TA912e, TA916, TA916e
    --   03/23/2005 dhw Added adTA912eDualT1, adTA912eQuadT1, adTA916eDualT1, adTA916eQuadT1, adTA924eDualT1, adTA924eQuadT1
    --   03/23/2005 pnb Added Opti DS1VMT
    --   03/24/2005 pnb Add Opti STS/VLAN cards
    --   04/12/2005 pnb Add OMM3 & OMM12 muxes


    -- *** ENSURE ANY UPDATES TO THIS FILE ARE ALSO REFLECTED IN ADTRANTC.MI2 ***

    -- This mmodule of Textual Conventions contains definitions that can be
    --   imported into MIB modules so that independent additions can be made
    --   for new products without affecting existing MIBs.



    -- TYPES

    -- The first tier (adtran) and second tier (adProducts, adMgmt, adAdmin,
    --   adPerform, adShared) object identifiers are defined in the ADTRAN-MIB module.

    -- The third tier of adProducts and adMgmt object identifiers are defined
    --   in each product specific MIB in accordance with the enumeration above
    --   of the AdProductIdentifier textual convention type.

    -- The third tier of adAdmin objects are defined in the ADTRAN-MIB module.

    -- The third tier of adPerform objects are named here for use in generic
    --   performance statistics MIBs.

    -- The third tier of adShared objects are named here for use in generic
    --   shared MIBs.


    -- The following type defines the third tier of the ADTRAN OID sub-tree,
    --   or specifies where they are defined.
    -- They may be redefined in legacy modules, but the OIDs must mean the same.


    -- This type is used to define the product leaves
    --   in the subtree adtran(664).adProducts(1)

    AdProductIdentifier ::= INTEGER {  -- use to define all ADTRAN product OIDs
        adADVISOR(1),                  -- ADVISOR SNMP Proxy Agent
        adACTDAX(2),                   -- ACTDAX List 2
        reserved00(3),                 -- Used by the adDS1 DS1 extension MIB for mg only
        adTSU(4),                      -- TSU T1 Mux
        adLIU3(5),                     -- LIU3-PM T1 Line Interface Unit
        adOCUDP(6),                    -- OCUDP-PM / SD4 Channel Unit
        adDDST(7),                     -- DDST-PM DDS Termination Unit
        adDSUDP(8),                    -- DSUDP Channel Unit
        adACTDAXL3(9),                 -- ACTDAX List 3 - ACT1241 Line Interface Unit
        adTSU100(10),                  -- TSU 100 - T1 Multiplexer
        adTSU600(11),                  -- TSU 600
        adLPRPTR(12),                  -- LOOP REPEATER-PM
        adDSU3ARs(13),                 -- DSU III AR (standalone same as shelf MIB)
        adDSU3AR(14),                  -- DSU III AR (shelf)
        adDSU3S4Ws(15),                -- DSU III AR Switch 4 Wire
        adDSU3S4W(16),                 -- DSU III AR Switch 4 Wire (shelf)
        adDSU3DBS4Ws(17),              -- DSU III AR Dial Backup Switch 4 Wire
        adDSU3DBS4W(18),               -- DSU III AR Dial Backup S4W (shelf)
        adDSU3DBS2Ws(19),              -- DSU III AR Dial Backup Switch 2 Wire
        adDSU3DBS2W(20),               -- DSU III AR Dial Backup S2W (shelf)
        adDSU3DBV32s(21),              -- DSU III AR Dial Backup V.32
        adDSU3DBV32(22),               -- DSU III AR Dial Backup V.32 (shelf)
        adDSU3DBISDNs(23),             -- DSU III AR Dial Backup ISDN
        adDSU3DBISDN(24),              -- DSU III AR Dial Backup ISDN (shelf)
        adDSUS2Ws(25),                 -- DSU III Switch 2 Wire
        adOCUDPP(26),                  -- OCUDP-PLUS+ Channel Unit
        adDSUS2W(27),                  -- DSU III Switch 2 Wire (shelf)
        adACT2300BCU(28),              -- ACT2300 Bank Control Unit List 1
        adACT2300LIU(29),              -- ACT2300 Line Interface Unit List 1
        adACT2300OSU(30),              -- ACT2300 Office Support Unit List 1
        adACT2300PWR(31),              -- ACT2300 Power Unit List 1
        adHSU100(32),                  -- HDSL TSU100
        adHSU600(33),                  -- HDSL TSU600
        adSMART16SC(34),               -- Smart 16 Shelf Controller
        adSITEMGR(35),                 -- ACT2300 Site Manager
        adDSU3DBV34(36),               -- DSU III AR Dial Backup V.34 (shelf)
        adDSUCARs(37),                 -- DSU III AR Compression
        adDSUCAR(38),                  --
        adDSUCS4Ws(39),                -- DSU III AR C Switch 4 Wire
        adDSUCS4W(40),                 --
        adDSUCDBS4Ws(41),              -- DSU III AR C Dial Backup Switch 4 Wire
        adDSUCDBS4W(42),               --
        adDSUCDBS2Ws(43),              -- DSU III AR C Dial Backup Switch 2 Wire
        adDSUCDBS2W(44),               --
        adDSUCDBV32s(45),              -- DSU III AR C Dial Backup V.32
        adDSUCDBV32(46),               --
        adDSUCDBISDNs(47),             -- DSU III AR C Dial Backup ISDN
        adDSUCDBISDN(48),              --
        adTDMs(49),                    -- DSU III Time Division Mux (TDM) stand alone
        adTDM(50),                     -- DSU III TDM (shelf)
        adTDMDBS4Ws(51),               -- DSU III TDM Dial Backup Switch 4 Wire
        adTDMDBS4W(52),                -- DSU III TDM Dial Backup S4W (shelf)
        adTDMDBS2Ws(53),               -- DSU III TDM Dial Backup Switch 2 Wire
        adTDMDBS2W(54),                -- DSU III TDM Dial Backup S2W (shelf)
        adTDMDBV32s(55),               -- DSU III TDM Dial Backup V.32
        adTDMDBV32(56),                -- DSU III TDM Dial Backup V.32 (shelf)
        adTDMDBISDNs(57),              -- DSU III TDM Dial Backup ISDN
        adTDMDBISDN(58),               -- DSU III TDM Dial Backup ISDN (shelf)
        adISU128(59),                  -- ISU 128 (shelf)
        adISU2X64(60),                 -- ISU 2 X 64 (shelf)
        adT1CSUACE(61),                -- T1 ESF CSU ACE
        adSMX(62),                     -- SMX RS485 DSU PM channel unit
        adEMTO(63),                    -- EMTO - 4WE&M PM channel unit
        adLIU3PML2(64),                -- LIU3 PM List 2
        adTSURM(65),                   -- TSU RM - SMART16 Shelf card
        adCSURM(66),                   -- CSU RM - SMART16 Shelf card
        adFXS2DPO(67),                 -- D4 analog channel unit
        adFXO2DPT(68),                 -- D4 analog channel unit
        adExpressSL(69),               -- Express SL
        adTSUNXBase(70),               -- Nx56/64 V.35/530
        adTSUNxV35(71),                -- Nx56/64 V.35
        adTSUNx530(72),                -- Nx56/64 530
        adTSUDSX1(73),                 -- DSX-1 Plug In
        adTSUOCU(74),                  -- OCU DP
        adTSUDI(75),                   -- Drop  and Insert
        adTSUFXS(76),                  -- FXS
        adTSUunassign(77),             -- ???????
        adTSUDSX1PO(78),               -- DSX-1 Plug On
        adTSUFXO(79),                  -- FX0
        adTSUDBU(80),                  -- Multi Port DBU
        adTSUNX2(81),                  -- 2nd Gen Nx56/64 V.35/530
        adTSUNX2V35(82),               -- 2nd Gen Nx56/64 V.35
        adTSUNX2530(83),               -- 2nd Gen Nx56/64 530
        adTSUEM(84),                   -- E and M
        adTSUCmprss(85),               -- Compression Card
        adTSUNxBase120(86),            -- Base 120 Nx
        adTSUDsxBase120(87),           -- Base 120 Dsx
        adTSUFXS2(88),                 -- FXS Voice 2
        adTSUNxDBU(89),                -- Nx DBU
        adTSUDsxBase140(90),           -- Base 140 Dsx
        adTSUPassThru(91),             -- Pass Thru
        adTSUMUXAgent(92),             -- Agent
        adTSUNX2DUAL(93),              -- Dual Nx56/64
        adTSUDSUDP(94),                -- Dual DSU III
        adNxDBUTest(95),               -- Nx DBU Test Card
        adTSUDModem(96),               -- Dual V.34 Modem
        adTSUQmodem(97),               -- Quad V.34 Modem
        adTSUDXC(98),                  -- DXC
        adTSUUBrite(99),               -- U Brite
        adTSUNxeBase(100),             -- TSU 1x0e Base Nx56/64
        adTSUDsxBase120e(101),         -- TSU120e Base DSX-1
        adTSUDUALOCU(102),             -- Dual OCU DP
        adTSUNXDBUeBase(103),          -- TSU 1x0e Base NXDBU
        adFXSG2(104),                  -- FXS_Gen2
        adTSU4FXS(105),                -- Quad FXS
        adTSU8FXS(106),                -- Octal FXS
        adTSUNxIQ(107),                -- Nx IQ
        adTSURtr(108),                 -- Router
        adTSUDrop(109),                -- DropPort
        adESUNxBase(110),              -- ESUBaseNx
        adTSU4FXSG2(111),              -- Quad FXS Gen2
        optionCards70to120(120),       -- TSU Mux option cards
        adDS0PM(121),                  -- DS0DP /PM
        adUBRITE(122),                 -- UBRITE /PM
        adISU512(123),                 -- ISU512 standalone unit
        adTSUMUXAGENT(124),            -- TSU Embedded Agent Option card
        adDSUIVESP(125),               -- DSU IV ESP
        adFSU(126),                    -- FSU
        adTSUESP(127),                 -- TSU ESP
        adTSU120(128),                 -- TSU 120
        adTSU600e(129),                -- TSU 600 e
        adTSU120e(130),                -- TSU 120 e
        ad4WEM(131),                   -- 4 Wire E&M
        ad2WEM(132),                   -- 2 Wire E&M
        adESPEtherCard(133),           -- ESP Ethernet Card
        adESPS4WCard(134),             -- ESP S4W DBU Card
        adESPV34Card(135),             -- ESP V34 DBU Card
        adESPISDNCard(136),            -- ESP ISDN DBU Card
        adESPDTECard(137),             -- ESP DTE DBU Card
        adESPDualISDNCard(138),        -- ESP Dual ISDN DBU Card
        adFramePort144(139),           -- D4 FramePort 144
        adFSU5622(140),                -- FSU 5622 ESP
        adDSUIQ(141),                  -- DSU IQ
        adTSU100e(142),                -- TSU 100 with Embedded SNMP
        adATLAS800(143),               -- ATLAS 800 (1200.180L1)
        adCOFRAD(144),                 -- CO FRAD
        adFramePort768(145),           -- D4 FramePort 768
        adBR110Chassis(146),           -- BR 1/10 Chassis used by CO FRAD
        adTSUIQ(147),                  -- TSU IQ
        adExpressL128FR(148),          -- Express L128 Frame Relay    1202.070L1
        adExpressL768(149),            --  Express L768 1202.192L1
        adExpressL15(150),             -- Express L1.5   1202.192L2
        adTotalAccessSCU(151),         -- Total Access SCU (1181.010L1)
        adTotalAccessHTUC(152),        -- Total Access HTU-C (1181.101L1)
        adTDU120E(153),                -- TDU 120 E
        adATLASGen(154),               -- ATLAS Generic
        adATLAS800Plus(155),           -- ATLAS 800Plus (1200.226L1)
        adATLAS1200(156),              -- ATLAS 1200
        adATLASOC(157),                -- ATLAS Generic Option Card
        adATLAST1PRI4OC(158),          -- ATLAS T1PRI4 Option Card (1200.185L1-L3)
        adATLASV35Nx4OC(159),          -- ATLAS V35Nx4 Option Card 1200184L1
        adATLASUBRI8OC(160),           -- ATLAS UBRI8 Option Card 1200186L2
        adATLAST3OC(161),              -- ATLAS T3 Option Card 1200223L1
        adATLASSerialOC(162),          -- ATLAS Serial Option Card 1200182L1
        adATLASModemOC(163),           -- ATLAS Modem Option Card 1200181L1
        adATLASE1OC(164),              -- ATLAS E1 Option Card 1200264L1
        adATLASHDLCOC(165),            -- ATLAS HDLC Option Card 1200222L1
        adATLASCompVoiceOC(166),       -- ATLAS Comp Voice Option Card (1200.221L1 - L4)
        adATLASSyncSerialOC(167),      -- ATLAS Synchronous Serial OC (NO LONGER ACTIVE)
        adESU120e(168),                -- ESU 120e 1200.420L1
        adESU120eHDSL(169),            -- ESU 120e HDSL 1200.421L1
        adT3SU300(170),                -- T3SU-300 1200.217L1
        adBRFP144(171),                -- BR 1/10 FramePort 144
        adBRFP768(172),                -- BR 1/10 FramePort 768
        adBRFP768SP(173),              -- BR 1/10 FramePort 768 SpanPowering
        adT3SUHSSIOC(174),             -- T3SU HSSI Option Card
        adT3SUV35OC(175),              -- T3SU V35 Option Card
        adIQPROBE(176),                -- IQPROBE
        adESPEM(177),                  -- Dual ESP E&M Option Card
        adESPFXO(178),                 -- Dual ESP FXO Option Card
        adESPFXS(179),                 -- Dual ESP FXS Option Card
        adTotalAccessNMI(180),         -- Total Access NMI
        adTADS3MUX(181),               -- Total Access DS3 MUX
        adTotalAccessE1HDSL(182),      -- Total Access E1 HDSL LTU (1181.102L1)
        adT3SUQDSX1OC(183),            -- T3SU Quad DSX1 Option Card
        adTAGenCard(184),              -- Total Access Generic Card
        adTotalAccessHD10(185),        -- Total Access HD10 (1181.200L1)
        adTSUIQPlus(186),              -- TSU IQ+
        adTAQFOC(187),                 -- Total Access Westell Quad Fiber Optic Card
        adTA3000DSX1(188),             -- Total Access 3000 DSX1 Module (1181.050L1)
        adTASTS1Mux(189),              -- Total Access STS1 Mux
        reserved01(190),               -- Total Access STS1 Mux (trap extension)
        adTAT1OR(191),                 -- Total Access Westell T1 Office Repeater
        adTAECU(192),                  -- Total Access E1 External Clock Module
        reserved02(193),               -- Total Access DS3 MUX (trap extension)
        adTAOC3MUX(194),               -- Total Access OC-3 MUX
        adTSU610(195),                 -- TSU 610
        adISU512e(196),                -- ISU 512e
        reserved03(197),               -- Total Access DSX1 module (trap extension)
        adMX2800(198),                 -- MX2800 (T3 Mux)
        adESULT(199),                  -- ESU LT
        adD4DIGROUP(200),              -- Virtual FramePort Controller
        adTAH2TUC(201),                -- Total Access H2TUC for Bell Atl. (1181.111L1)
        adTAHD10E1(202),               -- Total Access HD10 E1 version
        adTADS3MUXL2(203),             -- Total Access DS3 MUX List 2
        adTA850BCU(204),               -- Total Access 850 BCU
        reserved04(205),               -- Total Access OC-3 MUX (trap extension)
        adTRSDSL(206),                 -- D4 TR-SDSL
        adBRTRSDSL(207),               -- BR1/10 TR-SDSL
        adEx6100(208),                 -- Express 6100
        adTAE1LTU(209),                -- Total Access HDSL LTU (1182007L1)
        adTA750BCU(210),               -- Total Access 750 BCU (1175012L1)
        adTAQuadFXS(211),              -- Total Access Quad FXS (1175408L1)
        adTAQuadFXO(212),              -- Total Access Quad FXO (1175407L1)
        adTANx64(213),                 -- Total Access Nx56/64 (1175025L1)
        adTAOCUDP(214),                -- Total Access OCU-DP (1180005L1)
        adTADSODP(215),                -- Total Access DSO-DP (1180003L1)
        adTAUBRITE(216),               -- Total Access U-BRITE (1180020L1)
        adTSUIQRM(217),                -- TSU IQ Smart 16 Rackmount
        adF3SU300(218),                -- NTU-45 (1200.660L1) former name: F3SU-300
        adATLAS550(219),               -- ATLAS 550
        adTALTU45(220),                -- Total Access LTU-45 (1182.033L1)
        adTA1500qLIU(221),             -- TA1500 Quad LIU (1180109L1)
        adTA1500dLIU(222),             -- TA1500 Dual LIU (1180009L1)
        adTA1500SCUrt(223),            -- TA1500 SCU RT w/MLT (1180008L2)
        adTA1500SCUcot(224),           -- TA1500 SCU COT w/MLT (1180008L3)
        adTAEM(225),                   -- TotalAccess E&M (1180402L1)
        adTAFXO(226),                  -- TotalAccess FXO/DPT (1180404L1)
        adTAFXS (227),                 -- TotalAccess FXS (1180403L1)
        adTAqPOTS(228),                -- TotalAccess Quad POTS RT (1180408L1)
        adTA1500SCU(229),              -- TA1500 SCU w/o MLT  (1180008L1)
        adTA1500DualFXS(230),          -- Total Access 1500 Dual FXS (1180208L1)
        adTA1500DualFXO(231),          -- Total Access 1500 Dual FXO (1180207L1)
        adLucentDualOCUDP(232),        -- Lucent Dual OCUDP (1133205L1)
        adLucentDualDS0DP(233),        -- Lucent Dual DS0DP (1133203L1)
        adTASTS1MuxL2(234),            -- Total Access STS1 Mux L2 (1181030L2)
        adTA4303(235),                 -- Total Access 4303 (1200.330L1) chassis
        reserved05(236),               -- Total Access STS1 Mux L2 (trap extension)
        adTA1500EMsmas(237),           -- TA1500 E&M w/SMAS (1180402L2 / 1133402L1)
        adTAH2TUCgte(238),             -- Total Access H2TUC for GTE  (1181.111L2)
        adTAH2TUCsbc(239),             -- Total Access H2TUC for SBC (1181.111L4)
        adTAH2TUCclec(240),            -- Total Access H2TUC for CLEC (1181.111L1#C)
        adTA3000eSCU(241),             -- Total Access SCU (1181.018L1)
        adESPPRIdbu(242),              -- ESP PRI DBU Card
        adTA1500DualDSU(243),          -- Total Access 750/1500 Dual DSU DP (1175225L1)
        adTA4303Ctrl(244),             -- TA4303 EN GR303 Controller 1200.334L1
        adTA3000(245),                 -- TA3000  1181.001L1 TA3000 23 inch domestic shelf
        adTA3010(246),                 -- TA3010  1182.003L1 TA3010 19 inch domestic shelf
        adTA3011(247),                 -- TA3011  1182.001L1 Total Access OMP-FC
        adTA3011Mex(248),              -- TA3011   1181.001L1#M Total Access for Mexico
        adTA3012(249),                 -- TA3012  1182.004L1 Total Access 3000 DA
        adTA1500(250),                 -- TA1500  1180.001L1 TA1500 23 inch chassis
        adTA1000(251),                 -- TA1000  1179.001L1 Total Access 1000 OSP housing
        adTA1000COT(252),              -- TA1000   1179.501L1 Total Access 1000 COT chassis
        adTA850(253),                  -- TA850  1200.375L1 Total Access 850 chassis
        adTA750(254),                  -- TA750  1175.001L1 Total Access 750 chassis
        adATLASt3DI(255),              -- ATLAS T3 Drop & Insert module 1200225L1
        adATLASussi(256),              -- ATLAS USSI module (1200.261L1-L4)
        adATLASimux(257),              -- ATLAS IMUX (Nx56/64 Bonding Rsrc) module (1200.262L1)
        adATLAS8DSX(258),              -- ATLAS Octal DSX module 1200317L1
        adATLAS4DSX(259),              -- ATLAS Quad DSX module 1200320L1
        adTA4303QuadDSX(260),          -- TA4303 Quad DSX module 1200331L1
        adTA4303OctalDSX(261),         -- TA4303 Octal DSX module 1200332L1
        adTA4303DS3(262),              -- TA4303 DS3 module 1200333L1
        adTA4303DualDS3(263),          -- TA4303 Dual DS3 module 1200336L1
        adTADS3TSIE1(264),             -- TA 3010 DS3 TSI E1 MUX (1182.020L1) 22 slot
        adTAOC3L2(265),                -- TA 3000 OC-3 MUX L2 1181031L2
        reserved06(266),               -- TA 3000 OC-3 MUX L2 (trap extension)
        reserved07(267),               -- TA 3000 OC-3 MUX L2 (trap extension)
        reserved08(268),               -- TA 3000 OC-3 MUX L2 (trap extension)
        adATLAS550VCom(269),           -- ATLAS 550 VCOM Module - 1200312Lx (x = 1,2,3,5)
        adATLAS550IMux(270),           -- ATLAS 550 IMUX Module - 1200326L1
        adATLAS550T1(271),             -- ATLAS 550 T1 Network Module - 1200307L1
        adATLAS550DualT1(272),         -- ATLAS 550 Dual T1/Pri Module - 1200314L1
        adATLAS550DualNx(273),         -- ATLAS 550  Dual NX Module - 1200311L1
        adATLAS550QuadBRI(274),        -- ATLAS 550 Quad Bri Module - 1200315L1
        adATLAS550OctFXS(275),         -- ATLAS 550 Octal FXS Module - 1200309L1
        adATLAS550OctFXO(276),         -- ATLAS 550 Octal FX0 Module - 1200310L1
        adATLAS550QuadFXS(277),        -- ATLAS 550 Quad FXS Module - 1200328L1
        adATLAS550QuadFXO(278),        -- ATLAS 550 Quad FX0 Module - 1200329L1
        adATLAS550RsrcHost(279),       -- ATLAS 550 Resource Host Module - 1200324L1
        adATLAS550E1(280),             -- ATLAS 550 E1 Network Module - 1200308L1
        adATLAS550EM(281),             -- ATLAS 550 E&M Module - 1200313L1
        adOSU300(282),                 -- OSU 300 - 1200663-L1
        adTAATMMUX(283),               -- Total Access ATM MUX - 1181041L1
        adTA1500DualFXSL2(284),        -- Total Access 1500 Dual FXS/DPT w/o SMAS (1180208L2)
        adTA1500DualFXOL2(285),        -- Total Access 1500 Dual FXO/DPT w/o SMAS (1180207L2)
        adTA3000HTUCICOT(286),         -- Total Access 3000 HTU-C ICOT (1179511L1)
        adTA3000quadDSX1E1(287),       -- Total Access 3000 quad DSX-1/E1 (1181402L1)
        adMX2800STS1(288),             -- MX2800 STS-1 multiplexer (1200659)
        adTA1500dNx64(289),            -- TA1500 Daul Nx56/64 (1180025L1)
        adTA1500DDS4x4(290),           -- TA1500 4x4 DDS (1180106L1)
        adTA1500DDS4x4PO(291),         -- TA1500 4x4 DDS Preferred Option (1180106L2)
        adLucentFXS(292),              -- Lucent FXS (1133406L1)
        adLucentFXO(293),              -- LucentFXO (1133405L1)
        adTA1500EML2unused(294),       -- TA1500 unassigned
        adStratum3Eclock(295),         -- Stratum 3E clock (1181930-L1)
        adTA1500LucentSCU(296),        -- TA1500 Lucent SCU (1133008L4)
        adTA3000qADSL(297),            -- TA3000 Quad ADSL (1181408L1)
        adTA3000OctIDSL(298),          -- TA3000 Octal IDSL (1181.407L1)
        adATLAS890(299),               -- ATLAS 890 (1200.321L1)
        adTA1500FT1dp(300),            -- Total Access 15000 FT1 DP (1180405L1)
        adLucentLIU(301),              -- TA1500 Lucent LIU (1133209L1)
        adTA3000OctIMA(302),           -- TA3000 Octal DS1 IMA (1181.409L1)
        reserved09(303),               -- Total Access ATM MUX  (1181041L1) (trap extension)
        adTADualOCUDP(304),            -- Total Access Dual OCU DP (1180205L1)
        adTADualDSODP(305),            -- Total Access Dual DSO DP (1180203L1)
        adTADualOCUDPL2(306),          -- Total Access Dual OCU DP w/o SMAS (1180205L2)
        adTADualDSODPL2(307),          -- Total Access Dual DSO DP w/o SMAS (1180203L2)
        adTA1500OCUDPoem(308),         -- Total Access 1500 OCU-DP OEM (1133105L1)
        adTA1500OCUDP(309),            -- Total Access 1500 OCU-DP Preferred Option (1180105L2)
        adTA3000qHDSL2(310),           -- TA3000 Quad HDSL2 (1181.404L1)
        adTAGSHDSL(311),               -- Total Access G.SHDSL Single Port (1182008L1)
        adMX2810(312),                 -- MX2810 (1185.002L1)
        adATLAS550PVRM(313),           -- ATLAS 550 Packet Voice Rsrc Module (1200752L1)
        adTA1500M4W(314),              -- TA1500 Multi 4 Wire (1180413L1)
        adTSULTX(315),                 -- TSU LTX (2200250)
        adTA1500DualOCUDPTJ(316),      -- TA 1500 Dual OCU DP w/ Tst Jacks (1180205L3, -L4 & 1133205L3)
        adTA1500DualDSODPTJ(317),      -- TA 1500 Dual DSO DP w/ Tst Jacks (1180203L3, -L4 & 1133203L3)
        adTA3000qGSHDSL(318),          -- TA 3000 G.SHDSL Quad Port (1181403L1#T)
        adTA3000oGSHDSL(319),          -- TA 3000 G.SHDSL Octal Port (1181403L1)  (1181403L2)
        adTA1500d2wTO(320),            -- TA1500 Dual 2-Wire TO w/o SMAS (1180212L2)
        adTA1500d2wTOsmas(321),        -- TA1500 Dual 2-Wire TO w/ SMAS (1180212L1 / 1133212L1)
        adTA1500d2wFXS(322),           -- TA1500 Dual 2-Wire FXS GT w/o SMAS (1180214L2)
        adTA1500d2wFXSsmas(323),       -- TA1500 Dual 2-Wire FXS GT w/ SMAS (1180214L1 / 1133214L1)
        adTA15002wFXO(324),            -- TA1500 2-Wire FXO GT w/o SMAS (1180115L2)
        adTA15002wFXOsmas(325),        -- TA1500 2-Wire FXO GT w/ SMAS (1180115L1 / 1133115L1)
        adTA1500d4wDX(326),            -- TA1500 Dual 4-Wire DX w/o SMAS (1180216L2)
        adTA1500d4wDXsmas(327),        -- TA1500 Dual 4-Wire DX w/ SMAS (1180216L1 / 1133216L1)
        adTA1500d4wFXO(328),           -- TA1500 Dual 4-Wire FXO w/o SMAS (1180217L2)
        adTA1500d4wFXOsmas(329),       -- TA1500 Dual 4-Wire FXO w/ SMAS (1180217L1 / 1133217L1)
        adTA1500d4wFXS(330),           -- TA1500 Dual 4-Wire FXS w/o SMAS (1180218L2)
        adTA1500d4wFXSsmas(331),       -- TA1500 Dual 4-Wire FXS w/ SMAS (1180218L1 / 1133218L1)
        adTA1500DDSdp(332),            -- TA1500 DDS-DP (1180105L1)
        reserved10(333),               -- TA 3000 DS3 TSI E1 MUX (trap extension)
        reserved11(334),               -- TA 3000 DS3 TSI E1 MUX (trap extension)
        adTA3000CES(335),              -- TA 3000 CES module (1181.420L1)
        adIQ710(336),                  -- IQ 710 (1200.800L1)
        adIQ7xxDDS(337),               -- IQ 710 DDS Interface Module (1200.801L1)
        adIQ7xxT1(338),                -- IQ 710 T1 Interface Module (1200.802L1)
        adIQ7xxT1DSX(339),             -- IQ 710 T1-DSX Interface Module (1200.803L1)
        adTA1500LcntUBR1TE(340),       -- TA1500 Lucent UBR1TE (1133120L1)
        adTA3000VCP(341),              -- TA 3000 Voice Cell Processor  (1181410L1)
        adExp6530SHDSL(342),           -- Express 6530 SHDSL NxNTU (1225001L1)
        adTA3000quadE1NTU(343),        -- Total Access 3000 quad E1 w/ NTU mgmt (1181402L1#T)
        adATLAS810(344),               -- ATLAS 810+ AC (1200265L1)
        adTA608(345),                  -- Total Access 608 (T1model)  (1200.680L1)
        adTA3000LTU8(346),             -- Total Access 3000 LTU-8  (1182.300L1)
        reserved12(347),               -- Total Access 3000 LTU-8  (trap extension)
        reserved13(348),               -- Total Access 3000 LTU-8  (trap extension)
        adTANTU8(349),                 -- Total Access NTU-8  (1182.301L1)
        adTA3000DS1FR(350),            -- TA 3000 DS1 Frame Relay (1181.414L1)
        adTASHDSLbnc(351),             -- Total Access SHDSL LTU w/ BNC (1182008L3)
        adTASHDSLv35(352),             -- Total Access SHDSL V.35 LTU (1182008L5)
        adTA3000ALEc(353),             -- TA3000 ADSL Loop Extender, CO Unit (181600L1)
        adTAH2TUCvrzneG2(354),         -- Total Access H2TUC for Versizon East, 2nd Gen (1181112L1)
        adTAH2TUCvrznwG2(355),         -- Total Access H2TUC for Versizon West, 2nd Gen (1181112L2)
        adTAH2TUCmciG2(356),           -- Total Access H2TUC for MCI, 2nd Gen (1181112L3)
        adTAH2TUCsbcG2(357),           -- Total Access H2TUC for SBC, 2nd Gen (1181112L4)
        adTAH2TUCqwestG2(358),         -- Total Access H2TUC for QWEST, 2nd Gen (1181112L5)
        adTAH2TUCbellsG2(359),         -- Total Access H2TUC for BellSouth, 2nd Gen (1181112L6)
        adTA3000HTUCg6(360),           -- Total Access 3000 HTU-C 6th Gen for SBC (1181.106L4)
        adTA3000HTUCg6HLSS(361),       -- Total Access 3000 HTU-C 6th Gen for Qwest (1181.106L5)
        adTADS3TSIE3(362),             -- TA 3000 DS3 TSI E3 MUX 1182021L1
        adTA1000qADSL(363),            -- Total Access 1000 QUAD ADSL            (1179413L1)
        adTA1000qH2LIU(364),           -- Total Access 1000 DSLAM QUAD HDSL2 LIU (1179109L1)
        adTA1000atmBCU(365),           -- Total Access 1000 ATM BCU              (1179112L1)
        adTA1000dslamPSU(366),         -- Total Access 1000 DSLAM PSU            (1179008L1)
        adXprs6503(367),               -- Express 6503  (1200296L1)
        adTA3000HTUCg6BSouth(368),     -- Total Access 3000 HTU-C 6th Gen for BellSouth (1181106L6)
        adTA3000H4TUCL4G1(369),        -- Total Access 3000 H4TUC, 1st Gen (1181411L4)
        adTA3000H4TUCL5G1(370),        -- Total Access 3000 H4TUC, 1st Gen (1181411L5)
        adTA300DS3LM(371),             -- TA 3000 DS3 Line Module (1181450L1)
        adTA300H2TURsprint(372),       -- Total Access 3000 H2TU-R L6 for Sprint (1181126L6)
        adTA1500MCU(373),              -- TA1500 MCU (1180434L1)
        adTA3000BATS(374),             -- TA3000 Broadband ATM Test System (1358007L1)
        adTA1500DDSdpQwest(375),       -- TA1500 TR DDS-DP Qwest Red-Opt (1180105L2#Q)
        adTA3000qSHDSL(376),           -- TA 3000 SHDSL Quad Port (1181423L1)
        adTA3000T1OR(377),             -- TA 3000 T1-OR 1st Gen (1181310L2)
        adTA3000OC3CSM(378),           -- TA 3000 OC3 CSM ATM MUX (1181044L1)
        reserved14(379),               -- TA 3000 OC3 CSM ATM MUX (1181044L1) (trap extension)
        adTA1500DualCoinCot(380),      -- TA 1500 Dual Coin COT (1180432L1)
        adTA1500DualCoinRt(381),       -- TA 1500 Dual Coin RT (1180433L1)
        adATLAS550NxT1hssi(382),       -- ATLAS 550 NxT1 HSSI Module (1200346L1)
        adNV3200(383),                 -- NetVanta 3200 (1200860L1)
        adTASHDSLprot(384),            -- Total Access SHDSL LTU w/ Prot (1182008L6)
        adTA1500qFXOMLT(385),          -- Total Access 1500 quad FXO w/ MLT (1180407L1)
        adTAOC3L3(386),                -- TA OC-3 MUX L3 w/ 2 DS3 drops & 1 DS3 to 28 DS1s (1181031L3)
        reserved15(387),               -- TA OC-3 MUX L3  (1181031L3) trap extension 1
        reserved16(388),               -- TA OC-3 MUX L3  (1181031L3) trap extension 2
        adTA1500EBSCot(389),           -- TA 1500 CO p-phone card (1180430L1)
        adTA1500EBSRt(390),            -- TA 1500 RT p-phone card (1180431L1)
        adIQ710Gen2(391),              -- IQ 710 2nd Gen (1202.800L1)
        adTA3000quadE1(392),           -- Total Access 3000 quad E1 (1181402L1#E)
        adTA1500s4wDX(393),            -- TA1500 Single 4-Wire DX w/o SMAS (1180116L1)
        adTA1500s4wDXsmas(394),        -- TA1500 Single 4-Wire DX w/ SMAS (1180116L2)
        adTA4303PSU(395),              -- TA4303 Power Supply module (1200335L1)
        adATLAS550MdmMgmt(396),        -- ATLAS 550 Modem Management Network Module (1200341L1)
        adATLAS550BriDbu(397),         -- ATLAS 550 BRI DBU Network Interface Module (1200327L1)
        adATLAS550DualUssi(398),       -- ATLAS 550 Dual USSI Module (1200754L1)
        adATLAS550QuadT1(399),         -- ATLAS 550 Quad T1/PRI Module (1200755L1)
        adATLAS550LgcyData(400),       -- ATLAS 550 Legacy Data Module (1200342L1)
        adTA4303STS1(401),             -- TA4303 STS1 module (1200352L1)
        adTADS0TSIMux(402),            -- TA 3000 DS0 TSI MUX (1182022L1)
        adTA4303OctalBRI(403),         -- TA4303 Octal BRI module 1202332L1
        adTA3000IVD(404),              -- TA 3000 Integrated Voice & Data triple wide (1181424L1)
        adATLAS550PbxRsrc(405),        -- ATLAS 550 PBX Resource Module (1200756L1)
        adATLAS550Pots(406),           -- ATLAS 550 Lifeline/POTS Network Module (1200757L1)
        adATLAS550OctDss(407),         -- ATLAS 550 Octal DSS User Module (1200758L1)
        adATLAS550qStBri(408),         -- ATLAS 550 Quad S/T BRI Module (1200764L1)
        adATLAS550NxT1Imux(409),       -- ATLAS 550 NxT1 IMUX Module (1200347L1)
        adATLAS550NxT1hssiL2(410),     -- ATLAS 550 NxT1 HSSI/V.35 Module (1200346L2)
        adMX2810STS1(411),             -- MX2810 STS-1 card (1185004L1)
        adTA3000H4TUCL1G1(412),        -- Total Access 3000 H4TUC, 1st Gen (1181411L1)
        adTA850RCU(413),               -- TA850 RCU (1200376L1)
        adTA3000SHDSLltu15gSp(414),    -- TA 3000 SHDSL LTU Single port, 1.5 Gen (1182108L1)
        adTA3000SHDSLltu15gSpBnc(415), -- TA 3000 SHDSL LTU Single port w/ BNC, 1.5 Gen (1182108L3)
        adTA3000SHDSLltu15gV35Bnc(416),-- TA 3000 SHDSL LTU V.35 w/ BNC 1.5 Gen (1182108L5)
        adTA3000SHDSLltu15gSp11(417),  -- TA 3000 SHDSL LTU Single port w/ 1:1, 1.5 Gen (1182108L6)
        adTA3000SHDSLltu15gSpT(418),   -- TA 3000 SHDSL LTU Single port, 1.5 Gen Telstra (1182108L7)
        adTADSX1(419),                 -- TA 750/850/1500 DSX1 Module (1200.385L1, 2200.385-3)
        adATLASRdntAcPs(420),          -- ATLAS Redundant AC Pwr Supply (1200.220L1)
        adATLASRdntDcPs(421),          -- ATLAS Redundant DC Pwr Supply (1200.316L1)
        adATLAS890Cntrlr(422),         -- ATLAS 890 System Controller (1200.322L1)
        adATLASOctBRI(423),            -- ATLAS Octal S/T BRI Option (1200.343L1)
        adATLAS890AcPs(424),           -- ATLAS 890 AC Power Supply (1200.344L1)
        adATLAS890DcPs(425),           -- ATLAS 890 DC Power Supply (1200.345L1)
        adATLASadpcmRsrc(426),         -- ATLAS ADPCM Resource Module (1200.770L1)
        adATLASNxT1hssi(427),          -- ATLAS NxT1 HSSI/V.35 Option (1200.771L1)
        adATLASNxT1IMUX(428),          -- ATLAS NxT1 IMUX Resource (1200.772L1)
        adATLASvideo(429),             -- ATLAS Video Option (1200.773L1)
        adATLAS830(430),               -- ATLAS 830 (1200.780L1)
        adTA3000H2TucHKT(431),         -- TA 3000 H2TUC for HKT (1181.112L9)
        adTA3000OctADSL(432),          -- TA 3000 octal ADSL (1181.405L1)
        adTAH2TUCvrzneG3(433),         -- TA 3000 H2TUC for Verizon East, 3rd Gen (1181.113L1)
        adTAH2TUCG3(434),              -- TA 3000 H2TUC for general distribution, 3rd Gen (1181.113L2)
        adTAH2TUCmciG3(435),           -- TA 3000 H2TUC for MCI, 3rd Gen (1181.113L3)
        adTAH2TUCsbcG3(436),           -- TA 3000 H2TUC for SBC, 3rd Gen (1181.113L4)
        adTAH2TUCqwestG3(437),         -- TA 3000 H2TUC for QWEST, 3rd Gen (1181.113L5)
        adTAH2TUCbellsG3(438),         -- TA 3000 H2TUC for BellSouth, 3rd Gen (1181.113L6)
        adTA3000H2TucHKTG3(439),       -- TA 3000 H2TUC for HKT, 3rd Gen (1181.113L9)
        adTA3000LTU4(440),             -- Total Access 3000 LTU-4  (1181.308L1)
        reserved17(441),               -- Total Access 3000 LTU-4  (trap extension)
        reserved18(442),               -- Total Access 3000 LTU-4  (trap extension)
        adTANTU4(443),                 -- Total Access NTU-4  (1181.307L1)
        adTA4303snmp(444),             -- Total Access 4303 (1200.330L1) chassis w/ full SNMP
        reserved18a(445),              -- was (1181.405L2), moved to 455
        reserved19(446),               -- MX2800 Trap extensions (1204.288L1/L2)
        adTADS3TSIE1L2(447),           -- TA 3000 DS3 TSI E1 MUX (1182.020L2) 28 slot
        adTAH2TUCHlss(448),            -- Total Access H2TUC single port dual circuit (1181.213L1)
        adTA3000H4TUCL1G2(449),        -- Total Access 3000 H4TUC, 2nd Gen (1181.412L1)
        adTA3000H4TUCL4G2(450),        -- Total Access 3000 H4TUC, 2nd Gen (1181.412L4)
        adTA3000H4TUCL5G2(451),        -- Total Access 3000 H4TUC, 2nd Gen (1181.412L5)
        adTA3000CSM128(452),           -- Total Access 3000 128 port Cell Switch Module (1181.041L4)
        adATLAS550DualVideo(453),      -- ATLAS 550 Dual Video Option (1200.765L1)
        adATLAS800octalFxs(454),       -- ATLAS 800 Octal FXS (1200.338L1)
        adTA3000OctADSL2(455),         -- TA 3000 octal ADSL + POTS splitters (1181.405L2)
        adT200SHDSLNTU(456),           -- T200 SHDSL NTU  (1225.035L1)
        adTAT1E1SHDSLLtu(457),         -- Total Access T1/E1 SHDSL LTU  (1182.210L1)
        adTAOPTI3L2(458),              -- Total Access OPTI3L2 (1184.002L2)
        adTA1500s4wFxoSmas(459),       -- TA1500 Single 4-Wire FXO w/  SMAS (1180117L1)
        adTA1500s4wFxoNoSmas(460),     -- TA1500 Single 4-Wire FXO w/o SMAS (1180117L2)
        adTA1500s4wFxsSmas(461),       -- TA1500 Single 4-Wire FXS w/  SMAS (1180118L1)
        adTA1500s4wFxsNoSmas(462),     -- TA1500 Single 4-Wire FXS w/o SMAS (1180118L2)
        adTA1000DualT1E1Liu(463),      -- Total Access 1000 DSLAM DUAL T1/E1 LIU (1179010L1)
        adTA3000CSMcr(464),            -- Total Access 3000 DS3 Cell Switch Module cost reduced (1181.041L2)
        adATLAS550EtherSwitch(465),    -- ATLAS 550 Ethernet Switch Module (1200.766L1)
        adNV3205(466),                 -- NetVanta 3205 (1200870L1)
        adNV3305(467),                 -- NetVanta 3305 (1200880L1)
        adNV3xxxDDS(468),              -- NetVanta 3xxx DDS (1200861L1)
        adNV3xxxT1(469),               -- NetVanta 3xxx T1 (1200862L1)
        adNV3xxxT1Dsx1(470),           -- NetVanta 3xxx T1/Dsx-1 (1200863L1)
        adNV3xxxV90dbu(471),           -- NetVanta 3xxx V.90 DBU (1200864L1)
        adNV3xxxISDNdbu(472),          -- NetVanta 3xxx ISDN DBU (1200865L1)
        adNV3xxxSerial(473),           -- NetVanta 3xxx Serial (1200866L1)
        adNV3xxxSHDSL(474),            -- NetVanta 3xxx SHDSL (1200867L1)
        adTA624(475),                  -- Total Access 624 (4200624L1#ATM & 4200624L1#TDM)
        adTA600R(476),                 -- Total Access 600R Router-Only (4200600L1#TDM)
        adTA1500s4wToSmas(477),        -- TA1500 Single 4-Wire TO w/ SMAS (1180.112L1)
        adTA1500s4wToNoSmas(478),      -- TA1500 Single 4-Wire TO w/o SMAS (1180.112L2)
        adTA3000E1FR(479),             -- TA 3000 E1 Frame Relay (1182.414L1)
        adTA1500s2wFxsGtSmas(480),     -- TA1500 Single 2-Wire FXS/GT w/  SMAS (1180.114L1)
        adTA1500s2wFxsGtNoSmas(481),   -- TA1500 Single 2-Wire FXS/GT w/o SMAS (1180.114L2)
        adTA3000OctDs1E1IMA(482),      -- TA3000 Octal DS1/E1 IMA (1181.409L2)
        adTA3000QuadDs1IMA(483),       -- TA3000 Quad DS1 IMA (1181.409L10)
        adMX2820(484),                 -- MX2820 shelf  19"             (1186001L1)
        adMX2820M13(485),              -- MX2820 M13 DS3 Mux module     (1186002L1)
        adMX2820Scu(486),              -- MX2820 SCU card               (1186003L1)
        adMX2820Clock(487),            -- MX2820 Clock card             (1186004L1)
        adTASHDSL4(488),               -- Total Access SHDSL4 LTU  (1182118L1)
        adTA1500s4wEtoSmas(489),       -- TA1500 Single 4-Wire ETO w/ SMAS (1180.113L1)
        adTA1500s4wEtoNoSmas(490),     -- TA1500 Single 4-Wire ETO w/o SMAS (1180.113L2)
        adTA604(491),                  -- Total Access 604 (T1model)  (1200.641L1)
        adTA612(492),                  -- Total Access 612 (T1model)  (1200.612L1)
        adTA616(493),                  -- Total Access 616 (T1model)  (1200.616L1)
        adMX2820wide(494),             -- MX2820 shelf  23"        (1186001L2)
        adOptiMXshelf(495),            -- OPTI-MX shelf                            (1184501L1)
        adOptiMXOc3OMM(496),           -- OPTI-MX OC3 Mux                          (1184502L1)
        adOptiMXOc3OMMx1(497),         -- OPTI-MX OC3 Mux Trap Exten               (1184502L1)
        adOptiMXT1E1(498),             -- OPTI-MX DS1 line card (T1/E1)            (1184513L1)
        adOptiMXT1E1x1(499),           -- OPTI-MX DS1 line card (T1/E1) Trap Exten (1184513L1)
        adOptiMXDs3(500),              -- OPTI-MX DS3 line card                    (1184503L1)
        adNV2050(501),                 -- NetVanta 2050 (1202362L1)
        adNV2054(502),                 -- NetVanta 2054 (1202362L2)
        adNV2100(503),                 -- NetVanta 2100 (1202361L1)
        adNV2104(504),                 -- NetVanta 2104 (1202361L2)
        adNV2300(505),                 -- NetVanta 2300 (1202366L1)
        adNV2400(506),                 -- NetVanta 2400 (1202367L1)
        adOptiMXScm(507),              -- OPTI-MX SCM Controller                   (1184500L1)
        adTA1200Shelf(508),            -- TA1200 RDS shelf                                (1179601L1)
        adTA1280Shelfalc(509),         -- TA1280 RDS shelf                      (Alcatel) (1179601L1#A)
        adTA1200QuadIMA(510),          -- TA1200 Quad IMA module "network card"           (1179611L1)
        adTA1280QuadIMAalc(511),       -- TA1280 Quad IMA module "network card" (Alcatel) (1179611L1#A)
        adTA3000HC(512),               -- TA3000 23 inch domestic High Cap shelf    (1181.001L2)
        adTA3kPCU(513),                -- TA3000 Primary Controller Unit            (1181918L1)
        adTA3kPSM(514),                -- TA3000 Primary Switch Module              (1181041L3)
        adTA3kECU(515),                -- TA3000 Expansion Controller Unit          (1181919L1)
        adTA3kSAM(516),                -- TA3000 Subtending Access Module           (1181046L1)
        adTA3kSCUL2(517),              -- TA3000 System Controller Unit - No FLD    (1181018L2)
        adTA3kH4TUCL1G3(518),          -- TA3000 H4TUC, 3rd Gen (1181.413L1)
        adTA3kH4TUCL4G3(519),          -- TA3000 H4TUC, 3rd Gen (1181.413L4)
        adTA3kH4TUCL5G3(520),          -- TA3000 H4TUC, 3rd Gen (1181.413L5)
        adTA3kSCUL3(521),              -- TA3000 System Controller Unit - No FCD, w/Inband (1181018L3)
        adTA1500d4wEtoSmas(522),       -- TA1500 Dual 4-Wire ETO w/ SMAS (1180.213L1)
        adTA1500d4wEtoNoSmas(523),     -- TA1500 Dual 4-Wire ETO w/o SMAS (1180.213L2)
        adTA1500UBRITE(524),           -- TA1500 U-BRITE w/PWR (1180020L2)
        adNV1224(525),                 -- NetVanta 1224 (1200500L1)
        adNV1224ST(526),               -- NetVanta 1224ST (1200500L2)
        adATLAS550Nx(527),             -- ATLAS 550 NX Module - 1200349L1
        adTA3KoADSLCwEta(528),         -- TA 3000 octal ADSL-C w/ ETA               (1181.425L2)
        adATLAS550DualFXO(529),        -- ATLAS 550 Dual FX0 Module - 1200349L1
        adTA1500dFXOGT(530),           -- TA1500 Dual FXO GT w/o SMAS (1180215L2)
        adTA1500dFXOGTsmas(531),       -- TA1500 Dual FXO GT w/ SMAS  (1180215L1)
        adTA1500dFXOGTLuc(532),        -- Dual FXO GT                 (1133215L1)
        adOptiMXOc12OMM(533),          -- OPTI-MX OC12 Sonet Mux      (1184504L1-4)
        adTA1500s4wTdmSmas(534),       -- TA1500 4-Wire TDM w/  SMAS  (1180119L1)
        adTA1500s4wTdm(535),           -- TA1500 4-Wire TDM w/o SMAS  (1180119L2)
        adOptiSMXshelf(536),           -- OPTI-SMX shelf              (1184514L1)
        adTA1200ADSL(537),             -- TA1200 24 port ADSL module            (1179601L1)  Same ID as shelf
        adTA1280ADSLalc(538),          -- TA1280 24 port ADSL module  (Alcatel) (1179601L1#A)Same ID as shelf
        adTADS3MUXL3(539),             -- Total Access DS3 MUX List 3 (1181020L3)
        adTADS3MUXL4(540),             -- Total Access DS3 MUX List 4 (1181020L4)
        adTA3000SAM(541),              -- TA3000  1181.001L1    TA3000 23 inch domestic shelf          SAM/DSLAM
        adTA3010SAM(542),              -- TA3010  1182.003L1    TA3010 19 inch domestic shelf          SAM/DSLAM
        adTA3011SAM(543),              -- TA3011  1182.001L1    Total Access OMP-FC                    SAM/DSLAM
        adTA3011MexSAM(544),           -- TA3011  1181.001L1#M  Total Access for Mexico                SAM/DSLAM
        adTA3012SAM(545),              -- TA3012  1182.004L1    Total Access 3000 DA                   SAM/DSLAM
        adTA3000HCSAM(546),            -- TA3000  1181.001L2    TA3000 23 inch domestic High Cap shelf SAM/DSLAM
        adOptiMXVT15(547),             -- OPTI-MX VT1.5 line card               (1184515L1)
        adOptiMXVT15x1(548),           -- OPTI-MX VT1.5 line card Trap Exten    (1184515L1)
        adTA3kQDFC(549),               -- TA3000 QDFC, Quad DS1/Mux to Fiber           (1181308L4)
        adTA3kQDFCx1(550),             -- TA3000 QDFC, Quad DS1/Mux to Fiber Trap Ext. (1181308L4)
        adTA3kQDFR(551),               -- TA3000 QDFR, Fiber to Quad DS1/Mux           (1181307L4)
        adTA3kQuadFrAtm(552),          -- TA3000 Quad E1/DSX1 Frame Relay/ATM          (1181415L1)
        adTA3kOC3Qmux(553),            -- TA3000 OC3 Mux w/ Quad DSX to line cards     (1181031L4)
        adTA3kOC3Qmuxx1(554),          -- TA3000 OC3 Mux w/ Quad DSX to line cards Trap Ext. (1181031L4)
        adTAIadNwPhoneT1(555),         -- Total Access IAD Network Telephone T1        (1200.608L1)
        adTAIad600Rg3(556),            -- Total Access IAD 3rd gen 600R Router         (1203.600L1)
        adTAIad604g3(557),             -- Total Access IAD 3rd gen 604                 (1203.640L1)
        adTAIad608g3(558),             -- Total Access IAD 3rd gen 608                 (1203.680L1)
        adTAIad612g3(559),             -- Total Access IAD 3rd gen 612                 (1203.612L1)
        adTAIad616g3(560),             -- Total Access IAD 3rd gen 616                 (1203.616L1)
        adTAIad624g3(561),             -- Total Access IAD 3rd gen 624                 (1203.624L1)
        adMX2820M13L10(562),           -- MX2820 M13 access module DS1->DS3 (1186002L10)
        adTA3kH4TUCL2G3(563),          -- TA3000 H4TUC, 3rd Gen (1181.413L2)  augments 518-520
        adOptiMXTransMux(564),         -- OPTI-MX STS-1 to DS3 with VT1.5 payload      (1184512L1)
        adOptiMXOC3Trib(565),          -- OPTI-MX OC3 Fiber Card                       (1184543L1)
        adOptiMXDS3TripleW(566),       -- OPTI-MX Triple Wide DS3 Interface            (1184533L1)
        adSmart16eGen2(567),           -- Gen 2 Smart 16 Shelf Controller (1202162L1)
        adMX2820STS1(568),             -- MX2820 STS1 Mux module     (1186005L1)
        adTA4303Plus(569),             -- TA4303 Plus chassis              (1200.330L2)
        adTA4303PlusScu(570),          -- TA4303 Plus SCU                  (1202.334L1)
        adTA4303PlusDS3(571),          -- TA4303 Plus DS3                  (1202.333L1)
        adTA4303PlusSTS1(572),         -- TA4303 Plus STS1                 (1202.352L1)
        adTA4303PlusDSX1(573),         -- TA4303 Plus Octal DSX1 (BRI)     (1202.331L1)
        adTA4303PlusPsu(574),          -- TA4303 Plus Power Supply Unit    (1202.335L1)
        adTA30x0AccMTC(575),           -- TA30x0 Accessory Metallic Test Controller  (1183.010L1)
        adExp6531SHDSL(576),           -- Express 6531 SHDSL NxNTU         (1225.105L1)
        adIQ790(577),                  -- IQ 790            (1200.831L1)
        adNV5305(578),                 -- Netvanta 5305     (1200.990L1)
        adTA1124OSP(579),              -- TA1124 OSP shelf                 (1179724L1)
        adTA1125DSLAM(580),            -- TA1124 DSLAM shelf               (1179725L1)
        adNvIsdnSt(581),               -- NetVanta ISDN S/T DIM            (1200875L1)
        adNV1224R(582),                -- NetVanta 1224R                   (1200510L1)
        adNV1224STR(583),              -- NetVanta 1224STR                 (1200520L1)
        adNvE1(584),                   -- NetVanta E1 NIM                  (1200868L1)
        adNvE1G703(585),               -- NetVanta E1 & G.703 NIM          (1200878L1)
        adNv4305(586),                 -- NetVanta 4305                    (1200890L1)
        adTAH2TUCHlssVrz(587),         -- Total Access H2TUC HLSS dual circuit for Verizon,      (1181214L1)
        adTAH2TUCHlssDist(588),        -- Total Access H2TUC HLSS dual circuit for Distribution, (1181214L2)
        adTAH2TUCHlssSbc(589),         -- Total Access H2TUC HLSS dual circuit for SBC,          (1181214L4)
        adTAH2TUCHlssBells(590),       -- Total Access H2TUC HLSS dual circuit for Bellsouth,    (1181214L6)
        adTA1124ADSL(591),             -- TA1124 24 port internal ADSL module       (2179724-1)
        adTA1124Network(592),          -- TA1124 internal network module            (2179724-10)
        adTracer6420(593),             -- Tracer 6420 5.8ghz Modular Radio          (12806420L1A) and (12806420L1B)
        adOptiMXEthM(594),             -- OPTI-MX Ethernet Module                (1184510L1)
        adOptiMXEthMx1(595),           -- OPTI-MX Ethernet Module trap extension (1184510L1)
        adTSUNvRouter(596),            -- TSU Router Module Option Card (1202350L1)
        adIQ7xxT1Probe(597),           -- IQ710 T1 Probe Card (1202804L1)
        adTA1500qRS232(598),           -- TA1500 Quad RS232 (1180.435L1)
        adTA1200NetworkL2(599),        -- (1179.611L2)       TA1200 Network module
        adTA1200NetworkL3IP(600),      -- (1179.611L3)       TA1200 Network Module  (IP Fed)
        adCN24Shelf(601),              -- (1179.601L1#C)     TA1200 CN24 Chassis
        adCN24ADSL(602),               -- (1179.601L1#C)     TA1200 CN24 24 port ADSL
        adCN24Network(603),            -- (1179.611L1#C)     TA1200 CN24 Network/IMA
        adOptiMXEthGB(604),            -- (1184.516L1)       OPTI-MX Single port Giga-Bit Cu Ethernet
        adTAH2TUCSpHlssDist(605),      -- (1181.213L2)       Total Access H2TUC HLSS single port dual circuit for Distribution,
        adTA900Rac(606),               -- (1200.630L1)       TA900R AC version
        adTA900Rdc(607),               -- (1200.630L2)       TA900R DC version
        adTA3kQDFCL7G1(608),           -- (1181.308L7)       TA3000 QDFC, 1st Gen
        adCN24m211(609),               -- (1179.701L1#C)     TA1200 CN24 Model 211 Mini-DSLAM (chassis, ADSL module, network module) Sealed, Quad T1 IMA fed
        adCN24m211ADSL(610),           -- (1179.701L1#C)     TA1200 CN24 Model 211 ADSL module
        adCN24m211Network(611),        -- (1179.701L1#C)     TA1200 CN24 Model 211 Network Quad T1 IMA module
        adCN24m212(612),               -- (1179.702L1#C)     TA1200 CN24 Model 212 Mini-DSLAM (chassis, ADSL module, network module) Sealed, Quad HDSL4 IMA
        adCN24m212ADSL(613),           -- (1179.702L1#C)     TA1200 CN24 Model 212 ADSL module
        adCN24m212Network(614),        -- (1179.702L1#C)     TA1200 CN24 Model 212 Network Quad HDSL4 IMA module
        adTA1101(615),                 -- (1179.701L1)       TA1101 (chassis, ADSL module, network module) Sealed, Quad T1 IMA fed
        adTA1101ADSL(616),             -- (1179.701L1)       TA1101 ADSL module
        adTA1101Network(617),          -- (1179.701L1)       TA1101 Network Quad T1 IMA module
        adTA1102(618),                 -- (1179.702L1)       TA1102 (chassis, ADSL module, network module) Sealed, Quad HDSL4 IMA fed
        adTA1102ADSL(619),             -- (1179.702L1)       TA1102 ADSL module
        adTA1102Network(620),          -- (1179.702L1)       TA1102 Network Quad HDSL4 IMA module
        adTA3050(621),                 -- (1183.001L1)       TA3050 23" Accessory Shelf for 3000
        adTA3060(622),                 -- (1183.006L1)       TA3060 19" Accessory Shelf for 3010
        adTA30x0AccSpltrNoTest(623),   -- (1183.002L1)       TA30x0 Accessory ADSL Splitter w/o Test Access
        adTA30x0AccSpltrTest(624),     -- (1183.002L2)       TA30x0 Accessory ADSL Splitter w/  Test Access
        adTA30x0AccCTMNoTest(625),     -- (1183.003L1)       TA30x0 Accessory Cut Thru Module w/o Test Access
        adTA30x0AccCTMTest(626),       -- (1183.003L2)       TA30x0 Accessory Cut Thru Module w/  Test Access
        adTA30x0AccETSINoTest(627),    -- (1183.007L1)       TA30x0 Accessory ETSI Splitter w/o Test Access
        adTA1500TriCdp(628),           -- (1180.182L1)       TA1500 TRI-C DP
        adTA3kLpu(629),                -- (1181.500L1)       TA3000 LPU line Power Unit for remote power
        adOptiMXGESM(630),             -- (1184.518L1)       OPTI-MX · Giga-Bit Ethernet With Single-Mode Fiber Interface
        adOptiMXGEMM(631),             -- (1184.519L1)       OPTI-MX · Giga-Bit Ethernet With Multi-Mode Fiber Interface
        adOptiMXTRAM3(632),            -- (1184.532L1)       OPTI-MX · 3 Wide TransMux
        adIQ310(633),                  -- (1203800L1)        IQ310
        adTA3kRMM(634),                -- (1181.019L1)       TA3000 RMM  Remote management module ethernet bridge
        adTA3kIMA16GSHDSL(635),        -- (1181.429L1)       TA3000 IMA G.SHDSL 16 Port
        adTA3kSHDSLqE1CES(636),        -- (1182.421L1)       TA3000 SHDSL E1/CES 4 Port
        adNV5xxxT3(637),               -- (1200832L1)        NetVanta 5305 T3 NIM
        adNV950(638),                  -- (1200788L1)        NetVanta 950 System Controller Unit
        adNV970(639),                  -- (1200787L1)        NetVanta 970 System Controller Unit
        adNV9xxESM(640),              -- (1200793L1)        NetVanta 950/970 Octal Ethernet Switch Module
        adNV9xxFXS(641),              -- (1200791L1)        NetVanta 950/970 Octal FXS Module
        adNV9xxFXO(642),              -- (1200792L1)        NetVanta 950/970 Octal FXO Module
        adNV970DSS(643),               -- (1200790L1)        NetVanta 970 Octal DSS Module
        adNV950T1V35(644),             -- (1200798L1)        NetVanta T1/V35 Expansion Module
        adTA1500singleFXSsmas(645),    -- (1180.108L1)       TA 1500 Single FXS w/ SMAS
        adTA1500singleFXS(646),        -- (1180.108L2)       TA 1500 Single FXS w/o SMAS
        adTA1500sFXOdptTOsmas(647),    -- (1180.107L3)       TA 1500 Single FXO/DPT/TO w/ SMAS
        adTA1500sFXOdptTO(648),        -- (1180.107L4)       TA 1500 Single FXO/DPT/TO w/o SMAS
        adTA1500dFXOdptTO(649),        -- (1180.207L4)       TA 1500 Dual FXO/DPT/TO w/o SMAS
        adTA1500dFXOdptTOsmasLuc(650), -- (1133.207L3)       TA 1500 Dual FXO/DPT/TO w/ SMAS
        adTA600Ratm(651),              -- (4203.600L1#ATM)   TA 600R Router-Only
        adTA612atm(652),               -- (4203.612L1#ATM)   TA 612 ATM IAD
        adTA616atm(653),               -- (4203.616L1#ATM)   TA 616 ATM IAD
        adTA624atm(654),               -- (4203.624L1#ATM)   TA 624 ATM IAD
        adTA604atm(655),               -- (4203.640L1#ATM)   TA 604 ATM IAD
        adTA608atm(656),               -- (4203.680L1#ATM)   TA 608 ATM IAD
        adTA850Rcu3Gatm(657),          -- (4203.376L1#ATM)   TA 850 3G RCU ATM IAD
        adOptiMXEth8(658),             -- (1184.524L1)       OPTI-MX 8 port 10/100 Ethernet
        adTA3kHexADSL2Plus(659),       -- (1181.426L1)       TA 3000 hex (16 port) ADSL2+
        adTA3kSpirentITH(660),         -- (KD #?)            TA 3000  Spirent ITH Test Access Card
        adTA3kSM2(661),                -- (1181.047L1)       TA 3000 Dual GigE Switch Module
        adTA30x0AccDS1CutThruNoTest(662), -- (1183.008L1)    TA30x0 Accessory DS1 Cut Thru w/o Test Access
        adMX3000(663),                 -- (1189.001L1)       MX3000 Chassis
        adMX3208Ctrl(664),             -- (1189.002L1)       MX3208 Controller  2-DS3, 8-DSX
        adOptiMXDS1VME(665),           -- (1184.515L2 )      OPTI-MX 28 Port VT1.5 card with framers
        adTA1148qT1oL123(667),         -- (1179.741L1/L2/L3) TA1148 w/ 4 T1 IMA Network Interface, 48 ADSL ports in OSP enclosure
        adTA1148qT1oL4v5v(668),        -- (1179.741L4V/L5V)  TA1148 w/ 4 T1 IMA Network Interface, 48 ADSL ports in OSP enclosure
        adTA1148sNIoL123(669),         -- (1179.740L1/L2/L3) TA1148 Subtended Network Interface, 48 ADSL Ports in OSP enclosure
        adTA1148qHDSLoL123(670),       -- (1179.742L1/L2/L3) TA1148 w/ 4 HDSL4 IMA Network Interface, 48 ADSL ports in OSP enclosure
        adTA1148qHDSLoL4v5v(671),      -- (1179.742L4V/L5V)  TA1148 w/ 4 HDSL4 IMA Network Interface, 48 ADSL ports in OSP enclosure
        adTA1248qT1L1(672),            -- (1179.641L1)       TA1248 w/ 4 T1 IMA Network Interface, 48 ADSL ports in 1 mtg space 19" rack enclosure
        adTA1248sNIL5(673),            -- (1179.641L5)       TA1248 Subtended Network Interface, 48 ADSL ports in 1 mtg space 19" rack enclosure
        adTA1124qT1oL123(674),         -- (1179.721L1/L2/L3) TA1124 w/ 4 T1 IMA Network Interface, 24 ADSL ports in OSP enclosure
        adTA1124qHDSLoL123(675),       -- (1179.722L1/L2/L3) TA1124 w/ 4 HDSL4 IMA Network Interface, 24 ADSL ports in OSP enclosure
        adTA1124sNIL123(676),          -- (1179.720L1/L2/L3) TA1124 Subtended Network Interface, 24 ADSL Ports in OSP enclosure
        adTA1224qT1L1(677),            -- (1179.621L1)       TA1224 w/ 4 T1 IMA Network Interface, 24 ADSL ports in 1 mtg space 19" rack enclosure
        adTA1224sNIL5(678),            -- (1179.621L5)       TA1224 Subtended Network Interface, 24 ADSL ports in 1 mtg space 19" rack enclosure
        adOptiMXEthM8E(679),           -- (1184.525L1)       OPTI-MX 8 Port 10/100 Enhanced Ethernet with VLAN Double Tagging
        adExp6540acSHDSL(680),         -- (1230.001L1)       Express 6540, AC, SHDSL remote unit
        adExp6540dcSHDSL(681),         -- (1230.002L1)       Express 6540, DC, SHDSL remote unit
        adExp6541acSHDSL(682),         -- (1230.007L1)       Express 6541, AC, SHDSL remote unit
        adExp6541dcSHDSL(683),         -- (1230.008L1)       Express 6541, DC, SHDSL remote unit
        adExp6542SHDSL(684),           -- (1230.009L1)       Express 6542, SHDSL remote unit
        adOpti61VTccMux(685),          -- (1184.536L1)       OPTI-6100 VT Cross-Connect MUX
        adTA1148oT1ospL123(686),       -- (1179.743L1/L2/L3) TA1148 w/ 8 T1 IMA Network Interface, 48 ADSL ports in OSP enclosure
        adTA1148oHDSLospL123(687),     -- (1179.748L1/L2/L3) TA1148 w/ 8 HDSL4 IMA Network Interface, 48 ADSL ports in OSP enclosure
        adTA1248oT1L4(688),            -- (1179.641L4)       TA1248 w/ 8 T1 IMA Network Interface, 48 ADSL ports in 1 mtg space 19" rack enclosure
        adTA1124oT1ospL123(689),       -- (1179.723L1/L2/L3) TA1124 w/ 8 T1 IMA Network Interface, 24 ADSL ports in OSP enclosure
        adTA1124oHDSLospL123(690),     -- (1179.728L1/L2/L3) TA1124 w/ 8 HDSL4 IMA Network Interface, 24 ADSL ports in OSP enclosure
        adTA1224oT1L4(691),            -- (1179.621L4)       TA1224 w/ 8 T1 IMA Network Interface, 24 ADSL ports in 1 mtg space 19" rack enclosure
        adTA1148qT1oL123A(692),        -- (1179.741L1/L2/L3-A) TA1148 1179741L1/L2/L3 48 Port ADSL Module
        adTA1148qT1oL123N(693),        -- (1179.741L1/L2/L3-N) TA1148 1179741L1/L2/L3 4 Port T1 IMA Network Module
        adTA1148qT1oL4v5vA(694),       -- (1179.741L4V/L5V-A)  TA1148 1179741L4V/L5V 48 Port ADSL Module
        adTA1148qT1oL4v5vN(695),       -- (1179.741L4V/L5V-N)  TA1148 1179741L4V/L5V 4 Port T1 IMA Network Module
        adTA1148sNIoL123A(696),        -- (1179.740L1/L2/L3-A) TA1148 1179740L1/L2/L3 48 Port ADSL Module
        adTA1148sNIoL123N(697),        -- (1179.740L1/L2/L3-N) TA1148 1179740L1/L2/L3 Subtending Network Module
        adTA1148qHDSLoL123A(698),      -- (1179.742L1/L2/L3-A) TA1148 1179742L1/L2/L3 48 Port ADSL Module
        adTA1148qHDSLoL123N(699),      -- (1179.742L1/L2/L3-N) TA1148 1179742L1/L2/L3 4 Port HDSL4 IMA Network Module
        adTA1148qHDSLoL4v5vA(700),     -- (1179.742L4V/L5V-A)  TA1148 1179742L4V/L5V 48 Port ADSL Module
        adTA1148qHDSLoL4v5vN(701),     -- (1179.742L4V/L5V-N)  TA1148 1179742L4V/L5V 4 Port HDSL4 Network Module
        adTA1248qT1L1A(702),           -- (1179.641L1-A)       TA1248 1179641L1 48 Port ADSL Module
        adTA1248qT1L1N(703),           -- (1179.641L1-N)       TA1248 1179641L1 4 Port T1 IMA Network Module
        adTA1248sNIL5A(704),           -- (1179.641L5-A)       TA1248 1179641L5 48 Port ADSL Module
        adTA1248sNIL5N(705),           -- (1179.641L5-N)       TA1248 1179641L5 Subtending Network Module
        adTA1124qT1oL123A(706),        -- (1179.721L1/L2/L3-A) TA1124 1179721L1/L2/L3 24 Port ADSL Module
        adTA1124qT1oL123N(707),        -- (1179.721L1/L2/L3-N) TA1124 1179721L1/L2/L3 4 Port T1 IMA Network Module
        adTA1124qHDSLoL123A(708),      -- (1179.722L1/L2/L3-A) TA1124 1179722L1/L2/L3 24 Port ADSL Module
        adTA1124qHDSLoL123N(709),      -- (1179.722L1/L2/L3-N) TA1124 1179722L1/L2/L3 4 Port HDSL4 IMA Network Module
        adTA1124sNIL123A(710),         -- (1179.720L1/L2/L3-A) TA1124 1179720L1/L2/L3 24 Port ADSL Module
        adTA1124sNIL123N(711),         -- (1179.720L1/L2/L3-N) TA1124 1179720L1/L2/L3 Subtending Network Module
        adTA1224qT1L1A(712),           -- (1179.621L1-A)       TA1224 1179621L1 24 Port ADSL Module
        adTA1224qT1L1N(713),           -- (1179.621L1-N)       TA1224 1179621L1 4 Port T1 IMA Network Module
        adTA1224sNIL5A(714),           -- (1179.621L5-A)       TA1224 1179621L5 24 Port ADSL Module
        adTA1224sNIL5N(715),           -- (1179.621L5-N)       TA1224 1179621L5 Subtending Network Module
        adTA1148oT1ospL123A(716),      -- (1179.743L1/L2/L3-A) TA1148 1179743L1/L2/L3 48 Port ADSL Module
        adTA1148oT1ospL123N(717),      -- (1179.743L1/L2/L3-N) TA1148 1179743L1/L2/L3 8 Port T1 IMA Network Module
        adTA1148oHDSLospL123A(718),    -- (1179.748L1/L2/L3-A) TA1148 1179748L1/L2/L3 48 Port ADSL Module
        adTA1148oHDSLospL123N(719),    -- (1179.748L1/L2/L3-N) TA1148 1179748L1/L2/L3 8 Port HDSL4 Network Module
        adTA1248oT1L4A(720),           -- (1179.641L4-A)       TA1248 1179641L4 48 Port ADSL Module
        adTA1248oT1L4N(721),           -- (1179.641L4-N)       TA1248 1179641L4 8 Port T1 IMA Network Module
        adTA1124oT1ospL123A(722),      -- (1179.723L1/L2/L3-A) TA1124 1179723L1/L2/L3 24 Port ADSL Module
        adTA1124oT1ospL123N(723),      -- (1179.723L1/L2/L3-N) TA1124 1179723L1/L2/L3 8 Port T1 IMA Network Module
        adTA1124oHDSLospL123A(724),    -- (1179.728L1/L2/L3-A) TA1124 1179728L1/L2/L3 24 Port ADSL Module
        adTA1124oHDSLospL123N(725),    -- (1179.728L1/L2/L3-N) TA1124 1179728L1/L2/L3 8 Port HDSL4 Network Module
        adTA1224oT1L4A(726),           -- (1179.621L4-A)       TA1224 1179621L4 24 Port ADSL Module
        adTA1224oT1L4N(727),           -- (1179.621L4-N)       TA1224 1179621L4 8 Port T1 IMA Network Module
        adTA1124qHDSLoL4v5vns(728),    -- (1179.722L4V/L5V)    TA1124 w/ 4 HDSL4 IMA Network Interface, 24 ADSL Ports in OSP enclosure (no subtending)
        adTA1124qHDSLoL4v5vnsA(729),   -- (1179.722L4V/L5V-A)  TA1124 1179722L4V/L5V 24 Port ADSL Module
        adTA1124qHDSLoL4v5vnsN(730),   -- (1179.722L4V/L5V-N)  TA1124 1179722L4V/L5V 4 Port HDSL4 IMA Network Module
        adTA1124qT1oL4v5vns(731),      -- (1179.721L4V/L5V)    TA1124 w/ 4 T1 IMA Network Interface, 24 ADSL Ports in OSP enclosure (no subtending)
        adTA1124qT1oL4v5vnsA(732),     -- (1179.721L4V/L5V-A)  TA1124 1179721L4V/L5V 24 Port ADSL Module
        adTA1124qT1oL4v5vnsN(733),     -- (1179.721L4V/L5V-N)  TA1124 1179721L4V/L5V 4 Port T1 IMA Network Module
        adTA1224qT1L1ns(734),          -- (1179.622L1)         TA1224 w/ 4 T1 IMA Network Interface, 24 ADSL ports in 1 mtg space 19" rack enclosure (no subtending)
        adTA1224qT1L1nsA(735),         -- (1179.622L1-A)       TA1224 1179622L1 24 Port ADSL Module
        adTA1224qT1L1nsN(736),         -- (1179.622L1-N)       TA1224 1179622L1 4 Port T1 IMA Network Module
        adTA1248qT1L1ns(737),          -- (1179.642L1)         TA1248 w/ 4 T1 IMA Network Interface, 48 ADSL ports in 1 mtg space 19" rack enclosure (no subtending)
        adTA1248qT1L1nsA(738),         -- (1179.642L1-A)       TA1248 1179642L1 48 Port ADSL Module
        adTA1248qT1L1nsN(739),         -- (1179.642L1-N)       TA1248 1179642L1 4 Port T1 IMA Network Module
        adTA3kOC3LM(740),              -- (1181.454L1)       TA3000 OC3 Line Module
        adTA3kHexSHDSL(741),           -- (1181.422L1)       TA 3000 2w4w SHDSL 16 Port
        adNV1224PoE(742),              -- (1200580L1)        NV1224 PoE
        adNV1224STPoE(743),            -- (1200584L1)        NV1224ST PoE
        adNV1224RPoE(744),             -- (1200530L1)        NV1224R PoE
        adNV1224STRPoE(745),           -- (1200570L1)        NV1224STR PoE
        adNV340(746),                  -- (1200422L1)        Netvanta 340 chassis
        adTA500023(747),               -- (1187.001L1)       TA 5000 23 inch shelf
        adTA500019(748),               -- (1187.002L1)       TA 5000 19 inch shelf
        adTA5kSCM(749),                -- (1187.010L1)       TA5k System Controller Module
        adTA5kSwM(750),                -- (1187.020L1)       TA5k Switch Module
        adTA5kFan23(751),              -- (1187.080L1)       TA5k 23" Fan Module
        adTA5k32pADSL2(752),           -- (1187.101L1)       TA5k 32 PORT ADSL2+
        adTA5k32pPOTS(753),            -- (1187.150L1)       TA5k 32 PORT POTS
        adTA5kETSI32Spltr(754),        -- (1188.105L1)       TA5k ETSI ADJ 32 SPLITTER
        adTA5kANSI32Spltr(755),        -- (1187.105L1)       TA5k ANSI ADJ 32 SPLITTER
        adTA5kSHDSL(756),              -- (1187.110L1)       TA5k SHDSL
        adTA5kqOC3LM(757),             -- (1187.200L1)       TA5k Quad OC3 line module
        adTA5kOLT(758),                -- (1187.201L1)       TA5k PON 622/155 OLT card
        adTA5k32DS1vGW(759),           -- (1187.800L1)       TA5k 32 DS1 voice gateway
        adNV1524ST(760),               -- (1200.560L1)       Netvanta 1524ST
        adOptiMXDS3M3E(761),           -- (1184.533L2)       OPTI-MX 3 Port DS3/EC1 card with framers
        adTA3kHexPOTS(762),            -- (1181.441L1)       TA 3000 hex (16 port) POTS
        adTA3kHexPOTSADSL(763),        -- (1181.442L1)       TA 3000 hex (16 port) POTS + ADSL
        adNV344(764),                  -- (1200.423L1)       Netvanta 344
        adTA3kQuadVDSL(765),           -- (1181.470L1)       TA 3000 Quad VDSL
        adTA1240EthSHDSL2w4wShelf(766),-- (1179.605L5)       TA1240 L5 Ethernet 2w4w SHDSL Shelf
        adTA1240SHDSL2w4w(767),        -- (1179.605L5)A      TA1240 L5 2w4w SHDSL module
        adTA1240Eth(768),              -- (1179.605L5)B      TA1240 L5 Ethernet module
        adTA3kLTU8cr(769),             -- (1182.300L1)       Total Access 3000 cost-reduced LTU-8 (346)
        adTA3kOctADSL2Plus(770),       -- (1181.426L2)       TA 3000 octal (8 port) ADSL2+ Splitter card w/ ETA
        adNV3xxxDualT1(771),           -- (1200.872L1)       NetVanta 3xxx DualT1 (1200872L1)
        adMX3RMM(772),                 -- (1189.004L1)       MX3 Remote Management Module
        adTA5kFan19(773),              -- (1187.085L1)       TA5k 19" Fan Module
        adTA3kOctDs1E1IMAg3(774),      -- (1181.409L12)      TA3000 Octal DS1/E1 IMA, 3rd Gen
        adTA3kQuadDs1E1IMAg3(775),     -- (1181.409L14)      TA3000 Quad DS1/E1 IMA, 3rd Gen
        adTA30x0AccSpltrEmVid(776),    -- (1183.102L1)       TA30x0 Accessory 8-port POTS Splitter with enhanced magnetics for Video Support
        adTA30x0AccSpltrEmTest(777),   -- (1183.102L2)       TA30x0 Accessory 8-port POTS Splitter with enhanced magnetics and test access
        adTA30x0AccSpltrEmTestProt(778),--(1183.002L12)      TA30x0 Accessory 8-port POTS Splitter with enhanced magnetics and test access and POTS protection
        adTA908(779),                  -- (1200.908L1)       TA908
        adTA912(780),                  -- (4210.912L1)       TA912
        adTA916(781),                  -- (4210.916L1)       TA916
        adTA908e(782),                 -- (1200.909L1)       TA908e
        adTA912e(783),                 -- (1200.913L1)       TA912e
        adTA916e(784),                 -- (1200.917L1)       TA916e
        adTAEMSL1(785),                -- (4150TAEMSL1)      TAEMS Element Management System
        adTAOptiO3TME(786),            -- (1184.543L4)       Opti-6100 Enhanced OC-3 Tributary Module
        adTA3k2gCSM128(787),           -- (1181.041L14)      TA3000 2nd gen 128 port Cell Switch Module
        adTA4303PlusScuL2(788),        -- (1202.334L2)       TA4303 Plus SCU L2
        adOptiMXOc12OMMsdh(789),       -- (1184.504L1-4)     OPTI-6100 OC12 Sonet/SDH Mux firmware
        adTA5kSCMint(790),             -- (1188.010L1)       TA5k System Controller Module International
        adTA924(791),                  -- (4210.924L1)       TA924
        adTA912eDualT1(792),           -- (4220.912L1)       TA912e Dual T1
        adTA916eDualT1(793),           -- (4220.916L1)       TA916e Dual T1
        adTA924eDualT1(794),           -- (4220.924L1)       TA924e Dual T1
        adTA912eQuadT1(795),           -- (4240.912L1)       TA912e Quad T1
        adTA916eQuadT1(796),           -- (4240.916L1)       TA916e Quad T1
        adTA924eQuadT1(797),           -- (4240.924L1)       TA924e Quad T1
        adOptiMXDS1VMT(798),           -- (1184.515L3)       OPTI-MX 28 Port VT1.5 card with Tx Timing Option
        adOptiMXEthM8Eh(799),          -- (1184.545L1)       OPTI-MX 8-port 10/100 Ethernet to STS - 12 single VCG card w/ VLANs
        adOptiMXGefM1Eh(800),          -- (1184.546L1)       OPTI-MX 1-port Gigabit Ethernet Fiber (SFP) to STS - 12 single VCG card w/ VLANs
        adOptiMXOc12OMMy(801),         -- (1184.504L6-8)     OPTI-6100 OC12 Mux OMM12 UPSR w/ Y
        adOptiMXOc3OMMy(802),          -- (1184.502L5-7)     OPTI-6100 OC3  Mux OMM3  UPSR w/ Y


                      -- GAP HERE TO BE MANUALLY FILLED IN UNTIL 999
        adUnknown(999),                -- Any unresponsive or unrecognizable card actually detectable

                      -- GAP HERE TO BE MANUALLY FILLED IN AFTER 999
        adEndOfList(9999)              -- place holder for editing, never used.
        }

   -- These identifiers are used to define the product leaves
   --   in the subtree adtran(664).adPerform(4)

    AdPerformance ::= INTEGER { -- use to define all ADTRAN performance OIDs
        adFRPerformmg (1),
        adL3Performmg (2)
        }

    -- These identifiers are used to define the product leaves
    --   in the subtree adtran(664).adShared(5)

    AdSharedCommon ::= INTEGER { -- use to define all ADTRAN shared OIDs
        adExLan(1),
        adFRHistory(2),
        adEOCxxx(3),
        adTARouterGroup(4),
        adFXOcommon(5),
        adNx64common(6),
        adOCUDPcommon(7),
        adDSODPcommon(8),
        adUBRITEcommon(9),
        adFXScommon(10),
        adPRI(11),
        adXSUIQEXTmg(12),
        adGenericShelves(13),
        adH2TUCcommon(14),
        adENDgenChassis(15),
        adTrapInform(16),
        adSCUCommon(17),
        adEandMcommon(18),
        adGenVoice(19),
        adGenLIU(20),
        adDSX1Common(21),
        adTA1500SCUCommon(22),
        adPSUcommon(23),
        adGenSHDSL(24),
        adTARouterTraps(25),
        adTracerCommon(26),
        adExp653x(27),
        adTASHDSLSP(28),
        adDSX1CommonTraps(29),  -- extends adDSX1Common for traps
        adunit(30),
        adH4TUCcommon(31),
        adIadSysMib(32),
        adIadRouter(33),
        adIadVoice(34),
        adGenOPTI3(35),
        adGenAtm(36),
        ad4WCommon(37),
        adDXCommon(38),
        adGTCommon(39),
        adGenOPTI3Traps(40),
        adgenDSX1FR(41),
        adTa6xx(42),
        adIadIwf(43),
        adGen654x(44),
        adGenSHDSL4(45),
        adMCUcommon(46),
        adTA1500FT1common(47),
        adGenOMMX(48),
        adGenOMMXTraps(49),
        adGenOptical(50),      -- All future Phoenix (JV)
        adGenHDSL(51),         -- All future HDSL (BS, BT, JT)
        adRfc2955FrAtm(52),    -- CND (DC)
        adGenAOS(53),
        adGenAccessories(54),  -- TA 3xxx apps (AP, GF, MR, EB)
        adETOCommon(55),       -- 1500
        ad4WTDMCommon(56),     -- 1500
        adGen1500(57),         -- All future 1500 (KW, PD)
        adGenOMMXTraps2(58),
        adSHDSL(59),           -- All future SHDSL (JB, JB)
        adCndRemRep(60),       -- All future Rem Rep products (KE, BT)
        adGenMiniDSLAM(61)     -- All future Mini DSLAM products (GO, JT)
       }

    -- A type to define occupancy of a slot (real or virtual)

    AdPresence ::=  INTEGER {    -- used to reflect occupancy status
        empty(1),         -- not occupied and not reserved
        virtual(2),       -- empty, but was, or is
                          --   preprovisioned (optional)
        occupied(3)       -- occupied with designated type
        }


    -- A type to define alarm severities

    AdAlarmSeverity ::= INTEGER {    -- A type to define alarm severities
        informational(1),
        warning(2),
        minor(3),
        major(4),
        critical(5)
        }

    -- A type for dynamic row creation, maintenance, and deletion

    EntryStatus ::= INTEGER {    -- used to dynamically manage rows
        valid(1),         -- row exists, or command
                          --   to signal row complete
        createRequest(2), -- command to insert row
        underCreation(3), -- status upon creation if interim
        invalid(4)        -- command to delete row
        }

    -- Table algorithm from rfc1757 RMON-MIB:

              --   EntryStatus ::= INTEGER
              --           { valid(1),
              --             createRequest(2),
              --             underCreation(3),
              --             invalid(4)
              --           }
              -- The status of a table entry.
              --
              -- Setting this object to the value invalid(4) has the
              -- effect of invalidating the corresponding entry.
              -- That is, it effectively disassociates the mapping
              -- identified with said entry.
              -- It is an implementation-specific matter as to whether
              -- the agent removes an invalidated entry from the table.
              -- Accordingly, management stations must be prepared to
              -- receive tabular information from agents that
              -- corresponds to entries currently not in use.  Proper
              -- interpretation of such entries requires examination
              -- of the relevant EntryStatus object.
              --
              -- An existing instance of this object cannot be set to
              -- createRequest(2).  This object may only be set to
              -- createRequest(2) when this instance is created.  When
              -- this object is created, the agent may wish to create
              -- supplemental object instances with default values
              -- to complete a conceptual row in this table.  Because
              -- the creation of these default objects is entirely at
              -- the option of the agent, the manager must not assume
              -- that any will be created, but may make use of any that
              -- are created. Immediately after completing the create
              -- operation, the agent must set this object to
              -- underCreation(3).
              --
              -- When in the underCreation(3) state, an entry is
              -- allowed to exist in a possibly incomplete, possibly
              -- inconsistent state, usually to allow it to be
              -- modified in mutiple PDUs.  When in this state, an
              -- entry is not fully active.  Entries shall exist in
              -- the underCreation(3) state until the management
              -- station is finished configuring the entry and sets
              -- this object to valid(1) or aborts, setting this
              -- object to invalid(4).  If the agent determines that
              -- an entry has been in the underCreation(3) state for
              -- an abnormally long time, it may decide that the
              -- management station has crashed.  If the agent makes
              -- this decision, it may set this object to invalid(4)
              -- to reclaim the entry.  A prudent agent will
              -- understand that the management station may need to
              -- wait for human input and will allow for that
              -- possibility in its determination of this abnormally
              -- long period.
              --
              -- An entry in the valid(1) state is fully configured and
              -- consistent and fully represents the configuration or
              -- operation such a row is intended to represent.  For
              -- example, it could be a statistical function that is
              -- configured and active, or a filter that is available
              -- in the list of filters processed by the packet capture
              -- process.
              --
              -- A manager is restricted to changing the state of an
              -- entry in the following ways:
              --
              --                       create   under
              --      To:       valid  Request  Creation  invalid
              -- From:
              -- valid             OK       NO        OK       OK
              -- createRequest    N/A      N/A       N/A      N/A
              -- underCreation     OK       NO        OK       OK
              -- invalid           NO       NO        NO       OK
              -- nonExistent       NO       OK        NO       OK
              --
              -- In the table above, it is not applicable to move the
              -- state from the createRequest state to any other
              -- state because the manager will never find the
              -- variable in that state.  The nonExistent state is
              -- not a value of the enumeration, rather it means that
              -- the entryStatus variable does not exist at all.
              --
              -- An agent may allow an entryStatus variable to change
              -- state in additional ways, so long as the semantics
              -- of the states are followed.  This allowance is made
              -- to ease the implementation of the agent and is made
              -- despite the fact that managers should never
              -- excercise these additional state transitions.

    END
