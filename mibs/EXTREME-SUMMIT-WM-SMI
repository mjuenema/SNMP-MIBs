--
-- EXTREME-SUMMIT-WM-SMI.my
-- MIB generated by MG-SOFT Visual MIB Builder Version 4.0 Build 349
-- Friday, September 02, 2005 at 17:16:19
--

	EXTREME-SUMMIT-WM-SMI DEFINITIONS ::= BEGIN
 
		IMPORTS
			enterprises			
				FROM RFC1155-SMI			
			MODULE-IDENTITY, OBJECT-IDENTITY			
				FROM SNMPv2-SMI;
	
	
		-- 1.3.6.1.4.1.1916.5
		extremeSummitWMAgent MODULE-IDENTITY 
			LAST-UPDATED "200509010237Z"		-- September 01, 2005 at 02:37 GMT
			ORGANIZATION 
				"Extreme Networks, Inc."
			CONTACT-INFO 
				"www.extremenetworks.com"
			DESCRIPTION 
				"Summit WM switch MIB root node definitions."
			REVISION "200509010237Z"		-- September 01, 2005 at 02:37 GMT
			DESCRIPTION 
				"Initial revision."
			::= { extremenetworks 5 }

		
	
--
-- Node definitions
--
	
--  September 01, 2005 at 02:37 GMT
-- 
-- 
		-- 1.3.6.1.4.1.1916
		extremenetworks OBJECT IDENTIFIER ::= { enterprises 1916 }

		
		-- 1.3.6.1.4.1.1916.2
		extremeProduct OBJECT IDENTIFIER ::= { extremenetworks 2 }

		
		-- 1.3.6.1.4.1.1916.2.68
		wm100 OBJECT IDENTIFIER ::= { extremeProduct 68 }

		
		-- 1.3.6.1.4.1.1916.2.69
		wm1000 OBJECT IDENTIFIER ::= { extremeProduct 69 }

		
		-- 1.3.6.1.4.1.1916.2.75
		altitude350 OBJECT IDENTIFIER ::= { extremeProduct 75 }

		
		-- 1.3.6.1.4.1.1916.5.1
		summitWMProducts OBJECT-IDENTITY
			STATUS obsolete
			DESCRIPTION 
				"Provides a root OID from which MIB-II sysObjectID values 
				are assigned.  Actual product OIDs are defined in
				EXTREME-WM-PRODUCTS-MIB."
			::= { extremeSummitWMAgent 1 }

		
		-- 1.3.6.1.4.1.1916.5.3
		summitWMMgmt OBJECT-IDENTITY
			STATUS current
			DESCRIPTION 
				"Main subtree for Extreme Networks Summit WM management information."
			::= { extremeSummitWMAgent 3 }

		
		-- 1.3.6.1.4.1.1916.5.4
		summitWMDevelopment OBJECT-IDENTITY
			STATUS current
			DESCRIPTION 
				"Subtree for pre-release MIB development. 
				Elements in this subtree are eventually moved to 
				'summitWMMgmt'."
			::= { extremeSummitWMAgent 4 }

		
		-- 1.3.6.1.4.1.1916.5.5
		summitWMModules OBJECT-IDENTITY
			STATUS current
			DESCRIPTION 
				"summitWMModules provides a root object identifier
				from which MODULE-IDENTITY values are assigned."
			::= { extremeSummitWMAgent 5 }

		
	
	END

--
-- EXTREME-SUMMIT-WM-SMI.my
--
