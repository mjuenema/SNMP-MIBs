-- file automatically created


TELDAT-TRAP-DNAT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


dnatTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the DNAT event subsystem."
    REVISION "201401200930Z"
    DESCRIPTION "Initial implementation"
        ::= { telEventTraps 160 }


dnatEventsGroup	OBJECT IDENTIFIER	::= { dnatTrapsMIB 1 }

dnatNotifications	OBJECT IDENTIFIER	::= { dnatTrapsMIB 2 }
dnatNotificationsPrefix	OBJECT IDENTIFIER	::= { dnatNotifications 0 }

dnatEventObjects1 OBJECT-IDENTITY
    STATUS current
    DESCRIPTION
        "Event DNAT.1
        IPSec is requesting DNat service for next new IPSec client."
    ::= { dnatEventsGroup 1 }

dnat1_src_address OBJECT-TYPE
    SYNTAX IpAddress
    MAX-ACCESS accessible-for-notify
    STATUS current
    DESCRIPTION
        "Parameter 'src_address' in event DNAT.1"
    ::= { dnatEventObjects1 1 }

dnat1_dst_address OBJECT-TYPE
    SYNTAX IpAddress
    MAX-ACCESS accessible-for-notify
    STATUS current
    DESCRIPTION
        "Parameter 'dst_address' in event DNAT.1"
    ::= { dnatEventObjects1 2 }

dnatEventObjects2 OBJECT-IDENTITY
    STATUS current
    DESCRIPTION
        "Event DNAT.2
        DNat has established a new translation for a new client."
    ::= { dnatEventsGroup 2 }

dnat2_src_address OBJECT-TYPE
    SYNTAX IpAddress
    MAX-ACCESS accessible-for-notify
    STATUS current
    DESCRIPTION
        "Parameter 'src_address' in event DNAT.2"
    ::= { dnatEventObjects2 1 }

dnat2_dst_address OBJECT-TYPE
    SYNTAX IpAddress
    MAX-ACCESS accessible-for-notify
    STATUS current
    DESCRIPTION
        "Parameter 'dst_address' in event DNAT.2"
    ::= { dnatEventObjects2 2 }

dnat2_new_src_address OBJECT-TYPE
    SYNTAX IpAddress
    MAX-ACCESS accessible-for-notify
    STATUS current
    DESCRIPTION
        "Parameter 'new_src_address' in event DNAT.2"
    ::= { dnatEventObjects2 3 }

dnat2_new_dst_address OBJECT-TYPE
    SYNTAX IpAddress
    MAX-ACCESS accessible-for-notify
    STATUS current
    DESCRIPTION
        "Parameter 'new_dst_address' in event DNAT.2"
    ::= { dnatEventObjects2 4 }

dnatEventObjects3 OBJECT-IDENTITY
    STATUS current
    DESCRIPTION
        "Event DNAT.3
        There is no match on rules DNat for a packet."
    ::= { dnatEventsGroup 3 }

dnat3_src_address OBJECT-TYPE
    SYNTAX IpAddress
    MAX-ACCESS accessible-for-notify
    STATUS current
    DESCRIPTION
        "Parameter 'src_address' in event DNAT.3"
    ::= { dnatEventObjects3 1 }

dnat3_dst_address OBJECT-TYPE
    SYNTAX IpAddress
    MAX-ACCESS accessible-for-notify
    STATUS current
    DESCRIPTION
        "Parameter 'dst_address' in event DNAT.3"
    ::= { dnatEventObjects3 2 }

dnatEventObjects4 OBJECT-IDENTITY
    STATUS current
    DESCRIPTION
        "Event DNAT.4
        IPSec is asking DNat service about translation on packet."
    ::= { dnatEventsGroup 4 }

dnat4_src_address OBJECT-TYPE
    SYNTAX IpAddress
    MAX-ACCESS accessible-for-notify
    STATUS current
    DESCRIPTION
        "Parameter 'src_address' in event DNAT.4"
    ::= { dnatEventObjects4 1 }

dnat4_dst_address OBJECT-TYPE
    SYNTAX IpAddress
    MAX-ACCESS accessible-for-notify
    STATUS current
    DESCRIPTION
        "Parameter 'dst_address' in event DNAT.4"
    ::= { dnatEventObjects4 2 }

dnatEventObjects5 OBJECT-IDENTITY
    STATUS current
    DESCRIPTION
        "Event DNAT.5
        Translation to do on packet found."
    ::= { dnatEventsGroup 5 }

dnat5_src_address OBJECT-TYPE
    SYNTAX IpAddress
    MAX-ACCESS accessible-for-notify
    STATUS current
    DESCRIPTION
        "Parameter 'src_address' in event DNAT.5"
    ::= { dnatEventObjects5 1 }

dnat5_dst_address OBJECT-TYPE
    SYNTAX IpAddress
    MAX-ACCESS accessible-for-notify
    STATUS current
    DESCRIPTION
        "Parameter 'dst_address' in event DNAT.5"
    ::= { dnatEventObjects5 2 }

dnat5_new_src_address OBJECT-TYPE
    SYNTAX IpAddress
    MAX-ACCESS accessible-for-notify
    STATUS current
    DESCRIPTION
        "Parameter 'new_src_address' in event DNAT.5"
    ::= { dnatEventObjects5 3 }

dnat5_new_dst_address OBJECT-TYPE
    SYNTAX IpAddress
    MAX-ACCESS accessible-for-notify
    STATUS current
    DESCRIPTION
        "Parameter 'new_dst_address' in event DNAT.5"
    ::= { dnatEventObjects5 4 }

dnatEventObjects6 OBJECT-IDENTITY
    STATUS current
    DESCRIPTION
        "Event DNAT.6
        An old IPSec 'SA' used in DNat client is now updated to the actual SA."
    ::= { dnatEventsGroup 6 }

dnat6_src_address OBJECT-TYPE
    SYNTAX IpAddress
    MAX-ACCESS accessible-for-notify
    STATUS current
    DESCRIPTION
        "Parameter 'src_address' in event DNAT.6"
    ::= { dnatEventObjects6 1 }

dnat6_dst_address OBJECT-TYPE
    SYNTAX IpAddress
    MAX-ACCESS accessible-for-notify
    STATUS current
    DESCRIPTION
        "Parameter 'dst_address' in event DNAT.6"
    ::= { dnatEventObjects6 2 }

dnatEventObjects7 OBJECT-IDENTITY
    STATUS current
    DESCRIPTION
        "Event DNAT.7
        DNat client is updated to the actual SA."
    ::= { dnatEventsGroup 7 }

dnat7_src_address OBJECT-TYPE
    SYNTAX IpAddress
    MAX-ACCESS accessible-for-notify
    STATUS current
    DESCRIPTION
        "Parameter 'src_address' in event DNAT.7"
    ::= { dnatEventObjects7 1 }

dnat7_dst_address OBJECT-TYPE
    SYNTAX IpAddress
    MAX-ACCESS accessible-for-notify
    STATUS current
    DESCRIPTION
        "Parameter 'dst_address' in event DNAT.7"
    ::= { dnatEventObjects7 2 }

dnatEventObjects8 OBJECT-IDENTITY
    STATUS current
    DESCRIPTION
        "Event DNAT.8
        Incoming packet from outside interface."
    ::= { dnatEventsGroup 8 }

dnat8_src_address OBJECT-TYPE
    SYNTAX IpAddress
    MAX-ACCESS accessible-for-notify
    STATUS current
    DESCRIPTION
        "Parameter 'src_address' in event DNAT.8"
    ::= { dnatEventObjects8 1 }

dnat8_dst_address OBJECT-TYPE
    SYNTAX IpAddress
    MAX-ACCESS accessible-for-notify
    STATUS current
    DESCRIPTION
        "Parameter 'dst_address' in event DNAT.8"
    ::= { dnatEventObjects8 2 }

dnat8_protocol OBJECT-TYPE
    SYNTAX Integer32
    MAX-ACCESS accessible-for-notify
    STATUS current
    DESCRIPTION
        "Parameter 'protocol' in event DNAT.8"
    ::= { dnatEventObjects8 3 }

dnatEventObjects9 OBJECT-IDENTITY
    STATUS current
    DESCRIPTION
        "Event DNAT.9
        Outgoing packet from inside interface."
    ::= { dnatEventsGroup 9 }

dnat9_src_address OBJECT-TYPE
    SYNTAX IpAddress
    MAX-ACCESS accessible-for-notify
    STATUS current
    DESCRIPTION
        "Parameter 'src_address' in event DNAT.9"
    ::= { dnatEventObjects9 1 }

dnat9_dst_address OBJECT-TYPE
    SYNTAX IpAddress
    MAX-ACCESS accessible-for-notify
    STATUS current
    DESCRIPTION
        "Parameter 'dst_address' in event DNAT.9"
    ::= { dnatEventObjects9 2 }

dnat9_protocol OBJECT-TYPE
    SYNTAX Integer32
    MAX-ACCESS accessible-for-notify
    STATUS current
    DESCRIPTION
        "Parameter 'protocol' in event DNAT.9"
    ::= { dnatEventObjects9 3 }

dnatEventObjects10 OBJECT-IDENTITY
    STATUS current
    DESCRIPTION
        "Event DNAT.10
        DNat translation on packet."
    ::= { dnatEventsGroup 10 }

dnat10_src_address OBJECT-TYPE
    SYNTAX IpAddress
    MAX-ACCESS accessible-for-notify
    STATUS current
    DESCRIPTION
        "Parameter 'src_address' in event DNAT.10"
    ::= { dnatEventObjects10 1 }

dnat10_dst_address OBJECT-TYPE
    SYNTAX IpAddress
    MAX-ACCESS accessible-for-notify
    STATUS current
    DESCRIPTION
        "Parameter 'dst_address' in event DNAT.10"
    ::= { dnatEventObjects10 2 }

dnat10_new_src_address OBJECT-TYPE
    SYNTAX IpAddress
    MAX-ACCESS accessible-for-notify
    STATUS current
    DESCRIPTION
        "Parameter 'new_src_address' in event DNAT.10"
    ::= { dnatEventObjects10 3 }

dnat10_new_dst_address OBJECT-TYPE
    SYNTAX IpAddress
    MAX-ACCESS accessible-for-notify
    STATUS current
    DESCRIPTION
        "Parameter 'new_dst_address' in event DNAT.10"
    ::= { dnatEventObjects10 4 }

dnatEventObjects11 OBJECT-IDENTITY
    STATUS current
    DESCRIPTION
        "Event DNAT.11
        IPSec SA deleted, delete client DNat."
    ::= { dnatEventsGroup 11 }

dnat11_src_address OBJECT-TYPE
    SYNTAX IpAddress
    MAX-ACCESS accessible-for-notify
    STATUS current
    DESCRIPTION
        "Parameter 'src_address' in event DNAT.11"
    ::= { dnatEventObjects11 1 }

dnat11_dst_address OBJECT-TYPE
    SYNTAX IpAddress
    MAX-ACCESS accessible-for-notify
    STATUS current
    DESCRIPTION
        "Parameter 'dst_address' in event DNAT.11"
    ::= { dnatEventObjects11 2 }

dnatEventObjects12 OBJECT-IDENTITY
    STATUS current
    DESCRIPTION
        "Event DNAT.12
        DNat client (and reciprocal client) deleted."
    ::= { dnatEventsGroup 12 }

dnat12_src_address OBJECT-TYPE
    SYNTAX IpAddress
    MAX-ACCESS accessible-for-notify
    STATUS current
    DESCRIPTION
        "Parameter 'src_address' in event DNAT.12"
    ::= { dnatEventObjects12 1 }

dnat12_dst_address OBJECT-TYPE
    SYNTAX IpAddress
    MAX-ACCESS accessible-for-notify
    STATUS current
    DESCRIPTION
        "Parameter 'dst_address' in event DNAT.12"
    ::= { dnatEventObjects12 2 }


dnatNotification1 NOTIFICATION-TYPE
    OBJECTS { 
              dnat1_src_address, 
              dnat1_dst_address 
            }
    STATUS current
    DESCRIPTION
        "Notification of Event DNAT.1

        Message: 'IPSec requesting DNat for packet $1->$2'

        Parameters list:
              $1: dnat1_src_address
              $2: dnat1_dst_address

        IPSec is requesting DNat service for next new IPSec client."
    ::= { dnatNotificationsPrefix 1 }

dnatNotification2 NOTIFICATION-TYPE
    OBJECTS { 
              dnat2_src_address, 
              dnat2_dst_address,
              dnat2_new_src_address,
              dnat2_new_dst_address 
            }
    STATUS current
    DESCRIPTION
        "Notification of Event DNAT.2

        Message: 'New client in DNat, $1->$2 translates into $3->$4'

        Parameters list:
              $1: dnat2_src_address
              $2: dnat2_dst_address
              $3: dnat2_new_src_address
              $4: dnat2_new_dst_address

        DNat has established a new translation for a new client."
    ::= { dnatNotificationsPrefix 2 }

dnatNotification3 NOTIFICATION-TYPE
    OBJECTS { 
              dnat3_src_address, 
              dnat3_dst_address 
            }
    STATUS current
    DESCRIPTION
        "Notification of Event DNAT.3

        Message: 'No rule match for packet ($1->$2)'

        Parameters list:
              $1: dnat3_src_address
              $2: dnat3_dst_address

        There is no match on rules DNat for a packet."
    ::= { dnatNotificationsPrefix 3 }

dnatNotification4 NOTIFICATION-TYPE
    OBJECTS { 
              dnat4_src_address, 
              dnat4_dst_address 
            }
    STATUS current
    DESCRIPTION
        "Notification of Event DNAT.4

        Message: 'IPSec asking DNat about packet $1->$2'

        Parameters list:
              $1: dnat4_src_address
              $2: dnat4_dst_address

        IPSec is asking DNat service about translation on packet."
    ::= { dnatNotificationsPrefix 4 }

dnatNotification5 NOTIFICATION-TYPE
    OBJECTS { 
              dnat5_src_address, 
              dnat5_dst_address,
              dnat5_new_src_address,
              dnat5_new_dst_address 
            }
    STATUS current
    DESCRIPTION
        "Notification of Event DNAT.5

        Message: 'Client DNat found, $1->$2 translates into $3->$4'

        Parameters list:
              $1: dnat5_src_address
              $2: dnat5_dst_address
              $3: dnat5_new_src_address
              $4: dnat5_new_dst_address

        Translation to do on packet found."
    ::= { dnatNotificationsPrefix 5 }

dnatNotification6 NOTIFICATION-TYPE
    OBJECTS { 
              dnat6_src_address, 
              dnat6_dst_address 
            }
    STATUS current
    DESCRIPTION
        "Notification of Event DNAT.6

        Message: 'IPSec updating DNat client $1->$2 with new SA'

        Parameters list:
              $1: dnat6_src_address
              $2: dnat6_dst_address

        An old IPSec 'SA' used in DNat client is now updated to the actual SA."
    ::= { dnatNotificationsPrefix 6 }

dnatNotification7 NOTIFICATION-TYPE
    OBJECTS { 
              dnat7_src_address, 
              dnat7_dst_address 
            }
    STATUS current
    DESCRIPTION
        "Notification of Event DNAT.7

        Message: 'DNat client $1->$2 updated with new SA'

        Parameters list:
              $1: dnat7_src_address
              $2: dnat7_dst_address

        DNat client is updated to the actual SA."
    ::= { dnatNotificationsPrefix 7 }

dnatNotification8 NOTIFICATION-TYPE
    OBJECTS { 
              dnat8_src_address, 
              dnat8_dst_address,
              dnat8_protocol 
            }
    STATUS current
    DESCRIPTION
        "Notification of Event DNAT.8

        Message: 'Incoming packet $1->$2 protocol $3'

        Parameters list:
              $1: dnat8_src_address
              $2: dnat8_dst_address
              $3: dnat8_protocol

        Incoming packet from outside interface."
    ::= { dnatNotificationsPrefix 8 }

dnatNotification9 NOTIFICATION-TYPE
    OBJECTS { 
              dnat9_src_address, 
              dnat9_dst_address,
              dnat9_protocol 
            }
    STATUS current
    DESCRIPTION
        "Notification of Event DNAT.9

        Message: 'Outgoing packet $1->$2 protocol $3'

        Parameters list:
              $1: dnat9_src_address
              $2: dnat9_dst_address
              $3: dnat9_protocol

        Outgoing packet from inside interface."
    ::= { dnatNotificationsPrefix 9 }

dnatNotification10 NOTIFICATION-TYPE
    OBJECTS { 
              dnat10_src_address, 
              dnat10_dst_address,
              dnat10_new_src_address,
              dnat10_new_dst_address 
            }
    STATUS current
    DESCRIPTION
        "Notification of Event DNAT.10

        Message: 'DNat translation $1->$2 => $3->$4'

        Parameters list:
              $1: dnat10_src_address
              $2: dnat10_dst_address
              $3: dnat10_new_src_address
              $4: dnat10_new_dst_address

        DNat translation on packet."
    ::= { dnatNotificationsPrefix 10 }

dnatNotification11 NOTIFICATION-TYPE
    OBJECTS { 
              dnat11_src_address, 
              dnat11_dst_address 
            }
    STATUS current
    DESCRIPTION
        "Notification of Event DNAT.11

        Message: 'IPSec clearing DNat client $1->$2 with fixed SA'

        Parameters list:
              $1: dnat11_src_address
              $2: dnat11_dst_address

        IPSec SA deleted, delete client DNat."
    ::= { dnatNotificationsPrefix 11 }

dnatNotification12 NOTIFICATION-TYPE
    OBJECTS { 
              dnat12_src_address, 
              dnat12_dst_address 
            }
    STATUS current
    DESCRIPTION
        "Notification of Event DNAT.12

        Message: 'DNat client $1->$2 deleted'

        Parameters list:
              $1: dnat12_src_address
              $2: dnat12_dst_address

        DNat client (and reciprocal client) deleted."
    ::= { dnatNotificationsPrefix 12 }


END
