CAMEDIATIONMANAGER-ENTERPRISES-MIB DEFINITIONS ::= BEGIN
 
--
-- Enterprise infrastructure of the CA MEDIATION MANAGER enterprise MIB tree
--
 
IMPORTS
    MODULE-IDENTITY, caMediationManager FROM CAMEDIATIONMANAGER-MIB;
 
caMMEnterprises MODULE-IDENTITY
    LAST-UPDATED "201201300000Z"
    ORGANIZATION "www.CA.com"
    CONTACT-INFO   
                 "postal:   One CA Plaza
                        Islandia, NY 11749
                        USA
          email:    support@ca.com"
    DESCRIPTION
                "Enterprise infrastructure of the CA Mediation Manager enterprise MIB tree"
    REVISION     "201201300000Z"
    DESCRIPTION
                "First draft"
    ::= { caMediationManager 9}
    
-- We use the IANA registered enterprise IDs here 

-- caMMLucent OBJECT IDENTIFIER ::= { caMMEnterprises 637 }
-- caMMHuawei OBJECT IDENTIFIER ::= { caMMEnterprises 2011 }
 
--
--  CAMEDIATIONMANAGER-ENTERPRISES enterprise-specific management objects
--
 
 
END
