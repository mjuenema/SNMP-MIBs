--
-- MODULE-IDENTITY
--  OrgName
--     Fortinet Technologies, Inc.
--  ContactInfo
--     Technical Support
--     e-mail: support@fortinet.com
--     http://www.fortinet.com
--

FORTINET-300-MIB DEFINITIONS ::= BEGIN
	IMPORTS
		TEXTUAL-CONVENTION, DisplayString
			FROM SNMPv2-TC
 		ifIndex
 			FROM IF-MIB
		MODULE-IDENTITY, OBJECT-TYPE, NOTIFICATION-TYPE, enterprises,
		Integer32, Gauge32, IpAddress, Counter32
			FROM SNMPv2-SMI
		sysName
			FROM SNMPv2-MIB
		OBJECT-GROUP, NOTIFICATION-GROUP, MODULE-COMPLIANCE
			FROM SNMPv2-CONF;

	fortinet MODULE-IDENTITY
		LAST-UPDATED "200009030000Z" -- Sep. 03, 2009
		ORGANIZATION "Fortinet Technologies, Inc."
		CONTACT-INFO
			"
			      Technical Support
			      email: support@fortinet.com
			      http://www.fortinet.com
			"
		DESCRIPTION
			"MIB module for Fortinet network devices."

		REVISION "200009030000Z" -- Sep. 03, 2009
		DESCRIPTION "Fixed syntax warnings."

		REVISION "200710240000Z" -- Oct. 24, 2007
		DESCRIPTION "Added traps for RAID events and Power Supply Events."

		REVISION "200606210000Z" -- Jun. 21, 2006
		DESCRIPTION "Expanded traps to include sysName (hostname).
			Added new traps for other AV events, including
			oversize file blocking, file pattern matching, and
			fragmented file blocking.
			Renamed main AV trap to show actual usage."

		REVISION "200604260000Z" -- Apr. 26, 2006
		DESCRIPTION "Expanded vpn up/down traps and added
			OID's for local and remote gateway parameters.
			Updated Wifi platforms."

		REVISION "200601090000Z" -- Jan. 9, 2006
		DESCRIPTION "Added OID's for hdd usage and capacity.
			Added 5004 platform."

		REVISION "200512070000Z" -- Dec. 7, 2005
		DESCRIPTION "Added missing OID's for several traps used in
			communication between FortiGate and FortiManager.
			Also added some missing models.
			Moved fnIps group to correct OID."

		REVISION "200509200000Z" -- Sept. 20, 2005
		DESCRIPTION "Initial creation of unified MIB for products
			based on FortiOS >=3.00"

		::= { enterprises 12356 }

	--
	-- Textual conventions --
	--

	FnBoolState ::= TEXTUAL-CONVENTION
		STATUS current
		DESCRIPTION "boolean data type representing enabled/disabled"
		SYNTAX INTEGER { 
			disabled ( 1 ),
			enabled  ( 2 )
		} 

	FnIndex ::= TEXTUAL-CONVENTION
		DISPLAY-HINT "d"
		STATUS current
		DESCRIPTION "data type for table index values"
		SYNTAX Integer32 ( 0 .. 2147483647 )

	FnOpMode ::= TEXTUAL-CONVENTION
		STATUS current
		DESCRIPTION "enumerated type for device operation modes"
		SYNTAX INTEGER { 
			nat         ( 1 ),
			transparent ( 2 )
		}

	FnHaMode ::= TEXTUAL-CONVENTION
		STATUS current
		DESCRIPTION "enumerated type for HA cluster modes"
		SYNTAX INTEGER {
			standalone     ( 1 ),
			activeActive   ( 2 ),
			activePassive  ( 3 )
		}

	FnHaLBSchedule ::= TEXTUAL-CONVENTION
		STATUS current
		DESCRIPTION "enumerated type for HA load-balancing schedules"
		SYNTAX INTEGER { 
			none                 ( 1 ),
			hub                  ( 2 ),
			leastConnections     ( 3 ),
			roundRobin           ( 4 ),
			weightedRoundRobin   ( 5 ),
			random               ( 6 ),
			ipBased              ( 7 ),
			ipPortBased          ( 8 )
		} 

	FnAdminPermLevel ::= TEXTUAL-CONVENTION
		STATUS current
		DESCRIPTION "enumerated type for adminitrative permissions"
		SYNTAX INTEGER { 
			readAdmin   ( 0 ),
			writeAdmin  ( 1 ),
			domainAdmin ( 15 ),
			superAdmin  ( 255 )
		} 

	FnUserAuthType ::= TEXTUAL-CONVENTION
		STATUS current
		DESCRIPTION "enumerated type for user authentication types"
		SYNTAX INTEGER { 
			local           ( 1 ),
			radiusSingle    ( 2 ),
			radiusMultiple  ( 3 ),
			ldap            ( 4 )
		} 

	FnLanguage ::= TEXTUAL-CONVENTION
		STATUS current
		DESCRIPTION "enumerated type for user interface languages"
		SYNTAX INTEGER { 
			english            ( 1 ),
			simplifiedChinese  ( 2 ),
			japanese           ( 3 ),
			korean             ( 4 ),
			spanish            ( 5 ),
			traditionalChinese ( 6 ),
			french             ( 7 ),
			undefined          ( 255 )
		} 

	FnSessProto ::= TEXTUAL-CONVENTION
		STATUS current
		DESCRIPTION "data type for session protocols"
		SYNTAX INTEGER  {
			ip   ( 0 ) ,
			icmp ( 1 ) ,
			igmp ( 2 ) ,
			ipip ( 4 ) ,
			tcp  ( 6 ) , 
			egp  ( 8 ) ,
			pup  ( 12 ) ,				
			udp  ( 17 ) ,
			idp  ( 22 ) ,
			ipv6 ( 41 ) ,
			rsvp ( 46 ) ,
			gre  ( 47 ) ,
			esp  ( 50 ) ,
			ah   ( 51 ) ,
			ospf ( 89 ) ,
			pim  ( 103 ) ,
			comp ( 108 ) ,
			raw  ( 255 )
		}

	FnModel ::= TEXTUAL-CONVENTION
		STATUS current
		DESCRIPTION "enumerated type for Fortinet product models"
		SYNTAX INTEGER  {
			unknown       ( 0 ) ,
			fgt50A        ( 500 ) ,
			fgt50AM       ( 501 ) ,
			fgt60         ( 600 ) ,
			fgt60M        ( 601 ) ,
			fwf60         ( 610 ) , 
			fwf60A        ( 611 ) , 
			fwf60AM       ( 612 ) , 
			fgt100        ( 1000 ),
			fgt100A       ( 1001 ),
			fgt200        ( 2000 ),
			fgt200A       ( 2001 ),
			fgt300        ( 3000 ),
			fgt300A       ( 3001 ),
			fgt400        ( 4000 ),
			fgt400A       ( 4001 ),
			fgt500        ( 5000 ),
			fgt500A       ( 5001 ),
			fgt800        ( 8000 ),
			fgt800F       ( 8001 ),
			fgt1000       ( 10000 ),
			fgt1000A      ( 10001 ),
			fgt1000AFA2   ( 10002 ),
			fgt2000       ( 20000 ),
			fgt3000       ( 30000 ),
			fgt3600       ( 36000 ),
			fgt4000       ( 40000 ),
			fgt5000       ( 50000 ),
			fortiBoost    ( 50001 ),
			fgt5002A      ( 50021 ),
			fgt5004       ( 50040 )
		}

	FnSystemEventCode ::= TEXTUAL-CONVENTION
		STATUS current
		DESCRIPTION "enumerated type for System component events"
		SYNTAX INTEGER  {
			systemHalt ( 1 ),
			systemReboot ( 2 ),
			systemReload ( 3 ),
			systemUpgrade ( 4 ),
			guiUpgrade ( 5 ),
			logdiskFormat ( 6 )
		}

	FnRAIDSystemCode ::= TEXTUAL-CONVENTION
		STATUS current
		DESCRIPTION "enumerated type for RAID system events"
		SYNTAX INTEGER  {
			degradedArray ( 1 ),
			sparesMissing ( 2 ),
			rebuildStarted ( 3 ),
			rebuildFinished ( 4 ),
			fail ( 5 ),
			failSpare ( 6 ),
			spareActive ( 7 )
		}


-- UNUSED
--	FnIfAddrMode ::= TEXTUAL-CONVENTION
--		STATUS current
--		DESCRIPTION "data type for interface address mode"
--		SYNTAX INTEGER  {
--			static ( 1 )
--		} 

-- basic tree layout:
--  fortinet     : enterprises.12356
--    fnTraps    : fortinet.0
--    fnSystem   : fortinet.1
--    fnDomains  : fortinet.2
--    fnIp       : fortinet.4
--    fnVpn      : fortinet.9
--    fnBridge   : fortinet.15
--    fnIps      : fortinet.16

--	fortinet          OBJECT IDENTIFIER ::=  { enterprises  12356 }
	fnTraps           OBJECT IDENTIFIER ::=  { fortinet  0 }
	fnSystem          OBJECT IDENTIFIER ::=  { fortinet  1 }
	fnDomains         OBJECT IDENTIFIER ::=  { fortinet  2 }
--	fnInterfaces      OBJECT IDENTIFIER ::=  { fortinet  3 }
	fnIp              OBJECT IDENTIFIER ::=  { fortinet  4 }
--	fnDhcp            OBJECT IDENTIFIER ::=  { fortinet  5 }
--	fnSnmp            OBJECT IDENTIFIER ::=  { fortinet  6 }
--	fnDns             OBJECT IDENTIFIER ::=  { fortinet  7 }
--	fnFirewall        OBJECT IDENTIFIER ::=  { fortinet  8 }
	fnVpn             OBJECT IDENTIFIER ::=  { fortinet  9 }
	fnManagement      OBJECT IDENTIFIER ::=  { fortinet  10 }
	fnAntivirus       OBJECT IDENTIFIER ::=  { fortinet  11 }
--	fnVip             OBJECT IDENTIFIER ::=  { fortinet  12 }
--	fnWebfilter       OBJECT IDENTIFIER ::=  { fortinet  13 }
--	fnAntispam        OBJECT IDENTIFIER ::=  { fortinet  14 }
	fnBridge          OBJECT IDENTIFIER ::=  { fortinet  15 }
	fnIps             OBJECT IDENTIFIER ::=  { fortinet  16 }
	fnAnalyzer        OBJECT IDENTIFIER ::=  { fortinet  20 }
	fnMIBConformance  OBJECT IDENTIFIER ::=  { fortinet  99 }

--
-- fortinet.fnSystem.
--
	fnSysModel          OBJECT-TYPE
		SYNTAX          FnModel
		MAX-ACCESS      read-only
		STATUS          current
		DESCRIPTION     "System model"
		::= { fnSystem    1 }

	fnSysSerial         OBJECT-TYPE
		SYNTAX          DisplayString  ( SIZE ( 0 .. 32  ) ) 
		MAX-ACCESS      read-only
		STATUS          current
		DESCRIPTION     "Device serial number"
		::= { fnSystem    2 }

	fnSysVersion        OBJECT-TYPE
		SYNTAX          DisplayString  ( SIZE ( 0 .. 128 ) ) 
		MAX-ACCESS      read-only
		STATUS          current
		DESCRIPTION     "Device firmware version"
		::= { fnSystem    3 }

	fnSysVersionAv      OBJECT-TYPE
		SYNTAX          DisplayString  ( SIZE ( 0 .. 128 ) ) 
		MAX-ACCESS      read-only
		STATUS          current
		DESCRIPTION     "Antivirus DB version"
		::= { fnSystem    4 }

	fnSysVersionNids    OBJECT-TYPE
		SYNTAX          DisplayString  ( SIZE ( 0 .. 128 ) ) 
		MAX-ACCESS      read-only
		STATUS          current
		DESCRIPTION     "NIDS DB version"
		::= { fnSystem    5 }

	fnSysHaMode         OBJECT-TYPE
		SYNTAX          FnHaMode
		MAX-ACCESS      read-only
		STATUS          current
		DESCRIPTION     "High-availabilty mode (Standalone, A-A or A-P)"
		::= { fnSystem    6 }

	fnSysOpMode         OBJECT-TYPE
		SYNTAX          FnOpMode
		MAX-ACCESS      read-only
		STATUS          current
		DESCRIPTION     "Operational mode (Transparent or Nat)"
		::= { fnSystem    7 }

	fnSysCpuUsage       OBJECT-TYPE
		SYNTAX          Gauge32
		MAX-ACCESS      read-only
		STATUS          current
		DESCRIPTION     "Instantaneous CPU usage"
		::= { fnSystem    8 }

	fnSysMemUsage       OBJECT-TYPE
		SYNTAX          Gauge32
		MAX-ACCESS      read-only
		STATUS          current
		DESCRIPTION     "Instantaneous memory utilization"
		::= { fnSystem    9 }

	fnSysSesCount       OBJECT-TYPE
		SYNTAX          Gauge32
		MAX-ACCESS      read-only
		STATUS          current
		DESCRIPTION     "Instantaneous session count"
		::= { fnSystem    10 }

	fnSysDiskCapacity   OBJECT-TYPE
		SYNTAX		Gauge32
		MAX-ACCESS	read-only
		STATUS		current
		DESCRIPTION	"Hard disk capacity (MB)"
		::= { fnSystem    11 }

	fnSysDiskUsage      OBJECT-TYPE
		SYNTAX		Gauge32
		MAX-ACCESS	read-only
		STATUS		current
		DESCRIPTION	"Current hard disk usage (MB)"
		::= { fnSystem    12 }

	fnSysMemCapacity    OBJECT-TYPE
		SYNTAX		Gauge32
		MAX-ACCESS	read-only
		STATUS		current
		DESCRIPTION	"Physical memory installed (KB)"
		::= { fnSystem    13 }

	fnSysEventCode OBJECT-TYPE
		SYNTAX          FnSystemEventCode
		MAX-ACCESS      read-only
		STATUS          current
		DESCRIPTION     "System component events"
		::= { fnSystem  14 }

	fnRAIDCode OBJECT-TYPE
		SYNTAX          FnRAIDSystemCode
		MAX-ACCESS      read-only
		STATUS          current
		DESCRIPTION     "RAID system events"
		::= { fnSystem  15 }

	fnRAIDDevName      OBJECT-TYPE
		SYNTAX          DisplayString  ( SIZE ( 0 .. 32  ) ) 
		MAX-ACCESS      read-only
		STATUS          current
		DESCRIPTION     "RAID Device name"
		::= { fnSystem    16 }


	fnHa            OBJECT IDENTIFIER ::=  { fnSystem 100 }
	fnAdmin         OBJECT IDENTIFIER ::=  { fnSystem 101 }
	fnUsers         OBJECT IDENTIFIER ::=  { fnSystem 102 }
	fnOptions       OBJECT IDENTIFIER ::=  { fnSystem 103 }
	fnLogging       OBJECT IDENTIFIER ::=  { fnSystem 104 }
	fnMessages      OBJECT IDENTIFIER ::=  { fnSystem 105 }

	fnHwSensors	  OBJECT IDENTIFIER ::=  { fnSystem  106 }

--
-- fortinet.fnSystem.fnHa.
--

-- NO LONGER VALID
	fnHaGroupId      OBJECT-TYPE
		SYNTAX          FnIndex
		MAX-ACCESS      read-only
		STATUS          current
		DESCRIPTION     "HA cluster group ID"
		::= { fnHa        1 }

-- NO LONGER VALID
	fnHaPriority     OBJECT-TYPE
		SYNTAX          Integer32 (0 .. 255)
		MAX-ACCESS      read-only
		STATUS          current
		DESCRIPTION     "HA clustering priority (default - 127)"
		::= { fnHa        2 }

-- NO LONGER VALID
	fnHaOverride     OBJECT-TYPE
		SYNTAX          FnBoolState
		MAX-ACCESS      read-only
		STATUS          current
		DESCRIPTION     "Status of a master override flag"
		::= { fnHa        3 }

-- NO LONGER VALID
	fnHaAutoSync     OBJECT-TYPE
		SYNTAX          FnBoolState
		MAX-ACCESS      read-only
		STATUS          current
		DESCRIPTION     "Status of an automatic configuration 
		                 synchronization"
		::= { fnHa        4 }

	fnHaSchedule     OBJECT-TYPE
		SYNTAX          FnHaLBSchedule
		MAX-ACCESS      read-only
		STATUS          current
		DESCRIPTION     "Load-balancing schedule in A-A mode"
		::= { fnHa        5 }

--
-- fortinet.fnSystem.fnHa.fnHaStatusTable.
--

	fnHaStatsTable  OBJECT-TYPE
        	SYNTAX     SEQUENCE OF FnHaStatsEntry
	        MAX-ACCESS not-accessible
        	STATUS     current
	        DESCRIPTION "HA cluster status"
        	::= { fnHa        6 }

	fnHaStatsEntry  OBJECT-TYPE
        	SYNTAX     FnHaStatsEntry
	        MAX-ACCESS not-accessible
        	STATUS     current
	        DESCRIPTION "Statistics for a particular HA cluster's unit"
	        INDEX       { fnHaStatsIndex }
        	::= { fnHaStatsTable 1 }

	FnHaStatsEntry ::= SEQUENCE {
		    fnHaStatsIndex        FnIndex,
		    fnHaStatsSerial       DisplayString,
		    fnHaStatsCpuUsage     Gauge32,
		    fnHaStatsMemUsage     Gauge32,
		    fnHaStatsNetUsage     Gauge32,
		    fnHaStatsSesCount     Gauge32,
		    fnHaStatsPktCount     Counter32,
		    fnHaStatsByteCount    Counter32,
		    fnHaStatsIdsCount     Counter32,
		    fnHaStatsAvCount      Counter32,
		    fnHaStatsHostname     DisplayString
        	}

	fnHaStatsIndex      OBJECT-TYPE
	        SYNTAX      FnIndex
        	MAX-ACCESS  not-accessible
	        STATUS      current
        	DESCRIPTION "An index value that uniquely identifies an
                	     unit in the HA Cluster"
        	::= { fnHaStatsEntry 1 }

	fnHaStatsSerial     OBJECT-TYPE
	        SYNTAX      DisplayString  ( SIZE ( 0 .. 32  ) )
        	MAX-ACCESS  read-only
	        STATUS      current
        	DESCRIPTION "Serial number of HA Cluster's unit"
        	::= { fnHaStatsEntry 2 }

	fnHaStatsCpuUsage   OBJECT-TYPE
	        SYNTAX      Gauge32
        	MAX-ACCESS  read-only
	        STATUS      current
        	DESCRIPTION "CPU Usage of HA Cluster's unit"
        	::= { fnHaStatsEntry 3 }

	fnHaStatsMemUsage   OBJECT-TYPE
	        SYNTAX      Gauge32
        	MAX-ACCESS  read-only
	        STATUS      current
        	DESCRIPTION "Memory Usage of HA Cluster's unit"
        	::= { fnHaStatsEntry 4 }

	fnHaStatsNetUsage   OBJECT-TYPE
	        SYNTAX      Gauge32
        	MAX-ACCESS  read-only
	        STATUS      current
        	DESCRIPTION "Network Usage of HA Cluster's unit"
        	::= { fnHaStatsEntry 5 }

	fnHaStatsSesCount   OBJECT-TYPE
	        SYNTAX      Gauge32
        	MAX-ACCESS  read-only
	        STATUS      current
        	DESCRIPTION "Sessions Counter of HA Cluster's unit"
        	::= { fnHaStatsEntry 6 }

	fnHaStatsPktCount   OBJECT-TYPE
	        SYNTAX      Counter32
        	MAX-ACCESS  read-only
	        STATUS      current
        	DESCRIPTION "Packets Counter of HA Cluster's unit"
        	::= { fnHaStatsEntry 7 }

	fnHaStatsByteCount  OBJECT-TYPE
	        SYNTAX      Counter32
        	MAX-ACCESS  read-only
	        STATUS      current
        	DESCRIPTION "Bytes Counter of HA Cluster's unit"
        	::= { fnHaStatsEntry 8 }

	fnHaStatsIdsCount   OBJECT-TYPE
	        SYNTAX      Counter32
        	MAX-ACCESS  read-only
	        STATUS      current
        	DESCRIPTION "IDS Counter of HA Cluster's unit"
        	::= { fnHaStatsEntry 9 }

	fnHaStatsAvCount    OBJECT-TYPE
	        SYNTAX      Counter32
        	MAX-ACCESS  read-only
	        STATUS      current
        	DESCRIPTION "AV Counter of HA Cluster's unit"
        	::= { fnHaStatsEntry 10 }

	fnHaStatsHostname   OBJECT-TYPE
	        SYNTAX      DisplayString  ( SIZE ( 0 .. 255  ) )
        	MAX-ACCESS  read-only
	        STATUS      current
        	DESCRIPTION "Hostname of HA Cluster's unit"
        	::= { fnHaStatsEntry 11 }

--
-- fortinet.fnSystem.fnAdmin.
--

	fnAdminNumber           OBJECT-TYPE
		SYNTAX          Integer32
		MAX-ACCESS      read-only
		STATUS          current
		DESCRIPTION     "The number of admin accounts in fnAdminTable"
		::= { fnAdmin 1 }

	fnAdminTable            OBJECT-TYPE
		SYNTAX          SEQUENCE OF FnAdminEntry
		MAX-ACCESS      not-accessible
		STATUS          current
		DESCRIPTION     "A list of admin accounts"
		::= { fnAdmin 2 }

	fnAdminEntry            OBJECT-TYPE
		SYNTAX          FnAdminEntry
		MAX-ACCESS      not-accessible
		STATUS          current
		DESCRIPTION     "An entry containing information applicable
		                 to a particular admin account"
        INDEX          { fnAdminIndex }
		::= { fnAdminTable 1 }

	FnAdminEntry ::= SEQUENCE {
		fnAdminIndex   FnIndex,
		fnAdminName    DisplayString,
		fnAdminAddr    IpAddress,
		fnAdminMask    IpAddress
--		,
--		fnAdminPerm    FnAdminPermLevel
	}

	fnAdminIndex     OBJECT-TYPE
		SYNTAX          FnIndex
		MAX-ACCESS      not-accessible
		STATUS          current
		DESCRIPTION     "An index of admin account"
		::= { fnAdminEntry 1 }

	fnAdminName      OBJECT-TYPE
		SYNTAX          DisplayString
		MAX-ACCESS      read-only
		STATUS          current
		DESCRIPTION     "A username of an account"
		::= { fnAdminEntry 2 }

	fnAdminAddr      OBJECT-TYPE
		SYNTAX          IpAddress
		MAX-ACCESS      read-only
		STATUS          current
		DESCRIPTION     "An address of a subnet where this admin account
		                 can be used from"
		::= { fnAdminEntry 3 }

	fnAdminMask      OBJECT-TYPE
		SYNTAX          IpAddress
		MAX-ACCESS      read-only
		STATUS          current
		DESCRIPTION     "A mask of a subnet where this admin account
		                 can be used from"
		::= { fnAdminEntry 4 }

-- UNUSED
-- 	fnAdminPerm      OBJECT-TYPE
-- 		SYNTAX          FnAdminPermLevel
-- 		MAX-ACCESS      read-only
-- 		STATUS          current
-- 		DESCRIPTION     "Access level of this admin account"
-- 		::= { fnAdminEntry 5 }


--
-- fortinet.fnSystem.fnUsers.
--

	fnUserNumber    OBJECT-TYPE
		SYNTAX          Integer32
		MAX-ACCESS      read-only
		STATUS          current
		DESCRIPTION     "The number of user accounts in fnUserTable"
		::= { fnUsers     1 }

	fnUserTable     OBJECT-TYPE
		SYNTAX          SEQUENCE OF FnUserEntry
		MAX-ACCESS      not-accessible
		STATUS          current
		DESCRIPTION     "A list of local and proxied (Radius server)
		                 user accounts"
		::= { fnUsers     2 }

	fnUserEntry     OBJECT-TYPE
		SYNTAX          FnUserEntry
		MAX-ACCESS      not-accessible
		STATUS          current
		DESCRIPTION     "An entry containing information applicable
		                 to a particular user account"
        INDEX           { fnUserIndex }
		::= { fnUserTable 1 }

	FnUserEntry ::= SEQUENCE {
		fnUserIndex    FnIndex,
		fnUserName     DisplayString,
		fnUserAuth     FnUserAuthType,
		fnUserState    FnBoolState
	}

	fnUserIndex      OBJECT-TYPE
		SYNTAX          FnIndex
		MAX-ACCESS      not-accessible
		STATUS          current
		DESCRIPTION     "An index of user account"
		::= { fnUserEntry 1 }

	fnUserName       OBJECT-TYPE
		SYNTAX          DisplayString
		MAX-ACCESS      read-only
		STATUS          current
		DESCRIPTION     "A name of user account"
		::= { fnUserEntry 2 }

	fnUserAuth       OBJECT-TYPE
		SYNTAX          FnUserAuthType
		MAX-ACCESS      read-only
		STATUS          current
		DESCRIPTION     "Authentication type of the account"
		::= { fnUserEntry 3 }

	fnUserState      OBJECT-TYPE
		SYNTAX          FnBoolState
		MAX-ACCESS      read-only
		STATUS          current
		DESCRIPTION     "Status of the user account"
		::= { fnUserEntry 4 }

--
-- fortinet.fnSystem.fnOptions.
--

	fnOptIdleTimeout OBJECT-TYPE
		SYNTAX          Integer32
		MAX-ACCESS      read-only
		STATUS          current
		DESCRIPTION     "Idle period after which the administrator
		                 is automatically logged out off the system"
		::= { fnOptions  1 }

	fnOptAuthTimeout OBJECT-TYPE
		SYNTAX          Integer32
		MAX-ACCESS      read-only
		STATUS          current
		DESCRIPTION     "Idle period after which firewall-authentication
		                 is automatically expired"
		::= { fnOptions  2 }

	fnOptLanguage OBJECT-TYPE
		SYNTAX          FnLanguage
		MAX-ACCESS      read-only
		STATUS          current
		DESCRIPTION     "Language used for user interface"
		::= { fnOptions  3 }

	fnOptLcdProtection OBJECT-TYPE
		SYNTAX          FnBoolState
		MAX-ACCESS      read-only
		STATUS          current
		DESCRIPTION     "Status of the LCD protection"
		::= { fnOptions  4 }

--
-- fortinet.fnSystem.fnLogging.
--

	fnLogOption      OBJECT-TYPE
		SYNTAX          Integer32
		MAX-ACCESS      read-only
		STATUS          current
		DESCRIPTION     "Logging preferences"
		::= { fnLogging  1 }

--
-- fortinet.fnSystem.fnMessages.
--

	fnMesgNumber    OBJECT-TYPE
		SYNTAX          Integer32
		MAX-ACCESS      read-only
		STATUS          current
		DESCRIPTION     "The number of custom messages in sysMesgTable"
		::= { fnMessages  1 }

--
-- fortinet.fnDomains.
--

	fnVdNumber          OBJECT-TYPE
		SYNTAX          Integer32
		MAX-ACCESS      read-only
		STATUS          current
		DESCRIPTION     "The number of virtual fnDomains in vdTable"
		::= { fnDomains   1 }

	fnVdTable           OBJECT-TYPE
		SYNTAX          SEQUENCE OF FnVdEntry
		MAX-ACCESS      not-accessible
		STATUS          current
		DESCRIPTION     "A list of virtual fnDomains"
		::= { fnDomains   2 }

	fnVdEntry           OBJECT-TYPE
		SYNTAX          FnVdEntry
		MAX-ACCESS      not-accessible
		STATUS          current
		DESCRIPTION     "An entry containing information applicable
		                 to a particular virtual domain"
		INDEX          { fnVdIndex }
		::= { fnVdTable 1 }

	FnVdEntry ::= SEQUENCE {
		fnVdIndex   FnIndex,
		fnVdName    DisplayString
	}

	fnVdIndex          OBJECT-TYPE
		SYNTAX          FnIndex
		MAX-ACCESS      not-accessible
		STATUS          current
		DESCRIPTION     "Internal virtual domain index"
		::= { fnVdEntry   1 }

	fnVdName            OBJECT-TYPE
		SYNTAX          DisplayString
		MAX-ACCESS      read-only
		STATUS          current
		DESCRIPTION     "Virtual domain name"
		::= { fnVdEntry   2 }

--
-- fortinet.fnIp.
--

	fnIpSessTable       OBJECT-TYPE
        	SYNTAX      SEQUENCE OF FnIpSessEntry
	        MAX-ACCESS  not-accessible
        	STATUS      current
	        DESCRIPTION "IP Sessions Info"
        	::= { fnIp        2 }

	fnIpSessEntry	OBJECT-TYPE
        	SYNTAX      FnIpSessEntry
	        MAX-ACCESS  not-accessible
        	STATUS      current
	        DESCRIPTION "Particular IP Session info"
	        INDEX       { fnIpSessIndex }
        	::= { fnIpSessTable 1 }

	FnIpSessEntry ::=
        	SEQUENCE {
		    fnIpSessIndex	FnIndex,
		    fnIpSessProto	FnSessProto,
		    fnIpSessFromAddr	IpAddress,
		    fnIpSessFromPort	Integer32,
		    fnIpSessToAddr	IpAddress,
		    fnIpSessToPort	Integer32,
		    fnIpSessExp		Counter32
        	}

	fnIpSessIndex	OBJECT-TYPE	
		SYNTAX      FnIndex
		MAX-ACCESS  not-accessible
		STATUS      current
		DESCRIPTION "An index value that uniquely identifies
                	     an IP session"
		::=  { fnIpSessEntry  1 }

	fnIpSessProto	OBJECT-TYPE	
		SYNTAX      FnSessProto
		MAX-ACCESS  read-only
		STATUS      current
		DESCRIPTION "The protocol of the connection"
		::=  { fnIpSessEntry  2 }

	fnIpSessFromAddr	OBJECT-TYPE	
		SYNTAX      IpAddress
		MAX-ACCESS  read-only
		STATUS      current
		DESCRIPTION "Source IP address"
		::=  { fnIpSessEntry  3 }

	fnIpSessFromPort	OBJECT-TYPE	
		SYNTAX      Integer32  ( 0 .. 65535  )
		MAX-ACCESS  read-only
		STATUS      current
		DESCRIPTION "Source Port number"
		::=  { fnIpSessEntry  4 }

	fnIpSessToAddr	OBJECT-TYPE	
		SYNTAX      IpAddress
		MAX-ACCESS  read-only
		STATUS      current
		DESCRIPTION "Destination IP address"
		::=  { fnIpSessEntry  5 }

	fnIpSessToPort	OBJECT-TYPE	
		SYNTAX      Integer32  ( 0 .. 65535  )
		MAX-ACCESS  read-only
		STATUS      current
		DESCRIPTION "Destination Port number"
		::=  { fnIpSessEntry  6 }

	fnIpSessExp	OBJECT-TYPE	
		SYNTAX      Counter32
		MAX-ACCESS  read-only
		STATUS      current
		DESCRIPTION "Time (in seconds) before connection expires"
		::=  { fnIpSessEntry  7 }

--
-- fortinet.fnVpn.
--

	fnVpnDialupTable       OBJECT-TYPE
        	SYNTAX      SEQUENCE OF FnVpnDialupEntry
	        MAX-ACCESS  not-accessible
        	STATUS      current
	        DESCRIPTION "Dialup VPN peers info"
        	::= { fnVpn        1 }

	fnVpnDialupEntry	OBJECT-TYPE
        	SYNTAX      FnVpnDialupEntry
	        MAX-ACCESS  not-accessible
        	STATUS      current
	        DESCRIPTION "Dialup VPN peer info"
	        INDEX       { fnVpnDialupIndex }
        	::= { fnVpnDialupTable 1 }

	FnVpnDialupEntry ::=
        	SEQUENCE {
		    fnVpnDialupIndex		FnIndex,
		    fnVpnDialupGateway		IpAddress,
		    fnVpnDialupLifetime		Integer32,
		    fnVpnDialupTimeout		Integer32,
		    fnVpnDialupSrcBegin		IpAddress,
		    fnVpnDialupSrcEnd		IpAddress,
		    fnVpnDialupDstAddr		IpAddress
--		    fnVpnDialupDstMask		IpAddress
        	}

	fnVpnDialupIndex	OBJECT-TYPE	
		SYNTAX      FnIndex
		MAX-ACCESS  not-accessible
		STATUS      current
		DESCRIPTION "An index value that uniquely identifies
                	     an VPN dialup peer"
		::=  { fnVpnDialupEntry  1 }

	fnVpnDialupGateway	OBJECT-TYPE	
		SYNTAX      IpAddress
		MAX-ACCESS  read-only
		STATUS      current
		DESCRIPTION "Remote gateway IP address"
		::=  { fnVpnDialupEntry  2 }

	fnVpnDialupLifetime	OBJECT-TYPE	
		SYNTAX      Integer32
		MAX-ACCESS  read-only
		STATUS      current
		DESCRIPTION "Tunnel life time (seconds)"
		::=  { fnVpnDialupEntry  3 }

	fnVpnDialupTimeout	OBJECT-TYPE	
		SYNTAX      Integer32
		MAX-ACCESS  read-only
		STATUS      current
		DESCRIPTION "Time before the next key exchange (seconds)"
		::=  { fnVpnDialupEntry  4 }

	fnVpnDialupSrcBegin	OBJECT-TYPE	
		SYNTAX      IpAddress
		MAX-ACCESS  read-only
		STATUS      current
		DESCRIPTION "Remote subnet address"
		::=  { fnVpnDialupEntry  5 }

	fnVpnDialupSrcEnd	OBJECT-TYPE	
		SYNTAX      IpAddress
		MAX-ACCESS  read-only
		STATUS      current
		DESCRIPTION "Remote subnet mask"
		::=  { fnVpnDialupEntry  6 }

	fnVpnDialupDstAddr	OBJECT-TYPE	
		SYNTAX      IpAddress
		MAX-ACCESS  read-only
		STATUS      current
		DESCRIPTION "Local subnet address"
		::=  { fnVpnDialupEntry  7 }

--	fnVpnDialupDstMask	OBJECT-TYPE	
--		SYNTAX		IpAddress
--		MAX-ACCESS	read-only
--		STATUS		current
--		DESCRIPTION	"Local subnet mask"
--		::=  { fnVpnDialupEntry	8 }

	fnVpnLocalGateway	OBJECT-TYPE	
		SYNTAX      IpAddress
		MAX-ACCESS  read-only
		STATUS      current
		DESCRIPTION "Local gateway IP address"
        	::= { fnVpn        2 }

	fnVpnRemoteGateway	OBJECT-TYPE	
		SYNTAX      IpAddress
		MAX-ACCESS  read-only
		STATUS      current
		DESCRIPTION "Remote gateway IP address"
        	::= { fnVpn        3 }


--
-- fortinet.fnManagement.
--

	fnManSysSerial		OBJECT-TYPE
		SYNTAX          DisplayString  ( SIZE ( 0 .. 32  ) ) 
		MAX-ACCESS      read-only
		STATUS		current
		DESCRIPTION	"Serial number of FortiGate sending trap"
		::= { fnManagement	1 }

	fnManIfName		OBJECT-TYPE
		SYNTAX		DisplayString 
		MAX-ACCESS      read-only
		STATUS		current
		DESCRIPTION	"Name of interface as used in configuration"
		::= { fnManagement	2 }

	fnManIfIp		OBJECT-TYPE
		SYNTAX          IpAddress
		MAX-ACCESS      read-only
		STATUS          current
		DESCRIPTION     "IP address of the interface"
		::= { fnManagement	3 }

	fnManIfMask		OBJECT-TYPE
		SYNTAX          IpAddress
		MAX-ACCESS      read-only
		STATUS          current
		DESCRIPTION     "Mask of subnet the interface belongs to"
		::= { fnManagement	4 }


--
-- fortinet.fnAntivirus.
--

	fnAntivirusVirName      OBJECT-TYPE
		SYNTAX          DisplayString
		MAX-ACCESS      read-only
		STATUS          current
		DESCRIPTION     "Virus name that triggered event"
		::= { fnAntivirus 1 }

--
-- fortinet.fnBridge.
--

	fnBridgeFgtFailure      OBJECT-TYPE
		SYNTAX          DisplayString 
		MAX-ACCESS      read-only
		STATUS          current
		DESCRIPTION     "FortiGate failure detected by FortiBridge"
		::= { fnBridge  1 }

--
-- fortinet.fnIps.
--

	fnIpsSigId		OBJECT-TYPE
		SYNTAX		FnIndex
		MAX-ACCESS	read-only
		STATUS		current
		DESCRIPTION	"ID of IPS signature"
		::= { fnIps	1 }

	fnIpsSigSrcIp		OBJECT-TYPE
		SYNTAX          IpAddress
		MAX-ACCESS      read-only
		STATUS          current
		DESCRIPTION     "Source IP Address of the IPS signature trigger"
		::= { fnIps     2 }

	fnIpsSigMsg             OBJECT-TYPE
		SYNTAX          DisplayString
		MAX-ACCESS      read-only
		STATUS          current
		DESCRIPTION     "Message associated with IPS event"
		::= { fnIps     3 }

--
-- fortinet.fnAnalyzer.
--

	fnAnalyzerEventAlert    OBJECT-TYPE
		SYNTAX          DisplayString 
		MAX-ACCESS      read-only
		STATUS          current
		DESCRIPTION     "Detail of defined event alert sent from FortiAnalyzer"
		::= { fnAnalyzer  1 }





-- fnSystem . fnHwSensors

	fnHwSensorCount         OBJECT-TYPE
		SYNTAX          Integer32
		MAX-ACCESS      read-only
		STATUS          current
		DESCRIPTION     "The number of hardware sensors in the system"
		::= { fnHwSensors 1 }

	fnHwSensorTable         OBJECT-TYPE
		SYNTAX          SEQUENCE OF FnHwSensorEntry
		MAX-ACCESS      not-accessible
		STATUS          current
		DESCRIPTION     "A list of hardware sensors in the sytem user accounts"
		::= { fnHwSensors 2 }

	fnHwSensorEntry         OBJECT-TYPE
		SYNTAX          FnHwSensorEntry
		MAX-ACCESS      not-accessible
		STATUS          current
		DESCRIPTION     "An entry containing information of hardware sensors"
		INDEX           { fnHwSensorEntIndex }
		::= { fnHwSensorTable 1 }

	FnHwSensorEntry ::= SEQUENCE {
		fnHwSensorEntIndex       FnIndex,
		fnHwSensorEntName        DisplayString,
		fnHwSensorEntValue       DisplayString,
		fnHwSensorEntAlarmStatus INTEGER
	}

	fnHwSensorEntIndex      OBJECT-TYPE
		SYNTAX          FnIndex
		MAX-ACCESS      not-accessible
		STATUS          current
		DESCRIPTION     "Index of the hardware sensors"
		::= { fnHwSensorEntry 1 }

	fnHwSensorEntName       OBJECT-TYPE
		SYNTAX          DisplayString
		MAX-ACCESS      read-only
		STATUS          current
		DESCRIPTION     "Sensor Name"
		::= { fnHwSensorEntry 2 }

	fnHwSensorEntValue      OBJECT-TYPE
		SYNTAX          DisplayString
		MAX-ACCESS      read-only
		STATUS          current
		DESCRIPTION     "Reading value of the sensor"
		::= { fnHwSensorEntry 3 }

	fnHwSensorEntAlarmStatus OBJECT-TYPE
		SYNTAX          INTEGER { false(0), true(1) }
		MAX-ACCESS      read-only
		STATUS          current
		DESCRIPTION     "Alarm status of the sensor"
		::= { fnHwSensorEntry 4 }

--
-- fnSystem.fnHwSensors.fnHwSensorTrapObjects
--

	fnHwSensorTrapObjects OBJECT IDENTIFIER ::= { fnHwSensors 3 }

	fnHwSensorTrapIndex OBJECT-TYPE
		SYNTAX          FnIndex
		MAX-ACCESS      accessible-for-notify
		STATUS          current
		DESCRIPTION     "Index of the hardware sensor"
		::= { fnHwSensorTrapObjects 1 }



--
-- NOTIFICATIONS-TYPES / traps
--
--

-- fortinet.fnTraps.
--

-- Sent from FortiOS to FortiManager only
	fnFMTrapIfChange       NOTIFICATION-TYPE
		OBJECTS        { fnManSysSerial, fnManIfName, fnManIfIp, fnManIfMask }
		STATUS         current
		DESCRIPTION    "Trap is sent to managing FortiManager if an interface
		                changes IP"
		::=  { fnTraps 100  }

	fnTrapCpuHigh          NOTIFICATION-TYPE
		OBJECTS        { fnSysSerial, sysName }
		STATUS         current
		DESCRIPTION    "Trap being sent if CPU usage becomes too high"
		::=  { fnTraps 101  }

	fnTrapMemLow           NOTIFICATION-TYPE
		OBJECTS        { fnSysSerial, sysName }
		STATUS         current
		DESCRIPTION    "Trap being sent if memory usage becomes too high"
		::=  { fnTraps 102  }

	fnTrapLogFull          NOTIFICATION-TYPE
		OBJECTS        { fnSysSerial, sysName }
		STATUS         current
		DESCRIPTION    "Trap being sent if log becomes full"
		::=  { fnTraps 103  }


	fnTrapPSUFailureEvent	NOTIFICATION-TYPE
		OBJECTS      { fnSysSerial, fnHwSensorTrapIndex }
		STATUS       current
		DESCRIPTION   "Trap being sent when detected a power supply unit failure"
		::=  {  fnTraps  104  }	

-- Sent from FortiOS to FortiManager only
	fnFMTrapConfChange     NOTIFICATION-TYPE
		OBJECTS        { fnSysSerial }
		STATUS         current
		DESCRIPTION    "Trap being sent if any configuration change is made,
		                excluding changes made by a FortiManager"
		::=  { fnTraps 150  }
--
-- FortiOS and FortiManager
	fnTrapIpChange	       NOTIFICATION-TYPE
		OBJECTS        { fnSysSerial, sysName, ifIndex }
		STATUS         current
		DESCRIPTION    "Trap being sent when IP address of
		                the specified interface has been
		                changed"
		::=  { fnTraps 201  }

--

	fnTrapSystemEvent	NOTIFICATION-TYPE
		OBJECTS      { fnSysSerial, fnSysEventCode }
		STATUS       current
		DESCRIPTION   "Trap being sent when system component halt, reboot, upgrade etc.,"
		::=  {  fnTraps  202  }
		
	fnTrapRAIDEvent	NOTIFICATION-TYPE
		OBJECTS      { fnSysSerial, fnRAIDCode, fnRAIDDevName }
		STATUS       current
		DESCRIPTION   "Trap being sent for RAID operation"
		::=  {  fnTraps  203  }


	fnTrapVpnTunUp	       NOTIFICATION-TYPE
		OBJECTS        { fnSysSerial, sysName, fnVpnLocalGateway, fnVpnRemoteGateway }
		STATUS         current
		DESCRIPTION    "Trap being sent when VPN tunnel is
		                brought up"
		::=  { fnTraps 301  }

	fnTrapVpnTunDown       NOTIFICATION-TYPE
		OBJECTS        { fnSysSerial, sysName, fnVpnLocalGateway, fnVpnRemoteGateway }
		STATUS         current
		DESCRIPTION    "Trap being sent when VPN tunnel is
		                brought down"
		::=  { fnTraps 302  }

--

	fnTrapHaSwitch	       NOTIFICATION-TYPE
		OBJECTS        { fnSysSerial, sysName }
		STATUS         current
		DESCRIPTION    "Trap being sent when the HA cluster 
		                master changes"
		::=  { fnTraps 401  }

-- unused in FortiOS 3.0
	fnTrapHaStateChange    NOTIFICATION-TYPE
		OBJECTS        { fnSysSerial }
		STATUS         obsolete
		DESCRIPTION    "Trap being sent when the HA cluster 
		                member changes its state"
		::=  { fnTraps 402  }

--

-- unused in FortiOS 3.0
	fnTrapIdsSynFlood      NOTIFICATION-TYPE
		OBJECTS        { fnSysSerial }
		STATUS         obsolete
		DESCRIPTION    "Trap being sent when SYN flood attack
		                is detected"
		::=  { fnTraps 501  }

-- unused in FortiOS 3.0
	fnTrapIdsPortScan      NOTIFICATION-TYPE
		OBJECTS        { fnSysSerial }
		STATUS         obsolete
		DESCRIPTION    "Trap being sent when port scan attack
		                is detected"
		::=  { fnTraps 502  }

	fnTrapIpsSignature     NOTIFICATION-TYPE
		OBJECTS        { fnSysSerial, sysName, fnIpsSigId, fnIpsSigSrcIp }
		STATUS         current
		DESCRIPTION    "Trap being sent when IPS signature is detected"
		::=  { fnTraps 503  }

	fnTrapIpsAnomaly       NOTIFICATION-TYPE
		OBJECTS        { fnSysSerial, sysName, fnIpsSigId, fnIpsSigSrcIp }
		STATUS         current
		DESCRIPTION    "Trap being sent when IPS anomaly is detected"
		::=  { fnTraps 504  }

--

	fnTrapAvVirus          NOTIFICATION-TYPE
		OBJECTS        { fnSysSerial, sysName, fnAntivirusVirName }
		STATUS         current
		DESCRIPTION    "Trap being sent when antivirus scanner
		                detects a virus"
		::=  { fnTraps 601 }

	fnTrapAvOversize       NOTIFICATION-TYPE
		OBJECTS        { fnSysSerial, sysName }
		STATUS         current
		DESCRIPTION    "Trap being sent when antivirus scanner
		                detects an oversized file"
		::=  { fnTraps 602 }

	fnTrapAvPattern        NOTIFICATION-TYPE
		OBJECTS        { fnSysSerial, sysName }
		STATUS         current
		DESCRIPTION    "Trap being sent when antivirus scanner
		                blocks a file matching a pattern"
		::=  { fnTraps 603 }

	fnTrapAvFragmented     NOTIFICATION-TYPE
		OBJECTS        { fnSysSerial, sysName }
		STATUS         current
		DESCRIPTION    "Trap being sent when antivirus scanner
		                detects a fragmented file or attachment"
		::=  { fnTraps 604 }


--

	fnTrapBridge           NOTIFICATION-TYPE
		OBJECTS        { fnSysSerial, sysName }
		STATUS         current
		DESCRIPTION    "Trap being sent by FortiBridge when 
		                detecting a FortiGate failure"
		::=  { fnTraps 701  }

--

-- UNUSED
	fnTrapImTableFull	 NOTIFICATION-TYPE
		OBJECTS      { fnSysSerial }
		STATUS       current
		DESCRIPTION  "Trap sent when Instant Message  
		              white/black list table is full"
		::=  {  fnTraps  801  }


-- FortiLog
	fnTrapAnalyzer	 	NOTIFICATION-TYPE
		OBJECTS      { fnSysSerial, fnAnalyzerEventAlert } -- add one new object to fix it
		STATUS       current
		DESCRIPTION  "Trap sent when FortiAnalyzer event parameter
			      exceeds configured limit. Event description
			      included in trap."
		::=  {  fnTraps  1001  }



--
-- compliance/conformance groups
-- These are mainly for "correctness"
--

	fnSystemComplianceGroup OBJECT-GROUP
		OBJECTS {
			fnSysModel,
			fnSysSerial,
			fnSysVersion,
			fnSysVersionAv,
			fnSysVersionNids,
			fnSysHaMode,
			fnSysOpMode,
			fnSysCpuUsage,
			fnSysMemUsage,
			fnSysDiskCapacity,
			fnSysDiskUsage,
			fnSysMemCapacity,
			fnSysEventCode,
			fnRAIDCode,
			fnRAIDDevName,
			fnSysSesCount,
			fnOptIdleTimeout,
			fnOptAuthTimeout,
			fnOptLanguage,
			fnOptLcdProtection,
			fnLogOption,
			fnMesgNumber,
			fnVdNumber,
			fnVdName
		}
		STATUS current
		DESCRIPTION "System related instrumentation"
		::= { fnMIBConformance 1 }

	fnHaComplianceGroup OBJECT-GROUP
		OBJECTS {
			fnHaGroupId,
			fnHaPriority,
			fnHaOverride,
			fnHaAutoSync,
			fnHaSchedule,
			fnHaStatsSerial,
			fnHaStatsCpuUsage,
			fnHaStatsMemUsage,
			fnHaStatsNetUsage,
			fnHaStatsSesCount,
			fnHaStatsPktCount,
			fnHaStatsByteCount,
			fnHaStatsIdsCount,
			fnHaStatsAvCount,
			fnHaStatsHostname
		}
		STATUS current
		DESCRIPTION "HA cluster related instrumentation"
		::= { fnMIBConformance 2 }

	fnAuthComplianceGroup OBJECT-GROUP
		OBJECTS {
			fnUserAuth,
			fnAdminNumber,
			fnAdminName,
			fnAdminAddr,
			fnAdminMask,
--			fnAdminPerm,
			fnUserNumber,
			fnUserName,
			fnUserState
		}
		STATUS current
		DESCRIPTION "Authentication related information"
		::= { fnMIBConformance 3 }

	fnSessionComplianceGroup OBJECT-GROUP
		OBJECTS {
			fnIpSessProto,
			fnIpSessFromAddr,
			fnIpSessFromPort,
			fnIpSessToAddr,
			fnIpSessToPort,
			fnIpSessExp
		}
		STATUS current
		DESCRIPTION "Session related instrumentation"
		::= { fnMIBConformance 4 }

	fnVPNComplianceGroup OBJECT-GROUP
		OBJECTS {
			fnVpnDialupGateway,
			fnVpnDialupLifetime,
			fnVpnDialupTimeout,
			fnVpnDialupSrcBegin,
			fnVpnDialupSrcEnd,
			fnVpnDialupDstAddr,
			fnVpnLocalGateway,
			fnVpnRemoteGateway
		}
		STATUS current
		DESCRIPTION "Session related instrumentation"
		::= { fnMIBConformance 5 }

	fnTrapsComplianceGroup NOTIFICATION-GROUP
		NOTIFICATIONS {
			fnTrapCpuHigh,
			fnTrapMemLow,
			fnTrapLogFull,
			fnTrapPSUFailureEvent,
			fnTrapIpChange,
			fnTrapSystemEvent,
			fnTrapRAIDEvent,
			fnTrapVpnTunUp,
			fnTrapVpnTunDown,
			fnTrapHaSwitch,
			fnTrapIpsSignature,
			fnTrapIpsAnomaly,
			fnTrapAvVirus,
			fnTrapAvOversize,
			fnTrapAvPattern,
			fnTrapAvFragmented,
			fnTrapImTableFull,
			fnTrapAnalyzer,
			fnTrapBridge,
			fnFMTrapConfChange,
			fnFMTrapIfChange
		}
		STATUS current
		DESCRIPTION "Event notifications"
		::= { fnMIBConformance 6 }

	fnTrapsComplianceGroupOld NOTIFICATION-GROUP
		NOTIFICATIONS {
			fnTrapHaStateChange,
			fnTrapIdsSynFlood,
			fnTrapIdsPortScan
		}
		STATUS obsolete
		DESCRIPTION "Unused notifications"
		::= { fnMIBConformance 7 }

	fnHwSensorComplianceGroup OBJECT-GROUP
		OBJECTS {
			fnHwSensorCount,
			fnHwSensorEntName,
			fnHwSensorEntValue,
			fnHwSensorEntAlarmStatus
		}
		STATUS current
		DESCRIPTION "Hardware sensor related information"
		::= { fnMIBConformance 8 }

	fnMiscComplianceGroup OBJECT-GROUP
		OBJECTS {
			fnBridgeFgtFailure,
			fnIpsSigId,
			fnIpsSigSrcIp,
			fnIpsSigMsg,
			fnManSysSerial,
			fnManIfName,
			fnManIfIp,
			fnManIfMask,
			fnAntivirusVirName,
			fnHwSensorTrapIndex,
			fnAnalyzerEventAlert
		}
		STATUS current
		DESCRIPTION "Miscellanious instrumentation"
		::= { fnMIBConformance 9 }

	fnMIBCompliance MODULE-COMPLIANCE
		STATUS current
		DESCRIPTION "The compliance statement for the application MIB."
		MODULE

		GROUP fnSystemComplianceGroup
		DESCRIPTION "System related instrumentation"

		GROUP fnHaComplianceGroup
		DESCRIPTION "HA cluster related instrumentation"

		GROUP fnAuthComplianceGroup
		DESCRIPTION "Authentication related information"

		GROUP fnSessionComplianceGroup
		DESCRIPTION "Session related instrumentation"

		GROUP fnVPNComplianceGroup
		DESCRIPTION "Session related instrumentation"

		GROUP fnHwSensorComplianceGroup
		DESCRIPTION "Hardware sensor related information"

		GROUP fnTrapsComplianceGroup
		DESCRIPTION "Miscellanious instrumentation"

		GROUP fnMiscComplianceGroup
		DESCRIPTION "Miscellanious instrumentation"
		
		::= { fnMIBConformance 10 }

END
