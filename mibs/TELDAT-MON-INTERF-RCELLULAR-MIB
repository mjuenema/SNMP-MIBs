-- Teldat, S.A.

                -- Parque Tecnolgico de Madrid

                -- 28760, Tres Cantos (Madrid)

                -- Tlf: +34-918076565

                -- Fax: +34-918076521

                -- e-mail: id@teldat.com


            -- MIB privada de Teldat

            -- Monitorizacin del interfaz RCELLULAR


    -- Historial:
    --      07/02/14    M.A. Pastor      XH 3523. Errors with HP Openview 9.20
    -- 1.3  11-01-13    E. Amorena      XH 2610. MIBs compilation.
    -- 1.2  03-09-12    M.A. Pastor      Compilation errors corrected
    -- 1.1  10-02-12    FDMB             Throughput included
    -- 1.0  29-09-08    P.Alonso         Implementacin inicial
--------------------------------------------------------------------------------

TELDAT-MON-INTERF-RCELLULAR-MIB DEFINITIONS ::= BEGIN

IMPORTS
    OBJECT-TYPE
        FROM RFC-1212
    DisplayString
        FROM RFC1213-MIB
    telProdNpMonInterfRouter
        FROM TELDAT-SW-STRUCTURE-MIB;


-- Monitorizacin privada del interfaz RCELLULAR

telProdNpMonInterfRcellular OBJECT IDENTIFIER ::= { telProdNpMonInterfRouter 20 }


--  = = = = = = = = = = = = = = = = = = = = = = = = = = = = = = = = = = = = = =
--  Global Rcellular monitoring variables
--  = = = = = = = = = = = = = = = = = = = = = = = = = = = = = = = = = = = = = =


--  = = = = = = = = = = = = = = = = = = = = = = = = = = = = = = = = = = = = = =
--  Global Info Rcellular monitoring variables
--  = = = = = = = = = = = = = = = = = = = = = = = = = = = = = = = = = = = = = =

teldatRcellularInfoInterfaceTable OBJECT-TYPE
    SYNTAX  SEQUENCE OF TeldatRcellularInfoInterfaceEntry
    ACCESS  not-accessible
    STATUS  mandatory
    DESCRIPTION
        "Table of information available for Rcellular interfaces.
        Each row represents an interface"
    ::= { telProdNpMonInterfRcellular 1 }

teldatRcellularInfoInterfaceEntry OBJECT-TYPE
    SYNTAX  TeldatRcellularInfoInterfaceEntry
    ACCESS  not-accessible
    STATUS  mandatory
    DESCRIPTION
        "A base list of objects that are information about a Rcellular interface.
        The inex is the number of the interface"
    INDEX   { teldatRcellularInfoInterfaceIndex }
    ::= { teldatRcellularInfoInterfaceTable 1 }

TeldatRcellularInfoInterfaceEntry ::= SEQUENCE
{
    teldatRcellularInfoInterfaceIndex                INTEGER,
    teldatRcellularInfoInterfaceModuleManufacturer   DisplayString,
    teldatRcellularInfoInterfaceModuleModel          DisplayString,
    teldatRcellularInfoInterfaceModuleFirmware       DisplayString,
    teldatRcellularInfoInterfaceModuleIMEI           DisplayString,
    teldatRcellularInfoInterfaceModuleIMSI           DisplayString,
    teldatRcellularInfoInterfaceSIMId                DisplayString,
    teldatRcellularInfoInterfaceSIMIcc               DisplayString
}

teldatRcellularInfoInterfaceIndex OBJECT-TYPE
    SYNTAX  INTEGER(1 .. 255)
    ACCESS  read-only
    STATUS  mandatory
    DESCRIPTION
        "Interface index"
    ::= { teldatRcellularInfoInterfaceEntry 1 }

teldatRcellularInfoInterfaceModuleManufacturer OBJECT-TYPE
    SYNTAX  DisplayString
    ACCESS  read-only
    STATUS  mandatory
    DESCRIPTION
        "Rcellular module manufacturer."
    ::={ teldatRcellularInfoInterfaceEntry 2 }

teldatRcellularInfoInterfaceModuleModel OBJECT-TYPE
    SYNTAX  DisplayString
    ACCESS  read-only
    STATUS  mandatory
    DESCRIPTION
        "Rcellular module model."
    ::={ teldatRcellularInfoInterfaceEntry 3 }

teldatRcellularInfoInterfaceModuleFirmware OBJECT-TYPE
    SYNTAX  DisplayString
    ACCESS  read-only
    STATUS  mandatory
    DESCRIPTION
        "Rcellular module firmware release."
    ::={ teldatRcellularInfoInterfaceEntry 4 }

teldatRcellularInfoInterfaceModuleIMEI OBJECT-TYPE
    SYNTAX  DisplayString
    ACCESS  read-only
    STATUS  mandatory
    DESCRIPTION
        "Rcellular module IMEI."
    ::={ teldatRcellularInfoInterfaceEntry 5 }

teldatRcellularInfoInterfaceModuleIMSI OBJECT-TYPE
    SYNTAX  DisplayString
    ACCESS  read-only
    STATUS  mandatory
    DESCRIPTION
        "Rcellular module IMSI."
    ::={ teldatRcellularInfoInterfaceEntry 6 }

teldatRcellularInfoInterfaceSIMId OBJECT-TYPE
    SYNTAX  DisplayString
    ACCESS  read-only
    STATUS  mandatory
    DESCRIPTION
        "Rcellular active SIM ID."
    ::={ teldatRcellularInfoInterfaceEntry 7 }

teldatRcellularInfoInterfaceSIMIcc OBJECT-TYPE
    SYNTAX  DisplayString
    ACCESS  read-only
    STATUS  mandatory
    DESCRIPTION
        "Rcellular active SIM ICC."
    ::={ teldatRcellularInfoInterfaceEntry 8 }


--  = = = = = = = = = = = = = = = = = = = = = = = = = = = = = = = = = = = = = =
--  Global Stats group Rcellular monitoring variables
--  = = = = = = = = = = = = = = = = = = = = = = = = = = = = = = = = = = = = = =

teldatRcellularStatObject    OBJECT IDENTIFIER ::= { telProdNpMonInterfRcellular 3 }

--  - - - - - - - - - - - - - - - - - - - - - - - - - - - - - - - - - - - - - -
--   Rcellular State Table, interface variables
--  - - - - - - - - - - - - - - - - - - - - - - - - - - - - - - - - - - - - - -

teldatRcellularStateInterfaceTable OBJECT-TYPE
    SYNTAX  SEQUENCE OF TeldatRcellularStateInterfaceEntry
    ACCESS  not-accessible
    STATUS  mandatory
    DESCRIPTION
        "Table of Rcellular interface state information."
    ::= { teldatRcellularStatObject 1 }

teldatRcellularStateInterfaceEntry OBJECT-TYPE
    SYNTAX  TeldatRcellularStateInterfaceEntry
    ACCESS  not-accessible
    STATUS  mandatory
    DESCRIPTION
        "A base list of objects that are interface state information."
    INDEX   { teldatRcellularStateInterfaceIndex}
    ::= { teldatRcellularStateInterfaceTable 1 }

TeldatRcellularStateInterfaceEntry ::= SEQUENCE
{
    teldatRcellularStateInterfaceIndex           INTEGER,
    teldatRcellularStateInterfaceState           INTEGER,
    teldatRcellularStateInterfaceDropPing        INTEGER,
    teldatRcellularStateInterfaceDropTrace       INTEGER,
    teldatRcellularStateInterfaceDropTraffic     INTEGER,
    teldatRcellularStateInterfaceTConnTime       INTEGER,
    teldatRcellularStateInterfaceCConnTime       INTEGER,
    teldatRcellularStateInterfaceCurDial         DisplayString,
    teldatRcellularStateInterfaceNCall           INTEGER,
    teldatRcellularStateInterfaceDestination     DisplayString,
    teldatRcellularStateInterfaceTime2Sp         INTEGER
}

teldatRcellularStateInterfaceIndex OBJECT-TYPE
    SYNTAX  INTEGER(1 .. 255)
    ACCESS  read-only
    STATUS  mandatory
    DESCRIPTION
        "Rcellular Interface index."
    ::={ teldatRcellularStateInterfaceEntry 1 }

teldatRcellularStateInterfaceState OBJECT-TYPE
    SYNTAX  INTEGER {
        initial(0),
        disconnect(1),
        trying_to_connect_ini(2),
        trying_to_connect_mk(3),
        trying_to_connect_cp(4),
        connect(5),
        waiting_call(6),
        hanging_up_ini(7),
        hanging_up(8),
        hanging_up_wta(9),
        hanging_up_wtar(10),
        discconnect_n_wait_call(11),
        wait_attach_wapn(12),
        wait_attach(13),
        wait_detach(14),
        wakeup_machine(15),
        command_mode(16),
        trying_to_connect_con(17),
        hanging_up_wesc(18),
        hanging_up_wt(19),
        disconnect_clcc(20),
        connect_wesc(21),
        connect_clcc(22),
        connect_ron(23),
        trying_to_connect_wgic(24),
        trying_to_connect_ucsq(25),
        trying_to_connect_unet(26),
        trying_to_connect_watc(27),
        establish_audio(28),
        gsm_incom_notify(29),
        wait_gsm_incom_notify(30),
        hanging_up_wdt(31)
        }
    ACCESS  read-only
    STATUS  mandatory
    DESCRIPTION
        "Call state."
    ::={ teldatRcellularStateInterfaceEntry 2 }


teldatRcellularStateInterfaceDropPing OBJECT-TYPE
    SYNTAX  INTEGER
    ACCESS  read-only
    STATUS  mandatory
    DESCRIPTION
        "Number of calls dropped due to ping supervision."
    ::={ teldatRcellularStateInterfaceEntry 3 }

teldatRcellularStateInterfaceDropTrace OBJECT-TYPE
    SYNTAX  INTEGER
    ACCESS  read-only
    STATUS  mandatory
    DESCRIPTION
        "Number of calls dropped due to traceroute supervision."
    ::={ teldatRcellularStateInterfaceEntry 4 }

teldatRcellularStateInterfaceDropTraffic OBJECT-TYPE
    SYNTAX  INTEGER
    ACCESS  read-only
    STATUS  mandatory
    DESCRIPTION
        "Number of calls dropped due to traffic supervision."
    ::={ teldatRcellularStateInterfaceEntry 5 }

teldatRcellularStateInterfaceTConnTime OBJECT-TYPE
    SYNTAX  INTEGER
    ACCESS  read-only
    STATUS  mandatory
    DESCRIPTION
        "Total connection time ."
    ::={ teldatRcellularStateInterfaceEntry 6 }

teldatRcellularStateInterfaceCConnTime OBJECT-TYPE
    SYNTAX  INTEGER
    ACCESS  read-only
    STATUS  mandatory
    DESCRIPTION
        "Current connection time."
    ::={ teldatRcellularStateInterfaceEntry 7 }

teldatRcellularStateInterfaceCurDial OBJECT-TYPE
    SYNTAX  DisplayString
    ACCESS  read-only
    STATUS  mandatory
    DESCRIPTION
        "Current dial-profile used."
    ::={ teldatRcellularStateInterfaceEntry 8 }

teldatRcellularStateInterfaceNCall OBJECT-TYPE
    SYNTAX  INTEGER
    ACCESS  read-only
    STATUS  mandatory
    DESCRIPTION
        "Number of processed calls."
    ::={ teldatRcellularStateInterfaceEntry 9 }

teldatRcellularStateInterfaceDestination OBJECT-TYPE
    SYNTAX  DisplayString
    ACCESS  read-only
    STATUS  mandatory
    DESCRIPTION
        "Connection destination."
    ::={ teldatRcellularStateInterfaceEntry 10 }

teldatRcellularStateInterfaceTime2Sp OBJECT-TYPE
    SYNTAX  INTEGER
    ACCESS  read-only
    STATUS  mandatory
    DESCRIPTION
        "Time to establish the call."
    ::={ teldatRcellularStateInterfaceEntry 11 }


--  - - - - - - - - - - - - - - - - - - - - - - - - - - - - - - - - - - - - - -
--   Rcellular State Table, Mobile variables
--  - - - - - - - - - - - - - - - - - - - - - - - - - - - - - - - - - - - - - -

teldatRcellularStateMobileTable OBJECT-TYPE
    SYNTAX  SEQUENCE OF TeldatRcellularStateMobileEntry
    ACCESS  not-accessible
    STATUS  mandatory
    DESCRIPTION
        "Table of Rcellular mobile state information."
    ::= { teldatRcellularStatObject 2 }

teldatRcellularStateMobileEntry OBJECT-TYPE
    SYNTAX  TeldatRcellularStateMobileEntry
    ACCESS  not-accessible
    STATUS  mandatory
    DESCRIPTION
        "A base list of objects that are mobile state information."
    INDEX   { teldatRcellularStateMobileIndex }
    ::= { teldatRcellularStateMobileTable 1 }

TeldatRcellularStateMobileEntry ::= SEQUENCE
{
    teldatRcellularStateMobileIndex                      INTEGER,
    teldatRcellularStateMobileRegistrationState          INTEGER,
    teldatRcellularStateMobilePublicLandMobileNtwCode    INTEGER,
    teldatRcellularStateMobileCellLocationAreaCode       INTEGER,
    teldatRcellularStateMobileCellId                     INTEGER,
    teldatRcellularStateMobileRadioTechnology            DisplayString,
    teldatRcellularStateMobileRadioBand                  DisplayString,
    teldatRcellularStateMobileRxSignalCodePwr            INTEGER,
    teldatRcellularStateMobileEnergyChipByPwrdnsty       INTEGER,
    teldatRcellularStateMobileSignalQuality              INTEGER,
    teldatRcellularStateMobileTemperature                INTEGER,
    teldatRcellularStateMobileRxPackets                  INTEGER,
    teldatRcellularStateMobileRxBytes                    INTEGER,
    teldatRcellularStateMobileTxPackets                  INTEGER,
    teldatRcellularStateMobileTxBytes                    INTEGER,
    teldatRcellularStateMobileRxBpsLast1s                INTEGER,
    teldatRcellularStateMobileTxBpsLast1s                INTEGER,
    teldatRcellularStateMobileRxBpsLast1m                INTEGER,
    teldatRcellularStateMobileTxBpsLast1m                INTEGER,
    teldatRcellularStateMobileRxBpsLast5m                INTEGER,
    teldatRcellularStateMobileTxBpsLast5m                INTEGER
}

teldatRcellularStateMobileIndex OBJECT-TYPE
    SYNTAX  INTEGER(1 .. 255)
    ACCESS  read-only
    STATUS  mandatory
    DESCRIPTION
        "Rcellular mobile state index."
    ::={ teldatRcellularStateMobileEntry 1 }

teldatRcellularStateMobileRegistrationState OBJECT-TYPE
    SYNTAX  INTEGER {
        searching(0),
        home_network(1),
        attaching(2),
        denied(3),
        unknown(4),
        roaming(5)
        }
    ACCESS  read-only
    STATUS  mandatory
    DESCRIPTION
        "Rcellular mobile registration state ()."
    ::={ teldatRcellularStateMobileEntry  2 }

teldatRcellularStateMobilePublicLandMobileNtwCode OBJECT-TYPE
    SYNTAX  INTEGER
    ACCESS  read-only
    STATUS  mandatory
    DESCRIPTION
        "Public land mobile network used (+COPS)."
    ::={ teldatRcellularStateMobileEntry  3 }


teldatRcellularStateMobileCellLocationAreaCode OBJECT-TYPE
    SYNTAX  INTEGER
    ACCESS  read-only
    STATUS  mandatory
    DESCRIPTION
        "Rcellular mobile cell location area code (+CGREG)."
    ::={ teldatRcellularStateMobileEntry  4 }

teldatRcellularStateMobileCellId OBJECT-TYPE
    SYNTAX  INTEGER
    ACCESS  read-only
    STATUS  mandatory
    DESCRIPTION
        "Rcellular mobile used cell id (+CGREG)."
    ::={ teldatRcellularStateMobileEntry  5 }

teldatRcellularStateMobileRadioTechnology OBJECT-TYPE
    SYNTAX  DisplayString
    ACCESS  read-only
    STATUS  mandatory
    DESCRIPTION
        "Rcellular mobile current radio access tecnology used (!GETRAT)."
    ::={ teldatRcellularStateMobileEntry  6 }

teldatRcellularStateMobileRadioBand OBJECT-TYPE
    SYNTAX  DisplayString
    ACCESS  read-only
    STATUS  mandatory
    DESCRIPTION
        "Rcellular mobile current active band (!GETBAND)."
    ::={ teldatRcellularStateMobileEntry  7 }


teldatRcellularStateMobileRxSignalCodePwr OBJECT-TYPE
    SYNTAX  INTEGER
    ACCESS  read-only
    STATUS  mandatory
    DESCRIPTION
        "Rcellular mobile received signal code power (RSCP)."
    ::={ teldatRcellularStateMobileEntry  8 }

teldatRcellularStateMobileEnergyChipByPwrdnsty OBJECT-TYPE
    SYNTAX  INTEGER
    ACCESS  read-only
    STATUS  mandatory
    DESCRIPTION
        "Rcellular mobile total energy per chip per power density (EcNo)."
    ::={ teldatRcellularStateMobileEntry  9 }

teldatRcellularStateMobileSignalQuality OBJECT-TYPE
    SYNTAX  INTEGER
    ACCESS  read-only
    STATUS  mandatory
    DESCRIPTION
        "Rcellular mobile reception signal quality (+CSQ)."
    ::={ teldatRcellularStateMobileEntry  10 }

teldatRcellularStateMobileTemperature OBJECT-TYPE
    SYNTAX  INTEGER
    ACCESS  read-only
    STATUS  mandatory
    DESCRIPTION
        "Rcellular mobile temperature (!PCTEMP)."
    ::={ teldatRcellularStateMobileEntry  11 }

teldatRcellularStateMobileRxPackets OBJECT-TYPE
    SYNTAX  INTEGER
    ACCESS  read-only
    STATUS  mandatory
    DESCRIPTION
        "Number of data packtes received by the radio interface"
    ::={ teldatRcellularStateMobileEntry  12 }

teldatRcellularStateMobileRxBytes OBJECT-TYPE
    SYNTAX  INTEGER
    ACCESS  read-only
    STATUS  mandatory
    DESCRIPTION
        "Number of data bytes received by the radio interface"
    ::={ teldatRcellularStateMobileEntry  13 }

teldatRcellularStateMobileTxPackets OBJECT-TYPE
    SYNTAX  INTEGER
    ACCESS  read-only
    STATUS  mandatory
    DESCRIPTION
        "Number of data packtes sent by the radio interface"
    ::={ teldatRcellularStateMobileEntry  14 }

teldatRcellularStateMobileTxBytes OBJECT-TYPE
    SYNTAX  INTEGER
    ACCESS  read-only
    STATUS  mandatory
    DESCRIPTION
        "Number of data packtes sent by the radio interface"
    ::={ teldatRcellularStateMobileEntry  15 }

teldatRcellularStateMobileRxBpsLast1s OBJECT-TYPE
    SYNTAX  INTEGER
    ACCESS  read-only
    STATUS  mandatory
    DESCRIPTION
        "Rx througput measured in the last second in bps"
    ::={ teldatRcellularStateMobileEntry  16 }

teldatRcellularStateMobileTxBpsLast1s OBJECT-TYPE
    SYNTAX  INTEGER
    ACCESS  read-only
    STATUS  mandatory
    DESCRIPTION
        "Tx througput measured in the last second in bps"
    ::={ teldatRcellularStateMobileEntry  17 }

teldatRcellularStateMobileRxBpsLast1m OBJECT-TYPE
    SYNTAX  INTEGER
    ACCESS  read-only
    STATUS  mandatory
    DESCRIPTION
        "Rx througput measured in the last minute in bps"
    ::={ teldatRcellularStateMobileEntry  18 }

teldatRcellularStateMobileTxBpsLast1m OBJECT-TYPE
    SYNTAX  INTEGER
    ACCESS  read-only
    STATUS  mandatory
    DESCRIPTION
        "Tx througput measured in the last minute in bps"
    ::={ teldatRcellularStateMobileEntry  19 }

teldatRcellularStateMobileRxBpsLast5m OBJECT-TYPE
    SYNTAX  INTEGER
    ACCESS  read-only
    STATUS  mandatory
    DESCRIPTION
        "Rx througput measured in the last five minutes in bps"
    ::={ teldatRcellularStateMobileEntry  20 }

teldatRcellularStateMobileTxBpsLast5m OBJECT-TYPE
    SYNTAX  INTEGER
    ACCESS  read-only
    STATUS  mandatory
    DESCRIPTION
        "Tx througput measured in the last five minutes in bps"
    ::={ teldatRcellularStateMobileEntry  21 }


END
