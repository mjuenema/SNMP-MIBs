-- 
-- Copyright 1999 by Fore Systems, Inc. 
-- Converted to SMIv2 rfc 2578,2579,2580 - STD 58
--
-- Copyright 1993-1999 by Fore Systems, Inc.

Fore-Switch-MIB DEFINITIONS ::= BEGIN

IMPORTS
	Counter32, Gauge32, Unsigned32,
	IpAddress, TimeTicks, Integer32,
	OBJECT-TYPE,	
	MODULE-IDENTITY,
	NOTIFICATION-TYPE			FROM SNMPv2-SMI
        TEXTUAL-CONVENTION,
	DisplayString, PhysAddress, TimeStamp,
	TestAndIncr, RowStatus,
	DateAndTime, TimeInterval               FROM SNMPv2-TC
	ifIndex	                                FROM IF-MIB
	atmSwitch, software,
	asxd, hardware, asx,
	SpansAddress, NsapPrefix,
	GeneralState, TransitNetwork,
	NsapAddr, EntryStatus,AtmSigProtocol,
	IntegerBitString, ConnectionType,
	systems                   		FROM Fore-Common-MIB
--  These are to get traps to work with SMF
	trapLogIndex				FROM Fore-TrapLog-MIB
	ipFilterStatsVPI,
	ipFilterStatsVCI,
	ipFilterStatsIfName			FROM Fore-Adapter-MIB
	crMemoryAllocated,
	crXfrIndex,
	crXfrPrimaryTrapStatus,
	crXfrSecondaryTrapStatus		FROM Fore-Callrecord-MIB
	pnniNodeId				FROM PNNI-MIB
	hrSystemDate		                FROM HOST-RESOURCES-MIB;

------------------------------------------------------------------------
-- MIB Groups

foreSwitchModule	MODULE-IDENTITY
          LAST-UPDATED         "9911050000Z"
          ORGANIZATION         "FORE"
          CONTACT-INFO         
               "      Postal:   FORE Systems Inc.
                                 1000 FORE Drive
                                 Warrendale, PA 15086-7502
                       Tel:      +1 724 742 6900
                       Email:    nm_mibs@fore.com
                       Web:      http://www.fore.com"
          DESCRIPTION "Fore Switch MIB"
    ::= { systems 7 }

boardGroup		OBJECT IDENTIFIER ::= { asx 1 }
moduleGroup		OBJECT IDENTIFIER ::= { asx 2 }

-- old environment group {hardware 2} deprecated.

timing			OBJECT IDENTIFIER ::= { hardware 3 }
netmodTimingGroup	OBJECT IDENTIFIER ::= { timing 1 }
boardTimingGroup	OBJECT IDENTIFIER ::= { timing 2 }

environment		OBJECT IDENTIFIER ::= { hardware 4 }
alarmGroup		OBJECT IDENTIFIER ::= { environment 1}
powerGroup		OBJECT IDENTIFIER ::= { environment 2 }
fansGroup		OBJECT IDENTIFIER ::= { environment 3 }
tempGroup		OBJECT IDENTIFIER ::= { environment 4 }
cpuGroup		OBJECT IDENTIFIER ::= { environment 5 }
mgmtGroup		OBJECT IDENTIFIER ::= { environment 6 }
fabricGroup		OBJECT IDENTIFIER ::= { environment 7 }

shmem			OBJECT IDENTIFIER ::= { hardware 5 }
netmodShmemGroup	OBJECT IDENTIFIER ::= { shmem 1 }
portShmemGroup		OBJECT IDENTIFIER ::= { shmem 2 }
netmodShmem2Group	OBJECT IDENTIFIER ::= { shmem 3 }
portShmem2Group		OBJECT IDENTIFIER ::= { shmem 4 }
connShmem2Group		OBJECT IDENTIFIER ::= { shmem 5 }
netmodShmem3Group       OBJECT IDENTIFIER ::= { shmem 6 }
portShmem3Group         OBJECT IDENTIFIER ::= { shmem 7 }
connShmem3Group         OBJECT IDENTIFIER ::= { shmem 8 }
netmodGenericShmemGroup OBJECT IDENTIFIER ::= { shmem 9 }
genericOutputPortGroup  OBJECT IDENTIFIER ::= { shmem 10 }


dualScp                 OBJECT IDENTIFIER ::= { hardware 6 }
dualScpGroup            OBJECT IDENTIFIER ::= { dualScp 1 }

etherChipSet            OBJECT IDENTIFIER ::= { hardware 10 }
etherChipSetDec         OBJECT IDENTIFIER ::= { etherChipSet 1 }
etherChipSetDec21440    OBJECT IDENTIFIER ::= { etherChipSetDec 1 }

switchGroup		OBJECT IDENTIFIER ::= { asxd 1 }
portGroup		OBJECT IDENTIFIER ::= { asxd 2 }
pathGroup		OBJECT IDENTIFIER ::= { asxd 3 }
channelGroup		OBJECT IDENTIFIER ::= { asxd 4 }
topologyGroup		OBJECT IDENTIFIER ::= { asxd 5 }
signalingGroup		OBJECT IDENTIFIER ::= { asxd 6 }
spansGroup		OBJECT IDENTIFIER ::= { signalingGroup 1 }
q2931Group              OBJECT IDENTIFIER ::= { signalingGroup 2 }
q2931LayerGroup         OBJECT IDENTIFIER ::= { q2931Group 1 }
swBoardGroup		OBJECT IDENTIFIER ::= { asxd 7 }
swBoardTopologyGroup	OBJECT IDENTIFIER ::= { asxd 8 }
nsapGroup               OBJECT IDENTIFIER ::= { asxd 9 }
upcContractGroup        OBJECT IDENTIFIER ::= { asxd 10 }
confTopologyGroup       OBJECT IDENTIFIER ::= { asxd 11 }
oamGroup		OBJECT IDENTIFIER ::= { asxd 12 }
guardGroup		OBJECT IDENTIFIER ::= { asxd 13 }
ifIndexMapGroup         OBJECT IDENTIFIER ::= { asxd 14 }
ifIndexNameGroup        OBJECT IDENTIFIER ::= { asxd 15 }
cesExtGroup             OBJECT IDENTIFIER ::= { asxd 16 }
qosClassExpansionGroup  OBJECT IDENTIFIER ::= { asxd 17 }
pathExtGroup            OBJECT IDENTIFIER ::= { asxd 18 }
poolGroup               OBJECT IDENTIFIER ::= { asxd 19 }
asxAtmIfGroup           OBJECT IDENTIFIER ::= { asxd 20 }
syncStatusMsgGroup	OBJECT IDENTIFIER ::= { asxd 21 }
syslogGroup             OBJECT IDENTIFIER ::= { asxd 22 }

poolConfGroup	OBJECT IDENTIFIER ::= { poolGroup 1 }
snmp			OBJECT IDENTIFIER ::= { software 2 }
trapConfGroup		OBJECT IDENTIFIER ::= { snmp 1 }
snmpConfGroup		OBJECT IDENTIFIER ::= { snmp 2 }
--foreViewGroup { snmp 3 } deprecated
--alarmGroup {snmp 4 } moved
snmpAgentAddressGroup	OBJECT IDENTIFIER ::= { snmp 5 }

E164Address ::= TEXTUAL-CONVENTION
	DISPLAY-HINT "15a"
	STATUS       current
	DESCRIPTION
		 "E164 address format defined as 15 ASCII characters."
	SYNTAX       OCTET STRING (SIZE(15))


------------------------------------------------------------------------
---
---   Connection Sheduling Type

AtmConnSchedMode ::= TEXTUAL-CONVENTION
      STATUS          current
      DESCRIPTION
                     "The value of this object identifies the scheduling
                       mode for an ATM connection (i.e., VCC or VPC). The
                       possible values are default, roundrobin, guaranteed,
                       and smoothed."
      SYNTAX          INTEGER {
                               default(1),
                               roundrobin(2),
                               smoothed(3),
                               guaranteed(4)
                      }

------------------------------------------------------------------------
---
---  Originating Path Scheduling Type

AtmOrigPathSchedMode ::= TEXTUAL-CONVENTION
      STATUS          current
      DESCRIPTION
                      "The value of this object identifies the scheduling
                       mode for an originating path. The possible values are
                       flat, shaped and shaped-roundrobin."
      SYNTAX          INTEGER {
                               flat(1),
                               shaped(2),
                               shaped-roundrobin(3)
                      }

------------------------------------------------------------------------
-- AAL5CountingMode
--
AAL5CountingMode  ::= TEXTUAL-CONVENTION
          STATUS       current
          DESCRIPTION
                  "The value of this object identifies the AAL5
                  counting mode for a connection (i.e., VCC or VPC).
                  Possible values for this object are default,
                  cell-counting and packet-counting."
         SYNTAX      INTEGER {
                      default(1),
                      cell-counting(2),
                      packet-counting (3)
                      }

------------------------------------------------------------------------
-- The Board Group

boardTable OBJECT-TYPE
	SYNTAX	SEQUENCE OF BoardEntry
	MAX-ACCESS	not-accessible
	STATUS	current
	DESCRIPTION
		"A table of ATM switch board information."
	::= { boardGroup 1 }

boardEntry OBJECT-TYPE
	SYNTAX	BoardEntry
	MAX-ACCESS	not-accessible
	STATUS	current
	DESCRIPTION
		"A table entry containing ATM switch board information."
	INDEX	{ boardIndex }
	::= { boardTable 1 }

BoardEntry ::=
	SEQUENCE {
		boardIndex		Integer32,
		boardVersion		Integer32,
		boardModel		INTEGER,
		boardSerialNumber	Integer32,
		numberOfModules		Integer32,
		vpiLookupErrors		Counter32,
		vciLookupErrors		Counter32,
		boardControlPort	Integer32,
		boardHDCOMPAsicVersion	Integer32,
		boardMcastSpaceIndex    Integer32
	}

boardIndex OBJECT-TYPE
	SYNTAX	Integer32
	MAX-ACCESS	read-only
	STATUS	current
	DESCRIPTION
		"The index of this board within the ATM switch."
	::= { boardEntry 1 }

boardVersion OBJECT-TYPE
	SYNTAX	Integer32
	MAX-ACCESS	read-only
	STATUS	current
	DESCRIPTION
		"The ATM switch board version number in hex.
		The version number 0x1 is revision A, 0x2 is
		revision B etc. Version number 0x0 represents an
		unknown type."
	::= { boardEntry 2 }

boardModel OBJECT-TYPE
	SYNTAX	INTEGER {
			unknown(0),
			asx100(1),
			asx200(2),
			asx200wg(4),
			asx200bx(5),
			asx200bxe(6),
			cabletron9A000(7),
			asx1000(8),
			le155(9),
			sfcs200wg(10),
			sfcs200bx(11),
			sfcs1000(12),
			tnx210(15),
			tnx1100(16),
			asx1200(17),
			asx4000(18),
			le25(19),
			esx3000(20),
			tnx1100b(21),
			asx150(22)
		}
	MAX-ACCESS	read-only
	STATUS	current
	DESCRIPTION
		"The ATM switch board model number."
	::= { boardEntry 3 }

boardSerialNumber OBJECT-TYPE
	SYNTAX	Integer32
	MAX-ACCESS	read-only
	STATUS	current
	DESCRIPTION
		"The ATM switch board serial number."
	::= { boardEntry 4 }

numberOfModules OBJECT-TYPE
	SYNTAX	Integer32
	MAX-ACCESS	read-only
	STATUS	current
	DESCRIPTION
		"The number of network modules on this ATM switch board."
	::= { boardEntry 5 }

vpiLookupErrors OBJECT-TYPE
	SYNTAX	Counter32
	MAX-ACCESS	read-only
	STATUS	obsolete
	DESCRIPTION
		"The number of VPI lookup errors."
	::= { boardEntry 6 }

vciLookupErrors OBJECT-TYPE
	SYNTAX	Counter32
	MAX-ACCESS	read-only
	STATUS	obsolete
	DESCRIPTION
		"The number of VCI lookup errors."
	::= { boardEntry 7 }

boardControlPort OBJECT-TYPE
	SYNTAX	Integer32
	MAX-ACCESS	read-only
	STATUS	current
	DESCRIPTION
		"This object identifies the index for the control
		port on this switch board."
	::= { boardEntry 8 }

boardHDCOMPAsicVersion OBJECT-TYPE
	SYNTAX  Integer32
	MAX-ACCESS  read-only
	STATUS  obsolete
	DESCRIPTION
	       "This object identifies the version number of the
	       HDCOMP ASIC on this switch board."
	::= { boardEntry 9 }

boardMcastSpaceIndex	OBJECT-TYPE
	SYNTAX  Integer32
	MAX-ACCESS  read-write
	STATUS  current
	DESCRIPTION
		"This object is the index into mcastSpaceTable that gives
		the number of multicast connections currently supported
		on this board. Changing this value has the effect of
		changing the number of multicast connections supported.
		Change will be effective after reboot only."
	::= { boardEntry 10 }

------------------------------------------------------------------------

numberOfBoards OBJECT-TYPE
	SYNTAX	Integer32
	MAX-ACCESS	read-only
	STATUS	current
	DESCRIPTION
		"The number of switch boards on this ATM switch."
	::= { boardGroup 2 }
-----------------------------------------------------------------------
-- The Utilization Group

utilization  OBJECT IDENTIFIER ::= { boardGroup 3 }

procUtilGroup   OBJECT IDENTIFIER ::= { utilization 1 }
mbufUtilGroup   OBJECT IDENTIFIER ::= { utilization 3 }

--
-- The Processor Utilization Group
--

procUtilLastUpdate OBJECT-TYPE
	SYNTAX  TimeTicks
	MAX-ACCESS  read-only
	STATUS  current
	DESCRIPTION
		" The time the procUtilValue was last updated"
	::= { procUtilGroup 1 }

procUtilValue OBJECT-TYPE
	SYNTAX  Gauge32 (0..100)
	MAX-ACCESS  read-only
	STATUS  current
	DESCRIPTION
		" The percentage of the processor power that has been used
		over the last monitoring interval"
	::= { procUtilGroup 2 }


procUtilMonInterval OBJECT-TYPE
	SYNTAX  INTEGER(100..6000)
	MAX-ACCESS  read-write
	STATUS  current
	DESCRIPTION
		"The amount of time between calculations of the procUtilValue.
		This value is expressed in units of 10 msec, (100 per sec).
		This value may take the value of 1 to 60 seconds"
--        DEFVAL{ 1500 }
	::= { procUtilGroup 3 }

procUtilMinLoad OBJECT-TYPE
	SYNTAX  Gauge32 (0..100)
	MAX-ACCESS  read-only
	STATUS  current
	DESCRIPTION
		" The MIN percentage of the processor power that has been.
		This value can be reset by setting the field
		procUtilHistoryReset."
--      DEFVAL(0)
	::= { procUtilGroup 4 }

procUtilMinLoadLastUpdate OBJECT-TYPE
	SYNTAX  TimeTicks
	MAX-ACCESS  read-only
	STATUS  current
	DESCRIPTION
		" The time the procUtilMinLoad was last updated"
	::= { procUtilGroup 5 }

procUtilMaxLoad OBJECT-TYPE
	SYNTAX  Gauge32 (0..100)
	MAX-ACCESS  read-only
	STATUS  current
	DESCRIPTION
		" The MAX percentage of the processor power that has been.
		This value can be reset by setting the field
		procUtilHistoryReset."
--      DEFVAL(0)
	::= { procUtilGroup 6 }

procUtilMaxLoadLastUpdate OBJECT-TYPE
	SYNTAX  TimeTicks
	MAX-ACCESS  read-only
	STATUS  current
	DESCRIPTION
		" The time the procUtilMaxLoad was last updated"
	::= { procUtilGroup 7 }

procUtilHistoryReset OBJECT-TYPE
	SYNTAX  INTEGER (0)
	MAX-ACCESS  read-write
	STATUS  current
	DESCRIPTION
		"This is in effect a WRITE_ONLY field. Setting this field
		resets the procUtilMinLoad, procUtilMinLoadLastUpdate,
		procUtilMaxLoad, and procUtilMaxLoadLastUpdate. This
		field can be set to anything by the NMS. When this field is
		read, it will always report NULL."
	::= { procUtilGroup 8 }

procUtilsNumMallocPart OBJECT-TYPE
	SYNTAX  Integer32
	MAX-ACCESS  read-only
	STATUS  current
	DESCRIPTION
		" The number of malloc partitions used on this SCP."
	::= { procUtilGroup 9 }

procUtilsSystemPartitionID OBJECT-TYPE
	SYNTAX  Integer32
	MAX-ACCESS  read-only
	STATUS  current
	DESCRIPTION
		" The partition ID os the system MALLOC pool. Use this
		value as an ID into the mallocUtilTable to view the
		system malloc pool statistics"
	::= { procUtilGroup 10 }

---------------------------------------------------
-- Board Statistics Table

boardStatsTable OBJECT-TYPE
	SYNTAX  SEQUENCE OF BoardStatsEntry
	MAX-ACCESS  not-accessible
	STATUS  current
	DESCRIPTION
		"A table of ATM switch fabric statistics information."
	::= { boardGroup 4 }

boardStatsEntry OBJECT-TYPE
	SYNTAX  BoardStatsEntry
	MAX-ACCESS  not-accessible
	STATUS  current
	DESCRIPTION
		"A table entry containing ATM switch fabric statistics information."
	INDEX   { boardStatsBoard, boardStatsIndex}
	::= { boardStatsTable 1 }

BoardStatsEntry ::=
	SEQUENCE {
		boardStatsBoard         Integer32,
		boardStatsIndex         Integer32,
		boardStatsName          DisplayString,
		boardStatsValue         Gauge32
	}

boardStatsBoard OBJECT-TYPE
	SYNTAX  Integer32
	MAX-ACCESS  not-accessible
	STATUS  current
	DESCRIPTION
		"The index of this fabric within the ATM switch."
	::= { boardStatsEntry 1 }

boardStatsIndex OBJECT-TYPE
	SYNTAX  Integer32
	MAX-ACCESS  not-accessible
	STATUS  current
	DESCRIPTION
		"The index of this statistics within the ATM switch fabric."
	::= { boardStatsEntry 2 }

boardStatsName OBJECT-TYPE
	SYNTAX  DisplayString
	MAX-ACCESS  read-only
	STATUS  current
	DESCRIPTION
		"The name of this statistics within the ATM switch fabric."
	::= { boardStatsEntry 3 }

boardStatsValue OBJECT-TYPE
	SYNTAX  Gauge32
	MAX-ACCESS  read-only
	STATUS  current
	DESCRIPTION
		"The value of this statistics within the ATM switch fabric."
	::= { boardStatsEntry 4 }

------------------------------------------------------------------------

portCardGroup OBJECT IDENTIFIER ::= { boardGroup 5 }

portCardTable OBJECT-TYPE
	SYNTAX SEQUENCE OF PortCardEntry
	MAX-ACCESS not-accessible
	STATUS current
	DESCRIPTION
		"A table of ATM switch port card information."
	::= { portCardGroup 1 }

portCardEntry OBJECT-TYPE
	SYNTAX PortCardEntry
	MAX-ACCESS not-accessible
	STATUS current
	DESCRIPTION
		"A table entry containing ATM switch port card information."
	INDEX { portCardIndex }
	::= { portCardTable 1 }

PortCardEntry ::=
	SEQUENCE {
		portCardIndex Integer32,
		portCardName DisplayString,
		portCardFlavor DisplayString,
		portCardType DisplayString,
		portCardUptime TimeTicks,
		portCardSerialNumber DisplayString,
		portCardAssemblyRevision Integer32,
		portCardHardwareConf Integer32,
		portCardState INTEGER
	}

portCardIndex OBJECT-TYPE
	SYNTAX Integer32
	MAX-ACCESS not-accessible
	STATUS current
	DESCRIPTION
		"The unique index of this port card within the ATM switch."
	::= { portCardEntry 1 }

portCardName OBJECT-TYPE
	SYNTAX DisplayString
	MAX-ACCESS read-only
	STATUS current
	DESCRIPTION
		"The name of this port card."
	::= { portCardEntry 2 }

portCardFlavor OBJECT-TYPE
	SYNTAX DisplayString
	MAX-ACCESS read-only
	STATUS current
	DESCRIPTION
		"The flavor of this port card."
	::= { portCardEntry 3 }

portCardType OBJECT-TYPE
	SYNTAX DisplayString
	MAX-ACCESS read-only
	STATUS current
	DESCRIPTION
		"The type description of this port card."
	::= { portCardEntry 4 }

portCardUptime OBJECT-TYPE
	SYNTAX TimeTicks
	MAX-ACCESS read-only
	STATUS current
	DESCRIPTION
		"The length of time this port card has been up in hundredths
		of a second."
	::= { portCardEntry 5 }

portCardSerialNumber OBJECT-TYPE
	SYNTAX DisplayString
	MAX-ACCESS read-only
	STATUS current
	DESCRIPTION
		"The serial number of this port card."
	::= { portCardEntry 6 }

portCardAssemblyRevision OBJECT-TYPE
	SYNTAX Integer32
	MAX-ACCESS read-only
	STATUS current
	DESCRIPTION
		"The assembly revision number of this port card."
	::= { portCardEntry 7 }

portCardHardwareConf OBJECT-TYPE
	SYNTAX Integer32
	MAX-ACCESS read-only
	STATUS current
	DESCRIPTION
		"The hardware configuration number of this port card."
	::= { portCardEntry 8 }

portCardState OBJECT-TYPE
	SYNTAX	INTEGER {
		reset(1),
		inService(2),
		outOfService(3)
		}
	MAX-ACCESS	read-write
	STATUS	current
	DESCRIPTION
		"The desired state of this port card. If set to
		reset(1), the port card is reset. Normally, when the
		port card is active, it is inService(2)."
	::= { portCardEntry 9 }


------------------------------------------------------------------------
---------------------------------------------------
-- Board Traffic Management Table

boardTrafficManagementGroup	OBJECT IDENTIFIER ::= { boardGroup 6 }

boardTrafficManagementPerPriorityTable	OBJECT-TYPE
	SYNTAX	SEQUENCE OF BoardTrafficManagementPerPriorityEntry
	MAX-ACCESS	not-accessible
	STATUS	current
	DESCRIPTION
		"A table of ATM switch fabric traffic management features
		that can be controlled per fabric and per priority."
	::= { boardTrafficManagementGroup 1 }

boardTrafficManagementPerPriorityEntry	OBJECT-TYPE
	SYNTAX	BoardTrafficManagementPerPriorityEntry
	MAX-ACCESS	not-accessible
	STATUS	current
	DESCRIPTION
		"A table entry of ATM switch fabric traffic management features
		that can be controlled per fabric and per priority."
	INDEX	{ btmPerPriorityBoard, btmPerPriorityPriority, btmPerPriorityFeature }
	::= { boardTrafficManagementPerPriorityTable 1 }

BoardTrafficManagementPerPriorityEntry	::=
	SEQUENCE {
		btmPerPriorityBoard		Integer32,
		btmPerPriorityPriority		Integer32,
		btmPerPriorityFeature		Integer32,
		btmPerPriorityPriorityName	DisplayString,
		btmPerPriorityValue		Integer32
	}

btmPerPriorityBoard	OBJECT-TYPE
	SYNTAX	Integer32
	MAX-ACCESS	not-accessible
	STATUS	current
	DESCRIPTION
		"The index of the fabric."
	::= { boardTrafficManagementPerPriorityEntry 1 }

btmPerPriorityPriority	OBJECT-TYPE
	SYNTAX	Integer32
	MAX-ACCESS	not-accessible
	STATUS	current
	DESCRIPTION
		"The index of the traffic priority."
	::= { boardTrafficManagementPerPriorityEntry 2 }

btmPerPriorityFeature	OBJECT-TYPE
	SYNTAX	Integer32
	MAX-ACCESS	not-accessible
	STATUS	current
	DESCRIPTION
		"The index of the feature.
		Feature 1 is EPD Threshold."
	::= { boardTrafficManagementPerPriorityEntry 3 }

btmPerPriorityPriorityName	OBJECT-TYPE
	SYNTAX	DisplayString
	MAX-ACCESS	read-only
	STATUS	current
	DESCRIPTION
		"The name of the traffic priority (e.g. CBR or UBR)."
	::= { boardTrafficManagementPerPriorityEntry 4 }

btmPerPriorityValue	OBJECT-TYPE
	SYNTAX	Integer32
	MAX-ACCESS	read-write
	STATUS	current
	DESCRIPTION
		"The value of the specified feature for the specified
		priority."
	::= { boardTrafficManagementPerPriorityEntry 5 }

---------------------------------------------------
-- The table that provides the MALLOC information
---------------------------------------------------

mallocUtilTable OBJECT-TYPE
	SYNTAX  SEQUENCE OF MallocUtilEntry
	MAX-ACCESS  not-accessible
	STATUS  current
	DESCRIPTION
		"A table containing malloc statistics for each memory partition"
	::= { utilization 2 }

mallocUtilEntry OBJECT-TYPE
	SYNTAX  MallocUtilEntry
	MAX-ACCESS  not-accessible
	STATUS  current
	DESCRIPTION
		"A table containing malloc statistics for each memory partition"
	INDEX { mallocPartId }
	::= { mallocUtilTable 1 }

MallocUtilEntry ::=
	SEQUENCE {
		mallocPartId            Integer32,
		numBytesFree            Integer32,
		numBlocksFree           Integer32,
		maxBlockSizeFree        Integer32,
		numBytesAlloc           Integer32,
		numBlocksAlloc          Integer32
	}




mallocPartId OBJECT-TYPE
	SYNTAX  Integer32
	MAX-ACCESS  not-accessible
	STATUS  current
	DESCRIPTION
		" The partition number for this malloc partition. The switch
		has a default partition named (procUtilsSystemPartitionID)."
	::= { mallocUtilEntry 1 }

numBytesFree OBJECT-TYPE
	SYNTAX  Integer32
	MAX-ACCESS  read-only
	STATUS  current
	DESCRIPTION
		" Number of Free Bytes in this partition"
	::= { mallocUtilEntry 2 }

numBlocksFree OBJECT-TYPE
	SYNTAX  Integer32
	MAX-ACCESS  read-only
	STATUS  current
	DESCRIPTION
		" The number of free blocks in this partition"
	::= { mallocUtilEntry 3 }

maxBlockSizeFree OBJECT-TYPE
	SYNTAX  Integer32
	MAX-ACCESS  read-only
	STATUS  current
	DESCRIPTION
		" The max block size that is free"
	::= { mallocUtilEntry 4 }

numBytesAlloc OBJECT-TYPE
	SYNTAX  Integer32
	MAX-ACCESS  read-only
	STATUS  current
	DESCRIPTION
		" Number of allocated bytes in this partition"
	::= { mallocUtilEntry 5 }

numBlocksAlloc OBJECT-TYPE
	SYNTAX  Integer32
	MAX-ACCESS  read-only
	STATUS  current
	DESCRIPTION
		" The number of allocated blocks in this partiton"
	::= { mallocUtilEntry 6 }


------------------------------------
------------------------------------
--      The mbuf Group
--

mbufsCount      OBJECT-TYPE
	SYNTAX  Integer32
	MAX-ACCESS  read-only
	STATUS  current
	DESCRIPTION
		" mbufs obtained from page pool"
	::= { mbufUtilGroup 1 }

mbufsClusters   OBJECT-TYPE
	SYNTAX  Integer32
	MAX-ACCESS  read-only
	STATUS  current
	DESCRIPTION
		" clusters obtained from page pool "
	::= { mbufUtilGroup 2 }

mbufsSpace      OBJECT-TYPE
	SYNTAX  Integer32
	MAX-ACCESS  read-only
	STATUS  current
	DESCRIPTION
		" interface pages obtained from page pool "
	::= { mbufUtilGroup 3 }

mbufsClFree     OBJECT-TYPE
	SYNTAX  Integer32
	MAX-ACCESS  read-only
	STATUS  current
	DESCRIPTION
		" Free Clusters "
	::= { mbufUtilGroup 4 }

mbufsDrops      OBJECT-TYPE
	SYNTAX  Integer32
	MAX-ACCESS  read-only
	STATUS  current
	DESCRIPTION
		" Times failed to find space "
	::= { mbufUtilGroup 5 }

mbufsWait       OBJECT-TYPE
	SYNTAX  Integer32
	MAX-ACCESS  read-only
	STATUS  current
	DESCRIPTION
		" Times waited for space"
	::= { mbufUtilGroup 6 }

mbufsDrain      OBJECT-TYPE
	SYNTAX  Integer32
	MAX-ACCESS  read-only
	STATUS  current
	DESCRIPTION
		" Times drained protocols for space "
	::= { mbufUtilGroup 7 }

mbufsFreeAlloc  OBJECT-TYPE
	SYNTAX  Integer32
	MAX-ACCESS  read-only
	STATUS  current
	DESCRIPTION
		" # of mbufs allocated to free list "
	::= { mbufUtilGroup 8 }

mbufsDataFreeAlloc      OBJECT-TYPE
	SYNTAX  Integer32
	MAX-ACCESS  read-only
	STATUS  current
	DESCRIPTION
		" # of mbufs allocated to dynamic (data) allocation "
	::= { mbufUtilGroup 9 }

mbufsHeaderAlloc        OBJECT-TYPE
	SYNTAX  Integer32
	MAX-ACCESS  read-only
	STATUS  current
	DESCRIPTION
		" # of mbufs allocated to packet headers "
	::= { mbufUtilGroup 10 }

mbufsSocketAlloc        OBJECT-TYPE
	SYNTAX  Integer32
	MAX-ACCESS  read-only
	STATUS  current
	DESCRIPTION
		" # of mbufs allocated to socket structures "
	::= { mbufUtilGroup 11 }

mbufsPcbAlloc   OBJECT-TYPE
	SYNTAX  Integer32
	MAX-ACCESS  read-only
	STATUS  current
	DESCRIPTION
		" # of mbufs allocated to protocol control blocks "
	::= { mbufUtilGroup 12 }

mbufsRtableAlloc        OBJECT-TYPE
	SYNTAX  Integer32
	MAX-ACCESS  read-only
	STATUS  current
	DESCRIPTION
		" # of mbufs allocated to routing tables "
	::= { mbufUtilGroup 13 }

mbufsHtableAlloc        OBJECT-TYPE
	SYNTAX  Integer32
	MAX-ACCESS  read-only
	STATUS  current
	DESCRIPTION
		" # of mbufs allocated to IMP Host Tables "
	::= { mbufUtilGroup 14 }

mbufsAtableAlloc        OBJECT-TYPE
	SYNTAX  Integer32
	MAX-ACCESS  read-only
	STATUS  current
	DESCRIPTION
		" # of mbufs allocated to Address Resolution Tables "
	::= { mbufUtilGroup 15 }

mbufsSoNameAlloc        OBJECT-TYPE
	SYNTAX  Integer32
	MAX-ACCESS  read-only
	STATUS  current
	DESCRIPTION
		" # of mbufs allocated to Socket Name "
	::= { mbufUtilGroup 16 }

mbufsZombieAlloc        OBJECT-TYPE
	SYNTAX  Integer32
	MAX-ACCESS  read-only
	STATUS  current
	DESCRIPTION
		" # of mbufs allocated to Zombie Processes "
	::= { mbufUtilGroup 17 }

mbufsSoOptsAlloc        OBJECT-TYPE
	SYNTAX  Integer32
	MAX-ACCESS  read-only
	STATUS  current
	DESCRIPTION
		" # of mbufs allocated to Socket Options "
	::= { mbufUtilGroup 18 }

mbufsFtableAlloc        OBJECT-TYPE
	SYNTAX  Integer32
	MAX-ACCESS  read-only
	STATUS  current
	DESCRIPTION
		" # of mbufs allocated to Fragment Re-assembly Headers "
	::= { mbufUtilGroup 19 }

mbufsRightsAlloc        OBJECT-TYPE
	SYNTAX  Integer32
	MAX-ACCESS  read-only
	STATUS  current
	DESCRIPTION
		" # of mbufs allocated to Access Rights "
	::= { mbufUtilGroup 20 }

mbufsIFaddrAlloc        OBJECT-TYPE
	SYNTAX  Integer32
	MAX-ACCESS  read-only
	STATUS  current
	DESCRIPTION
		" # of mbufs allocated to Interface Addresses "
	::= { mbufUtilGroup 21 }



------------------------------------------------------------------------
-- The Module Group

moduleTable OBJECT-TYPE
	SYNTAX	SEQUENCE OF ModuleEntry
	MAX-ACCESS	not-accessible
	STATUS	current
	DESCRIPTION
		"A table of network module information."
	::= { moduleGroup 1 }

moduleEntry OBJECT-TYPE
	SYNTAX	ModuleEntry
	MAX-ACCESS	not-accessible
	STATUS	current
	DESCRIPTION
		"A table entry containing network module information."
	INDEX	{ moduleBoard, moduleNumber }
	::= { moduleTable 1 }

ModuleEntry ::=
	SEQUENCE {
		moduleBoard		Integer32,
		moduleNumber		Integer32,
		moduleName		DisplayString,
		moduleSpeed		Unsigned32,
		moduleNumberOfPorts	Integer32,
		moduleUptime		TimeTicks,
		moduleHwMajorRev        Integer32,
		moduleHwMinorRev        Integer32,
		moduleVersion		INTEGER,
		moduleTimingSupport	INTEGER,
		moduleProductNumber	DisplayString,
		moduleState             INTEGER,
		moduleSerialNumber      DisplayString,
		moduleTestAdminStatus   INTEGER,
		moduleTestOperStatus    INTEGER,
		moduleTestStatusText    DisplayString,
		moduleAttachState       INTEGER,
		moduleCLEI              DisplayString
	}

moduleBoard OBJECT-TYPE
	SYNTAX	Integer32
	MAX-ACCESS	read-only
	STATUS	current
	DESCRIPTION
		"The index of this board within the ATM switch."
	::= { moduleEntry 1 }

moduleNumber OBJECT-TYPE
	SYNTAX	Integer32
	MAX-ACCESS	read-only
	STATUS	current
	DESCRIPTION
		"The number of this network module within the ATM switch."
	::= { moduleEntry 2 }

moduleName OBJECT-TYPE
	SYNTAX	DisplayString (SIZE (0..63))
	MAX-ACCESS	read-only
	STATUS	current
	DESCRIPTION
		"The type name of this network module within the ATM switch."
	::= { moduleEntry 3 }

moduleSpeed OBJECT-TYPE
	SYNTAX	Unsigned32
	MAX-ACCESS	read-only
	STATUS	current
	DESCRIPTION
		"The speed of this network module within the ATM switch."
	::= { moduleEntry 4 }

moduleNumberOfPorts OBJECT-TYPE
	SYNTAX	Integer32
	MAX-ACCESS	read-only
	STATUS	current
	DESCRIPTION
		"The number of ports on this network module."
	::= { moduleEntry 5 }

moduleUptime OBJECT-TYPE
	SYNTAX	TimeTicks
	MAX-ACCESS	read-only
	STATUS	current
	DESCRIPTION
		"The length of time this network module has been up,
		in hundredths of a second."
	::= { moduleEntry 6 }

moduleHwMajorRev OBJECT-TYPE
	SYNTAX	Integer32
	MAX-ACCESS	read-only
	STATUS	current
	DESCRIPTION
		"The hardware major revision number of the network
		module.  For generationD network modules this revision
		number is an ascii character value."
	::= { moduleEntry 7 }

moduleHwMinorRev OBJECT-TYPE
	SYNTAX	Integer32
	MAX-ACCESS	read-only
	STATUS	current
	DESCRIPTION
		"The hardware minor revision number of the network module."
	::= { moduleEntry 8 }

moduleVersion OBJECT-TYPE
	SYNTAX	INTEGER {
		generationA(1),
		generationB(2),
		generationC(3),
		generationLC(4),
		generationLE(5),
		generationD(6),
		generationPC1(7),
		generationPC2(8),
		generationE(10),
		generationPCF1(11),
		generationC2(67)
	}
	MAX-ACCESS	read-only
	STATUS	current
	DESCRIPTION
		"The hardware version of this network module."
	::= { moduleEntry 9 }

moduleTimingSupport OBJECT-TYPE
	SYNTAX	INTEGER {
		no(1),
		yes(2)
	}
	MAX-ACCESS	read-only
	STATUS	current
	DESCRIPTION
		"Does this network module support distributed timing?"
	::= { moduleEntry 10 }

moduleProductNumber OBJECT-TYPE
	SYNTAX	DisplayString (SIZE (0..63))
	MAX-ACCESS	read-only
	STATUS	current
	DESCRIPTION
		"The product number of this network module."
	::= { moduleEntry 11 }

moduleState OBJECT-TYPE
	SYNTAX	INTEGER {
		reset(1),
		inService(2),
	outOfService(3),
	resetPair(4)
		}
	MAX-ACCESS	read-write
	STATUS	current
	DESCRIPTION
		"The desired state of this network module. If set to
		reset(1), the netmod is reset. Normally, when the
		netmod is active, it is inService(2). To put a netmod
		out of service, this entry must be set to
		outOfService(3)."
	::= { moduleEntry 12 }

moduleSerialNumber OBJECT-TYPE
	SYNTAX  DisplayString
	MAX-ACCESS  read-only
	STATUS  current
	DESCRIPTION
		"The string representing the serial number for this
		network module."
	::= { moduleEntry 13 }

moduleTestAdminStatus OBJECT-TYPE
	SYNTAX INTEGER {
		normal (1),
		startTest(2),
		abortTest(3)
	}
	MAX-ACCESS read-write
	STATUS current
	DESCRIPTION
		"This variable indicates the hardware test configuration
		of the network module. It can be set to startTest(2), which
		starts the hardware tests on the network module. abortTest(3)
		aborts the test, if the network module is under test. The
		network module returns to normal(0) after the test ends or
		is aborted."
	::= { moduleEntry 14 }

moduleTestOperStatus OBJECT-TYPE
	SYNTAX INTEGER {
		normal (1),
		underTest (2),
		testSuccessful (3),
		testFailed (4),
		testAborted (5),
		testUnsupported (6)
	}
	MAX-ACCESS read-only
	STATUS current
	DESCRIPTION
		"The status of the hardware tests on the network module.
		normal (1) indicates that the network module has never
		undergone hardware tests. The network module is underTest (2),
		after the test is started on it, and goes to testSuccessful (3)
		or testFailed (4), after the tests end. If the tests are
		aborted, the network module goes to testAborted (5) state. Those
		network modules that do not support hardware tests like
		Series-C and LC modules, are in testUnsupported (6) state."
	::= { moduleEntry 15 }

moduleTestStatusText OBJECT-TYPE
	SYNTAX DisplayString (SIZE (0..100))
	MAX-ACCESS read-only
	STATUS current
	DESCRIPTION
		"A message describing the status of the current test"
	::= { moduleEntry 16 }

moduleAttachState OBJECT-TYPE
	SYNTAX	INTEGER {
		inService(1),
		outOfService(2)
		}
	MAX-ACCESS	read-only
	STATUS	current
	DESCRIPTION
		"The actual state of this network module.  The netmod
		state is directed by the moduleState variable.  This
		variable gives the actual state at a given time (which
		may lag behind the moduleState by several seconds)."
	::= { moduleEntry 17 }

moduleCLEI OBJECT-TYPE
	SYNTAX	DisplayString (SIZE (0..63))
	MAX-ACCESS	read-only
	STATUS	current
	DESCRIPTION
		"The Common Language Equipment identifications (CLEI)
		of this network module."
	::= { moduleEntry 18 }

------------------------------------------------------------------------

appModuleTable OBJECT-TYPE
	SYNTAX	SEQUENCE OF AppModuleEntry
	MAX-ACCESS	not-accessible
	STATUS	current
	DESCRIPTION
		"A table consisting of hardware components that have
	on-board CPUs. Currently, the FR/ATM, FUNI and IMA network
		modules appear in this table."
	::= { moduleGroup 6 }

appModuleEntry OBJECT-TYPE
	SYNTAX	AppModuleEntry
	MAX-ACCESS	not-accessible
	STATUS	current
	DESCRIPTION
		"A table entry containing application module information."
	INDEX	{ appModuleIndex }
	::= { appModuleTable 1 }

AppModuleEntry ::=
	SEQUENCE {
		appModuleIndex			Integer32,
		appModuleName			DisplayString,
		appModuleOperState		INTEGER,
		appModuleStatusText		DisplayString,
		appModuleApplicationType	DisplayString,
		appModuleSoftwareVersion	DisplayString,
		appModuleBootSoftwareVersion	DisplayString,
		appModuleOosLed			INTEGER,
		appModulePanicAction		INTEGER
	}

appModuleIndex	OBJECT-TYPE
	SYNTAX	Integer32
	MAX-ACCESS	read-only
	STATUS	current
	DESCRIPTION
		"The index of the application module in this switch."
	::= { appModuleEntry 1 }

appModuleName	OBJECT-TYPE
	SYNTAX	DisplayString
	MAX-ACCESS	read-only
	STATUS	current
	DESCRIPTION
		"The name of this application module."
	::= { appModuleEntry 2 }

appModuleOperState OBJECT-TYPE
	SYNTAX	INTEGER {
		notConfigured (1),
		hwInitInProgress (2),
		up (3),
		shutDownInProgress (4),
		down (5),
		failed (6)
	}
	MAX-ACCESS	read-only
	STATUS	current
	DESCRIPTION
		"The operational state of this network module's hardware."
	::= { appModuleEntry 3 }

appModuleStatusText OBJECT-TYPE
	SYNTAX	DisplayString (SIZE (0..100))
	MAX-ACCESS	read-only
	STATUS	current
	DESCRIPTION
		"A text string describing the current state of the hardware."
	::= { appModuleEntry 4 }

appModuleApplicationType OBJECT-TYPE
	SYNTAX	DisplayString
	MAX-ACCESS	read-only
	STATUS	current
	DESCRIPTION
		"This variable indicates the application(s) running on this
		application module."
	::= { appModuleEntry 5 }

appModuleSoftwareVersion OBJECT-TYPE
	SYNTAX	DisplayString (SIZE (0..100))
	MAX-ACCESS	read-only
	STATUS	current
	DESCRIPTION
		"Version of the software running on this application module."
	::= { appModuleEntry 6 }

appModuleBootSoftwareVersion OBJECT-TYPE
	SYNTAX	DisplayString (SIZE (0..100))
	MAX-ACCESS	read-only
	STATUS	current
	DESCRIPTION
		"Version of the BOOT PROM software on this application module."
	::= { appModuleEntry 7 }

appModuleOosLed OBJECT-TYPE
	SYNTAX	INTEGER {
		off (1),
		red (2)
	}
	MAX-ACCESS	read-only
	STATUS	current
	DESCRIPTION
		"The color of the OOS LED on the application module. This LED
		is off (1) when the network module is up and running and
		red (2) when the network module is down (administratively
		placed out of service or operationally down temporarily).
		For example, when the network module's hardware initialization
		is in progress, the LED will be red until the hardware
		initialization is complete."
	::= { appModuleEntry 8 }

appModulePanicAction OBJECT-TYPE
	SYNTAX  INTEGER {
		reset (1),
		suspend (2)
	}
	MAX-ACCESS  read-write
	STATUS  current
	DESCRIPTION
		"This variable indicates the action to be taken if the
		on-board CPU fails. This module will be reset if this
		variable is set to reset(1) and will be suspended if
		this variable is set to suspend(2)."
	DEFVAL { reset }
	::= { appModuleEntry 9 }

----------------------------------------------------------------------------

outputBufferTable OBJECT-TYPE
	SYNTAX	SEQUENCE OF OutputBufferEntry
	MAX-ACCESS	not-accessible
	STATUS	current
	DESCRIPTION
		"A table of output buffer information."
	::= { moduleGroup 2 }

outputBufferEntry OBJECT-TYPE
	SYNTAX	OutputBufferEntry
	MAX-ACCESS	not-accessible
	STATUS	current
	DESCRIPTION
		"A table entry containing output buffer information."
	INDEX	{ obufBoard, obufNumber, obufType }
	::= { outputBufferTable 1 }

OutputBufferEntry ::=
	SEQUENCE {
		obufBoard	 Integer32,
		obufNumber	 Integer32,
		obufType	 Integer32,
		obufOperStatus	 INTEGER,
		obufBufferSize	 Integer32,
		obufQueueLength	 Gauge32,
		obufOverflows	 Gauge32,
		obufPriorityName DisplayString,
		obufName	 DisplayString
	}

obufBoard OBJECT-TYPE
	SYNTAX	Integer32
	MAX-ACCESS	read-only
	STATUS	current
	DESCRIPTION
		"The index of this output buffer's switch board."
	::= { outputBufferEntry 1 }

obufNumber OBJECT-TYPE
	SYNTAX	Integer32
	MAX-ACCESS	read-only
	STATUS	current
	DESCRIPTION
		"The number of the network module for this output buffer."
	::= { outputBufferEntry 2 }

obufType OBJECT-TYPE
	SYNTAX	Integer32
	MAX-ACCESS	read-only
	STATUS	current
	DESCRIPTION
		"The Priority of this output buffer- 0 is lowest priority"
	::= { outputBufferEntry 3 }

obufOperStatus OBJECT-TYPE
	SYNTAX	INTEGER {
			other(1),
			enabled(2),
			disabled(3)
		}
	MAX-ACCESS	read-only
	STATUS	current
	DESCRIPTION
		"The operational status of this output buffer."
	::= { outputBufferEntry 4 }

obufBufferSize OBJECT-TYPE
	SYNTAX	Integer32
	MAX-ACCESS	read-only
	STATUS	current
	DESCRIPTION
		"The logical size of this output buffer, in cells."
	::= { outputBufferEntry 5 }

obufQueueLength OBJECT-TYPE
	SYNTAX	Gauge32
	MAX-ACCESS	read-only
	STATUS	current
	DESCRIPTION
		"The number of cells in this output buffer."
	::= { outputBufferEntry 6 }

obufOverflows OBJECT-TYPE
	SYNTAX	Gauge32
	MAX-ACCESS	read-only
	STATUS	current
	DESCRIPTION
		"The number of cells dropped because this output buffer
		was full."
	::= { outputBufferEntry 7 }

obufPriorityName OBJECT-TYPE
	SYNTAX  DisplayString
	MAX-ACCESS  read-only
	STATUS  current
	DESCRIPTION
		"The priority name (eg. CBR, VBR) for this buffer."
	::= { outputBufferEntry 8 }

obufName OBJECT-TYPE
	SYNTAX  DisplayString
	MAX-ACCESS  read-only
	STATUS  current
	DESCRIPTION
		"The name (eg. 1, 1A) of this buffer."
	::= { outputBufferEntry 9 }

------------------------------------------------------------------------

hwPortTable OBJECT-TYPE
	SYNTAX	SEQUENCE OF HwPortEntry
	MAX-ACCESS	not-accessible
	STATUS	current
	DESCRIPTION
		"A table of hardware port information."
	::= { moduleGroup 3 }

hwPortEntry OBJECT-TYPE
	SYNTAX	HwPortEntry
	MAX-ACCESS	not-accessible
	STATUS	current
	DESCRIPTION
		"A table entry containing hardware port information."
	INDEX	{ hwPortBoard, hwPortModule, hwPortNumber }
	::= { hwPortTable 1 }

HwPortEntry ::=
	SEQUENCE {
		hwPortBoard		Integer32,
		hwPortModule		Integer32,
		hwPortNumber		Integer32,
		hwPortVersion		INTEGER,
		hwPortModel		INTEGER,
		hwPortOperStatus	INTEGER,
		hwPortBufferSize	Integer32,
		hwPortQueueLength	Gauge32,
		hwPortOverflows		Counter32,
		hwPortErrors		Counter32,
		hwPortCarrier		INTEGER,
		hwPortGlobalIndex	Integer32,
		hwPortName		DisplayString,
		hwPortAdminStatus	INTEGER,
		hwPortTAXILoopback	INTEGER,
		hwPortLEDModel		INTEGER,
		hwPortTxLED		INTEGER,
		hwPortRxLED		INTEGER,
		hwPortIfIndex           Integer32,
		hwPortRxSyncLED         INTEGER,
		hwPortCounterResetTime  TimeStamp,
		hwPortCounterReset      INTEGER,
		hwPortSpeed		Unsigned32
	}

hwPortBoard OBJECT-TYPE
	SYNTAX	Integer32
	MAX-ACCESS	read-only
	STATUS	current
	DESCRIPTION
		"The switch board index of this port."
	::= { hwPortEntry 1 }

hwPortModule OBJECT-TYPE
	SYNTAX	Integer32
	MAX-ACCESS	read-only
	STATUS	current
	DESCRIPTION
		"The network module number of this port."
	::= { hwPortEntry 2 }

hwPortNumber OBJECT-TYPE
	SYNTAX	Integer32
	MAX-ACCESS	read-only
	STATUS	current
	DESCRIPTION
		"The number of this port within its network module."
	::= { hwPortEntry 3 }

hwPortVersion OBJECT-TYPE
	SYNTAX	INTEGER {
			generationA(1),
			generationB(2),
			generationC(3),
			generationLC(4),
			generationLE(5),
			generationD(6),
			generationPC1(7),
			generationPC2(8),
			generationE(10),
			generationPCF1(11),
                        generationC2(67)
	}
	MAX-ACCESS	read-only
	STATUS	current
	DESCRIPTION
		"The generation of this network module.  In general,
		 generation A indicates the most original FORE Systems
		 netmods.  Generation-B are intermediate DS3/E3/TAXI.
		 Generation-C are shared-memory based netmods."
	::= { hwPortEntry 4 }

hwPortModel OBJECT-TYPE
	SYNTAX	INTEGER {
			model-TAXI-100(1),
			model-TAXI-140(2),
			model-DS3(3),
			model-OC3(4),
			model-8B10B(5),
			model-6port-TAXI-100(6),
			model-ASX-CTL(7),
			model-OC12(8),
			model-OC48(9),
			model-DS3-PDH(16),
			model-E3(17),
			model-J2(18),
			model-DS1(19),
			model-E1(20),
			model-TP25(21),
			model-ASX-BP(22),
			model-CESDS1(23),
			model-CESE1(24),
			model-FRAMDS1(25),
			model-FRAME1(26),
			model-IMADS1(27),
			model-IMAE1(28),
			model-RJ-45(29),
			model-CHOC12(30),
	                model-STM1(31),
	                model-OC3-POS(32),
	                model-OC12-POS(33),
			model-CHOC3(34),
			model-ETH(35)
		}
	MAX-ACCESS	read-only
	STATUS	current
	DESCRIPTION
		"The type of physical connection of this port. The model-ASX(7)
		indicates this is the control port of the switch.
		NOTE: as of 2/8/95 the elements model-6port-TAXI-100(6) and
		      model-DS3-PDH(16) should no longer be used.  Use
		      the basic types model-TAXI-100(1) and model-DS3(3)
		      to indicate these."
	::= { hwPortEntry 5 }

hwPortOperStatus OBJECT-TYPE
	SYNTAX	INTEGER {
			other(1),
			up(2),
			down(3),
			unused(4)	-- was loopback
		}
	MAX-ACCESS	read-only
	STATUS	current
	DESCRIPTION
		"The operational status of this port. If a port was
		administered up (by hwPortAdminStatus), but the carrier
		or the framing bits were lost, the hwPortOperStatus
		indicates that the port is down(3). Otherwise, the
		hwPortOperStatus is up(2)."
	::= { hwPortEntry 6 }

hwPortBufferSize OBJECT-TYPE
	SYNTAX	Integer32
	MAX-ACCESS	read-only
	STATUS	deprecated
	DESCRIPTION
		"The logical size of this port's output buffer, in cells."
	::= { hwPortEntry 7 }

hwPortQueueLength OBJECT-TYPE
	SYNTAX	Gauge32
	MAX-ACCESS	read-only
	STATUS	deprecated
	DESCRIPTION
		"The number of cells in this port's output buffer."
	::= { hwPortEntry 8 }

hwPortOverflows OBJECT-TYPE
	SYNTAX	Counter32
	MAX-ACCESS	read-only
	STATUS	deprecated
	DESCRIPTION
		"The number of seconds in which cells were dropped because
this port's output buffer was full."
	::= { hwPortEntry 9 }

hwPortErrors OBJECT-TYPE
	SYNTAX	Counter32
	MAX-ACCESS	read-only
	STATUS	deprecated
	DESCRIPTION
		"The number of seconds in which errored cells were dropped by this port."
	::= { hwPortEntry 10 }

hwPortCarrier OBJECT-TYPE
	SYNTAX	INTEGER {
			carrier(1),
			noCarrier(2)
		}
	MAX-ACCESS	read-only
	STATUS	current
	DESCRIPTION
		"The presence or absence of carrier at this port."
	::= { hwPortEntry 11 }

hwPortGlobalIndex OBJECT-TYPE
	SYNTAX	Integer32
	MAX-ACCESS	read-only
	STATUS	deprecated
	DESCRIPTION
		"The global index of this port within the ATM switch
		as a whole. It corresponds to the port number
		used in the software group of this MIB."
	::= { hwPortEntry 12 }

hwPortName OBJECT-TYPE
	SYNTAX	DisplayString (SIZE(0..5))
	MAX-ACCESS	read-only
	STATUS	current
	DESCRIPTION
		"A textual description of the port indicating
		the Board Network module and Port (BNP) identifiers.
		The module is indicated by a letter (A-D), while
		the board and the port are indicated by numbers."
	::= { hwPortEntry 13 }

hwPortAdminStatus OBJECT-TYPE
	SYNTAX	INTEGER {
			up(1),
			down(2)
		}
	MAX-ACCESS	read-write
	STATUS	current
	DESCRIPTION
		"The administrative state of the physical layer of this
		port. When a port is configured up(1), the physical layer
		is configured to process all physical layer events including
		the transmission and reception of data (cells).  When a port
		is configured down(2), the physical layer should be shut down
		and should ignore all physical layer events (e.g. cell reception,
		carrier loss, loss of framing, parity errors, etc.).  The
		operational status of a port is reflected in the
		hwPortOperStatus object."
	::= { hwPortEntry 14 }

hwPortTAXILoopback OBJECT-TYPE
	SYNTAX	INTEGER {
			noLoopback(1),
			loopback(2)
		}
	MAX-ACCESS	read-write
	STATUS	current
	DESCRIPTION
		"This variable represents the loopback status of a TAXI port.
		For non-TAXI ports (e.g. DS3/E3 or SONET) the loopback
		configuration should be set in their specific tables."
	DEFVAL { noLoopback }
	::= { hwPortEntry 15 }

hwPortLEDModel OBJECT-TYPE
	SYNTAX	INTEGER {
			lan(1),
			wan(2)
		}
	MAX-ACCESS	read-write
	STATUS	current
	DESCRIPTION 
	       "The LED model to use for setting the colors of the
		LEDs on each port.  LAN models typically blink the
		LEDs when data is transmitted or received on the port.
		WAN models typically keep the LEDs green unless an
		error condition exists on the port.

		With SONET netmods the LED models use the following
		algorithms:

		LAN (3 states):

			if (LOS || LOF || AIS_L || LOP_P ||
			    UNEQ_P || PLM_P || LCD) {
				rxLED = RED
			}
			else if (RDI_L) {
				rxLED = YELLOW
			}
			else {
				rxLED = AUTO
			}
			txLED = AUTO

		WAN (3 states):

			if (LOS || LOF || AIS_L || LOP_P ||
			    UNEQ_P || PLM_P || LCD) {
				rxLED = RED
			}
			else if (RDI_L) {
				rxLED = YELLOW
			}
			else {
				rxLED = GREEN
			}
			txLED = GREEN

		With LAN and WAN models: RED means fault in receive
		direction, YELLOW means fault in transmit direction
		(RDI_L defect), AUTO/GREEN means no fault.  Only the
		receive LED color is changed.  These models show only
		three states and do not reflect the status of the
		AIS_P and RDI_P defects."
	DEFVAL { lan }
	::= { hwPortEntry 16 }

hwPortTxLED OBJECT-TYPE
	SYNTAX	INTEGER {
			off(1),
			green(2),
			red(3),
			yellow(4),
			auto(5)
		}
	MAX-ACCESS	read-only
	STATUS	current
	DESCRIPTION
		"Indicates the color of the transmit LED for this
		port.  Auto means that the LED is under hardware
		control.  Typically hardware control means that the
		LED is normally dark with green blinks to indicate
		data traffic."
	::= { hwPortEntry 17 }

hwPortRxLED OBJECT-TYPE
	SYNTAX	INTEGER {
			off(1),
			green(2),
			red(3),
			yellow(4),
			auto(5)
		}
	MAX-ACCESS	read-only
	STATUS	current
	DESCRIPTION
		"Indicates the color of the receive LED for this
		port.  Auto means that the LED is under hardware
		control.  Typically hardware control means that the
		LED is normally dark with green blinks to indicate
		data traffic."
	::= { hwPortEntry 18 }

hwPortIfIndex OBJECT-TYPE
	SYNTAX	Integer32
	MAX-ACCESS	read-only
	STATUS	current
	DESCRIPTION
		"This entry indicates the IfIndex used to identify this
		port. It corresponds to the ifIndex used in the rfc2233
		rfc1573 ifTables"
	::= { hwPortEntry 19 }

hwPortRxSyncLED OBJECT-TYPE
	SYNTAX  INTEGER {
			off(1),
			green(2)
		}
	MAX-ACCESS  read-only
	STATUS  current
	DESCRIPTION
		"The synchronization LED which only applies to the receivers.
		When green, it indicates that the port is providing the
		8 khz clock reference to the switch. This is a new entry
		which makes sense to those netmod ( currently only FRAM
		netmod support this LED) which can provide a 8 khz clock
		reference to the switch. At the netmod scope, only one
		such LED should be green if the switch is importing a port
		timing clock."
	 ::= { hwPortEntry 20 }

hwPortCounterResetTime OBJECT-TYPE
	SYNTAX  TimeStamp
	MAX-ACCESS  read-only
	STATUS  current
	DESCRIPTION
		"Indicates when this port's physical interface counters were
		 reset.  The TimeStamp is equal to moduleUptime when the reset
		 occurred.  If this ports counters were never reset,
		 hwPortCounterResetTime will be zero.  This variable is
		 updated whenever hwPortCounterReset or switchCounterReset
		 is written."
	::= { hwPortEntry 21 }

hwPortCounterReset OBJECT-TYPE
	SYNTAX  INTEGER {
		   resetRequest(1),
		   resetTrue(3),
		   resetFalse(4)
		}
	MAX-ACCESS  read-write
	STATUS  current
	DESCRIPTION
		"Writing a value of resetRequest will result in a
		reset of all physical interface counters on this port.  VCC
		indexed counters are excluded.  A response value of resetTrue
		indicates a resetRequest has succeeded and is currently
		in effect.  A response value of resetFalse indicates
		a reset is not currently in effect."
	::= { hwPortEntry 22 }


hwPortSpeed OBJECT-TYPE
	SYNTAX	Unsigned32
	MAX-ACCESS	read-only
	STATUS	current
	DESCRIPTION
		"The speed of this physical port in the ATM switch."
	::= { hwPortEntry 23 }

------------------------------------------------------------------------
netmodAlarmsTable OBJECT-TYPE
	SYNTAX  SEQUENCE OF NetmodAlarmsEntry
	MAX-ACCESS  not-accessible
	STATUS  current
	DESCRIPTION
		"A table of network module alarms information categorized
		 on a per slot basis."
	::= { moduleGroup 4 }

netmodAlarmsEntry OBJECT-TYPE
	SYNTAX  NetmodAlarmsEntry
	MAX-ACCESS  not-accessible
	STATUS  current
	DESCRIPTION
		"A table entry containing network module alarm information."
	INDEX   { netmodSlot }
	::= { netmodAlarmsTable 1 }

NetmodAlarmsEntry ::=
	SEQUENCE {
		netmodSlot              Integer32,
		netmodSlotPriority      INTEGER,
		netmodStatus            INTEGER,
		netmodName		DisplayString
	}

netmodSlot OBJECT-TYPE
	SYNTAX Integer32
	MAX-ACCESS read-only
	STATUS current
	DESCRIPTION
		"This number represents the unique number of this netmod within
		the ATM switch. This number starts at 0."
	::= { netmodAlarmsEntry 1 }

netmodSlotPriority OBJECT-TYPE
	SYNTAX INTEGER {
		       high (1),
		       low  (2),
		       none (3)
	       }
	MAX-ACCESS read-write
	STATUS current
	DESCRIPTION
		"The priority assigned to this slot. Possible values are
		 High (corresponding to netmodRemovedHighPrio), Low
		 (corresponding to netmodRemovedLowPrio) and None (default)"
	::= { netmodAlarmsEntry 2 }

netmodStatus OBJECT-TYPE
	SYNTAX INTEGER {
		       present (1),
		       absent  (2)
	       }
	MAX-ACCESS read-only
	STATUS current
	DESCRIPTION
		"The presence/absence of a netmod in this slot is determined
		 by this variable."
	::= { netmodAlarmsEntry 3 }

netmodName OBJECT-TYPE
	SYNTAX DisplayString
	MAX-ACCESS read-only
	STATUS current
	DESCRIPTION
		"The name of this netmod. Example: 1A, 3D for ASX4000 and A, B
		for pre-ASX4000 switches."
	::= { netmodAlarmsEntry 4 }

--------------------------------------------------------------------------------
--- The hdcomp group

hdcompTable OBJECT-TYPE
	SYNTAX	SEQUENCE OF HdcompEntry
	MAX-ACCESS	not-accessible
	STATUS	current
	DESCRIPTION
		"A table for information about HDCOMPs."
	::= { moduleGroup 5 }

hdcompEntry	OBJECT-TYPE
	SYNTAX	HdcompEntry
	MAX-ACCESS	not-accessible
	STATUS	current
	DESCRIPTION
		"A table for information about HDCOMPs."
	INDEX { hdcompIndex }
	::= { hdcompTable 1 }

HdcompEntry ::=
	SEQUENCE {
		hdcompIndex		Integer32,
		hdcompDescr		DisplayString,
		hdcompAsicVersion	Integer32,
		hdcompVpiLookupErrors	Counter32,
		hdcompVciLookupErrors	Counter32
	}

hdcompIndex OBJECT-TYPE
	SYNTAX  Integer32
	MAX-ACCESS  not-accessible
	STATUS  current
	DESCRIPTION
	       "Index of the HDCOMP on the switch."
	::= { hdcompEntry 1 }

hdcompDescr OBJECT-TYPE
	SYNTAX  DisplayString (SIZE (0..5))
	MAX-ACCESS  read-only
	STATUS  current
	DESCRIPTION
		"Description of the HDCOMP location on the switch."
	::= { hdcompEntry 2 }

hdcompAsicVersion OBJECT-TYPE
	SYNTAX  Integer32
	MAX-ACCESS  read-only
	STATUS  current
	DESCRIPTION
		"Version number of the HDCOMP ASIC on the switch."
	::= { hdcompEntry 3 }

hdcompVpiLookupErrors OBJECT-TYPE
	SYNTAX	Counter32
	MAX-ACCESS	read-only
	STATUS	current
	DESCRIPTION
		"The number of VPI lookup errors."
	::= { hdcompEntry 4 }

hdcompVciLookupErrors OBJECT-TYPE
	SYNTAX	Counter32
	MAX-ACCESS	read-only
	STATUS	current
	DESCRIPTION
		"The number of VCI lookup errors."
	::= { hdcompEntry 5 }

------------------------------------------------------------------------
-- The Environment Group

-- Implementation of this group is mandatory
-- for all ForeRunner switches that implement
-- software access to environment state.

------------------------------------------------------------------------
-- The Switch Alarm Group

swAlarmTable OBJECT-TYPE
	SYNTAX	SEQUENCE OF SwAlarmEntry
	MAX-ACCESS	not-accessible
	STATUS	current
	DESCRIPTION
		"A table of switch alarm definitions and configuration."
	::= { alarmGroup 1 }

swAlarmEntry OBJECT-TYPE
	SYNTAX	SwAlarmEntry
	MAX-ACCESS	not-accessible
	STATUS	current
	DESCRIPTION
		"A table entry containing switch alarm definitions."
	INDEX	{ swAlarmType }
	::= { swAlarmTable 1 }

SwAlarmEntry ::=
	SEQUENCE {
		swAlarmType		INTEGER,
		swAlarmStatus		INTEGER,
		swAlarmMinorCategory	INTEGER,
		swAlarmMajorCategory	INTEGER,
		swAlarmReset		INTEGER,
                swAlarmCriticalCategory INTEGER,
		swAlarmACOState		INTEGER
	}

swAlarmType OBJECT-TYPE
	SYNTAX INTEGER {
			powerSupplyInputFailed(1),
			powerSupplyOutputFailed(2),
			fanBankFailed(3),
			tempSensorOverTemp(4),
			linkFailed(5),
			spansFailed(6),
			powerSupplyOverCurrent(7),
			powerSupply5VoltFailed(8),
			netmodRemovedHighPrio(9),
			netmodRemovedLowPrio(10),
			fabricRemoved(11),
			genPortFailure(12),
                        singleTimingRefFailed(13),
                        allTimingRefsFailed(14),
                        singleTCMFailed(15),
                        allTCMsFailed(16)
		}
	MAX-ACCESS	read-only
	STATUS	current
	DESCRIPTION
		"The type of the alarm."
	::= { swAlarmEntry 1 }

swAlarmStatus OBJECT-TYPE
	SYNTAX	INTEGER {
			active(1),
			inactive(2)
		}
	MAX-ACCESS	read-only
	STATUS	current
	DESCRIPTION
		"The status of this alarm entry. An alarm becomes
		active if the underlying condition is detected.
		For power supplies, the input failed alarm condition
		is asserted if the input voltage is not within
		the nominal range for the supply. This does not
		necessarily mean that an ouput failure will result.
		A power supply output failure condition is asserted
		if any power supply is failing or if it is physically
		removed. Power supply output alarms are only applicable
		to switches with multiple power supplies. Fan bank
		and temperature sensor failures are applicable only
		to switches with the appropriate sensing capabilities.
		Link and spans failures are applicable to all switches."
	::= { swAlarmEntry 2 }

swAlarmMinorCategory OBJECT-TYPE
	SYNTAX	INTEGER {
			enabled(1),
			disabled(2)
		}
	MAX-ACCESS	read-write
	STATUS	current
	DESCRIPTION
		"This object indicates whether a minor alarm is triggered
		when this event occurs."
	::= { swAlarmEntry 3 }

swAlarmMajorCategory OBJECT-TYPE
	SYNTAX	INTEGER {
			enabled(1),
			disabled(2)
		}
	MAX-ACCESS	read-write
	STATUS	current
	DESCRIPTION
		"This object indicates whether a major alarm is triggered
		when this event occurs."
	::= { swAlarmEntry 4 }

swAlarmReset OBJECT-TYPE
	SYNTAX INTEGER {
		default(0),
		enabled(1)
	       }
	MAX-ACCESS read-write
	STATUS current
	DESCRIPTION
		"The manager may set this to the value 0 or 1 to cancel
		 a current alarm. This is useful for silencing alarms
		 triggered via edge detection. If this variable is
		 readable, then the alarm is resettable."
	::= { swAlarmEntry 5 }

swAlarmCriticalCategory OBJECT-TYPE
        SYNTAX  INTEGER {
                        enabled(1),
                        disabled(2)
                }
        MAX-ACCESS  read-write
        STATUS  current
        DESCRIPTION
                "This object indicates whether a critical alarm is triggered
                when this event occurs. This is supported only on
		certain platforms."
        ::= { swAlarmEntry 6 }

swAlarmACOState OBJECT-TYPE
	SYNTAX	INTEGER {
			on(1),
			off(2)
		}
	MAX-ACCESS 	read-only
	STATUS	current
	DESCRIPTION
		"This object indicates the Alarm Cutoff Status(ACO) of
		this alarm entry. To silence an active alarm relay
		condition this value can be set to on(1), by pushing
		the front panel ACO button. The ACO is turned off when
		the alarm status(SwAlarmStatus) becomes inactive."
	::= { swAlarmEntry 7 }

------------------------------------------------------------------------

swAlarmMajorRelayState OBJECT-TYPE
	SYNTAX	INTEGER {
			on(1),
			off(2)
		}
	MAX-ACCESS	read-only
	STATUS	current
	DESCRIPTION
		"This object indicates the current state of the major alarm
		relay. If one or more of the alarms (swAlarmType) that are
		defined major (swAlarmMajorCategory) are currently active
		(swAlarmStatus), and the alarm cutoff(swAlarmACOState) is
		off then this object will be on(1)."
	::= { alarmGroup 2 }


swAlarmMinorRelayState OBJECT-TYPE
	SYNTAX	INTEGER {
			on(1),
			off(2)
		}
	MAX-ACCESS	read-only
	STATUS	current
	DESCRIPTION
		"This object indicates the current state of the minor alarm
		relay. If one or more of the alarms (swAlarmType) that are
		defined minor (swAlarmMinorCategory) are currently active
		(swAlarmStatus), and the alarm cutoff(swAlarmACOState)
		is off then this object will be on(1)."
	::= { alarmGroup 3 }

swAlarmCriticalRelayState OBJECT-TYPE
        SYNTAX  INTEGER {
                        on(1),
                        off(2)
                }
        MAX-ACCESS  read-only
        STATUS  current
        DESCRIPTION
                "This object indicates the current state of the
                critical alarm relay. If one or more of the alarms
                (swAlarmType) that are defined critical
                (swAlarmCriticalCategory) are currently active
                (swAlarmStatus), and the alarm cutoff(swAlarmACOState)
		is off then this object will be on(1)."
        ::= { alarmGroup 4 }

------------------------------------------------------------------------
swAlarmRelayTable  OBJECT-TYPE
        SYNTAX  SEQUENCE OF SwAlarmRelayEntry 
        MAX-ACCESS  not-accessible
        STATUS current
        DESCRIPTION
                "This table contains the alarm relay definitions for the 
                switch alarms"
        ::= { alarmGroup 5 }

swAlarmRelayEntry  OBJECT-TYPE
        SYNTAX  SwAlarmRelayEntry
        MAX-ACCESS  not-accessible
        STATUS  current
        DESCRIPTION
                "This entry contains the alarm relay definitions for the 
                switch alarms."
        INDEX   { swAlarmRelayIndex }
        ::= { swAlarmRelayTable 1 }

SwAlarmRelayEntry ::=
        SEQUENCE {
                swAlarmRelayIndex       Integer32,
                swAlarmRelayFunction    INTEGER,
                swAlarmRelayState       INTEGER,
                swAlarmRelayOperMode    INTEGER
        }

swAlarmRelayIndex  OBJECT-TYPE
        SYNTAX  Integer32
        MAX-ACCESS  read-only
        STATUS  current
        DESCRIPTION
                "This is the index of the alarm relay on the switch."
        ::= { swAlarmRelayEntry 1 }

swAlarmRelayFunction  OBJECT-TYPE
        SYNTAX  INTEGER {
                        swUnusedRelay(1),
                        swMajorAlarmRelay(2),
                        swMinorAlarmRelay(3),
                        swCriticalAlarmRelay(4)
                }
        MAX-ACCESS  read-write
        STATUS  current
        DESCRIPTION
                "This is the alarm function associated with an alarm
                relay on the switch. An alarm relay may either be 
                unused, assigned to one of critical, major and minor alarm."
        ::= { swAlarmRelayEntry 2 }

swAlarmRelayState  OBJECT-TYPE
        SYNTAX  INTEGER {
                        on(1),
                        off(2)
                }
        MAX-ACCESS  read-only
        STATUS  current
        DESCRIPTION
                "This is the current state of the alarm relay. The state 'on'
                means that the alarm relay is activated; the state 'off'
                means that it is deactivated."
        ::= { swAlarmRelayEntry 3 }


swAlarmRelayOperMode  OBJECT-TYPE
        SYNTAX  INTEGER {
                        enabled(1),
                        disabled(2),
                        test(3)
                }
        MAX-ACCESS  read-write
        STATUS  current
        DESCRIPTION
                "This variable represents the operational mode of the
                relay. The operational mode 'enabled' means that the 
                relay is under software control and the relay state
                will reflect 'on' or 'off' according to the alarm
                conditions. 'disabled'  will make the alarm relay
                state always 'off'. 'test' will make it always 'on'."

        ::= { swAlarmRelayEntry 4 }

---------------------------------------------------------------------------

-- The Power Supply Group

envMaxNumberOfPowerSupplies OBJECT-TYPE
	SYNTAX	Integer32
	MAX-ACCESS	read-only
	STATUS	current
	DESCRIPTION
		"The maximum number of power supplies that can be installed
		on this ATM switch."
	::= { powerGroup 1 }

envNumberOfPowerSupplies OBJECT-TYPE
	SYNTAX  Integer32
	MAX-ACCESS	read-only
	STATUS	current
	DESCRIPTION
		"The number of power supply entries in the power
		 supply table. This is the number of power supplies
		 actually present."
	::= { powerGroup 2 }

envPowerSupplyTable OBJECT-TYPE
	SYNTAX	SEQUENCE OF EnvPowerSupplyEntry
	MAX-ACCESS	not-accessible
	STATUS	current
	DESCRIPTION
		"A table of power supply information."
	::= { powerGroup 3 }

envPowerSupplyEntry OBJECT-TYPE
	SYNTAX	EnvPowerSupplyEntry
	MAX-ACCESS	not-accessible
	STATUS	current
	DESCRIPTION
		"A table entry containing power supply information."
	INDEX	{ envPowerSupplyIndex }
	::= { envPowerSupplyTable 1 }

EnvPowerSupplyEntry ::=
	SEQUENCE {
		envPowerSupplyIndex		Integer32,
		envPowerSupplyType		INTEGER,
		envPowerSupplyInputState	GeneralState,
		envPowerSupplyOutputState	GeneralState,
		envPowerSupplySerialNumber	Integer32,
		envPowerSupplyVersion		Integer32,
		envPowerSupplyCurrentState	GeneralState,
		envPowerSupply5VoltState	GeneralState
	}

envPowerSupplyIndex OBJECT-TYPE
	SYNTAX	Integer32
	MAX-ACCESS	read-only
	STATUS	current
	DESCRIPTION
		"The index of this power supply."
	::= { envPowerSupplyEntry 1 }

envPowerSupplyType OBJECT-TYPE
	SYNTAX	INTEGER {
			psUnknown(1),
			psAutoRangeAC(4),
			ps48VDC(5),
			psRM1000HA(6),
			ps30ADC(7),
			psRM1000HA-C(8)
		}
	MAX-ACCESS	read-only
	STATUS	current
	DESCRIPTION
		"The type of this power supply."
	::= { envPowerSupplyEntry 2 }

envPowerSupplyInputState OBJECT-TYPE
	SYNTAX	GeneralState
	MAX-ACCESS	read-only
	STATUS	current
	DESCRIPTION
		"The state of the input voltage to this power supply."
	::= { envPowerSupplyEntry 3 }

envPowerSupplyOutputState OBJECT-TYPE
	SYNTAX	GeneralState
	MAX-ACCESS	read-only
	STATUS	current
	DESCRIPTION
		"The status of the output of this power supply. In case
		there are several output supplies (like +5V, +12V, -12V)
		this object indicates the aggregate state of all outputs."
	::= { envPowerSupplyEntry 4 }

envPowerSupplySerialNumber OBJECT-TYPE
	SYNTAX	Integer32
	MAX-ACCESS	read-only
	STATUS	current
	DESCRIPTION
		"The serial number of this power supply, if available."
	::= { envPowerSupplyEntry 5 }

envPowerSupplyVersion OBJECT-TYPE
	SYNTAX	Integer32
	MAX-ACCESS	read-only
	STATUS	current
	DESCRIPTION
		"The version of this power supply, if available."
	::= { envPowerSupplyEntry 6 }

envPowerSupplyCurrentState OBJECT-TYPE
	SYNTAX	GeneralState
	MAX-ACCESS	read-only
	STATUS	current
	DESCRIPTION
		"The state of the current on the input return path
		of this power supply. Should be within 28A +/-2A."
	::= { envPowerSupplyEntry 7 }

envPowerSupply5VoltState OBJECT-TYPE
	SYNTAX	GeneralState
	MAX-ACCESS	read-only
	STATUS	current
	DESCRIPTION
		"The state of the +5V output of this power supply.
		Should be within tolerance of 5.0 +/-0.1VDC."
	::= { envPowerSupplyEntry 8 }


------------------------------------------------------------------------
-- The Fans Group

envNumberOfFanBanks OBJECT-TYPE
	SYNTAX	Integer32
	MAX-ACCESS	read-only
	STATUS	current
	DESCRIPTION
		"The number of fan banks on this ATM switch."
	::= { fansGroup 1 }

envFanBanksTable OBJECT-TYPE
	SYNTAX	SEQUENCE OF EnvFanBanksEntry
	MAX-ACCESS	not-accessible
	STATUS	current
	DESCRIPTION
		"A table of fan bank information."
	::= { fansGroup 2 }

envFanBanksEntry OBJECT-TYPE
	SYNTAX	EnvFanBanksEntry
	MAX-ACCESS	not-accessible
	STATUS	current
	DESCRIPTION
		"A table entry containing fan bank information."
	INDEX	{ envFanBankIndex }
	::= { envFanBanksTable 1 }

EnvFanBanksEntry ::=
	SEQUENCE {
		envFanBankIndex		Integer32,
		envFanBankState		GeneralState,
		envFanBankSerialNumber	DisplayString,
		envFanBankType		Integer32,
		envFanBankRevision	Integer32
	}

envFanBankIndex OBJECT-TYPE
	SYNTAX	Integer32
	MAX-ACCESS	read-only
	STATUS	current
	DESCRIPTION
		"The index of this fan bank."
	::= { envFanBanksEntry 1 }

envFanBankState OBJECT-TYPE
	SYNTAX	GeneralState
	MAX-ACCESS	read-only
	STATUS	current
	DESCRIPTION
		"The status of the fan bank."
	::= { envFanBanksEntry 3 }

envFanBankSerialNumber OBJECT-TYPE
	SYNTAX	DisplayString
	MAX-ACCESS	read-only
	STATUS	current
	DESCRIPTION
		"Serial number of the fan tray."
	::= { envFanBanksEntry 4 }

envFanBankType OBJECT-TYPE
	SYNTAX	Integer32
	MAX-ACCESS	read-only
	STATUS	current
	DESCRIPTION
		"The type of fan bank installed."
	::= { envFanBanksEntry 5 }

envFanBankRevision OBJECT-TYPE
	SYNTAX	Integer32
	MAX-ACCESS	read-only
	STATUS	current
	DESCRIPTION
		"The revision of the fan bank, as an ASCII character."
	::= { envFanBanksEntry 6 }

------------------------------------------------------------------------
-- The Temperature Sensors Group

-- Implementation of this group is mandatory
-- for all ForeRunner switches that implement
-- software access to temperature sensors information.

envNumberOfTempSensors OBJECT-TYPE
	SYNTAX	Integer32
	MAX-ACCESS	read-only
	STATUS	current
	DESCRIPTION
		"The number of temperature sensors
		installed on this ATM switch."
	::= { tempGroup 1 }

envTempSensorsTable OBJECT-TYPE
	SYNTAX	SEQUENCE OF EnvTempSensorsEntry
	MAX-ACCESS	not-accessible
	STATUS	current
	DESCRIPTION
		"A table of temperature sensors information."
	::= { tempGroup 2 }

envTempSensorsEntry OBJECT-TYPE
	SYNTAX	EnvTempSensorsEntry
	MAX-ACCESS	not-accessible
	STATUS	current
	DESCRIPTION
		"A table entry containing temperature sensor information."
	INDEX	{ envTempSensorIndex }
	::= { envTempSensorsTable 1 }

EnvTempSensorsEntry ::=
	SEQUENCE {
		envTempSensorIndex		INTEGER,
		envTempSensorState		INTEGER
	}

envTempSensorIndex OBJECT-TYPE
	SYNTAX	INTEGER {
			enclosure(1),
			power-supply-1(2),
			power-supply-2(3),
			power-supply-3(4),
			power-supply-4(5),
			power-supply-5(6)
		}
	MAX-ACCESS	read-only
	STATUS	current
	DESCRIPTION
		"The index of this temperature sensor. The value of
		 the index provides an indication of the location
		 and function of the temperature sensor. The set
		 of temperature sensors may vary by switch type."
	::= { envTempSensorsEntry 1 }

envTempSensorState OBJECT-TYPE
	SYNTAX	INTEGER {
			normal(1),
			overTemp(2)
		}
	MAX-ACCESS	read-only
	STATUS	current
	DESCRIPTION
		"The temperature state of this sensor."
	::= { envTempSensorsEntry 2 }


------------------------------------------------------------------------
-- The CPU Group

-- Implementation of this group is mandatory
-- for all ForeRunner switches that implement
-- software access to CPU state information.

envMaxNumberOfCPUs OBJECT-TYPE
	SYNTAX	Integer32
	MAX-ACCESS	read-only
	STATUS	current
	DESCRIPTION
		"The maximum number of CPUs that can be installed on
		this ATM switch."
	::= { cpuGroup 1 }

envNumberOfCPUs OBJECT-TYPE
	SYNTAX	Integer32
	MAX-ACCESS	read-only
	STATUS	current
	DESCRIPTION
		"The number entries in the CPU table."
	::= { cpuGroup 2 }

envCPUsTable OBJECT-TYPE
	SYNTAX	SEQUENCE OF EnvCPUsEntry
	MAX-ACCESS	not-accessible
	STATUS	current
	DESCRIPTION
		"A table of CPU information."
	::= { cpuGroup 3 }

envCPUsEntry OBJECT-TYPE
	SYNTAX	EnvCPUsEntry
	MAX-ACCESS	not-accessible
	STATUS	current
	DESCRIPTION
		"A table entry containing CPU information."
	INDEX	{ envCpuBoard, envCpuSlot }
	::= { envCPUsTable 1 }

EnvCPUsEntry ::=
	SEQUENCE {
		envCpuBoard		Integer32,
		envCpuSlot		Integer32,
		envCpuType		INTEGER,
		envCPUState		INTEGER,
		envCpuDRAMSize		Integer32,
		envCpuRevLevel		Integer32,
		envCpuFlashSize		Integer32,
		envCpuBoardRevision	Integer32,
		envCpuPromRevision	Integer32,
		envCpuMACAddress        PhysAddress,
		envCpuSerialNumber	DisplayString,
		envCpuProductPartNumber	DisplayString,
		envCpuCLEI		DisplayString,
                envCpuIDESize           Integer32
	}

envCpuBoard OBJECT-TYPE
	SYNTAX	Integer32
	MAX-ACCESS	read-only
	STATUS	current
	DESCRIPTION
		"The board index of this CPU."
	::= { envCPUsEntry 1 }

envCpuSlot OBJECT-TYPE
	SYNTAX	Integer32
	MAX-ACCESS	read-only
	STATUS	current
	DESCRIPTION
		"The slot index of this CPU."
	::= { envCPUsEntry 2 }

envCpuType OBJECT-TYPE
	SYNTAX	INTEGER {
			other(1),
			sun4e(2),
			sun4c(3),
			sparc(4),
			i960ca(5),
			i960cf(6),
			i960ha(7),
			i960hd(8),
			p55(9),
			p6(10),
			cpv5000(11),
			p266(12),
			p200(13)
		}
	MAX-ACCESS	read-only
	STATUS	current
	DESCRIPTION
		"The type of this CPU.  The i960 processor further can
		 be of three types - ca, cf and ha."
	::= { envCPUsEntry 3 }

envCPUState OBJECT-TYPE
	SYNTAX	INTEGER {
			normal(1),
			fail(2),
			standby(3),
			boot(4)
		}
	MAX-ACCESS	read-only
	STATUS	current
	DESCRIPTION
		"The state of the processor."
	::= { envCPUsEntry 4 }

envCpuDRAMSize OBJECT-TYPE
	SYNTAX	Integer32
	MAX-ACCESS	read-only
	STATUS	current
	DESCRIPTION
		"The size of the DRAM in bytes installed on the SCP."
	::= { envCPUsEntry 5 }

envCpuRevLevel OBJECT-TYPE
	SYNTAX	Integer32
	MAX-ACCESS	read-only
	STATUS	current
	DESCRIPTION
		"The revision level of the processor."
	::= { envCPUsEntry 6 }

envCpuFlashSize OBJECT-TYPE
	SYNTAX	Integer32
	MAX-ACCESS	read-only
	STATUS	current
	DESCRIPTION
		"Size of Flash in bytes installed on this SCP board."
	::= { envCPUsEntry 7 }

envCpuBoardRevision OBJECT-TYPE
	SYNTAX	Integer32
	MAX-ACCESS  read-only
	STATUS	current
	DESCRIPTION
		"Revision number of this SCP board. A 32-bit number
	with the most significant 16 bits represent the revison
	alphabet. For example, 0x20000 represents Rev B, 0xd0000
	represents Rev M."
	::= { envCPUsEntry 8 }

envCpuPromRevision OBJECT-TYPE
	SYNTAX	Integer32
	MAX-ACCESS	read-only
	STATUS	current
	DESCRIPTION
		"Revision number of the SCP PROM. Currently only
	available for boards with i960HA and i960HD processors. A
	32-bit number. For example, 0x20000 represents Rev 2.0 and
	0x20001 represents Rev 2.1"
	::= { envCPUsEntry 9 }

envCpuMACAddress OBJECT-TYPE
	SYNTAX  PhysAddress
	MAX-ACCESS  read-only
	STATUS  current
	DESCRIPTION
		"MAC address of ethernet chip on the SCP board."
	::= { envCPUsEntry 10 }

envCpuSerialNumber OBJECT-TYPE
	SYNTAX  DisplayString
	MAX-ACCESS  read-only
	STATUS  current
	DESCRIPTION
		"Serial number of the SCP card.  This gives the SCPIM
	serial number on an ASX-4000."
	::= { envCPUsEntry 11 }

envCpuProductPartNumber OBJECT-TYPE
	SYNTAX  DisplayString
	MAX-ACCESS  read-only
	STATUS  current
	DESCRIPTION
		"Product part number of the SCE.  This gives the marketing
	product part number of RASCAL."
	::= { envCPUsEntry 12 }

envCpuCLEI OBJECT-TYPE
        SYNTAX  DisplayString
        MAX-ACCESS  read-only
        STATUS  current
        DESCRIPTION
                "The Common Language Equipment Identification (CLEI)
                 of this SCP."
        ::= { envCPUsEntry 13 }

envCpuIDESize OBJECT-TYPE
        SYNTAX  Integer32
        MAX-ACCESS  read-only
        STATUS  current
        DESCRIPTION
                "Size of IDE disk in bytes installed on this SCP board."
        ::= { envCPUsEntry 14 }

------------------------------------------------------------------------
-- The Mgmt Group
-- This group provides information about the management station
-- board, on those switches with management station support, or the
-- backplane, on ASX-4000 and other systems with a backplane ID card.

envMgmtBoardType OBJECT-TYPE
	SYNTAX	Integer32
	MAX-ACCESS	read-only
	STATUS	current
	DESCRIPTION
		"The board type of the management station or backplane."
	::= { mgmtGroup 1 }

envMgmtBoardRevision OBJECT-TYPE
	SYNTAX	Integer32
	MAX-ACCESS	read-only
	STATUS	current
	DESCRIPTION
		"The board revision number of the management station
		 or backplane."
	::= { mgmtGroup 2 }

envMgmtBoardSerialNumber OBJECT-TYPE
	SYNTAX	Integer32
	MAX-ACCESS	read-only
	STATUS	current
	DESCRIPTION
		"The serial number of the management station or backplane."
	::= { mgmtGroup 3 }

------------------------------------------------------------------------
-- Fabric Group
-- This group provides environmental information about individual
-- switch fabrics. This may or may not be supported on all switches.

envFabricAlarmTripTemperature OBJECT-TYPE
	SYNTAX  Integer32
	MAX-ACCESS	read-write
	STATUS  current
	DESCRIPTION
		"The temperature threshold in degrees C at which a
		 fabric temperature alarm will be raised."
	::= {fabricGroup 1}

envFabricAlarmResetTemperature OBJECT-TYPE
	SYNTAX  Integer32
	MAX-ACCESS	read-write
	STATUS	current
	DESCRIPTION
		"The temperature in degrees C at which a fabric
		 temperature alarm will be cancelled."
	::= {fabricGroup 2}

envFabricTable OBJECT-TYPE
	SYNTAX	SEQUENCE OF EnvFabricEntry
	MAX-ACCESS	not-accessible
	STATUS	current
	DESCRIPTION
		"A table of fabric environmental information"
	::= { fabricGroup 3 }

envFabricEntry OBJECT-TYPE
	SYNTAX	EnvFabricEntry
	MAX-ACCESS	not-accessible
	STATUS	current
	DESCRIPTION
		"A table containing fabric environmental information"
	INDEX	{ envFabricIndex }
	::= { envFabricTable 1 }

EnvFabricEntry ::=
	SEQUENCE {
		envFabricIndex			Integer32,
		envFabricTemperature		Integer32,
		envFabricTemperatureState	INTEGER
	}

envFabricIndex OBJECT-TYPE
	SYNTAX	Integer32
	MAX-ACCESS	read-only
	STATUS	current
	DESCRIPTION
		"The index of the fabric"
	::= { envFabricEntry 1 }

envFabricTemperature OBJECT-TYPE
	SYNTAX	Integer32
	MAX-ACCESS	read-only
	STATUS	current
	DESCRIPTION
		"The temperature measured at the fabric, in degrees C"
	::= { envFabricEntry 2 }

envFabricTemperatureState OBJECT-TYPE
	SYNTAX	INTEGER {
			normal(1),
			overTemp(2)
		}
	MAX-ACCESS	read-only
	STATUS	current
	DESCRIPTION
		"The software state of this fabric temperature
		 sensor. This will indicate `normal' until the
		 sensor temperature reaches the current trip
		 threshold. It will then indicate `overTemp'
		 until the temperature reaches the current reset
		 threshold (or until the switch fabric is restarted)."
	::= { envFabricEntry 3}

------------------------------------------------------------------------
-- The Distributed Timing Group

-- Implementation of this table is mandatory for all hardware
-- that support distributed timing.

netmodTimingTable OBJECT-TYPE
	SYNTAX	SEQUENCE OF NetmodTimingEntry
	MAX-ACCESS	not-accessible
	STATUS	obsolete
	DESCRIPTION
		"This table is deprecated as the advanced timing options
		 are removed."
	::= { netmodTimingGroup 1 }

netmodTimingEntry OBJECT-TYPE
	SYNTAX	NetmodTimingEntry
	MAX-ACCESS	not-accessible
	STATUS	obsolete
	DESCRIPTION
		"A table entry containing network modeul timing information."
	INDEX	{ ntBoard, ntModule }
	::= { netmodTimingTable 1 }

NetmodTimingEntry ::=
	SEQUENCE {
		ntBoard				Integer32,
		ntModule			Integer32,
		ntPrimaryRecoveredClock		Integer32,
		ntSecondaryRecoveredClock	Integer32,
		ntPrimaryExportClock		INTEGER,
		ntSecondaryExportClock		INTEGER,
		ntGlobalClock			INTEGER,
		ntExportClockOperStatus		INTEGER,
		ntPrimaryImportClock		INTEGER,
		ntSecondaryImportClock		INTEGER,
		ntImportClockOperStatus		INTEGER
	}

ntBoard OBJECT-TYPE
	SYNTAX	Integer32
	MAX-ACCESS	read-only
	STATUS	obsolete
	DESCRIPTION
		"The index of this board within the ATM switch."
	::= { netmodTimingEntry 1 }

ntModule OBJECT-TYPE
	SYNTAX	Integer32
	MAX-ACCESS	read-only
	STATUS	obsolete
	DESCRIPTION
		"The number of this network module within the switch board."
	::= { netmodTimingEntry 2 }

ntPrimaryRecoveredClock OBJECT-TYPE
	SYNTAX	Integer32
	MAX-ACCESS	read-write
	STATUS	obsolete
	DESCRIPTION
		"The port number on this network module that provides the
		primary 8KHz reference clock from its received signal."
	::= { netmodTimingEntry 3 }

ntSecondaryRecoveredClock OBJECT-TYPE
	SYNTAX	Integer32
	MAX-ACCESS	read-write
	STATUS	obsolete
	DESCRIPTION
		"The port number on this network module that provides the
		secondary 8KHz reference clock from its received signal."
	::= { netmodTimingEntry 4 }

ntPrimaryExportClock OBJECT-TYPE
	SYNTAX	INTEGER {
			primaryRecoveredClock(1),
			crystalClock(2),
			noClock(3)
		}
	MAX-ACCESS	read-write
	STATUS	obsolete
	DESCRIPTION
		"The primary 8KHz clock exported by this network module.
		The exported clock may be used as the network module global
		clock, which in turn, may be used by all ports that link their
		transmit clock to the network module global clock. The noClock
		option is valid only for tp25 (25mb) netmods."
	::= { netmodTimingEntry 5 }

ntSecondaryExportClock OBJECT-TYPE
	SYNTAX	INTEGER {
			secondaryRecoveredClock(1),
			crystalClock(2),
			noClock(3)
		}
	MAX-ACCESS	read-write
	STATUS	obsolete
	DESCRIPTION
		"The secondary 8KHz clock exported by this network module.
		The exported clock may be used as the network module global
		clock. The secondary exported clock will be used if the
		primary exported clock is not available. The noClock option
		is valid only for tp25 (25mb) netmods."
	::= { netmodTimingEntry 6 }

ntGlobalClock OBJECT-TYPE
	SYNTAX	INTEGER {
			exportClock(1),
			importClock(2)
		}
	MAX-ACCESS	read-write
	STATUS	obsolete
	DESCRIPTION
		"The global 8KHz clock that is available to every port on this
		network module, when the port links its trasnmit clock to the
		network module global clock."
	::= { netmodTimingEntry 7 }

ntExportClockOperStatus OBJECT-TYPE
	SYNTAX  INTEGER {
			primaryClock(1),
			secondaryClock(2),
			crystalClock(3)
		}
	MAX-ACCESS  read-only
	STATUS  obsolete
	DESCRIPTION
		"The currently active 8KHz clock configuration. The tertiaryClock(3)
		is determined by the switch control software if both the primary
		and secondary clocks are not available."
	::= { netmodTimingEntry 8 }

ntPrimaryImportClock OBJECT-TYPE
	SYNTAX	INTEGER {
			netmodAExportClock(1),
			netmodBExportClock(2),
			netmodCExportClock(3),
			netmodDExportClock(4),
			board1PrimaryClock(5),
			board2PrimaryClock(6),
			board3PrimaryClock(7),
			board4PrimaryClock(8),
			managementStationClock(9)
		}
	MAX-ACCESS	read-write
	STATUS	obsolete
	DESCRIPTION
		"The primary 8kHz clock imported by this network module.
		The imported clock may be used as the network module global
		clock, which in turn, may be used by all ports that link their
		transmit clock to the network module global clock."
	::= { netmodTimingEntry 9 }

ntSecondaryImportClock OBJECT-TYPE
	SYNTAX	INTEGER {
			netmodAExportClock(1),
			netmodBExportClock(2),
			netmodCExportClock(3),
			netmodDExportClock(4),
			board1PrimaryClock(5),
			board2PrimaryClock(6),
			board3PrimaryClock(7),
			board4PrimaryClock(8),
			managementStationClock(9)
		}
	MAX-ACCESS	read-write
	STATUS	obsolete
	DESCRIPTION
		"The secondary 8kHz clock imported by this network module.
		The imported clock may be used as the network module global
		clock. The secondary imported clock will be used if the
		primary imported clock is not available."
	::= { netmodTimingEntry 10 }


ntImportClockOperStatus OBJECT-TYPE
	SYNTAX  INTEGER {
			primaryClock(1),
			secondaryClock(2),
			netmodExportClock(3)
		}
	MAX-ACCESS  read-only
	STATUS  obsolete
	DESCRIPTION
		"The currently active 8kHz import clock configuration. The
		tertiaryClock(3) is determined by the switch control software
		if both the primary and secondary clocks are not available."
	::= { netmodTimingEntry 11 }

----------------------------------------------------------------------------
--
-- The board bit is distributed timing added 06 June 1996 after no
-- deliberation whatsoever
--

boardTimingTable OBJECT-TYPE
	SYNTAX	SEQUENCE OF BoardTimingEntry
	MAX-ACCESS	not-accessible
	STATUS	obsolete
	DESCRIPTION
		"This table is deprecated as the advanced timing options
		 are removed."
	::= { boardTimingGroup 1 }

boardTimingEntry OBJECT-TYPE
	SYNTAX	BoardTimingEntry
	MAX-ACCESS	not-accessible
	STATUS	obsolete
	DESCRIPTION
		"A table entry containing switch board timing information."
	INDEX	{ btBoard }
	::= { boardTimingTable 1 }

BoardTimingEntry ::=
	SEQUENCE {
		btBoard				Integer32,
		btPrimaryClock			INTEGER,
		btSecondaryClock		INTEGER,
		btPrimaryClockOperStatus	INTEGER,
		btSecondaryClockOperStatus	INTEGER
	}

btBoard OBJECT-TYPE
	SYNTAX	Integer32
	MAX-ACCESS	read-only
	STATUS	obsolete
	DESCRIPTION
		"The index of this board within the ATM switch."
	::= { boardTimingEntry 1 }

btPrimaryClock OBJECT-TYPE
	SYNTAX	INTEGER {
			netmodAExportClock(1),
			netmodBExportClock(2),
			netmodCExportClock(3),
			netmodDExportClock(4),
			netmodNone(5)
		}
	MAX-ACCESS	read-write
	STATUS	obsolete
	DESCRIPTION
		"The source of the primary 8kHz clock for this board. The
		clock may be used by each network module in the switch as
		the network module import clock. The clock may also be used
		by the management station as the primary or secondary source
		of the Stratum 3E clock."
	::= { boardTimingEntry 2 }

btSecondaryClock OBJECT-TYPE
	SYNTAX	INTEGER {
			netmodAExportClock(1),
			netmodBExportClock(2),
			netmodCExportClock(3),
			netmodDExportClock(4),
			netmodNone(5)
		}
	MAX-ACCESS	read-write
	STATUS	obsolete
	DESCRIPTION
		"The source of the secondary 8kHz clock. The clock may be
		used by the management station as the primary or secondary
		source of the Stratum 3E clock."
	::= { boardTimingEntry 3 }

btPrimaryClockOperStatus OBJECT-TYPE
	SYNTAX  INTEGER {
			clockUp(1),
			clockDown(2)
		}
	MAX-ACCESS  read-only
	STATUS  obsolete
	DESCRIPTION
		"The current state of the 8kHz primary clock."
	::= { boardTimingEntry 4 }

btSecondaryClockOperStatus OBJECT-TYPE
	SYNTAX  INTEGER {
			clockUp(1),
			clockDown(2)
		}
	MAX-ACCESS  read-only
	STATUS  obsolete
	DESCRIPTION
		"The current state of the 8kHz secondary clock."
	::= { boardTimingEntry 5 }

------------------------------------------------------------------------
-- The Series-C Shared Memory Group

-- Implementation of this group is mandatory for all hardware
-- that support shared memory network modules.

shmemConfTable OBJECT-TYPE
	SYNTAX	SEQUENCE OF ShmemConfEntry
	MAX-ACCESS	not-accessible
	STATUS	current
	DESCRIPTION
		"A table for shared memory network modules configuration.
		Implementation of this table is mandatory if at least
		one of the network modules' hardware is based on shared
		memory. The user should walk this table and select the
		shared memory configuration that suits his/her needs.
		The selection is done in the specific network module
		shared memory configuration entry (netmodShmemTable)."
	::= { netmodShmemGroup 1 }

shmemConfEntry OBJECT-TYPE
	SYNTAX	ShmemConfEntry
	MAX-ACCESS	not-accessible
	STATUS	current
	DESCRIPTION
		"A table entry containing shared memory network module
		configuration information."
	INDEX	{ shmemConfIndex }
	::= { shmemConfTable 1 }

ShmemConfEntry ::=
	SEQUENCE {
		shmemConfIndex		Integer32,
		shmemUcastConnections	Integer32,
		shmemMcastConnections	Integer32,
		shmemVpiVciLists	Integer32,
		shmemCellsBuffers	Integer32,
		shmemConfName		DisplayString,
		shmemMemorySize		Integer32
	}

shmemConfIndex OBJECT-TYPE
	SYNTAX	Integer32
	MAX-ACCESS	read-only
	STATUS	current
	DESCRIPTION
		"The index of this shared memory configuration."
	::= { shmemConfEntry 1 }

shmemUcastConnections OBJECT-TYPE
	SYNTAX	Integer32
	MAX-ACCESS	read-only
	STATUS	current
	DESCRIPTION
		"The maximum number of unicast connections that is
		supported by this shared memory configuration."
	::= { shmemConfEntry 2 }

shmemMcastConnections OBJECT-TYPE
	SYNTAX	Integer32
	MAX-ACCESS	read-only
	STATUS	current
	DESCRIPTION
		"The maximum number of multicast connections that is
		supported by this shared memory configuration."
	::= { shmemConfEntry 3 }

shmemVpiVciLists OBJECT-TYPE
	SYNTAX	Integer32
	MAX-ACCESS	read-only
	STATUS	current
	DESCRIPTION
		"The memory allocated for VPI/VCI lists (which is used
		for multicast connections) by this shared memory
		configuration."
	::= { shmemConfEntry 4 }

shmemCellsBuffers OBJECT-TYPE
	SYNTAX	Integer32
	MAX-ACCESS	read-only
	STATUS	current
	DESCRIPTION
		"The number of cells buffers that is supported by
		this shared memory configuration."
	::= { shmemConfEntry 5 }

shmemConfName OBJECT-TYPE
	SYNTAX	DisplayString
	MAX-ACCESS	read-only
	STATUS	current
	DESCRIPTION
		"The name of this shared memory configuration."
	::= { shmemConfEntry 6 }

shmemMemorySize OBJECT-TYPE
	SYNTAX	Integer32
	MAX-ACCESS	read-only
	STATUS	current
	DESCRIPTION
		"The size of this shared memory configuration in units of
		48 bit words (x48)."
	::= { shmemConfEntry 7 }

------------------------------------------------------------------------

netmodShmemTable OBJECT-TYPE
	SYNTAX	SEQUENCE OF NetmodShmemEntry
	MAX-ACCESS	not-accessible
	STATUS	current
	DESCRIPTION
		"A table for shared memory network modules configuration.
		Implementation of this table is mandatory if the network
		module hardware is based on shared memory."
	::= { netmodShmemGroup 2 }

netmodShmemEntry OBJECT-TYPE
	SYNTAX	NetmodShmemEntry
	MAX-ACCESS	not-accessible
	STATUS	current
	DESCRIPTION
		"A table entry containing shared memory network module
		configuration information."
	INDEX	{ nshmemBoard, nshmemModule }
	::= { netmodShmemTable 1 }

NetmodShmemEntry ::=
	SEQUENCE {
		nshmemBoard				Integer32,
		nshmemModule				Integer32,
		nshmemConfRow				Integer32,
		nshmemConfSharedMemory			Integer32,
		nshmemCurrentUcastConnections		Gauge32,
		nshmemCurrentMcastConnections		Gauge32,
		nshmemCurrentVpiVciLists		Gauge32,
		nshmemCurrentCellsBuffers		Gauge32,
		nshmemCurrentSharedMemory		Gauge32,
		nshmemConfAal5PacketDrop		Integer32,
		nshmemAssertXACPT			INTEGER,
		nshmemMemorySize			Integer32
	}

nshmemBoard OBJECT-TYPE
	SYNTAX	Integer32
	MAX-ACCESS	read-only
	STATUS	current
	DESCRIPTION
		"The index of this board within the ATM switch."
	::= { netmodShmemEntry 1 }

nshmemModule OBJECT-TYPE
	SYNTAX	Integer32
	MAX-ACCESS	read-only
	STATUS	current
	DESCRIPTION
		"The number of this network module within the switch board."
	::= { netmodShmemEntry 2 }

nshmemConfRow OBJECT-TYPE
	SYNTAX	Integer32
	MAX-ACCESS	read-write
	STATUS	current
	DESCRIPTION
		"This object identify the row in the shared memory
		configuration table that was selected for this network
		module."
	::= { netmodShmemEntry 3 }

nshmemConfSharedMemory OBJECT-TYPE
	SYNTAX	Integer32
	MAX-ACCESS	read-only
	STATUS	current
	DESCRIPTION
		"The amount of memory that was configured for this
		network module given all the user requirements as
		specified in the selected shared memory configuration
		row."
	::= { netmodShmemEntry 4 }

nshmemCurrentUcastConnections OBJECT-TYPE
	SYNTAX	Gauge32
	MAX-ACCESS	read-only
	STATUS	current
	DESCRIPTION
		"The current number of unicast connections active
		on this shared memory network module."
	::= { netmodShmemEntry 5 }

nshmemCurrentMcastConnections OBJECT-TYPE
	SYNTAX	Gauge32
	MAX-ACCESS	read-only
	STATUS	current
	DESCRIPTION
		"The current number of multicast connections active
		on this shared memory network module."
	::= { netmodShmemEntry 6 }

nshmemCurrentVpiVciLists OBJECT-TYPE
	SYNTAX	Gauge32
	MAX-ACCESS	read-only
	STATUS	current
	DESCRIPTION
		"The current number of VPI/VCI lists active
		on this shared memory network module."
	::= { netmodShmemEntry 7 }

nshmemCurrentCellsBuffers OBJECT-TYPE
	SYNTAX	Gauge32
	MAX-ACCESS	read-only
	STATUS	current
	DESCRIPTION
		"The current number cells buffers active
		on this shared memory network module."
	::= { netmodShmemEntry 8 }

nshmemCurrentSharedMemory OBJECT-TYPE
	SYNTAX	Gauge32
	MAX-ACCESS	read-only
	STATUS	current
	DESCRIPTION
		"The current value of the used shared memory
		on this network module."
	::= { netmodShmemEntry 9 }

nshmemConfAal5PacketDrop OBJECT-TYPE
	SYNTAX	Integer32
	MAX-ACCESS	read-write
	STATUS	current
	DESCRIPTION
		"The AAL5 packet drop threshold in percentage of cells.
		The switch software provides a reasonable default,
		however, the user may wish to change this value
		according to the type of traffic and size of packets
		being transmitted on the network."
	::= { netmodShmemEntry 10 }

nshmemAssertXACPT OBJECT-TYPE
	SYNTAX INTEGER {
		clearXACPT (1),
		assertXACPT (2)
		}
	MAX-ACCESS  read-write
	STATUS  current
	DESCRIPTION
		"This variable establishes the setting fo the XACPT bit
		 in the fs200sm main control register (section 3.1).
		 This bit determines whether the signal XACPT is
		 asserted whenever the shared memory is full.  XACPT
		 prevents the switch from sending cells to the network
		 module.  This bit takes advantage of any buffers on the
		 switch to reduce cell loss, but it should not be used
		 if guaranteed cell delay is being provided to high
		 priority cells."
	::= { netmodShmemEntry 11 }

nshmemMemorySize OBJECT-TYPE
	SYNTAX	Integer32
	MAX-ACCESS	read-only
	STATUS	current
	DESCRIPTION
		"The size of this Series-C network module's shared memory
		in units of 48 bit words (x48)."
	::= { netmodShmemEntry 12 }

------------------------------------------------------------------------

portShmemConfTable OBJECT-TYPE
	SYNTAX	SEQUENCE OF PortShmemConfEntry
	MAX-ACCESS	not-accessible
	STATUS	current
	DESCRIPTION
		"A table for shared memory network modules configuration
		that is specified on a port basis. Implementation of this
		table is mandatory if the network module hardware is based
		on shared memory."
	::= { portShmemGroup 1 }

portShmemConfEntry OBJECT-TYPE
	SYNTAX	PortShmemConfEntry
	MAX-ACCESS	not-accessible
	STATUS	current
	DESCRIPTION
		"A table entry containing port configuration information
		for shared memory network modules."
	INDEX	{ pshmemConfBoard, pshmemConfModule, pshmemConfPort  }
	::= { portShmemConfTable 1 }

PortShmemConfEntry ::=
	SEQUENCE {
		pshmemConfBoard		Integer32,
		pshmemConfModule	Integer32,
		pshmemConfPort		Integer32,
		pshmemMaxCDVforCBR	Integer32,
		pshmemMaxCDVforVBR	Integer32,
		pshmemQsizeforABR	Integer32,
		pshmemEfciOnABR		Integer32,
		pshmemEfciOffABR	Integer32,
		pshmemQsizeforCBR	Integer32,
		pshmemQsizeforVBR	Integer32,
		pshmemClpThreshforCBR	Integer32,
		pshmemClpThreshforVBR	Integer32,
		pshmemClpThreshforABR	Integer32,
		pShmemAtmInterfaceIndex Integer32
	}

pshmemConfBoard OBJECT-TYPE
	SYNTAX	Integer32
	MAX-ACCESS	read-only
	STATUS	current
	DESCRIPTION
		"The index of this board within the ATM switch."
	::= { portShmemConfEntry 1 }

pshmemConfModule OBJECT-TYPE
	SYNTAX	Integer32
	MAX-ACCESS	read-only
	STATUS	current
	DESCRIPTION
		"The number of this network module within the switch board."
	::= { portShmemConfEntry 2 }

pshmemConfPort OBJECT-TYPE
	SYNTAX	Integer32
	MAX-ACCESS	read-only
	STATUS	current
	DESCRIPTION
		"The number of this port within the switch board and
		network module."
	::= { portShmemConfEntry 3 }

pshmemMaxCDVforCBR OBJECT-TYPE
	SYNTAX	Integer32
	MAX-ACCESS	read-write
	STATUS	current
	DESCRIPTION
		"The maximum transmitting CDV (Cell Delay Variation) in
		microseconds for CBR (Constant Bit Rate) / rtVBR (Real-Time
		Variable Bit Rate) traffic."
	::= { portShmemConfEntry 4 }

pshmemMaxCDVforVBR OBJECT-TYPE
	SYNTAX	Integer32
	MAX-ACCESS	read-write
	STATUS	current
	DESCRIPTION
		"The maximum transmitting CDV (Cell Delay Variation) in
		microseconds for nrtVBR (Non-Real-Time Variable Bit Rate)
		traffic."
	::= { portShmemConfEntry 5 }

pshmemQsizeforABR OBJECT-TYPE
	SYNTAX	Integer32
	MAX-ACCESS	read-write
	STATUS	current
	DESCRIPTION
		"The dedicated queue size in cells for ABR (Available
		Bit Rate) traffic."
	::= { portShmemConfEntry 6 }

pshmemEfciOnABR OBJECT-TYPE
	SYNTAX	Integer32
	MAX-ACCESS	read-write
	STATUS	current
	DESCRIPTION
		"The treshold on which the EFCI (Explicit Forward Congestion
		Indication) bit is turned on for ABR (Available Bit Rate) and
		UBR (Unspecified Bit Rate) traffic."
	::= { portShmemConfEntry 7 }

pshmemEfciOffABR OBJECT-TYPE
	SYNTAX	Integer32
	MAX-ACCESS	read-write
	STATUS	current
	DESCRIPTION
		"The treshold on which the EFCI (Explicit Forward Congestion
		Indication) bit is turned off for ABR (Available Bit Rate) and
		UBR (Unspecified Bit Rate) traffic."
	::= { portShmemConfEntry 8 }

pshmemQsizeforCBR OBJECT-TYPE
	SYNTAX	Integer32
	MAX-ACCESS	read-write
	STATUS	current
	DESCRIPTION
		"The dedicated queue size in cells for CBR (Constant
		Bit Rate) / rtVBR (Real-Time Variable Bit Rate) traffic."
	::= { portShmemConfEntry 9 }

pshmemQsizeforVBR OBJECT-TYPE
	SYNTAX	Integer32
	MAX-ACCESS	read-write
	STATUS	current
	DESCRIPTION
		"The dedicated queue size in cells for nrtVBR (Non-Real-Time
		 Variable Bit Rate) traffic."
	::= { portShmemConfEntry 10 }

pshmemClpThreshforCBR OBJECT-TYPE
	SYNTAX	Integer32
	MAX-ACCESS	read-write
	STATUS	current
	DESCRIPTION
		"The CLP=1 discard threshold in cells for CBR (Constant Bit Rate)
		 / rtVBR (Real-Time Variable Bit Rate) traffic."
	::= { portShmemConfEntry 11 }

pshmemClpThreshforVBR OBJECT-TYPE
	SYNTAX	Integer32
	MAX-ACCESS	read-write
	STATUS	current
	DESCRIPTION
		"The CLP=1 discard threshold in cells for nrtVBR (Non-Real-Time
		 Variable Bit Rate) traffic."
	::= { portShmemConfEntry 12 }

pshmemClpThreshforABR OBJECT-TYPE
	SYNTAX	Integer32
	MAX-ACCESS	read-write
	STATUS	current
	DESCRIPTION
		"The CLP=1 discard threshold in cells for ABR
		(Available Bit Rate) traffic."
	::= { portShmemConfEntry 13 }

pShmemAtmInterfaceIndex OBJECT-TYPE
	SYNTAX Integer32
	MAX-ACCESS  read-only
	STATUS  current
	DESCRIPTION
		"The Atm interface index correspong to this port.
		 This is also the index of the portTable."
	::= { portShmemConfEntry 14 }

------------------------------------------------------------------------

portShmemTable OBJECT-TYPE
	SYNTAX	SEQUENCE OF PortShmemEntry
	MAX-ACCESS	not-accessible
	STATUS	current
	DESCRIPTION
		"A table for current state of port on shared memory network
		modules. Implementation of this table is mandatory if the
		network module hardware is based on shared memory."
	::= { portShmemGroup 2 }

portShmemEntry OBJECT-TYPE
	SYNTAX	PortShmemEntry
	MAX-ACCESS	not-accessible
	STATUS	current
	DESCRIPTION
		"A table entry containing current port configuration
		information for shared memory network modules."
	INDEX	{ pshmemBoard, pshmemModule, pshmemPort, pshmemPriority  }
	::= { portShmemTable 1 }

PortShmemEntry ::=
	SEQUENCE {
		pshmemBoard			Integer32,
		pshmemModule			Integer32,
		pshmemPort			Integer32,
		pshmemPriority			INTEGER,
		pshmemClpThreshold		Integer32,
		pshmemDedicatedQsize		Integer32,
		pshmemCurrentQsize		Integer32,
		pshmemTxCells			Counter32,
		pshmemLostCells			Counter32
	}

pshmemBoard OBJECT-TYPE
	SYNTAX	Integer32
	MAX-ACCESS	read-only
	STATUS	current
	DESCRIPTION
		"The index of this board within the ATM switch."
	::= { portShmemEntry 1 }

pshmemModule OBJECT-TYPE
	SYNTAX	Integer32
	MAX-ACCESS	read-only
	STATUS	current
	DESCRIPTION
		"The number of this network module within the switch board."
	::= { portShmemEntry 2 }

pshmemPort OBJECT-TYPE
	SYNTAX	Integer32
	MAX-ACCESS	read-only
	STATUS	current
	DESCRIPTION
		"The number of this port within the switch board and
		network module."
	::= { portShmemEntry 3 }

pshmemPriority OBJECT-TYPE
	SYNTAX	INTEGER {
			priorityUBR-ABR(1),
			priorityVBR(2),
			priorityCBR(3)
		}
	MAX-ACCESS	read-only
	STATUS	current
	DESCRIPTION
		"The traffic type."
	::= { portShmemEntry 4 }

pshmemClpThreshold OBJECT-TYPE
	SYNTAX	Integer32
	MAX-ACCESS	read-only
	STATUS	current
	DESCRIPTION
		"The threshold level in number of cells in which CLP=1
		cells will be dropped."
	::= { portShmemEntry 5 }

pshmemDedicatedQsize OBJECT-TYPE
	SYNTAX	Integer32
	MAX-ACCESS	read-only
	STATUS	current
	DESCRIPTION
		"The dedicated queue size for this type of traffic as
		was calculated by the switch software. The dedicated
		queue size is determined by the configured maximum CDV
		(Cell Delay Variation) for CBR/rtVBR (Constant Bit Rate
		/ Real-Time Variable Bit Rate) and nrtVBR (Non-Real-Time
		Variable Bit Rate) as well as the configurable
		queue size for ABR (Available Bit Rate) and UBR
		(Unspecified Bit Rate) traffic."
	::= { portShmemEntry 6 }

pshmemCurrentQsize OBJECT-TYPE
	SYNTAX	Integer32
	MAX-ACCESS	read-only
	STATUS	current
	DESCRIPTION
		"The current size of the queue."
	::= { portShmemEntry 7 }

pshmemTxCells OBJECT-TYPE
	SYNTAX	Counter32
	MAX-ACCESS	read-only
	STATUS	current
	DESCRIPTION
		"The number of cells that were transmitted
		for this port and priority queue."
	::= { portShmemEntry 8 }

pshmemLostCells OBJECT-TYPE
	SYNTAX	Counter32
	MAX-ACCESS	read-only
	STATUS	current
	DESCRIPTION
		"The total number of cells that were lost for this port
		and priority queue."
	::= { portShmemEntry 9 }

------------------------------------------------------------------------
-- The Series-LC/LE Shared Memory Group

-- Implementation of this group is mandatory for all hardware
-- that support shared memory network modules.

shmem2ConfTable OBJECT-TYPE
	SYNTAX	SEQUENCE OF Shmem2ConfEntry
	MAX-ACCESS	not-accessible
	STATUS	current
	DESCRIPTION
		"A table for shared memory network modules configuration.
		Implementation of this table is mandatory if at least
		one of the network modules' hardware is based on shared
		memory. The user should walk this table and select the
		shared memory configuration that suits his/her needs.
		The selection is done in the specific network module
		shared memory configuration entry (netmodShmemTable)."
	::= { netmodShmem2Group 1 }

shmem2ConfEntry OBJECT-TYPE
	SYNTAX	Shmem2ConfEntry
	MAX-ACCESS	not-accessible
	STATUS	current
	DESCRIPTION
		"A table entry containing shared memory network module
		configuration information."
	INDEX	{ shmem2ConfIndex }
	::= { shmem2ConfTable 1 }

Shmem2ConfEntry ::=
	SEQUENCE {
		shmem2ConfIndex			Integer32,
		shmem2UcastConnections		Integer32,
		shmem2McastConnections		Integer32,
		shmem2CellsBuffers		Integer32,
		shmem2ConfName			DisplayString,
		shmem2Counters			Integer32,
		shmem2CellMemorySize		Integer32,
		shmem2TableMemorySize		Integer32,
		shmem2NumPriorities		Integer32
	}

shmem2ConfIndex OBJECT-TYPE
	SYNTAX	Integer32
	MAX-ACCESS	read-only
	STATUS	current
	DESCRIPTION
		"The index of this shared memory configuration."
	::= { shmem2ConfEntry 1 }

shmem2UcastConnections OBJECT-TYPE
	SYNTAX	Integer32
	MAX-ACCESS	read-only
	STATUS	current
	DESCRIPTION
		"The maximum number of unicast connections that is
		supported by this shared memory configuration."
	::= { shmem2ConfEntry 2 }

shmem2McastConnections OBJECT-TYPE
	SYNTAX	Integer32
	MAX-ACCESS	read-only
	STATUS	current
	DESCRIPTION
		"The maximum number of multicast connections that is
		supported by this shared memory configuration."
	::= { shmem2ConfEntry 3 }

shmem2CellsBuffers OBJECT-TYPE
	SYNTAX	Integer32
	MAX-ACCESS	read-only
	STATUS	current
	DESCRIPTION
		"The number of cells buffers that is supported by
		this shared memory configuration."
	::= { shmem2ConfEntry 4 }

shmem2ConfName OBJECT-TYPE
	SYNTAX	DisplayString
	MAX-ACCESS	read-only
	STATUS	current
	DESCRIPTION
		"The name of this shared memory configuration."
	::= { shmem2ConfEntry 5 }

shmem2Counters OBJECT-TYPE
	SYNTAX	Integer32
	MAX-ACCESS	read-only
	STATUS	current
	DESCRIPTION
		"The number of counters that is supported by
		this shared memory configuration."
	::= { shmem2ConfEntry 6 }

shmem2CellMemorySize OBJECT-TYPE
	SYNTAX	Integer32
	MAX-ACCESS	read-only
	STATUS	current
	DESCRIPTION
		"The size of this shared memory cell RAM configuration
		in units of 64 bit words (x64)."
	::= { shmem2ConfEntry 7 }

shmem2TableMemorySize OBJECT-TYPE
	SYNTAX	Integer32
	MAX-ACCESS	read-only
	STATUS	current
	DESCRIPTION
		"The size of this shared memory table RAM configuration
		in units of 32 bit words (x32)."
	::= { shmem2ConfEntry 8 }

shmem2NumPriorities OBJECT-TYPE
	SYNTAX	Integer32
	MAX-ACCESS	read-only
	STATUS	current
	DESCRIPTION
		"The number of priorities that this shared memory
		configuration supports."
	::= { shmem2ConfEntry 9 }

------------------------------------------------------------------------

netmodShmem2Table OBJECT-TYPE
	SYNTAX	SEQUENCE OF NetmodShmem2Entry
	MAX-ACCESS	not-accessible
	STATUS	current
	DESCRIPTION
		"A table for shared memory network modules configuration.
		Implementation of this table is mandatory if the network
		module hardware is based on shared memory."
	::= { netmodShmem2Group 2 }

netmodShmem2Entry OBJECT-TYPE
	SYNTAX	NetmodShmem2Entry
	MAX-ACCESS	not-accessible
	STATUS	current
	DESCRIPTION
		"A table entry containing shared memory network module
		configuration information."
	INDEX	{ nShmem2Board, nShmem2Module }
	::= { netmodShmem2Table 1 }

NetmodShmem2Entry ::=
	SEQUENCE {
		nShmem2Board				Integer32,
		nShmem2Module				Integer32,
		nShmem2ConfRow				Integer32,
		nShmem2ConfSharedMemory			Integer32,
		nShmem2CurrentUcastConnections		Gauge32,
		nShmem2CurrentMcastConnections		Gauge32,
		nShmem2CurrentCellsBuffers		Gauge32,
		nShmem2CurrentSharedMemory		Gauge32,
		nShmem2ConfAal5PacketDrop		Integer32,
		nShmem2ConfAal5PacketDropforUBR		Integer32,
		nShmem2ConfEfciOn			Integer32,
		nShmem2ConfEfciOff			Integer32,
		nShmem2CellMemorySize			Integer32,
		nShmem2TableMemorySize			Integer32,
		nShmem2NumPriorities			Integer32,
		nShmem2VBRPriority			INTEGER
	}

nShmem2Board OBJECT-TYPE
	SYNTAX	Integer32
	MAX-ACCESS	read-only
	STATUS	current
	DESCRIPTION
		"The index of this board within the ATM switch."
	::= { netmodShmem2Entry 1 }

nShmem2Module OBJECT-TYPE
	SYNTAX	Integer32
	MAX-ACCESS	read-only
	STATUS	current
	DESCRIPTION
		"The number of this network module within the switch board."
	::= { netmodShmem2Entry 2 }

nShmem2ConfRow OBJECT-TYPE
	SYNTAX	Integer32
	MAX-ACCESS	read-write
	STATUS	current
	DESCRIPTION
		"This object identify the row in the shared memory
		configuration table that was selected for this network
		module."
	::= { netmodShmem2Entry 3 }

nShmem2ConfSharedMemory OBJECT-TYPE
	SYNTAX	Integer32
	MAX-ACCESS	read-only
	STATUS	current
	DESCRIPTION
		"The amount of memory that was configured for this
		network module given all the user requirements as
		specified in the selected shared memory configuration
		row."
	::= { netmodShmem2Entry 4 }

nShmem2CurrentUcastConnections OBJECT-TYPE
	SYNTAX	Gauge32
	MAX-ACCESS	read-only
	STATUS	current
	DESCRIPTION
		"The current number of unicast connections active
		on this shared memory network module."
	::= { netmodShmem2Entry 5 }

nShmem2CurrentMcastConnections OBJECT-TYPE
	SYNTAX	Gauge32
	MAX-ACCESS	read-only
	STATUS	current
	DESCRIPTION
		"The current number of multicast connections active
		on this shared memory network module."
	::= { netmodShmem2Entry 6 }

nShmem2CurrentCellsBuffers OBJECT-TYPE
	SYNTAX	Gauge32
	MAX-ACCESS	read-only
	STATUS	current
	DESCRIPTION
		"The current number cells buffers active
		on this shared memory network module."
	::= { netmodShmem2Entry 7 }

nShmem2CurrentSharedMemory OBJECT-TYPE
	SYNTAX	Gauge32
	MAX-ACCESS	read-only
	STATUS	current
	DESCRIPTION
		"The current value of the used shared memory
		on this network module."
	::= { netmodShmem2Entry 8 }

nShmem2ConfAal5PacketDrop OBJECT-TYPE
	SYNTAX	Integer32
	MAX-ACCESS	read-write
	STATUS	current
	DESCRIPTION
		"The AAL5 packet drop threshold in percentage of cells.
		The switch software provides a reasonable default,
		however, the user may wish to change this value
		according to the type of traffic and size of packets
		being transmitted on the network."
	::= { netmodShmem2Entry 9 }

nShmem2ConfAal5PacketDropforUBR OBJECT-TYPE
	SYNTAX	Integer32
	MAX-ACCESS	read-write
	STATUS	current
	DESCRIPTION
		"The AAL5 packet drop threshold, in percentage of cells
		for UBR queue in a four priority configuration or
		priorityNrt queue in a two priority configuration.
		The switch software provides a reasonable default.
		However, the user may wish to change this value according
		to the type of traffic and size of packets being
		transmitted on the network."
	::= { netmodShmem2Entry 10 }

nShmem2ConfEfciOn OBJECT-TYPE
	SYNTAX	Integer32
	MAX-ACCESS	read-write
	STATUS	current
	DESCRIPTION
		"The threshold on which the EFCI (Explicit Forward Congestion
		Indication) is enabled for UBR (Unspecified Bit Rate) and
		ABR (Available Bit Rate) traffic."
	::= { netmodShmem2Entry 11 }

nShmem2ConfEfciOff OBJECT-TYPE
	SYNTAX	Integer32
	MAX-ACCESS	read-write
	STATUS	current
	DESCRIPTION
		"The threshold on which the EFCI (Explicit Forward Congestion
		Indication) is disabled for UBR (Unspecified Bit Rate) and
		ABR (Available Bit Rate) traffic."
	::= { netmodShmem2Entry 12 }

nShmem2CellMemorySize OBJECT-TYPE
	SYNTAX	Integer32
	MAX-ACCESS	read-only
	STATUS	current
	DESCRIPTION
		"The size of this shared memory cell RAM configuration
		in units of 64 bit words (x64)."
	::= { netmodShmem2Entry 13 }

nShmem2TableMemorySize OBJECT-TYPE
	SYNTAX	Integer32
	MAX-ACCESS	read-only
	STATUS	current
	DESCRIPTION
		"The size of this shared memory table RAM configuration
		in units of 32 bit words (x32)."
	::= { netmodShmem2Entry 14 }

nShmem2NumPriorities OBJECT-TYPE
	SYNTAX	Integer32
	MAX-ACCESS	read-only
	STATUS	current
	DESCRIPTION
		"The number of priorities that this network module supports."
	::= { netmodShmem2Entry 15 }

nShmem2VBRPriority OBJECT-TYPE
	SYNTAX	INTEGER {
		priorityRt(1),
		priorityNrt(2),
		unSupported(3)
		}
	MAX-ACCESS	read-write
	STATUS	current
	DESCRIPTION
		"The queue through which VBR traffic is routed in a two
		priority configuration (priorityRt or priorityNrt). For a
		four priority configuration, it is unSupported."
	::= { netmodShmem2Entry 16 }

------------------------------------------------------------------------

-- Shared Memory Port Configuration Table. All the items in this table
-- that are per-port per-priority have been deprecated. All the items
-- have been transferred to the portPriorityShmem2Conf table.

portShmem2ConfTable OBJECT-TYPE
	SYNTAX	SEQUENCE OF PortShmem2ConfEntry
	MAX-ACCESS	not-accessible
	STATUS	current
	DESCRIPTION
		"A table for shared memory network modules configuration
		that is specified on a port basis. Implementation of this
		table is mandatory if the network module hardware is based
		on shared memory."
	::= { portShmem2Group 1 }

portShmem2ConfEntry OBJECT-TYPE
	SYNTAX	PortShmem2ConfEntry
	MAX-ACCESS	not-accessible
	STATUS	current
	DESCRIPTION
		"A table entry containing port configuration information
		for shared memory network modules."
	INDEX	{ pShmem2ConfBoard, pShmem2ConfModule, pShmem2ConfPort  }
	::= { portShmem2ConfTable 1 }

PortShmem2ConfEntry ::=
	SEQUENCE {
		pShmem2ConfBoard		Integer32,
		pShmem2ConfModule		Integer32,
		pShmem2ConfPort			Integer32,
		pShmem2QsizeforCBR		Integer32,
		pShmem2QsizeforVBR		Integer32,
		pShmem2QsizeforABR		Integer32,
		pShmem2QsizeforUBR		Integer32,
		pShmem2ClpThreshforCBR		Integer32,
		pShmem2ClpThreshforVBR		Integer32,
		pShmem2ClpThreshforABR		Integer32,
		pShmem2ClpThreshforUBR		Integer32,
		pShmem2AtmInterfaceIndex        Integer32
	}

pShmem2ConfBoard OBJECT-TYPE
	SYNTAX	Integer32
	MAX-ACCESS	read-only
	STATUS	current
	DESCRIPTION
		"The index of this board within the ATM switch."
	::= { portShmem2ConfEntry 1 }

pShmem2ConfModule OBJECT-TYPE
	SYNTAX	Integer32
	MAX-ACCESS	read-only
	STATUS	current
	DESCRIPTION
		"The number of this network module within the switch board."
	::= { portShmem2ConfEntry 2 }

pShmem2ConfPort OBJECT-TYPE
	SYNTAX	Integer32
	MAX-ACCESS	read-only
	STATUS	current
	DESCRIPTION
		"The number of this port within the switch board and
		network module."
	::= { portShmem2ConfEntry 3 }

pShmem2QsizeforCBR OBJECT-TYPE
	SYNTAX	Integer32
	MAX-ACCESS	read-write
	STATUS	deprecated
	DESCRIPTION
		"The dedicated queue size in cells for CBR (Constant
		Bit Rate) / rtVBR (Real-Time Variable Bit Rate) traffic."
	::= { portShmem2ConfEntry 4 }

pShmem2QsizeforVBR OBJECT-TYPE
	SYNTAX	Integer32
	MAX-ACCESS	read-write
	STATUS	deprecated
	DESCRIPTION
		"The dedicated queue size in cells for nrtVBR (Non-Real-Time
		Variable Bit Rate) traffic."
	::= { portShmem2ConfEntry 5 }

pShmem2QsizeforABR OBJECT-TYPE
	SYNTAX	Integer32
	MAX-ACCESS	read-write
	STATUS	deprecated
	DESCRIPTION
		"The dedicated queue size in cells for ABR (Available
		Bit Rate) traffic."
	::= { portShmem2ConfEntry 6 }

pShmem2QsizeforUBR OBJECT-TYPE
	SYNTAX	Integer32
	MAX-ACCESS	read-write
	STATUS	deprecated
	DESCRIPTION
		"The dedicated queue size in cells for UBR (Unspecified
		Bit Rate) traffic."
	::= { portShmem2ConfEntry 7 }

pShmem2ClpThreshforCBR OBJECT-TYPE
	SYNTAX	Integer32
	MAX-ACCESS	read-write
	STATUS	deprecated
	DESCRIPTION
		"The CLP=1 discard threshold in cells for CBR
		(Constant Bit Rate) / rtVBR (Real-Time Variable
		Bit Rate) traffic."
	::= { portShmem2ConfEntry 8 }

pShmem2ClpThreshforVBR OBJECT-TYPE
	SYNTAX	Integer32
	MAX-ACCESS	read-write
	STATUS	deprecated
	DESCRIPTION
		"The CLP=1 discard threshold in cells for nrtVBR
		(Non-Real-Time Variable Bit Rate) traffic."
	::= { portShmem2ConfEntry 9 }

pShmem2ClpThreshforABR OBJECT-TYPE
	SYNTAX	Integer32
	MAX-ACCESS	read-write
	STATUS	deprecated
	DESCRIPTION
		"The CLP=1 discard threshold in cells for ABR
		(Available Bit Rate) traffic."
	::= { portShmem2ConfEntry 10 }

pShmem2ClpThreshforUBR OBJECT-TYPE
	SYNTAX	Integer32
	MAX-ACCESS	read-write
	STATUS	deprecated
	DESCRIPTION
		"The CLP=1 discard threshold in cells for UBR
		(Unspecified Bit Rate) traffic."
	::= { portShmem2ConfEntry 11 }

pShmem2AtmInterfaceIndex OBJECT-TYPE
	SYNTAX Integer32
	MAX-ACCESS  read-only
	STATUS  current
	DESCRIPTION
		"The Atm interface index correspong to this port.
		 This is also the index of the portTable."
	::= { portShmem2ConfEntry 12 }

------------------------------------------------------------------------
--portPriority shared memory configuration table.

portPriorityShmem2ConfTable OBJECT-TYPE
	SYNTAX	SEQUENCE OF PortPriorityShmem2ConfEntry
	MAX-ACCESS	not-accessible
	STATUS	current
	DESCRIPTION
		"A table for shared memory network modules configuration
		that is specified on a port-priority basis. Implementation of
	this table is mandatory if the network module hardware is based
		on shared memory."
	::= { portShmem2Group 3 }

portPriorityShmem2ConfEntry OBJECT-TYPE
	SYNTAX	PortPriorityShmem2ConfEntry
	MAX-ACCESS	not-accessible
	STATUS	current
	DESCRIPTION
		"A table entry containing port-priority configuration
		information for shared memory network modules."
	INDEX	{ ppShmem2ConfBoard, ppShmem2ConfModule, ppShmem2ConfPort, ppShmem2ConfPriority  }
	::= { portPriorityShmem2ConfTable 1 }

PortPriorityShmem2ConfEntry ::=
	SEQUENCE {
		ppShmem2ConfBoard	Integer32,
		ppShmem2ConfModule	Integer32,
		ppShmem2ConfPort	Integer32,
		ppShmem2ConfPriority	INTEGER,

		ppShmem2Qsize		Integer32,
		ppShmem2ClpThreshold	Integer32
	}

ppShmem2ConfBoard OBJECT-TYPE
	SYNTAX	Integer32
	MAX-ACCESS	read-only
	STATUS	current
	DESCRIPTION
		"The index of this board within the ATM switch."
	::= { portPriorityShmem2ConfEntry 1 }

ppShmem2ConfModule OBJECT-TYPE
	SYNTAX	Integer32
	MAX-ACCESS	read-only
	STATUS	current
	DESCRIPTION
		"The number of this network module within the switch board."
	::= { portPriorityShmem2ConfEntry 2 }

ppShmem2ConfPort OBJECT-TYPE
	SYNTAX	Integer32
	MAX-ACCESS	read-only
	STATUS	current
	DESCRIPTION
		"The number of this port within the switch board and the
		network module."
	::= { portPriorityShmem2ConfEntry 3 }

ppShmem2ConfPriority OBJECT-TYPE
	SYNTAX	INTEGER {
		-- for four priority configuration
		priorityABR(1),
		priorityVBR(2),
		priorityCBR(3),
		priorityUBR(4),

		-- for two priority configuration
		priorityRt(5),
		priorityNrt(6)
		}
	MAX-ACCESS	read-only
	STATUS	current
	DESCRIPTION
		"The priority queue in the shared memory network module."
	::= { portPriorityShmem2ConfEntry 4 }

ppShmem2Qsize OBJECT-TYPE
	SYNTAX	Integer32
	MAX-ACCESS	read-write
	STATUS	current
	DESCRIPTION
		"The dedicated queue size for this port-priority combination,
		in number of cells."
	::= { portPriorityShmem2ConfEntry 5 }

ppShmem2ClpThreshold OBJECT-TYPE
	SYNTAX	Integer32
	MAX-ACCESS	read-write
	STATUS	current
	DESCRIPTION
		"CLP=1 threshold of this port-priority combination, in
		number of cells."
	::= { portPriorityShmem2ConfEntry 6 }

------------------------------------------------------------------------

portShmem2Table OBJECT-TYPE
	SYNTAX	SEQUENCE OF PortShmem2Entry
	MAX-ACCESS	not-accessible
	STATUS	current
	DESCRIPTION
		"A table for current state of port on shared memory network
		modules. Implementation of this table is mandatory if the
		network module hardware is based on shared memory."
	::= { portShmem2Group 2 }

portShmem2Entry OBJECT-TYPE
	SYNTAX	PortShmem2Entry
	MAX-ACCESS	not-accessible
	STATUS	current
	DESCRIPTION
		"A table entry containing current port configuration
		information for shared memory network modules."
	INDEX	{ pShmem2Board, pShmem2Module, pShmem2Port, pShmem2Priority  }
	::= { portShmem2Table 1 }

PortShmem2Entry ::=
	SEQUENCE {
		pShmem2Board			Integer32,
		pShmem2Module			Integer32,
		pShmem2Port			Integer32,
		pShmem2Priority			INTEGER,
		pShmem2ClpThreshold		Integer32,
		pShmem2DedicatedQsize		Integer32,
		pShmem2CurrentQsize		Integer32,
		pShmem2TxCells			Counter32,
		pShmem2LostCells		Counter32,
		pShmem2IntentionalLostCells	Counter32,
		pShmem2UnintentionalLostCells	Counter32
	}

pShmem2Board OBJECT-TYPE
	SYNTAX	Integer32
	MAX-ACCESS	read-only
	STATUS	current
	DESCRIPTION
		"The index of this board within the ATM switch."
	::= { portShmem2Entry 1 }

pShmem2Module OBJECT-TYPE
	SYNTAX	Integer32
	MAX-ACCESS	read-only
	STATUS	current
	DESCRIPTION
		"The number of this network module within the switch board."
	::= { portShmem2Entry 2 }

pShmem2Port OBJECT-TYPE
	SYNTAX	Integer32
	MAX-ACCESS	read-only
	STATUS	current
	DESCRIPTION
		"The number of this port within the switch board and
		network module."
	::= { portShmem2Entry 3 }

pShmem2Priority OBJECT-TYPE
	SYNTAX	INTEGER {
			-- for four priority configuration
			priorityABR(1),
			priorityVBR(2),
			priorityCBR(3),
			priorityUBR(4),

			-- for two priority configuration
			priorityRt(5),
			priorityNrt(6)
		}
	MAX-ACCESS	read-only
	STATUS	current
	DESCRIPTION
		"The priority queue in the shared memory network module."
	::= { portShmem2Entry 4 }

pShmem2ClpThreshold OBJECT-TYPE
	SYNTAX	Integer32
	MAX-ACCESS	read-only
	STATUS	current
	DESCRIPTION
		"The threshold level in number of cells in which CLP=1
		cells will be dropped."
	::= { portShmem2Entry 5 }

pShmem2DedicatedQsize OBJECT-TYPE
	SYNTAX	Integer32
	MAX-ACCESS	read-only
	STATUS	current
	DESCRIPTION
		"The dedicated queue size for this type of traffic as
		was calculated by the switch software. The dedicated
		queue size is determined by the configured maximum CDV
		(Cell Delay Variation) for CBR/rtVBR (Constant Bit Rate
		/ Real-Time Variable Bit Rate) and nrtVBR (Non-Real-Time
		Variable Bit Rate) as well as the configurable
		queue size for ABR (Available Bit Rate) and UBR
		(Unspecified Bit Rate) traffic."
	::= { portShmem2Entry 6 }

pShmem2CurrentQsize OBJECT-TYPE
	SYNTAX	Integer32
	MAX-ACCESS	read-only
	STATUS	current
	DESCRIPTION
		"The current size of the queue."
	::= { portShmem2Entry 7 }

pShmem2TxCells OBJECT-TYPE
	SYNTAX	Counter32
	MAX-ACCESS	read-only
	STATUS	current
	DESCRIPTION
		"The number of cells that were transmitted
		for this port and priority queue."
	::= { portShmem2Entry 8 }

pShmem2LostCells OBJECT-TYPE
	SYNTAX	Counter32
	MAX-ACCESS	read-only
	STATUS	current
	DESCRIPTION
		"The total number of cells that were lost for this port
		and priority queue."
	::= { portShmem2Entry 9 }

pShmem2IntentionalLostCells OBJECT-TYPE
	SYNTAX	Counter32
	MAX-ACCESS	read-only
	STATUS	current
	DESCRIPTION
		"The number of cells that were lost for this port
		and priority queue due to EPD (Early Packet Discard)
		or PPD (Partial Packet Discard)."
	::= { portShmem2Entry 10 }

pShmem2UnintentionalLostCells OBJECT-TYPE
	SYNTAX	Counter32
	MAX-ACCESS	read-only
	STATUS	current
	DESCRIPTION
		"The number of cells that were lost for this port
		and priority queue due to output memory shortages
		or the CLP (Cell Loss Priority) threshold."
	::= { portShmem2Entry 11 }

------------------------------------------------------------------------

channelShmem2Table OBJECT-TYPE
	SYNTAX	SEQUENCE OF ChannelShmem2Entry
	MAX-ACCESS	not-accessible
	STATUS	current
	DESCRIPTION
		"A table of information about the channels through
		this shared memory network module."
	::= { connShmem2Group 1 }

channelShmem2Entry OBJECT-TYPE
	SYNTAX	ChannelShmem2Entry
	MAX-ACCESS	not-accessible
	STATUS	current
	DESCRIPTION
		"A table entry containing channel shmem2 information."
	INDEX	{ vcShmem2OutputPort, vcShmem2OutputVPI, vcShmem2OutputVCI }
	::= { channelShmem2Table 1 }

ChannelShmem2Entry ::= SEQUENCE {
	vcShmem2OutputPort		Integer32,
	vcShmem2OutputVPI		Integer32,
	vcShmem2OutputVCI		Integer32,
	vcShmem2TotalLostCells		Counter32,
	vcShmem2IntentionalLostCells	Counter32,
	vcShmem2UnintentionalLostCells	Counter32,
	vcShmem2TransmittedCells	Counter32
}

vcShmem2OutputPort OBJECT-TYPE
	SYNTAX	Integer32
	MAX-ACCESS	read-only
	STATUS	current
	DESCRIPTION
		"The value of this object identifies the output port
		of this channel and is the same as the opathPort,
		and portNumber."
	::= { channelShmem2Entry 1 }

vcShmem2OutputVPI OBJECT-TYPE
	SYNTAX	Integer32
	MAX-ACCESS	read-only
	STATUS	current
	DESCRIPTION
		"The value of this object identifies the output VPI
		(Virtual Path Identifier) of this channel and is the
		same as the opathVPI."
	::= { channelShmem2Entry 2 }

vcShmem2OutputVCI OBJECT-TYPE
	SYNTAX	Integer32
	MAX-ACCESS	read-only
	STATUS	current
	DESCRIPTION
		"The output VCI (Virtual Channel Identifier) of this channel."
	::= { channelShmem2Entry 3 }

vcShmem2TotalLostCells OBJECT-TYPE
	SYNTAX	Counter32
	MAX-ACCESS	read-only
	STATUS	current
	DESCRIPTION
		"The number of cells on this channel that were dropped
		by the output network module."
	::= { channelShmem2Entry 4 }

vcShmem2IntentionalLostCells OBJECT-TYPE
	SYNTAX	Counter32
	MAX-ACCESS	read-only
	STATUS	current
	DESCRIPTION
		"The number of cells on this channel that were dropped
		due to EPD (Early Packet Discard) or PPD (Partial Packet
		Discard)."
	::= { channelShmem2Entry 5 }

vcShmem2UnintentionalLostCells OBJECT-TYPE
	SYNTAX	Counter32
	MAX-ACCESS	read-only
	STATUS	current
	DESCRIPTION
		"The number of cells on this channel that were dropped
		due to output memory shortages or the CLP (Cell Loss
		Priority) threshold."
	::= { channelShmem2Entry 6 }

vcShmem2TransmittedCells OBJECT-TYPE
	SYNTAX	Counter32
	MAX-ACCESS	read-only
	STATUS	current
	DESCRIPTION
		"The number of cells on this channel that were transmitted."
	::= { channelShmem2Entry 7 }

------------------------------------------------------------------------

pathShmem2Table OBJECT-TYPE
	SYNTAX	SEQUENCE OF PathShmem2Entry
	MAX-ACCESS	not-accessible
	STATUS	current
	DESCRIPTION
		"A table of information about the paths through
		this shared memory network module."
	::= { connShmem2Group 2 }

pathShmem2Entry OBJECT-TYPE
	SYNTAX	PathShmem2Entry
	MAX-ACCESS	not-accessible
	STATUS	current
	DESCRIPTION
		"A table entry containing path shmem2 information."
	INDEX	{ vpShmem2OutputPort, vpShmem2OutputVPI }
	::= { pathShmem2Table 1 }

PathShmem2Entry ::=
	SEQUENCE {
		vpShmem2OutputPort		Integer32,
		vpShmem2OutputVPI		Integer32,
		vpShmem2TotalLostCells		Counter32,
		vpShmem2IntentionalLostCells	Counter32,
		vpShmem2UnintentionalLostCells	Counter32,
		vpShmem2TransmittedCells	Counter32
	}

vpShmem2OutputPort OBJECT-TYPE
	SYNTAX	Integer32
	MAX-ACCESS	read-only
	STATUS	current
	DESCRIPTION
		"The value of this object identifies the output port
		of this path and is the same as the portNumber."
	::= { pathShmem2Entry 1 }

vpShmem2OutputVPI OBJECT-TYPE
	SYNTAX	Integer32
	MAX-ACCESS	read-only
	STATUS	current
	DESCRIPTION
		"The output VPI  (Virtual Path Identifier) of this path."
	::= { pathShmem2Entry 2 }

vpShmem2TotalLostCells OBJECT-TYPE
	SYNTAX	Counter32
	MAX-ACCESS	read-only
	STATUS	current
	DESCRIPTION
		"The number of cells on this path that were dropped
		by the output network module."
	::= { pathShmem2Entry 3 }

vpShmem2IntentionalLostCells OBJECT-TYPE
	SYNTAX	Counter32
	MAX-ACCESS	read-only
	STATUS	current
	DESCRIPTION
		"The number of cells on this path that were dropped
		due to EPD (Early Packet Discard) or PPD (Partial Packet
		Discard)."
	::= { pathShmem2Entry 4 }

vpShmem2UnintentionalLostCells OBJECT-TYPE
	SYNTAX	Counter32
	MAX-ACCESS	read-only
	STATUS	current
	DESCRIPTION
		"The number of cells on this path that were dropped
		due to output memory shortages or the CLP (Cell Loss
		Priority) threshold."
	::= { pathShmem2Entry 5 }

vpShmem2TransmittedCells OBJECT-TYPE
	SYNTAX	Counter32
	MAX-ACCESS	read-only
	STATUS	current
	DESCRIPTION
		"The number of cells on this path that were transmitted."
	::= { pathShmem2Entry 6 }


------------------------------------------------------------------------
--  netmodShmem2CustomBCSTable Definition

netmodShmem2CustomBCSTable OBJECT-TYPE
        SYNTAX  SEQUENCE OF NetmodShmem2CustomBCSEntry
        MAX-ACCESS  not-accessible
        STATUS  current
        DESCRIPTION
                "A table for shared memory custom BCS mappings"
        ::= { netmodShmem2Group 3 }

netmodShmem2CustomBCSEntry OBJECT-TYPE
        SYNTAX  NetmodShmem2CustomBCSEntry
        MAX-ACCESS  not-accessible
        STATUS  current
        DESCRIPTION
                "A table entry containing shared memory custom BCS mappings"
        INDEX   { nShmem2CustomBCSBoard, nShmem2CustomBCSModule, nShmem2CustomBCSValue }
        ::= { netmodShmem2CustomBCSTable 1 }

NetmodShmem2CustomBCSEntry ::=
        SEQUENCE {
                nShmem2CustomBCSBoard                 Integer32,
                nShmem2CustomBCSModule                Integer32,
                nShmem2CustomBCSValue                 Integer32,
                nShmem2CustomBCSWeight                Integer32,
		nShmem2CustomBCSRowStatus	      RowStatus	
        }

nShmem2CustomBCSBoard OBJECT-TYPE
        SYNTAX  Integer32
        MAX-ACCESS  not-accessible
        STATUS  current
        DESCRIPTION
                "The index of this board within the ATM switch."
        ::= { netmodShmem2CustomBCSEntry 1 }

nShmem2CustomBCSModule OBJECT-TYPE
        SYNTAX  Integer32
        MAX-ACCESS  not-accessible
        STATUS  current
        DESCRIPTION
                "The number of this network module within the switch board."
        ::= { netmodShmem2CustomBCSEntry 2 }

nShmem2CustomBCSValue OBJECT-TYPE
        SYNTAX  Integer32
        MAX-ACCESS  not-accessible
        STATUS  current
        DESCRIPTION
                "The value of this BCS"
        ::= { netmodShmem2CustomBCSEntry 3 }

nShmem2CustomBCSWeight OBJECT-TYPE
        SYNTAX  Integer32
        MAX-ACCESS  read-write
        STATUS  current
        DESCRIPTION
                "The weight assigned to this BCS"
        ::= { netmodShmem2CustomBCSEntry 4 }

nShmem2CustomBCSRowStatus OBJECT-TYPE
        SYNTAX  RowStatus
        MAX-ACCESS  read-write
        STATUS  current
        DESCRIPTION
                "Administrative status of this entry"
        ::= { netmodShmem2CustomBCSEntry 5 }


------------------------------------------------------------------------
-- The Series-D Shared Memory Group

-- Implementation of this group is mandatory for all hardware
-- that support Series Dw shared memory network modules.

shmem3ConfTable OBJECT-TYPE
	SYNTAX	SEQUENCE OF Shmem3ConfEntry
	MAX-ACCESS	not-accessible
	STATUS	current
	DESCRIPTION
		"A table for shared memory network modules configuration.
		Implementation of this table is mandatory if at least
		one of the network modules' hardware is based on shared
		memory. The user should walk this table and select the
		shared memory configuration that suits his/her needs.
		The selection is done in the specific network module
		shared memory configuration entry (netmodShmemTable)."
	::= { netmodShmem3Group 1 }

shmem3ConfEntry OBJECT-TYPE
	SYNTAX	Shmem3ConfEntry
	MAX-ACCESS	not-accessible
	STATUS	current
	DESCRIPTION
		"A table entry containing shared memory network module
		configuration information."
	INDEX	{ shmem3ConfIndex }
	::= { shmem3ConfTable 1 }

Shmem3ConfEntry ::=
	SEQUENCE {
		shmem3ConfIndex                Integer32,
		shmem3UcastConnections         Integer32,
		shmem3McastConnections         Integer32,
		shmem3VpiVciLists              Integer32,
		shmem3CellsBuffers             Integer32,
		shmem3ConfName                 DisplayString,
		shmem3Counters                 Integer32,
		shmem3CellMemorySize           Integer32,
		shmem3TableMemorySize          Integer32
	}

shmem3ConfIndex OBJECT-TYPE
	SYNTAX  Integer32
	MAX-ACCESS  read-only
	STATUS  current
	DESCRIPTION
		"The index of this shared memory configuration."
	::= { shmem3ConfEntry 1 }

shmem3UcastConnections OBJECT-TYPE
	SYNTAX  Integer32
	MAX-ACCESS  read-only
	STATUS  current
	DESCRIPTION
		"The maximum number of unicast connections that is
		supported by this shared memory configuration."
	::= { shmem3ConfEntry 2 }

shmem3McastConnections OBJECT-TYPE
	SYNTAX  Integer32
	MAX-ACCESS  read-only
	STATUS  current
	DESCRIPTION
		"The maximum number of multicast connections that is
		supported by this shared memory configuration."
	::= { shmem3ConfEntry 3 }

shmem3VpiVciLists OBJECT-TYPE
	SYNTAX  Integer32
	MAX-ACCESS  read-only
	STATUS  current
	DESCRIPTION
		"The memory allocated for VPI/VCI lists (which is used
		for multicast connections) by this shared memory
		configuration."
	::= { shmem3ConfEntry 4 }

shmem3CellsBuffers OBJECT-TYPE
	SYNTAX  Integer32
	MAX-ACCESS  read-only
	STATUS  current
	DESCRIPTION
		"The number of cells buffers that is supported by
		this shared memory configuration."
	::= { shmem3ConfEntry 5 }

shmem3ConfName OBJECT-TYPE
	SYNTAX  DisplayString
	MAX-ACCESS  read-only
	STATUS  current
	DESCRIPTION
		"The name of this shared memory configuration."
	::= { shmem3ConfEntry 6 }

shmem3Counters OBJECT-TYPE
	SYNTAX  Integer32
	MAX-ACCESS  read-only
	STATUS  current
	DESCRIPTION
		"The number of counters that is supported by
		this shared memory configuration."
	::= { shmem3ConfEntry 7 }

shmem3CellMemorySize OBJECT-TYPE
	SYNTAX  Integer32
	MAX-ACCESS  read-only
	STATUS  current
	DESCRIPTION
		"The size of this shared memory cell RAM configuration."
	::= { shmem3ConfEntry 8 }

shmem3TableMemorySize OBJECT-TYPE
	SYNTAX  Integer32
	MAX-ACCESS  read-only
	STATUS  current
	DESCRIPTION
		"The size of this shared memory table RAM configuration."
	::= { shmem3ConfEntry 9 }

------------------------------------------------------------------------

netmodShmem3Table OBJECT-TYPE
	SYNTAX	SEQUENCE OF NetmodShmem3Entry
	MAX-ACCESS	not-accessible
	STATUS	current
	DESCRIPTION
		"A table for shared memory network modules configuration.
		Implementation of this table is mandatory if the network
		module hardware is based on shared memory."
	::= { netmodShmem3Group 2 }

netmodShmem3Entry OBJECT-TYPE
	SYNTAX	NetmodShmem3Entry
	MAX-ACCESS	not-accessible
	STATUS	current
	DESCRIPTION
		"A table entry containing shared memory network module
		configuration information."
	INDEX	{ nShmem3Board, nShmem3Module }
	::= { netmodShmem3Table 1 }

NetmodShmem3Entry ::=
	SEQUENCE {
		nShmem3Board                           Integer32,
		nShmem3Module                          Integer32,
		nShmem3ConfRow                         Integer32,
		nShmem3ConfSharedMemory                Integer32,
		nShmem3CurrentUcastConnections         Gauge32,
		nShmem3CurrentMcastConnections         Gauge32,
		nShmem3CurrentVpiVciLists	       Gauge32,
		nShmem3CurrentCellsBuffers             Gauge32,
		nShmem3ConfAal5PacketDrop              Integer32,
		nShmem3ConfAal5PacketDropforUBR        Integer32,
		nShmem3ConfEfciOn                      Integer32,
		nShmem3ConfEfciOff                     Integer32,
		nShmem3CellMemorySize                  Integer32,
		nShmem3TableMemorySize                 Integer32,
		nShmem3ConfCountPackets                INTEGER,
		nShmem3ConfAltCLP1Threshold            Integer32,
		nShmem3ConfAltCLP01Threshold           Integer32,
		nShmem3ConfVcCLP1ForCBR                Integer32,
		nShmem3ConfVcCLP01ForCBR               Integer32,
		nShmem3ConfVcCLP1ForVBR                Integer32,
		nShmem3ConfVcCLP01ForVBR               Integer32,
		nShmem3ConfVcCLP1ForABR                Integer32,
		nShmem3ConfVcCLP01ForABR               Integer32,
		nShmem3ConfVcCLP1ForUBR                Integer32,
		nShmem3ConfVcCLP01ForUBR               Integer32
	}

nShmem3Board OBJECT-TYPE
	SYNTAX  Integer32
	MAX-ACCESS  read-only
	STATUS  current
	DESCRIPTION
		"The index of this board within the ATM switch."
	::= { netmodShmem3Entry 1 }

nShmem3Module OBJECT-TYPE
	SYNTAX  Integer32
	MAX-ACCESS  read-only
	STATUS  current
	DESCRIPTION
		"The number of this network module within the switch board."
	::= { netmodShmem3Entry 2 }

nShmem3ConfRow OBJECT-TYPE
	SYNTAX  Integer32
	MAX-ACCESS  read-write
	STATUS  current
	DESCRIPTION
		"This object identify the row in the shared memory
		configuration table that was selected for this network
		module."
	::= { netmodShmem3Entry 3 }

nShmem3ConfSharedMemory OBJECT-TYPE
	SYNTAX  Integer32
	MAX-ACCESS  read-only
	STATUS  current
	DESCRIPTION
		"The amount of memory that was configured for this
		network module given all the user requirements as
		specified in the selected shared memory configuration
		row."
	::= { netmodShmem3Entry 4 }

nShmem3CurrentUcastConnections OBJECT-TYPE
	SYNTAX  Gauge32
	MAX-ACCESS  read-only
	STATUS  current
	DESCRIPTION
		"The current number of unicast connections active
		on this shared memory network module."
	::= { netmodShmem3Entry 5 }

nShmem3CurrentMcastConnections OBJECT-TYPE
	SYNTAX  Gauge32
	MAX-ACCESS  read-only
	STATUS  current
	DESCRIPTION
		"The current number of multicast connections active
		on this shared memory network module."
	::= { netmodShmem3Entry 6 }

nShmem3CurrentVpiVciLists OBJECT-TYPE
	SYNTAX	Gauge32
	MAX-ACCESS	read-only
	STATUS	current
	DESCRIPTION
		"The current number of VPI/VCI lists active
		on this shared memory network module."
	::= { netmodShmem3Entry 7 }

nShmem3CurrentCellsBuffers OBJECT-TYPE
	SYNTAX  Gauge32
	MAX-ACCESS  read-only
	STATUS  current
	DESCRIPTION
		"The current number cells buffers active
		on this shared memory network module."
	::= { netmodShmem3Entry 8 }

nShmem3ConfAal5PacketDrop OBJECT-TYPE
	SYNTAX  Integer32
	MAX-ACCESS  read-write
	STATUS  current
	DESCRIPTION
		"The AAL5 packet drop threshold in number of cells.
		The switch software provides a reasonable default,
		however, the user may wish to change this value
		according to the type of traffic and size of packets
		being transmitted on the network. Must be between 0
		and 32767"
	::= { netmodShmem3Entry 10 }

nShmem3ConfAal5PacketDropforUBR OBJECT-TYPE
	SYNTAX  Integer32
	MAX-ACCESS  read-write
	STATUS  current
	DESCRIPTION
		"The AAL5 packet drop threshold for UBR traffic in
		percentage of cells.  The switch software provides a
		reasonable default, however, the user may wish to
		change this value according to the type of traffic and
		size of packets being transmitted on the network. Must
		be between 0 and 32767"
	::= { netmodShmem3Entry 11 }

nShmem3ConfEfciOn OBJECT-TYPE
	SYNTAX  Integer32
	MAX-ACCESS  read-write
	STATUS  current
	DESCRIPTION
		"The threshold on which the EFCI (Explicit Forward Congestion
		Indication) is enabled for UBR (Unspecified Bit Rate) and
		ABR (Available Bit Rate) traffic.  Must be a multiple of 32,
		greater than or equal to EFCI-off threshold, and less than
		or equal to 32736."
	::= { netmodShmem3Entry 12 }

nShmem3ConfEfciOff OBJECT-TYPE
	SYNTAX  Integer32
	MAX-ACCESS  read-write
	STATUS  current
	DESCRIPTION
		"The threshold on which the EFCI (Explicit Forward Congestion
		Indication) is disabled for UBR (Unspecified Bit Rate) and
		ABR (Available Bit Rate) traffic.  Must be a multiple of 32,
		greater than or equal to 32, and less than or equal to EFCI-on
		threshold."
	::= { netmodShmem3Entry 13 }

nShmem3CellMemorySize OBJECT-TYPE
	SYNTAX  Integer32
	MAX-ACCESS  read-only
	STATUS  current
	DESCRIPTION
		"The physical size of this shared memory cell RAM configuration."
	::= { netmodShmem3Entry 14 }

nShmem3TableMemorySize OBJECT-TYPE
	SYNTAX  Integer32
	MAX-ACCESS  read-only
	STATUS  current
	DESCRIPTION
		"The physical size of this shared memory table RAM configuration."
	::= { netmodShmem3Entry 15 }

nShmem3ConfCountPackets OBJECT-TYPE
	SYNTAX  INTEGER {
			disable(1),
			enable(2)
		}
	MAX-ACCESS  read-write
	STATUS  current
	DESCRIPTION
		"Setting this variable to enable(1) causes the network
		module to count the number of AAL5 packets."
	::= { netmodShmem3Entry 16 }

nShmem3ConfAltCLP1Threshold OBJECT-TYPE
	SYNTAX  Integer32
	MAX-ACCESS  read-write
	STATUS  current
	DESCRIPTION
		"Alternate CLP=1 threshold for nrt-VBR service class.  Must
		be a multiple of 16, greater than or equal to 0, and less than
		AltCLP01 threshold."
	::= { netmodShmem3Entry 17 }

nShmem3ConfAltCLP01Threshold OBJECT-TYPE
	SYNTAX  Integer32
	MAX-ACCESS  read-write
	STATUS  current
	DESCRIPTION
		"Alternate CLP=0+1 threshold for nrt-VBR service class.  Must
		be a multiple of 16, greater than AltCLP1 threshold and less
		than or equal to 4080."
	::= { netmodShmem3Entry 18 }

nShmem3ConfVcCLP1ForCBR OBJECT-TYPE
	SYNTAX  Integer32
	MAX-ACCESS  read-write
	STATUS  current
	DESCRIPTION
		"Per class CLP=1 threshold for CBR/rtVBR service class.  Must
		be a multiple of 16, greater than or equal to 0, and less
		than VcCLP01ForCBR threshold."
	::= { netmodShmem3Entry 19 }

nShmem3ConfVcCLP01ForCBR OBJECT-TYPE
	SYNTAX  Integer32
	MAX-ACCESS  read-write
	STATUS  current
	DESCRIPTION
		"Per class CLP=0+1 threshold for CBR/rtVBR service class.  Must
		be a multiple of 16, greater than VcCLP1ForCBR threshold, and
		less than or equal to 4080."
	::= { netmodShmem3Entry 20 }

nShmem3ConfVcCLP1ForVBR OBJECT-TYPE
	SYNTAX  Integer32
	MAX-ACCESS  read-write
	STATUS  current
	DESCRIPTION
		"Per class CLP=1 threshold for nrt-VBR service class.  Must
		be a multiple of 16, greater than or equal to 0, and less
		than VcCLP01ForVBR threshold."
	::= { netmodShmem3Entry 21 }

nShmem3ConfVcCLP01ForVBR OBJECT-TYPE
	SYNTAX  Integer32
	MAX-ACCESS  read-write
	STATUS  current
	DESCRIPTION
		"Per class CLP=0+1 threshold for nrt-VBR service class.  Must
		be a multiple of 16, greater than VcCLP1ForVBR threshold, and
		less than or equal to 4080."
	::= { netmodShmem3Entry 22 }

nShmem3ConfVcCLP1ForABR OBJECT-TYPE
	SYNTAX  Integer32
	MAX-ACCESS  read-write
	STATUS  current
	DESCRIPTION
		"Per class CLP=1 threshold for ABR service class.  Must
		be a multiple of 16, greater than or equal to 0, and less
		than VcCLP01ForABR threshold."
	::= { netmodShmem3Entry 23 }

nShmem3ConfVcCLP01ForABR OBJECT-TYPE
	SYNTAX  Integer32
	MAX-ACCESS  read-write
	STATUS  current
	DESCRIPTION
		"Per class CLP=0+1 threshold for ABR service class.  Must
		be a multiple of 16, greater than VcCLP1ForABR threshold, and
		less than or equal to 4080."
	::= { netmodShmem3Entry 24 }

nShmem3ConfVcCLP1ForUBR OBJECT-TYPE
	SYNTAX  Integer32
	MAX-ACCESS  read-write
	STATUS  current
	DESCRIPTION
		"Per class CLP=1 threshold for UBR service class.  Must
		be a multiple of 16, greater than or equal to 0, and less
		than VcCLP01ForUBR threshold."
	::= { netmodShmem3Entry 25 }

nShmem3ConfVcCLP01ForUBR OBJECT-TYPE
	SYNTAX  Integer32
	MAX-ACCESS  read-write
	STATUS  current
	DESCRIPTION
		"Per class CLP=0+1 threshold for UBR service class.  Must
		be a multiple of 16, greater than VcCLP1ForUBR threshold, and
		less than or equal to 4080."
	::= { netmodShmem3Entry 26 }

------------------------------------------------------------------------

portShmem3ConfTable OBJECT-TYPE
	SYNTAX	SEQUENCE OF PortShmem3ConfEntry
	MAX-ACCESS	not-accessible
	STATUS	current
	DESCRIPTION
		"A table for shared memory network modules configuration
		that is specified on a port basis. Implementation of this
		table is mandatory if the network module hardware is based
		on shared memory."
	::= { portShmem3Group 1 }

portShmem3ConfEntry OBJECT-TYPE
	SYNTAX	PortShmem3ConfEntry
	MAX-ACCESS	not-accessible
	STATUS	current
	DESCRIPTION
		"A table entry containing port configuration information
		for shared memory network modules."
	INDEX	{ pShmem3ConfBoard, pShmem3ConfModule, pShmem3ConfPort  }
	::= { portShmem3ConfTable 1 }

PortShmem3ConfEntry ::=
	SEQUENCE {
		pShmem3ConfBoard               Integer32,
		pShmem3ConfModule              Integer32,
		pShmem3ConfPort                Integer32,
		pShmem3QsizeforCBR             Integer32,
		pShmem3QsizeforVBR             Integer32,
		pShmem3QsizeforABR             Integer32,
		pShmem3QsizeforUBR             Integer32,
		pShmem3Clp01ThreshforCBR       Integer32,
		pShmem3Clp1ThreshforCBR        Integer32,
		pShmem3Clp01ThreshforVBR       Integer32,
		pShmem3Clp1ThreshforVBR        Integer32,
		pShmem3Clp01ThreshforABR       Integer32,
		pShmem3Clp1ThreshforABR        Integer32,
		pShmem3Clp01ThreshforUBR       Integer32,
		pShmem3Clp1ThreshforUBR        Integer32,
		pShmem3RateLimit               Integer32,
		pShmem3ConfSVCSchedulingCBR    INTEGER,
		pShmem3ConfPVCSchedulingCBR    INTEGER,
		pShmem3ConfSVCSchedulingVBR    INTEGER,
		pShmem3ConfPVCSchedulingVBR    INTEGER,
		pShmem3ConfAltCLPConfigCBR     INTEGER,
		pShmem3ConfAltCLPConfigVBR     INTEGER,
		pShmem3ConfAltCLPConfigUBR     INTEGER,
		pShmem3AtmInterfaceIndex       Integer32
       }

pShmem3ConfBoard OBJECT-TYPE
	SYNTAX  Integer32
	MAX-ACCESS  read-only
	STATUS  current
	DESCRIPTION
		"The index of this board within the ATM switch."
	::= { portShmem3ConfEntry 1 }

pShmem3ConfModule OBJECT-TYPE
	SYNTAX  Integer32
	MAX-ACCESS  read-only
	STATUS  current
	DESCRIPTION
		"The number of this network module within the switch board."
	::= { portShmem3ConfEntry 2 }


pShmem3ConfPort OBJECT-TYPE
	SYNTAX  Integer32
	MAX-ACCESS  read-only
	STATUS  current
	DESCRIPTION
		"The number of this port within the switch board and
		 network module."
	::= { portShmem3ConfEntry 3 }

pShmem3QsizeforCBR OBJECT-TYPE
	SYNTAX  Integer32
	MAX-ACCESS  read-write
	STATUS  current
	DESCRIPTION
		"The dedicated queue size in cells for CBR (Constant
		 Bit Rate) / rtVBR (Real-Time Variable Bit Rate) traffic."
	::= { portShmem3ConfEntry 4 }

pShmem3QsizeforVBR OBJECT-TYPE
	SYNTAX  Integer32
	MAX-ACCESS  read-write
	STATUS  current
	DESCRIPTION
		"The dedicated queue size in cells for nrtVBR (Non-Real-Time
		Variable Bit Rate) traffic."
	::= { portShmem3ConfEntry 5 }

pShmem3QsizeforABR OBJECT-TYPE
	SYNTAX  Integer32
	MAX-ACCESS  read-write
	STATUS  current
	DESCRIPTION
		"The dedicated queue size in cells for ABR (Available
		 Bit Rate) traffic."
	::= { portShmem3ConfEntry 6 }

pShmem3QsizeforUBR OBJECT-TYPE
	SYNTAX  Integer32
	MAX-ACCESS  read-write
	STATUS  current
	DESCRIPTION
		"The dedicated queue size in cells for UBR (Unspecified
		 Bit Rate) traffic."
	::= { portShmem3ConfEntry 7 }

pShmem3Clp01ThreshforCBR OBJECT-TYPE
	SYNTAX  Integer32
	MAX-ACCESS  read-write
	STATUS  current
	DESCRIPTION
		"The CLP=0+1 discard threshold in cells for CBR
		 (Constant Bit Rate) / rtVBR (Real-Time Variable Bit Rate)
		 traffic."
	::= { portShmem3ConfEntry 8 }

pShmem3Clp1ThreshforCBR OBJECT-TYPE
	SYNTAX  Integer32
	MAX-ACCESS  read-write
	STATUS  current
	DESCRIPTION
		"The CLP=1 discard threshold in cells for CBR
		 (Constant Bit Rate) / rtVBR (Real-Time Variable Bit Rate)
		 traffic."
	::= { portShmem3ConfEntry 9 }

pShmem3Clp01ThreshforVBR OBJECT-TYPE
	SYNTAX  Integer32
	MAX-ACCESS  read-write
	STATUS  current
	DESCRIPTION
		"The CLP=0+1 discard threshold in cells for nrtVBR
		 (Variable Bit Rate) traffic."
	::= { portShmem3ConfEntry 10 }

pShmem3Clp1ThreshforVBR OBJECT-TYPE
	SYNTAX  Integer32
	MAX-ACCESS  read-write
	STATUS  current
	DESCRIPTION
		"The CLP=1 discard threshold in cells for nrtVBR
		 (Variable Bit Rate) traffic."
	::= { portShmem3ConfEntry 11 }

pShmem3Clp01ThreshforABR OBJECT-TYPE
	SYNTAX  Integer32
	MAX-ACCESS  read-write
	STATUS  current
	DESCRIPTION
		"The CLP=0+1 discard threshold in cells for ABR
		 (Available Bit Rate) traffic."
	::= { portShmem3ConfEntry 12 }

pShmem3Clp1ThreshforABR OBJECT-TYPE
	SYNTAX  Integer32
	MAX-ACCESS  read-write
	STATUS  current
	DESCRIPTION
		"The CLP=1 discard threshold in cells for ABR
		 (Available Bit Rate) traffic."
	::= { portShmem3ConfEntry 13 }

pShmem3Clp01ThreshforUBR OBJECT-TYPE
	SYNTAX  Integer32
	MAX-ACCESS  read-write
	STATUS  current
	DESCRIPTION
		"The CLP=0+1 discard threshold in cells for UBR
		 (Unspecified Bit Rate) traffic."
	::= { portShmem3ConfEntry 14 }

pShmem3Clp1ThreshforUBR OBJECT-TYPE
	SYNTAX  Integer32
	MAX-ACCESS  read-write
	STATUS  current
	DESCRIPTION
		"The CLP=1 discard threshold in cells for UBR
		 (Unspecified Bit Rate) traffic."
	::= { portShmem3ConfEntry 15 }

pShmem3RateLimit OBJECT-TYPE
	SYNTAX  Integer32
	MAX-ACCESS  read-write
	STATUS  current
	DESCRIPTION
		"The number of cells/second to limit this port. This
		 in effect, sets a new logical line rate for this
		 network module. If set to 0, rate-limiting is disabled.
		 (i.e. full bandwidth is returned to the port)."
	::= { portShmem3ConfEntry 16 }

pShmem3ConfSVCSchedulingCBR OBJECT-TYPE
	SYNTAX  INTEGER {
		    -- perupc(1) is not applicable to SVC's
		    roundrobin(2),
		    smoothed(3),
		    guaranteed(4)
		 }
	MAX-ACCESS  read-write
	STATUS  deprecated
	DESCRIPTION
		"This variable defines the scheduling discipline that is going
		 to be used to service all CBR SVC connections that
		 are output across this Series-D port.
		 roundrobin: On Series-D netmod, this means that all CBR SVC's
		    will be served only by one of the two round robin queues.
		 smoothed: On Series-D netmod, this means that all CBR SVC's
		    will be  served by the rate controller.
		 guaranteed: On Series-D netmod, this means that all CBR SVC's
		    will be  served by both the rate controller and the
		    round robin queues."
	DEFVAL { roundrobin }
	::= { portShmem3ConfEntry 17 }

pShmem3ConfPVCSchedulingCBR OBJECT-TYPE
	SYNTAX  INTEGER {
		    perupc(1),
		    roundrobin(2),
		    smoothed(3),
		    guaranteed(4)
		}
	MAX-ACCESS  read-write
	STATUS  deprecated
	DESCRIPTION
	       "This variable defines the scheduling discipline that is going
		to be used to service all CBR PVC connections that are
		output across this port. Series-D netmods support
		all three scheduling modes.
		perupc: This means that each individual CBR PVC will be
		   scheduled based on the discipline associated with the UPC
		   contract used to open the connection.
		roundrobin: This means that each individual CBR PVC will served
		   only by the rate controller.
		smoothed: On Series-D netmod, this means that all CBR PVC's will
		   be served  only by the rate controller.
		guaranteed: This means that all CBR PVC's will be served
		   by both the rate controller and the round robin queues."
	DEFVAL { roundrobin }
	::= { portShmem3ConfEntry 18 }

pShmem3ConfSVCSchedulingVBR OBJECT-TYPE
	SYNTAX  INTEGER {
		    -- perupc(1) is not applicable to SVC's
		    roundrobin(2),
		    smoothed(3),
		    guaranteed(4)
		 }
	MAX-ACCESS  read-write
	STATUS  deprecated
	DESCRIPTION
		"This variable defines the scheduling discipline that is going
		 to be used to service all VBR SVC connections that
		 are output across this Series-D port.
		 roundrobin: On Series-D netmod, this means that all VBR SVC's
		    will be served only by one of the two round robin queues.
		 smoothed: On Series-D netmod, this means that all VBR SVC's
		    will be  served by the rate controller.
		 guaranteed: On Series-D netmod, this means that all VBR SVC's
		    will be  served by both the rate controller and the
		    round robin queues."
	DEFVAL { roundrobin }
	::= { portShmem3ConfEntry 19 }

pShmem3ConfPVCSchedulingVBR OBJECT-TYPE
	SYNTAX  INTEGER {
		    perupc(1),
		    roundrobin(2),
		    smoothed(3),
		    guaranteed(4)
		}
	MAX-ACCESS  read-write
	STATUS  deprecated
	DESCRIPTION
	       "This variable defines the scheduling discipline that is going
		to be used to service all VBR PVC connections that are
		output across this port. Series-D netmods support
		all three scheduling modes.
		perupc: This means that each individual VBR PVC will be
		   scheduled based on the discipline associated with the UPC
		   contract used to open the connection.
		roundrobin: This means that each individual VBR PVC will served
		   only by the rate controller.
		smoothed: On Series-D netmod, this means that all VBR PVC's will
		   be served  only by the rate controller.
		guaranteed: This means that all VBR PVC's will be served
		   by both the rate controller and the round robin queues."
	DEFVAL { roundrobin }
	::= { portShmem3ConfEntry 20 }

pShmem3ConfAltCLPConfigCBR OBJECT-TYPE
	SYNTAX INTEGER {
		allOn(1),
		allOff(2), --default
		svcOn(3),
		svcOff(4)
		}
	MAX-ACCESS  read-write
	STATUS  current
	DESCRIPTION
		"This vairable defines the per-port configuration for
		the use of the VC level Alternate CLP Thresholdold on CBR/rtVBR
		connections.  The states mean the following:
		allOn:   All CBR/rtVBR connections use the alt CLP threshold.
		allOff:  No CBR/rtVBR connections use the alt CLP threshold.
		svcOn:   All CBR/rtVBR SVC's will use the alt CLP threshold.
			 For CBR/rtVBR PVC's, whether the alt CLP threshold
			 is used is determined by the presence or absence
			 of the 'altCLPthresh' flag in the UPC contract.
		svcOff:  No CBR/rtVBR SVC's will use the alt CLP threshold.
			 For CBR/rtVBR PVC's, whether the alt CLP threshold
			 is used is determined by the presence or absence
			 of the 'altCLPthresh' flag in the UPC contract."
	DEFVAL { allOff }
	::= { portShmem3ConfEntry 21 }


pShmem3ConfAltCLPConfigVBR OBJECT-TYPE
	SYNTAX INTEGER {
		allOn(1),
		allOff(2), --default
		svcOn(3),
		svcOff(4)
		}
	MAX-ACCESS  read-write
	STATUS  current
	DESCRIPTION
		"This vairable defines the per-port configuration for
		the use of the VC level Alternate CLP Thresholdold on nrtVBR
		connections.  The states mean the following:
		allOn:   All nrtVBR connections use the alt CLP threshold.
		allOff:  No nrtVBR connections use the alt CLP threshold.
		svcOn:   All nrtVBR SVC's will use the alt CLP threshold.
			 For nrtVBR PVC's, whether the alt CLP threshold
			 is used is determined by the presence or absence
			 of the 'altCLPthresh' flag in the UPC contract.
		svcOff:  No nrtVBR SVC's will use the alt CLP threshold.
			 For nrtVBR PVC's, whether the alt CLP threshold
			 is used is determined by the presence or absence
			 of the 'altCLPthresh' flag in the UPC contract."
	DEFVAL { allOff }
	::= { portShmem3ConfEntry 22 }


pShmem3ConfAltCLPConfigUBR OBJECT-TYPE
	SYNTAX INTEGER {
		allOn(1),
		allOff(2), --default
		svcOn(3),
		svcOff(4)
		}
	MAX-ACCESS  read-write
	STATUS  current
	DESCRIPTION
		"This vairable defines the per-port configuration for
		the use of the VC level Alternate CLP Thresholdold on UBR
		connections.  The states mean the following:
		allOn:   All UBR connections use the alt CLP threshold.
		allOff:  No UBR connections use the alt CLP threshold.
		svcOn:   All UBR SVC's will use the alt CLP threshold.
			 For UBR PVC's, whether the alt CLP threshold
			 is used is determined by the presence or absence
			 of the 'altCLPthresh' flag in the UPC contract.
		svcOff:  No UBR SVC's will use the alt CLP threshold.
			 For UBR PVC's, whether the alt CLP threshold
			 is used is determined by the presence or absence
			 of the 'altCLPthresh' flag in the UPC contract."
	DEFVAL { allOff }
	::= { portShmem3ConfEntry 23 }

pShmem3AtmInterfaceIndex OBJECT-TYPE
	SYNTAX Integer32
	MAX-ACCESS  read-only
	STATUS  current
	DESCRIPTION
		"The Atm interface index correspong to this port.
		 This is also the index of the portTable."
	::= { portShmem3ConfEntry 24 }

------------------------------------------------------------------------

portShmem3Table OBJECT-TYPE
	SYNTAX	SEQUENCE OF PortShmem3Entry
	MAX-ACCESS	not-accessible
	STATUS	current
	DESCRIPTION
		"A table for current state of port on shared memory network
		modules. Implementation of this table is mandatory if the
		network module hardware is based on shared memory."
	::= { portShmem3Group 2 }

portShmem3Entry OBJECT-TYPE
	SYNTAX	PortShmem3Entry
	MAX-ACCESS	not-accessible
	STATUS	current
	DESCRIPTION
		"A table entry containing current port configuration
		information for shared memory network modules."
	INDEX	{ pShmem3Board, pShmem3Module, pShmem3Port, pShmem3Priority  }
	::= { portShmem3Table 1 }

PortShmem3Entry ::=
	SEQUENCE {
		pShmem3Board                   Integer32,
		pShmem3Module                  Integer32,
		pShmem3Port                    Integer32,
		pShmem3Priority                INTEGER,
		pShmem3CurrentQsize            Integer32,
		pShmem3TxCells                 Counter32,
		pShmem3EPDLostCells            Counter32,
		pShmem3CLP01LostCells          Counter32,
		pShmem3CLP1LostCells           Counter32,
		pShmem3VcCLPLostCells          Counter32,
		pShmem3OverflowLostCells       Counter32,
		pShmem3PPDLostCells            Counter32
	}

pShmem3Board OBJECT-TYPE
	SYNTAX  Integer32
	MAX-ACCESS  read-only
	STATUS  current
	DESCRIPTION
		"The index of this board within the ATM switch."
	::= { portShmem3Entry 1 }

pShmem3Module OBJECT-TYPE
	SYNTAX  Integer32
	MAX-ACCESS  read-only
	STATUS  current
	DESCRIPTION
		"The number of this network module within the switch board."
	::= { portShmem3Entry 2 }

pShmem3Port OBJECT-TYPE
	SYNTAX  Integer32
	MAX-ACCESS  read-only
	STATUS  current
	DESCRIPTION
		"The number of this port within the switch board and
		network module."
	::= { portShmem3Entry 3 }

pShmem3Priority OBJECT-TYPE
	SYNTAX  INTEGER {
			priorityABR(1),
			priorityVBR(2),
			priorityCBR(3),
			priorityUBR(4)
		}
	MAX-ACCESS  read-only
	STATUS  current
	DESCRIPTION
		"The traffic type."
	::= { portShmem3Entry 4 }

pShmem3CurrentQsize OBJECT-TYPE
	SYNTAX  Integer32
	MAX-ACCESS  read-only
	STATUS  current
	DESCRIPTION
		"The current size of the queue."
	::= { portShmem3Entry 5 }

pShmem3TxCells OBJECT-TYPE
	SYNTAX  Counter32
	MAX-ACCESS  read-only
	STATUS  current
	DESCRIPTION
		"The number of cells that were transmitted
		for this port and priority queue."
	::= { portShmem3Entry 6 }

pShmem3EPDLostCells OBJECT-TYPE
	SYNTAX  Counter32
	MAX-ACCESS  read-only
	STATUS  current
	DESCRIPTION
		"The number of cells that were lost for this port
		and priority queue due to EPD threshold."
	::= { portShmem3Entry 7 }

pShmem3CLP01LostCells OBJECT-TYPE
	SYNTAX  Counter32
	MAX-ACCESS  read-only
	STATUS  current
	DESCRIPTION
		"The number of cells that were lost for this port
		and priority queue due CLP=0+1 threshold."
	::= { portShmem3Entry 8 }

pShmem3CLP1LostCells OBJECT-TYPE
	SYNTAX  Counter32
	MAX-ACCESS  read-only
	STATUS  current
	DESCRIPTION
		"The number of cells that were lost for this port
		and priority queue due to CLP=1 threshold."
	::= { portShmem3Entry 9 }

pShmem3VcCLPLostCells OBJECT-TYPE
	SYNTAX  Counter32
	MAX-ACCESS  read-only
	STATUS  current
	DESCRIPTION
		"The number of cells that were lost for this port
		and priority queue due to per VC CLP=1 and CLP=0+1
		thresholds."
	::= { portShmem3Entry 10 }

pShmem3OverflowLostCells OBJECT-TYPE
	SYNTAX  Counter32
	MAX-ACCESS  read-only
	STATUS  current
	DESCRIPTION
		"The number of cells that were lost for this port
		and priority queue due to memory overflows."
	::= { portShmem3Entry 11 }

pShmem3PPDLostCells OBJECT-TYPE
	SYNTAX  Counter32
	MAX-ACCESS  read-only
	STATUS  current
	DESCRIPTION
		"The number of cells that were lost for this port
		and priority queue due to EPD, per port and per VC
		CLP, and memory overflows."
	::= { portShmem3Entry 12 }

------------------------------------------------------------------------

channelShmem3Table OBJECT-TYPE
	SYNTAX	SEQUENCE OF ChannelShmem3Entry
	MAX-ACCESS	not-accessible
	STATUS	current
	DESCRIPTION
		"A table of information about the channels through
		this shared memory network module."
	::= { connShmem3Group 1 }

channelShmem3Entry OBJECT-TYPE
	SYNTAX	ChannelShmem3Entry
	MAX-ACCESS	not-accessible
	STATUS	current
	DESCRIPTION
		"A table entry containing channel seriesD information."
	INDEX	{ vcShmem3OutputPort, vcShmem3OutputVPI, vcShmem3OutputVCI }
	::= { channelShmem3Table 1 }

ChannelShmem3Entry ::= SEQUENCE {
	vcShmem3OutputPort             Integer32,
	vcShmem3OutputVPI              Integer32,
	vcShmem3OutputVCI              Integer32,
	vcShmem3IntentionalLostCells   Counter32,
	vcShmem3UnintentionalLostCells Counter32,
	vcShmem3CLP0TxCells            Counter32,
	vcShmem3CLP1TxCells            Counter32,
	vcShmem3EPDLostCells           Counter32,
	vcShmem3CLP1LostCells          Counter32,
	vcShmem3CLP01LostCells         Counter32,
	vcShmem3TransmittedPackets     Counter32,
	vcShmem3CurrentQsize           Integer32
}

vcShmem3OutputPort OBJECT-TYPE
	SYNTAX  Integer32
	MAX-ACCESS  read-only
	STATUS  current
	DESCRIPTION
		"The value of this object identifies the output port
		of this channel and is the same as the opathPort,
		and portNumber."
	::= { channelShmem3Entry 1 }

vcShmem3OutputVPI OBJECT-TYPE
	SYNTAX  Integer32
	MAX-ACCESS  read-only
	STATUS  current
	DESCRIPTION
		"The value of this object identifies the output VPI
		(Virtual Path Identifier) of this channel and is the
		same as the opathVPI."
	::= { channelShmem3Entry 2 }

vcShmem3OutputVCI OBJECT-TYPE
	SYNTAX  Integer32
	MAX-ACCESS  read-only
	STATUS  current
	DESCRIPTION
		"The output VCI (Virtual Channel Identifier) of this channel."
	::= { channelShmem3Entry 3 }

vcShmem3IntentionalLostCells OBJECT-TYPE
	SYNTAX  Counter32
	MAX-ACCESS  read-only
	STATUS  current
	DESCRIPTION
		"The number of cells on this channel that were dropped
		due to EPD (Early Packet Discard) or PPD (Partial Packet
		Discard)."
	::= { channelShmem3Entry 4 }


vcShmem3UnintentionalLostCells OBJECT-TYPE
	SYNTAX  Counter32
	MAX-ACCESS  read-only
	STATUS  current
	DESCRIPTION
		"The number of cells on this channel that were dropped
		due to output memory shortages or the CLP (Cell Loss
		Priority) threshold."
	::= { channelShmem3Entry 5 }

vcShmem3CLP0TxCells OBJECT-TYPE
	SYNTAX  Counter32
	MAX-ACCESS  read-only
	STATUS  current
	DESCRIPTION
		"The number of CLP=0 cells on this channel that were
		transmitted."
	::= { channelShmem3Entry 6 }

vcShmem3CLP1TxCells OBJECT-TYPE
	SYNTAX  Counter32
	MAX-ACCESS  read-only
	STATUS  current
	DESCRIPTION
		"The number of CLP=1 cells on this channel that were
		transmitted."
	::= { channelShmem3Entry 7 }

vcShmem3EPDLostCells OBJECT-TYPE
	SYNTAX  Counter32
	MAX-ACCESS  read-only
	STATUS  current
	DESCRIPTION
		"The number of cells lost on this channel due to EPD."
	::= { channelShmem3Entry 8 }

vcShmem3CLP1LostCells OBJECT-TYPE
	SYNTAX  Counter32
	MAX-ACCESS  read-only
	STATUS  current
	DESCRIPTION
		"The number of cells lost on this channel due to
		CLP=1 threshold."
	::= { channelShmem3Entry 9 }

vcShmem3CLP01LostCells OBJECT-TYPE
	SYNTAX  Counter32
	MAX-ACCESS  read-only
	STATUS  current
	DESCRIPTION
		"The number of cells lost on this channel due to
		CLP=0+1 threshold."
	::= { channelShmem3Entry 10 }

vcShmem3TransmittedPackets OBJECT-TYPE
	SYNTAX  Counter32
	MAX-ACCESS  read-only
	STATUS  current
	DESCRIPTION
		"The number of transmitted packets."
	::= { channelShmem3Entry 11 }

vcShmem3CurrentQsize OBJECT-TYPE
	SYNTAX  Integer32
	MAX-ACCESS  read-only
	STATUS  current
	DESCRIPTION
		"The current size of the queue."
	::= { channelShmem3Entry 12 }

------------------------------------------------------------------------

pathShmem3Table OBJECT-TYPE
	SYNTAX	SEQUENCE OF PathShmem3Entry
	MAX-ACCESS	not-accessible
	STATUS	current
	DESCRIPTION
		"A table of information about the paths through
		this shared memory network module."
	::= { connShmem3Group 2 }

pathShmem3Entry OBJECT-TYPE
	SYNTAX	PathShmem3Entry
	MAX-ACCESS	not-accessible
	STATUS	current
	DESCRIPTION
		"A table entry containing path seriesD information."
	INDEX	{ vpShmem3OutputPort, vpShmem3OutputVPI }
	::= { pathShmem3Table 1 }

PathShmem3Entry ::=
	SEQUENCE {
		vpShmem3OutputPort             Integer32,
		vpShmem3OutputVPI              Integer32,
		vpShmem3UnintentionalLostCells Counter32,
		vpShmem3CLP0TxCells            Counter32,
		vpShmem3CLP1TxCells            Counter32,
		vpShmem3CLP1LostCells          Counter32,
		vpShmem3CLP01LostCells         Counter32,
		vpShmem3TransmittedPackets     Counter32,
		vpShmem3CurrentQsize           Integer32
	}

vpShmem3OutputPort OBJECT-TYPE
	SYNTAX  Integer32
	MAX-ACCESS  read-only
	STATUS  current
	DESCRIPTION
		"The value of this object identifies the output port
		of this path and is the same as the portNumber."
	::= { pathShmem3Entry 1 }

vpShmem3OutputVPI OBJECT-TYPE
	SYNTAX  Integer32
	MAX-ACCESS  read-only
	STATUS  current
	DESCRIPTION
		"The output VPI  (Virtual Path Identifier) of this path."
	::= { pathShmem3Entry 2 }

vpShmem3UnintentionalLostCells OBJECT-TYPE
	SYNTAX  Counter32
	MAX-ACCESS  read-only
	STATUS  current
	DESCRIPTION
		"The number of cells on this path that were dropped
		due to output memory shortages or the CLP (Cell Loss
		Priority) threshold."
	::= { pathShmem3Entry 4 }

vpShmem3CLP0TxCells OBJECT-TYPE
	SYNTAX  Counter32
	MAX-ACCESS  read-only
	STATUS  current
	DESCRIPTION
		"The number of CLP=0 cells on this path that were
		transmitted."
	::= { pathShmem3Entry 5 }

vpShmem3CLP1TxCells OBJECT-TYPE
	SYNTAX  Counter32
	MAX-ACCESS  read-only
	STATUS  current
	DESCRIPTION
		"The number of CLP=1 cells on this path that were
		transmitted."
	::= { pathShmem3Entry 6 }

vpShmem3CLP1LostCells OBJECT-TYPE
	SYNTAX  Counter32
	MAX-ACCESS  read-only
	STATUS  current
	DESCRIPTION
		"The number of cells lost on this path due to
		CLP=1 threshold."
	::= { pathShmem3Entry 8 }

vpShmem3CLP01LostCells OBJECT-TYPE
	SYNTAX  Counter32
	MAX-ACCESS  read-only
	STATUS  current
	DESCRIPTION
		"The number of cells lost on this path due to
		CLP=0+1 threshold."
	::= { pathShmem3Entry 9 }

vpShmem3TransmittedPackets OBJECT-TYPE
	SYNTAX  Counter32
	MAX-ACCESS  read-only
	STATUS  current
	DESCRIPTION
		"The number of transmitted packets."
	::= { pathShmem3Entry 10 }

vpShmem3CurrentQsize OBJECT-TYPE
	SYNTAX  Integer32
	MAX-ACCESS  read-only
	STATUS  current
	DESCRIPTION
		"The current size of the queue."
	::= { pathShmem3Entry 11 }


------------------------------------------------------------------------
-- The generic shared memory group

-- Implementation of this group is optional for netmods.

netmodGenericShmemTable OBJECT-TYPE
	SYNTAX  SEQUENCE OF NetmodGenericShmemEntry
	MAX-ACCESS  not-accessible
	STATUS  current
	DESCRIPTION
		"A table for simple network modules. Implementation of
		this table is optional."
	::= { netmodGenericShmemGroup 1}

netmodGenericShmemEntry  OBJECT-TYPE
	SYNTAX  NetmodGenericShmemEntry
	MAX-ACCESS  not-accessible
	STATUS  current
	DESCRIPTION
		"A table entry containing simple network module
		configuration information"
	INDEX   { nGenericShmemBoard, nGenericShmemModule, nGenericShmemSubindex }
	::= { netmodGenericShmemTable 1 }

NetmodGenericShmemEntry ::=
	SEQUENCE {
		nGenericShmemBoard                      Integer32,
		nGenericShmemModule                     Integer32,
		nGenericShmemSubindex			Integer32,
		nGenericShmemCurrentUcastConnections    Integer32,
		nGenericShmemCurrentMcastConnections    Integer32,
		nGenericShmemCurrentConnections         Integer32,
		nGenericShmemMaxUcastConnections        Integer32,
		nGenericShmemMaxMcastConnections        Integer32,
		nGenericShmemMaxConnections             Integer32
	}

nGenericShmemBoard OBJECT-TYPE
	SYNTAX  Integer32
	MAX-ACCESS  read-only
	STATUS  current
	DESCRIPTION
		"The index of this board within the ATM switch."
	::= { netmodGenericShmemEntry 1 }

nGenericShmemModule OBJECT-TYPE
	SYNTAX  Integer32
	MAX-ACCESS  read-only
	STATUS  current
	DESCRIPTION
		"The number of this network module within the switch board."
	::= { netmodGenericShmemEntry 2 }

nGenericShmemSubindex OBJECT-TYPE
	SYNTAX  Integer32
	MAX-ACCESS  read-only
	STATUS  current
	DESCRIPTION
		"The subindex of this generic shmem within the network module."
	::= { netmodGenericShmemEntry 3 }

nGenericShmemCurrentUcastConnections OBJECT-TYPE
	SYNTAX  Integer32
	MAX-ACCESS  read-only
	STATUS  current
	DESCRIPTION
		"The current number of unicast connections active
		on this network module. If a separate unicast connection
		space is not supported, this value will be -1."
	::= { netmodGenericShmemEntry 4 }

nGenericShmemCurrentMcastConnections OBJECT-TYPE
	SYNTAX  Integer32
	MAX-ACCESS  read-only
	STATUS  current
	DESCRIPTION
		"The current number of multicast connections active
		on this network module. If a separate multicast connection
		space is not supported, this value will be -1."
	::= { netmodGenericShmemEntry 5 }

nGenericShmemCurrentConnections OBJECT-TYPE
	SYNTAX  Integer32
	MAX-ACCESS  read-only
	STATUS  current
	DESCRIPTION
		"The current number of connections (either multicast or
		unicast) active on this network module."
	::= { netmodGenericShmemEntry 6 }

nGenericShmemMaxUcastConnections OBJECT-TYPE
	SYNTAX  Integer32
	MAX-ACCESS  read-only
	STATUS  current
	DESCRIPTION
		"The total number of unicast connections that this network
		module can support. If a separate unicast connection space
		is not supported, this value will be -1.

		The largest possible number of ATM connections can be 2^28 - 1
		(i.e., 268435455) since VPI and VCI fields in the ATM cell
		header occupies a total of 28 bits (12 bits of VPI and 16 bits
		of VCI).  Any value greater than 2^28 - 1 for this MIB will
		indicate that this network module can support an unlimited
		number of unicast connections."
	::= { netmodGenericShmemEntry 7 }

nGenericShmemMaxMcastConnections OBJECT-TYPE
	SYNTAX  Integer32
	MAX-ACCESS  read-only
	STATUS  current
	DESCRIPTION
		"The total number of multicast connections that this network
		module can support. If a separate multicast connection space is
		not supported, this value will be -1.

		The largest possible number of ATM connections can be 2^28 - 1
		(i.e., 268435455) since VPI and VCI fields in the ATM cell
		header occupies a total of 28 bits (12 bits of VPI and 16 bits
		of VCI).  Any value greater than 2^28 - 1 for this MIB will
		indicate that this network module can support an unlimited
		number of multicast connections."
	::= { netmodGenericShmemEntry 8 }

nGenericShmemMaxConnections OBJECT-TYPE
	SYNTAX  Integer32
	MAX-ACCESS  read-only
	STATUS  current
	DESCRIPTION
		"The total number of connections (either multicast or
		unicast) that this network module can support.

		The largest possible number of ATM connections can be 2^28 - 1
		(i.e., 268435455) since VPI and VCI fields in the ATM cell
		header occupies a total of 28 bits (12 bits of VPI and 16 bits
		of VCI).  Any value greater than 2^28 - 1 for this MIB will
		indicate that this network module can support an unlimited
		number of connections."
	::= { netmodGenericShmemEntry 9 }

------------------------------------------------------------------------
--  netmodGenericShmemCustomBCSTable Definition

netmodGenericShmemCustomBCSTable OBJECT-TYPE
        SYNTAX  SEQUENCE OF NetmodGenericShmemCustomBCSEntry
        MAX-ACCESS  not-accessible
        STATUS  current
        DESCRIPTION
                "A table for shared memory custom BCS mappings"
        ::= { netmodGenericShmemGroup 3 }

netmodGenericShmemCustomBCSEntry OBJECT-TYPE
        SYNTAX  NetmodGenericShmemCustomBCSEntry
        MAX-ACCESS  not-accessible
        STATUS  current
        DESCRIPTION
                "A table entry containing shared memory custom BCS mappings"
        INDEX   { nGenericShmemCustomBCSBoard, nGenericShmemCustomBCSModule, 
		  nGenericShmemCustomBCSSubindex, nGenericShmemCustomBCSValue }
        ::= { netmodGenericShmemCustomBCSTable 1 }

NetmodGenericShmemCustomBCSEntry ::=
        SEQUENCE {
                nGenericShmemCustomBCSBoard          Integer32,
                nGenericShmemCustomBCSModule         Integer32,
                nGenericShmemCustomBCSSubindex       Integer32,
                nGenericShmemCustomBCSValue          Integer32,
                nGenericShmemCustomBCSWeight         Integer32,
		nGenericShmemCustomBCSRowStatus	     RowStatus
        }

nGenericShmemCustomBCSBoard OBJECT-TYPE
        SYNTAX  Integer32
        MAX-ACCESS  not-accessible
        STATUS  current
        DESCRIPTION
                "The index of this board within the ATM switch."
        ::= { netmodGenericShmemCustomBCSEntry 1 }

nGenericShmemCustomBCSModule OBJECT-TYPE
        SYNTAX  Integer32
        MAX-ACCESS  not-accessible
        STATUS  current
        DESCRIPTION
                "The number of this network module within the switch board."
        ::= { netmodGenericShmemCustomBCSEntry 2 }

nGenericShmemCustomBCSSubindex OBJECT-TYPE
        SYNTAX  Integer32
        MAX-ACCESS  not-accessible
        STATUS  current
        DESCRIPTION
                "The subindex of this generic shmem within the network module."
        ::= { netmodGenericShmemCustomBCSEntry 3 }

nGenericShmemCustomBCSValue OBJECT-TYPE
        SYNTAX  Integer32
        MAX-ACCESS  not-accessible
        STATUS  current
        DESCRIPTION
                "The value of this BCS"
        ::= { netmodGenericShmemCustomBCSEntry 4 }

nGenericShmemCustomBCSWeight OBJECT-TYPE
        SYNTAX  Integer32
        MAX-ACCESS  read-write
        STATUS  current
        DESCRIPTION
                "The weight assigned to this BCS"
        ::= { netmodGenericShmemCustomBCSEntry 5 }

nGenericShmemCustomBCSRowStatus OBJECT-TYPE
        SYNTAX  RowStatus
        MAX-ACCESS  read-write
        STATUS  current
        DESCRIPTION
                "Administrative status of this entry"
        ::= { netmodGenericShmemCustomBCSEntry 6 }

------------------------------------------------------------------------
-- Dual SCP (Switch Control Processor) Group

dualScpConfTable OBJECT-TYPE
	SYNTAX	SEQUENCE OF DualScpConfEntry
	MAX-ACCESS	not-accessible
	STATUS	current
	DESCRIPTION
		"A table for current state of dual SCP configuration."
	::= { dualScpGroup 1 }

dualScpConfEntry OBJECT-TYPE
	SYNTAX	DualScpConfEntry
	MAX-ACCESS	not-accessible
	STATUS	current
	DESCRIPTION
		"A table entry containing current dual SCP
		configuration."
	INDEX	{ boardIndex  }
	::= { dualScpConfTable 1 }

DualScpConfEntry ::=
	SEQUENCE {
		dualScpSlot		        INTEGER,
		dualScpState                    INTEGER,
		dualScpSyncState	        DisplayString,
		dualScpPrimary		        INTEGER,
		dualScpFailover		        INTEGER,
		dualScpManualSyncRequest	INTEGER,
		dualScpCdbSyncMode              INTEGER,
		dualScpManualSwitchOver         INTEGER,
		dualScpSwitchOverTime           DateAndTime,
		dualScpSwitchOverThreshold	Integer32,
		dualScpSyncRequestList          IntegerBitString,
		dualScpNumSyncRequests          Counter32,
		dualScpNumSyncFailures          Counter32,
		dualScpResetStandbyScp		INTEGER,
		dualScpAutoRemoveOldFiles       INTEGER,
		dualScpRedundancyState		DisplayString,
		dualScpSVXCPStateSyncPercent	Gauge,
		dualScpSVXCPStateTransferFailed	INTEGER,
		dualScpSVXCPdroppedCallCount	Integer32
	}

dualScpSlot OBJECT-TYPE
	SYNTAX  INTEGER {
			slotX(1),
			slotY(2)
		}
	MAX-ACCESS  read-only
	STATUS  current
	DESCRIPTION
		"The slot number for this SCP."
	::= { dualScpConfEntry 1 }

dualScpState OBJECT-TYPE
	SYNTAX  INTEGER {
			standalone(1),
			dual(2),
			other(3)
		}
	MAX-ACCESS  read-only
	STATUS  current
	DESCRIPTION
		"Shows whether the switch is operating with a
		 single or dual SCPs. The value other(3) denotes
		 that both SCPs are present but communication is
		 not yet established."
	::= { dualScpConfEntry 2 }

dualScpSyncState OBJECT-TYPE
	SYNTAX  DisplayString
	MAX-ACCESS  read-only
	STATUS  current
	DESCRIPTION
		"This variable contains the current state of
		synchronization."
	::= { dualScpConfEntry 3 }

dualScpPrimary OBJECT-TYPE
	SYNTAX  INTEGER {
			slotX(1),
			slotY(2)
		}
	MAX-ACCESS  read-write
	STATUS  current
	DESCRIPTION
		"Controls which SCP is designated as the primary SCP."
	DEFVAL  { slotX }
	::= { dualScpConfEntry 4 }

dualScpFailover OBJECT-TYPE
	SYNTAX  INTEGER {
			enable(1),
			disable(2)
		}
	MAX-ACCESS  read-write
	STATUS  current
	DESCRIPTION
		"Disables the dual SCP failover mechanism.  When set
		 to disable(2), the backup SCP will not take over if
		 the main SCP goes down."
	DEFVAL  { enable }
	::= { dualScpConfEntry 5 }

dualScpManualSyncRequest OBJECT-TYPE
	SYNTAX  INTEGER {
			syncIdle(1),
			syncFlash(2),
			syncCdb(3),
			syncPassword(4),
			syncLecsConfig(5),
			syncOS(6),
			syncInit(7),
			syncSecurid(8),
			syncSecret(9),
			syncLoader(10),
			syncKrb5KeyTab(12)
		}
	MAX-ACCESS  read-write
	STATUS  current
	DESCRIPTION
		"This variable can be used to manually synchronize
		 the entire flash or any of the specified files.
		    syncIdle(1)       - No synchronization.
		    syncFlash(2)      - Synchronize the entire flash.
		    syncCdb(3)        - Synchronize the CDB file.
		    syncPassword(4)   - Synchronize the password file (depracated).
		    syncLecsConfig(5) - Synchronize the LECS configuration file.
		    syncOS(6)         - Synchronize the OS.
		    syncInit(7)       - Reformat the entire flash.
		    syncSecurid(8)    - Synchronize the securid configuration file.
		    syncSecret(9)     - Synchronize the securid node secret file.
		    syncLoader(10)    - Synchronize the mini-loader.
		    syncKrb5KeyTab(12)- Synchronize the kerberos v5srvtab file."
	DEFVAL  { syncIdle }
	::= { dualScpConfEntry 6 }

dualScpCdbSyncMode OBJECT-TYPE
	SYNTAX  INTEGER {
			manual(1),
			automatic(2)
		}
	MAX-ACCESS  read-write
	STATUS  current
	DESCRIPTION
		"Controls whether CDB synchronization will be manual
		 or automatic."
	DEFVAL { automatic }
	::= { dualScpConfEntry 7 }

dualScpManualSwitchOver OBJECT-TYPE
	SYNTAX  INTEGER {
			enable(1),
			disable(2)
		}
	MAX-ACCESS  read-write
	STATUS  current
	DESCRIPTION
		"Forces the backup SCP to take switch control
		 from the main SCP."
	DEFVAL { disable }
	::= { dualScpConfEntry 8 }

dualScpSwitchOverTime OBJECT-TYPE
	SYNTAX  DateAndTime
	MAX-ACCESS  read-only
	STATUS  current
	DESCRIPTION
		"Show the time when switch over occurred."
	::= { dualScpConfEntry 9 }

dualScpSwitchOverThreshold OBJECT-TYPE
	SYNTAX  Integer32
	MAX-ACCESS  read-write
	STATUS  current
	DESCRIPTION
		"Amount of time the standby SCP will wait after
		 loss of active SCP's heartbeat before it takes
		 control of the switch. The valid range is 2-300
                 seconds."
	DEFVAL { 2 }
	::= { dualScpConfEntry 10 }

dualScpSyncRequestList OBJECT-TYPE
	SYNTAX  IntegerBitString
	MAX-ACCESS  read-only
	STATUS  current
	DESCRIPTION
		"The current list of items that are waiting to be
		synchronized.  This is a bit pattern containing the
		specified enumurated bits. The bit definitions are:
		0x02  -- syncFlash
		0x04  -- syncCdb
		0x08  -- syncPassword
		0x10  -- syncLecsConfig
		0x20  -- syncOS
		0x40  -- syncInit
		0x80  -- syncSecurid
		0x100 -- syncSecret
		0x200 -- syncLoader
		0x800 -- syncKrb5KeyTab"
	::= { dualScpConfEntry 11 }

dualScpNumSyncRequests OBJECT-TYPE
	SYNTAX  Counter32
	MAX-ACCESS  read-only
	STATUS  current
	DESCRIPTION
		"The number of synchronization requests since this
		agent was initialized."
	::= { dualScpConfEntry 12 }

dualScpNumSyncFailures OBJECT-TYPE
	SYNTAX  Counter32
	MAX-ACCESS  read-only
	STATUS  current
	DESCRIPTION
		"The number of synchronization failures since this
		agent was initialized."
	::= { dualScpConfEntry 13 }

dualScpResetStandbyScp OBJECT-TYPE
	SYNTAX  INTEGER {
			enable(1),
			disable(2)
		}
	MAX-ACCESS  read-write
	STATUS  current
	DESCRIPTION
		"Setting this variable to enable(1) resets the
		backup SCP forcing it to start over."
	DEFVAL { disable }
	::= { dualScpConfEntry 14 }

dualScpAutoRemoveOldFiles OBJECT-TYPE
	SYNTAX  INTEGER {
			enable(1),
			disable(2)
		}
	MAX-ACCESS  read-write
	STATUS  current
	DESCRIPTION
		"Setting this variable to enable(1) instructs
		the backup SCP to remove old files during file
		synchronization in order to make room for the
		files that are being synchronized. This usually
		removes older copies of OS files. When synchronizing
		the OS, the current version of the OS will be
		removed if there isn't sufficient space for the new
		OS being synchronized."
	DEFVAL { disable }
	::= { dualScpConfEntry 15 }

dualScpRedundancyState OBJECT-TYPE
	SYNTAX  DisplayString
	MAX-ACCESS  read-only
	STATUS  current
	DESCRIPTION
		"This variable contains the current state of
		Dual SCP Redundancy."
	::= { dualScpConfEntry 16 }


dualScpSVXCPStateSyncPercent OBJECT-TYPE
	SYNTAX  Gauge (0..100)
	MAX-ACCESS  read-only
	STATUS  current
	DESCRIPTION
		"When SVx/SPVx Preservation is enabled, call state 
		 information will be transferred from the Active SCP to 
		 the Standby SCP, prior to any SCP control transfer.  This 
		 MIB variable tracks the completion percentage of the 
		 information transfer.

		 Before SCP control transfer occurs, the user can query 
		 this variable to find out how much of the information 
		 transfer has been done."
	::= { dualScpConfEntry 17 }

dualScpSVXCPStateTransferFailed OBJECT-TYPE
	SYNTAX  INTEGER {
			failed(1),
			ok(2)
		}
	MAX-ACCESS  read-only
	STATUS  current
	DESCRIPTION
		"When SVx/SPVx Preservation is enabled, call state 
		 information will be transferred from the Active SCP to 
		 the Standby SCP.  The value returned is 'Failed' for any
		 failure in this transfer, 'OK' otherwise."
	DEFVAL { ok }
	::= { dualScpConfEntry 18 }

dualScpSVXCPdroppedCallCount OBJECT-TYPE
	SYNTAX      Integer32
	MAX-ACCESS  read-only
	STATUS  current
	DESCRIPTION
		"SVx/SPVx Preservation has failed to preserve zero
		 or more calls, whose number is given here."
	::= { dualScpConfEntry 19 }


------------------------------------------------------------------------
-- The generic Port Group Configuration table
-- This table is Part of the netmod Generic Shared memory group

-- Implementation of this group is optional for netmods.

genericPortGroupConfTable OBJECT-TYPE
	SYNTAX  SEQUENCE OF GenericPortGroupConfEntry
	MAX-ACCESS  not-accessible
	STATUS  current
	DESCRIPTION
		"A table for simple network modules. Implementation of
		this table is optional."
	::= { netmodGenericShmemGroup 2}

genericPortGroupConfEntry  OBJECT-TYPE
	SYNTAX  GenericPortGroupConfEntry
	MAX-ACCESS  not-accessible
	STATUS  current
	DESCRIPTION
		"A table entry containing simple network module
		configuration information"
	INDEX   { genericPortGroupBoard, genericPortGroupIndex, genericPortGroupSubindex, genericPortGroupPrioIndex }
	::= { genericPortGroupConfTable 1 }

GenericPortGroupConfEntry ::=
	SEQUENCE {
		genericPortGroupBoard                      Integer32,
		genericPortGroupIndex                      Integer32,
		genericPortGroupSubindex                   Integer32,
		genericPortGroupPrioIndex                  Integer32,
		genericPortGroupAal5PacketDrop             Integer32,
		genericPortGroupEfciOn                     Integer32,
		genericPortGroupEfciOff                    Integer32,
		genericPortGroupPrioName                   DisplayString
	}

genericPortGroupBoard OBJECT-TYPE
	SYNTAX  Integer32
	MAX-ACCESS  read-only
	STATUS  current
	DESCRIPTION
		"The index of this board within the ATM switch."
	::= { genericPortGroupConfEntry 1 }

genericPortGroupIndex OBJECT-TYPE
	SYNTAX  Integer32
	MAX-ACCESS  read-only
	STATUS  current
	DESCRIPTION
		"The number of this port group(module) within a switch board.
		 This is the number that identifies the port group within a
		 switch board."
	::= { genericPortGroupConfEntry 2 }

genericPortGroupSubindex OBJECT-TYPE
	SYNTAX  Integer32
	MAX-ACCESS  read-only
	STATUS  current
	DESCRIPTION
		"The subindex of this port group identifying a port within
		 this port group."
	::= { genericPortGroupConfEntry 3 }

genericPortGroupPrioIndex OBJECT-TYPE
	SYNTAX  Integer32
	MAX-ACCESS  read-only
	STATUS  current
	DESCRIPTION
		"The priority on the port."
	::= { genericPortGroupConfEntry 4 }

genericPortGroupAal5PacketDrop OBJECT-TYPE
	SYNTAX  Integer32
	MAX-ACCESS  read-only
	STATUS  current
	DESCRIPTION
		"The AAL5 packet drop threshold in percentage of cells.
		 The switch software provides a reasonable default,
		 however, the user may wish to change this value
		 according to the type of traffic and size of packets
		 being transmitted on the network."
	::= { genericPortGroupConfEntry 5 }

genericPortGroupEfciOn OBJECT-TYPE
	SYNTAX  Integer32
	MAX-ACCESS  read-only
	STATUS  current
	DESCRIPTION
		"The threshold at which the EFCI (Explicit Forward
		 Congestion Indication) bit is turned on for ABR
		 (Available Bit Rate) traffic. "
	::= { genericPortGroupConfEntry 6 }

genericPortGroupEfciOff OBJECT-TYPE
	SYNTAX  Integer32
	MAX-ACCESS  read-only
	STATUS  current
	DESCRIPTION
		"The threshold at which the EFCI (Explicit Forward
		 Congestion Indication) bit is turned off for ABR
		 (Available Bit Rate) traffic. "
	::= { genericPortGroupConfEntry 7 }

genericPortGroupPrioName OBJECT-TYPE
	SYNTAX  DisplayString
	MAX-ACCESS  read-only
	STATUS  current
	DESCRIPTION
		"The priority name (CBR, VBR, ABR, UBR) for this
		 priority index."
	::= { genericPortGroupConfEntry 8 }

------------------------------------------------------------------------
-- The generic Output Port Configuration table
-- This table is Part of the GenericOutputPort group

-- Implementation of this group is optional for netmods.

genericOutputPortConfTable OBJECT-TYPE
	SYNTAX  SEQUENCE OF GenericOutputPortConfEntry
	MAX-ACCESS  not-accessible
	STATUS  current
	DESCRIPTION
		"A table for managing the configurable items
		 for a port in a generic manner. Implementation
		 of this table is optional."
	::= { genericOutputPortGroup 1}

genericOutputPortConfEntry  OBJECT-TYPE
	SYNTAX  GenericOutputPortConfEntry
	MAX-ACCESS  not-accessible
	STATUS  current
	DESCRIPTION
		"A table entry containing generic port configuration
		information"
	INDEX   { genericOutputPortConfBoard, genericOutputPortConfModule,
		  genericOutputPortConfPort, genericOutputPortConfPrio }
	::= { genericOutputPortConfTable 1 }

GenericOutputPortConfEntry ::=
	SEQUENCE {
		genericOutputPortConfBoard                  Integer32,
		genericOutputPortConfModule                 Integer32,
		genericOutputPortConfPort                   Integer32,
		genericOutputPortConfPrio                   Integer32,
		genericOutputPortConfPrioDedicatedQSize     Integer32,
		genericOutputPortConfPrioClp1Threshold      Integer32,
		genericOutputPortConfPrioClp01Threshold     Integer32,
		genericOutputPortConfPrioName               DisplayString,
		genericOutputPortConfAtmif                  Integer32
	}

genericOutputPortConfBoard      OBJECT-TYPE
	SYNTAX  Integer32
	MAX-ACCESS  read-only
	STATUS  current
	DESCRIPTION
		"The index of this board within the ATM switch"
	::= { genericOutputPortConfEntry 1 }

genericOutputPortConfModule      OBJECT-TYPE
	SYNTAX  Integer32
	MAX-ACCESS  read-only
	STATUS  current
	DESCRIPTION
		"The number of this port group within the switch board."
	::= { genericOutputPortConfEntry 2 }

genericOutputPortConfPort      OBJECT-TYPE
	SYNTAX  Integer32
	MAX-ACCESS  read-only
	STATUS  current
	DESCRIPTION
		"The number identifies the port within a switch board and
		 a port group."
	::= { genericOutputPortConfEntry 3 }

genericOutputPortConfPrio     OBJECT-TYPE
	SYNTAX  Integer32
	MAX-ACCESS  read-only
	STATUS  current
	DESCRIPTION
		"The priority on the output port. "
	::= { genericOutputPortConfEntry 4 }

genericOutputPortConfPrioDedicatedQSize OBJECT-TYPE
	SYNTAX  Integer32
	MAX-ACCESS  read-only
	STATUS  current
	DESCRIPTION
		"The dedicated (minimum) queue size, in cells for this
		 pport and priority"
	::= { genericOutputPortConfEntry 5 }

genericOutputPortConfPrioClp1Threshold OBJECT-TYPE
	SYNTAX  Integer32
	MAX-ACCESS  read-only
	STATUS  current
	DESCRIPTION
		"The CLP=1 discard threshold, in cells for this port
		 and priority."
	::= { genericOutputPortConfEntry 6 }

genericOutputPortConfPrioClp01Threshold OBJECT-TYPE
	SYNTAX  Integer32
	MAX-ACCESS  read-only
	STATUS  current
	DESCRIPTION
		"The CLP=0+1 discard threshold, in cells for this port
		 and priority."
	::= { genericOutputPortConfEntry 7 }

genericOutputPortConfPrioName OBJECT-TYPE
	SYNTAX  DisplayString
	MAX-ACCESS  read-only
	STATUS  current
	DESCRIPTION
		"The priority name (CBR, VBR, ABR, UBR) for this
		 genericOutputPortIndex on this port."
	::= { genericOutputPortConfEntry 8 }

genericOutputPortConfAtmif      OBJECT-TYPE
	SYNTAX  Integer32
	MAX-ACCESS  read-only
	STATUS  current
	DESCRIPTION
		"The AtmIf(BNP) of this shmem within the ATM switch"
	::= { genericOutputPortConfEntry 9 }

------------------------------------------------------------------------
-- The generic Output Port Statistics table
-- This table is Part of the GenericOutputPort group

-- Implementation of this group is optional for netmods.

genericOutputPortStatsTable OBJECT-TYPE
	SYNTAX  SEQUENCE OF GenericOutputPortStatsEntry
	MAX-ACCESS  not-accessible
	STATUS  current
	DESCRIPTION
		"A table for managing Statistics information about
		 the current state of a port in a generic manner.
		 Implementation of this table is optional."
	::= { genericOutputPortGroup 2}

genericOutputPortStatsEntry  OBJECT-TYPE
	SYNTAX  GenericOutputPortStatsEntry
	MAX-ACCESS  not-accessible
	STATUS  current
	DESCRIPTION
		"A table entry containing generic port configuration
		information"
	INDEX   { genericOutputPortStatsBoard, genericOutputPortStatsModule,
		  genericOutputPortStatsPort,  genericOutputPortStatsPrio}
	::= { genericOutputPortStatsTable 1 }

GenericOutputPortStatsEntry ::=
	SEQUENCE {
		genericOutputPortStatsBoard                 Integer32,
		genericOutputPortStatsModule                Integer32,
		genericOutputPortStatsPort                  Integer32,
		genericOutputPortStatsPrio                  Integer32,
		genericOutputPortStatsPrioTransmittedCells  Counter32,
		genericOutputPortStatsPrioClp1LostCells     Counter32,
		genericOutputPortStatsPrioClp01LostCells    Counter32,
		genericOutputPortStatsPrioName              DisplayString,
		genericOutputPortStatsAtmif                 Integer32,
		genericOutputPortStatsPrioEpdPpdLostCells   Counter32
	}

genericOutputPortStatsBoard OBJECT-TYPE
	SYNTAX  Integer32
	MAX-ACCESS  read-only
	STATUS  current
	DESCRIPTION
		"The index of this board within the ATM switch."
	::= { genericOutputPortStatsEntry 1 }

genericOutputPortStatsModule OBJECT-TYPE
	SYNTAX  Integer32
	MAX-ACCESS  read-only
	STATUS  current
	DESCRIPTION
		"The number of this port group within the switch board."
	::= { genericOutputPortStatsEntry 2 }

genericOutputPortStatsPort OBJECT-TYPE
	SYNTAX  Integer32
	MAX-ACCESS  read-only
	STATUS  current
	DESCRIPTION
		"The number of this port within the switch board and
		 the port group."
	::= { genericOutputPortStatsEntry 3 }

genericOutputPortStatsPrio OBJECT-TYPE
	SYNTAX  Integer32
	MAX-ACCESS  read-only
	STATUS  current
	DESCRIPTION
		"The index of this priority. "
	::= { genericOutputPortStatsEntry 4 }

genericOutputPortStatsPrioTransmittedCells OBJECT-TYPE
	SYNTAX  Counter32
	MAX-ACCESS  read-only
	STATUS  current
	DESCRIPTION
		"The number of cells transmitted on this port for
		 this priority"
	::= { genericOutputPortStatsEntry 5 }

genericOutputPortStatsPrioClp1LostCells OBJECT-TYPE
	SYNTAX  Counter32
	MAX-ACCESS  read-only
	STATUS  current
	DESCRIPTION
		"The number of cells lost on this port for this
		 priority due to CLP=1 threshold."
	::= { genericOutputPortStatsEntry 6 }

genericOutputPortStatsPrioClp01LostCells OBJECT-TYPE
	SYNTAX  Counter32
	MAX-ACCESS  read-only
	STATUS  current
	DESCRIPTION
		"The number of cells lost on this port for this
		 priority due to CLP=0+1 threshold."
	::= { genericOutputPortStatsEntry 7 }

genericOutputPortStatsPrioName OBJECT-TYPE
	SYNTAX  DisplayString
	MAX-ACCESS  read-only
	STATUS  current
	DESCRIPTION
		"The priority name (CBR, VBR, ABR, UBR) for this
		 genericOutputPortIndex on this port."
	::= { genericOutputPortStatsEntry 8 }

genericOutputPortStatsAtmif OBJECT-TYPE
	SYNTAX  Integer32
	MAX-ACCESS  read-only
	STATUS  current
	DESCRIPTION
		"The index of Atmif associated with this shmem in
		 the ATM switch."
	::= { genericOutputPortStatsEntry 9 }

genericOutputPortStatsPrioEpdPpdLostCells OBJECT-TYPE
	SYNTAX   Counter32
	MAX-ACCESS   read-only
	STATUS   current
	DESCRIPTION
		"The number of cells lost on this port for this
		 priority due to EPD/PPD threshold."
	::= { genericOutputPortStatsEntry 10 }

------------------------------------------------------------------------
-- The Switch Group

hardwareVersion OBJECT-TYPE
	SYNTAX	Integer32
	MAX-ACCESS	read-only
	STATUS	current
	DESCRIPTION
		"The version of the ATM switch hardware in hex.
		The version number 0x1 is revision A, 0x2 is
		revision B etc. Version number 0x0 represents an
		unknown type."
	::= { switchGroup 1 }

softwareVersion OBJECT-TYPE
	SYNTAX	Integer32
	MAX-ACCESS	read-only
	STATUS	current
	DESCRIPTION
		"The version of the ATM switch control software in hex.
		The version number is encoded into 6 hex digits. For example,
		version 1.2.3 is encoded as 0x010203."
	::= { switchGroup 2 }

maxPaths OBJECT-TYPE
	SYNTAX	Integer32
	MAX-ACCESS	read-only
	STATUS	current
	DESCRIPTION
		"The maximum number of input VPIs (Virtual Path Identifies)."
	::= { switchGroup 3 }

maxChannels OBJECT-TYPE
	SYNTAX	Integer32
	MAX-ACCESS	read-only
	STATUS	current
	DESCRIPTION
		"The maximum number of input VCIs (Virtual Channel Identifiers)."
	::= { switchGroup 4 }

atmAddress OBJECT-TYPE
	SYNTAX	SpansAddress
	MAX-ACCESS	read-only
	STATUS	current
	DESCRIPTION
		"The address of this ATM switch."
	::= { switchGroup 5 }

uptime OBJECT-TYPE
	SYNTAX	TimeTicks
	MAX-ACCESS	read-only
	STATUS	current
	DESCRIPTION
		"The length of time this ATM switch has been up,
		in hundredths of a second."
	::= { switchGroup 6 }

switchCDV OBJECT-TYPE
	SYNTAX	Integer32
	MAX-ACCESS	read-write
	STATUS	obsolete
	DESCRIPTION
		"The switch Cell Delay Variation (CDV) specified in
		microseconds, indicates the time window in which a cell
		may be received on a connection and be accepted. A cell
		that is received on a connection outside the CDV window
		will be tagged or dropped as indicated by the
		switchPolicingAction object. The switchCDV is the default
		CDV for all the connections on this switch. Individual
		connections can be set to explicitly override this value."
	::= { switchGroup 7 }

switchPolicingAction OBJECT-TYPE
	SYNTAX	INTEGER {
			tag(1),
			drop(2)
		}
	MAX-ACCESS	read-write
	STATUS	obsolete
	DESCRIPTION
		"This object indicates the action the switch will take in case
		of bandwidth violation. The switchPolicingAction is the default
		policing action for all the connections on this switch.
		Individual connections can be set to explicitly override this
		default action."
	::= { switchGroup 8 }

softwareVersionText OBJECT-TYPE
	SYNTAX	DisplayString
	MAX-ACCESS	read-only
	STATUS	current
	DESCRIPTION
		"The version of the ATM switch control software. This object
		provides text information about the internal software configuration
		that was used when the switch control software was built."
	::= { switchGroup 9 }

switchType OBJECT-TYPE
	SYNTAX	INTEGER {
			asx100(1),
			asx200(2),
			asx200wg(4),
			asx200bx(5),
			asx200bxe(6),
			cabletron9A000(7),
			asx1000(8),
			le155(9),
			sfcs200wg(10),
			sfcs200bx(11),
			sfcs1000(12),
			tnx210(15),
			tnx1100(16),
			asx1200(17),
			asx4000(18),
			le25(19),
			esx3000(20),
			asx150(22)
		}
	MAX-ACCESS	read-only
	STATUS	current
	DESCRIPTION
		"This object identifies the switch type."
	::= { switchGroup 10 }

-- switchGroup 11 has been deprecated

switchReservedPMPMinVCI OBJECT-TYPE
	SYNTAX	Integer32
	MAX-ACCESS	read-write
	STATUS	current
	DESCRIPTION
		"The minimum VCI that is reserved for PMP connections."
	::= { switchGroup 12 }

switchReservedPMPMaxVCI OBJECT-TYPE
	SYNTAX	Integer32
	MAX-ACCESS	read-write
	STATUS	current
	DESCRIPTION
		"The maximum VCI that is reserved for PMP connections."
	::= { switchGroup 13 }

switchTimeZone OBJECT-TYPE
	SYNTAX	DisplayString (SIZE (0..255))
	MAX-ACCESS	read-write
	STATUS	current
	DESCRIPTION
		"The TimeZone configured for this ATM switch.
		This variable follows the POSIX standard 1003.1-1988
		for the format of the TZ environment variable.  In
		particular, it is general enough to specify the rules
		for converting from Standard to Daylight Savings time
		for most timezones of the world.

		By default, the switch has the rules built in for
		the following timezones:
			EST5EDT
			CST6CDT
			MST7MDT
			PST8PDT
			AKST9AKDT.

		Locales outside of these timezones will need to
		supply the appropriate rule for switching between
		Daylight and Standard time. "
	::= { switchGroup 14 }

switchGMTime OBJECT-TYPE
	SYNTAX	DateAndTime
	MAX-ACCESS	read-write
	STATUS	current
	DESCRIPTION
		"The switch's notion of Greenwich Mean Time.
		Linked to hrSystemDate.  Offset part of time
		spec, if supplied, is considered an error."
	::= { switchGroup 15 }

switchProtocolType OBJECT-TYPE
	SYNTAX	INTEGER {
			tftp(1),
			ftp(2)
		}
	MAX-ACCESS	read-write
	STATUS	current
	DESCRIPTION
		"The transfer protocol that is used when upgrading the
		 switch software, backing up the CDB, etc."
	::= { switchGroup 16 }

switchCurrentUserid OBJECT-TYPE
	SYNTAX  DisplayString
	MAX-ACCESS  read-only
	STATUS  current
	DESCRIPTION
		"The value of this object identifies the user
		 currently logged in or attempting to log in on the switch.
		 It would be a NULL string if no one is logged in currently."
	::= { switchGroup 17 }

switchCurrentLoginFrom OBJECT-TYPE
	SYNTAX  DisplayString
	MAX-ACCESS  read-only
	STATUS  current
	DESCRIPTION
		"This string gives the IP address of the host from
		 where the current user is logged in or attempting to log in.
		 A NULL string is returned if no one is currently logged in
		 on the switch. If its a serial port login, the string indicates
		 the same"
	::= { switchGroup 18 }

switchPrimaryClock OBJECT-TYPE
	SYNTAX  Integer32
	MAX-ACCESS  read-write
	STATUS  deprecated
	DESCRIPTION
		"The port number whose 8KHz clock is used as primary
		 clock by all the netmods on all the boards in this switch."
	::= { switchGroup 19 }

switchSecondaryClock OBJECT-TYPE
	SYNTAX  Integer32
	MAX-ACCESS  read-write
	STATUS  deprecated
	DESCRIPTION
		  "The port number whose 8KHz clock is used as secondary
		   clock by all the netmods on all the boards in this switch."
	::= { switchGroup 20 }

switchClockOperStatus OBJECT-TYPE
	SYNTAX  INTEGER {
			primaryClock(1),
			secondaryClock(2),
			crystalAClock(3),
			crystalBClock(4),
			crystalCClock(5),
			crystalDClock(6),
			tcmClock(7),
			localCrystalClock(8),
			primaryClockPartner(9),
			secondaryClockPartner(10)
		 }
	MAX-ACCESS  read-only
	STATUS  deprecated
	DESCRIPTION
		"The currently active 8KHz clock configuration. The
		 crystal?Clock types are not currently used.  The
		 default mode is localCrystalClock which means each
		 netmod runs off of its own crystal.  If primary,
		 secondary or tcm clocking is configured then the
		 status will be updated by switch software accordingly."
	::= { switchGroup 21 }

switchTimingMode OBJECT-TYPE
	SYNTAX  INTEGER {
			switchMode(1),
			-- advancedMode(2) deprecated
			tcmMode(3)
		}
	MAX-ACCESS  read-write
	STATUS  current
	DESCRIPTION
		"The timing mode in which the switch is running.
		switchMode(1) provides for the direct use of any
		port recovered clock from any timing-capable network
		module in the switch.  tcmMode(3) uses the clock
		provided by the CEC-Plus' Timing Control Modules
		(TCM)."
	::= { switchGroup 22 }

switchConnectionPreservation OBJECT-TYPE
	SYNTAX  INTEGER {
			disable(1),
			enable(2)
		}
	MAX-ACCESS  read-write
	STATUS  current
	DESCRIPTION
		"When connection preservation is enabled the switch
		will not reset the hardware when a fail-over or
		software-reboot occurs.  The software will preserve
		existing PVC connections and re-create other
		connections.  This prevents cell traffic on PVC
		connections from being disrupted during the fail-over
		/ software-reboot process.

		When connection preservation is disabled the switch
		will reset the hardware when a fail-over or
		software-reboot occurs.  All connections will then be
		re-created.  Cell traffic on all connections will be
		disrupted during the fail-over / software-reboot
		process.

		This is disabled by default on all asx200bx based switches.
		On all the other platforms, this is enabled by default."
	::= { switchGroup 23 }

switchATMLayerOAM OBJECT-TYPE
	SYNTAX  INTEGER {
			enabled(1),
			disabled(2)
		}
	MAX-ACCESS  read-write
	STATUS  current
	DESCRIPTION
		"This object specifies whether the processing of ATM layer
		OAM cells by this switch is enabled or disabled."
	DEFVAL  { disabled }
	::= { switchGroup 24 }

switchHttpServer OBJECT-TYPE
	SYNTAX  INTEGER {
			enabled(1),
			disabled(2)
		}
	MAX-ACCESS  read-write
	STATUS  current
	DESCRIPTION
		"This specifies whether the embedded HTTP Server (which
		is used for the element manager) is enabled or disabled."
	DEFVAL  { disabled }
	::= { switchGroup 25 }

switchHttpHelpUrl OBJECT-TYPE
	SYNTAX  DisplayString
	MAX-ACCESS  read-write
	STATUS  current
	DESCRIPTION
		"This specifies the URL path for the local depository of
		the WWW help pages for the web-based element manager on
		the switch.  The URL is in the form:
			<ipaddress>[:port][<pathname>]
		For example: 1.2.3.4:8000/usr/fore/www

		This includes the IP address host to contact, and optionally
		the port on that host, and the directory on that host where
		the help pages were saved. If an empty string, the switch will
		use a default location on FORE's external web site."
	::= { switchGroup 26 }

-- 27 in use by mcastGroup

switchCtrlLinkid OBJECT-TYPE
       SYNTAX  Integer32
       MAX-ACCESS  read-only
       STATUS  current
       DESCRIPTION
	       "The linkid of the ctrl port on this switch."
       ::= { switchGroup 28 }

switchClockCurrentStatus OBJECT-TYPE
	SYNTAX  DisplayString
	MAX-ACCESS  read-only
	STATUS  current
	DESCRIPTION
		"The currently active 8KHz clock configuration. The
		value would indicate primary Clock or secondary Clock or
		if neither is available a <netmod> crystal Clock is determined
		by the switch control software. The software chooses the
		lowest netmod number with timing support"
	::= { switchGroup 29 }

-- 30 in use by switchDebounceTable

softwareLicenseKey OBJECT-TYPE
	SYNTAX  DisplayString (SIZE (0..64))
	MAX-ACCESS  read-write
	STATUS  current
	DESCRIPTION
		"The software license key of this switch."
	::= { switchGroup 31 }

switchCounterResetTime OBJECT-TYPE
	SYNTAX  TimeStamp
	MAX-ACCESS  read-only
	STATUS  current
	DESCRIPTION
		"Indicates when all switch (except for virtual connection)
		 counters were reset.  The TimeStamp is equal to the
		 sysUpTime when the reset occurred.  If switch counters have
		 never been reset, the switchCounterResetTime will be zero.
		 This variable is updated whenever switchCounterReset is
		 written."
	::= { switchGroup 32 }

switchCounterReset OBJECT-TYPE
	SYNTAX  INTEGER {
		   resetRequest(1),
		   unresetRequest(2),
		   resetTrue(3),
		   resetFalse(4)
		}
	MAX-ACCESS  read-write
	STATUS  current
	DESCRIPTION
		"Writing a value of resetRequest will result in a reset
		 of all counters on the switch except for VCC indexed
		 counters.  Writing a value of unresetRequest will destroy
		 all counter offsets and restore counter values to
		 what has accumulated over the sysUpTime period.  A
		 response value of resetTrue indicates a resetRequest
		 succeeded and is in effect.  A response of resetFalse
		 indicates a reset is not currently in effect."
	::= { switchGroup 33 }

-- 34 in use by switchSbprServerAddressTable - Simple Bootp Relay
--                                             Server Address Table.

switchPrimaryClockPort OBJECT-TYPE
	SYNTAX  DisplayString (SIZE (0..5))
	MAX-ACCESS  read-write
	STATUS  current
	DESCRIPTION
		"The name of the hardware port whose 8KHz clock is used
		 as primary clock by all the netmods on all the boards
		 in this switch."
	::= { switchGroup 35 }

switchSecondaryClockPort OBJECT-TYPE
	SYNTAX  DisplayString (SIZE (0..5))
	MAX-ACCESS  read-write
	STATUS  current
	DESCRIPTION
		 "The name of the hardware port whose 8KHz clock is used
		  as secondary clock by all the netmods on all the boards
		  in this switch."
	::= { switchGroup 36 }

-- 37 is used by serviceCategoryTable

switchPmpEnable         OBJECT-TYPE
        SYNTAX  INTEGER {
                        disable(1),
                        enable(2)
                }
        MAX-ACCESS  read-write
        STATUS current 
        DESCRIPTION
                "Disabling the PMP Feature disallows any point to multipoint 
                 connections. The services which require point to multi point 
                 connections also need to be disabled. By default the feature 
                 is enabled."
        DEFVAL { 2 }
        ::= { switchGroup 38 }

switchCallPreservation OBJECT-TYPE
	SYNTAX	INTEGER {
			disable(1),
			enable(2)
		}
	MAX-ACCESS	read-write
	STATUS	current
	DESCRIPTION
		"When SVx/SPVx Preservation is enabled, existing switched 
		 connections will be preserved during transfers of switch 
		 control from the Active SCP to the Standby SCP, whether 
		 user-initiated or due to SCP failure.  Cell traffic is
		 preserved during the failover/switchover process.

		 When SVx/SPVx Preservation is disabled, and if Connection
		 Preservation also is disabled, control transfers from the 
		 Active SCP to the Standby SCP will reset the switch 
		 hardware without having preserved the necessary call-state
		 information.  Hence, all switched connections will be 
		 cleared and will then have to be recreated.  Cell traffic 
		 on all switched connections will be disrupted.

		 By default, this feature is disabled on all supported 
		 dual-scp platforms."
	::= { switchGroup 39 }

switchCallPresOperStatus OBJECT-TYPE
	SYNTAX	INTEGER {
			disable(1),
			enable(2)
		}
	MAX-ACCESS	read-only
	STATUS	current
	DESCRIPTION
		"When SVx/SPVx Preservation is enabled administratively,
		 the feature nevertheless may be disabled operationally
		 (e.g., because of hardware failures, like a missing
		 Standby SCP).  When it is operationally disabled, the
		 effect is as though SVx/SPVx Preservation were
		 disabled administratively."
	::= { switchGroup 40 }


------------------------------------------------------------------------
-- Switch Debounce table

switchDebounceTable OBJECT-TYPE
     SYNTAX  SEQUENCE OF SwitchDebounceEntry
     MAX-ACCESS  not-accessible
     STATUS  current
     DESCRIPTION
	  "A table, where each entry consists of debounce information
	   associated with a unique port. This information includes
	   the hysteresis value (a positive number in ms) for that port,
	   i.e, the number of ms for which a physical-level failure
	   persists for that port, after which the connection will
	   be brought down"
     ::= { switchGroup 30 }

switchDebounceEntry OBJECT-TYPE
     SYNTAX  SwitchDebounceEntry
     MAX-ACCESS  not-accessible
     STATUS  current
     DESCRIPTION
	  "A table entry containing physical interface debounce information."
     INDEX { switchDebounceIndex }
     ::= { switchDebounceTable 1 }

SwitchDebounceEntry ::=
     SEQUENCE {
	  switchDebounceIndex       Integer32,
	  switchDebounceName        DisplayString,
	  switchDebounceHysteresis  Integer32
     }

switchDebounceIndex OBJECT-TYPE
     SYNTAX  Integer32
     MAX-ACCESS  read-only
     STATUS  current
     DESCRIPTION
	  "The index value for this entry - ties in with a unique port"
     ::= { switchDebounceEntry 1 }

switchDebounceName OBJECT-TYPE
     SYNTAX  DisplayString
     MAX-ACCESS  read-only
     STATUS  current
     DESCRIPTION
	  "The persistent name of this interface - (the port name)"
     ::= { switchDebounceEntry 2 }

switchDebounceHysteresis OBJECT-TYPE
     SYNTAX  Integer32
     MAX-ACCESS  read-write
     STATUS  current
     DESCRIPTION
	  "The hysteresis value for  this interface.
	   The hysteresis value is the number of ms for which a
	   physical-level failure persists for that interface,
	   after which the connection will be brought down"
     ::= { switchDebounceEntry 3 }

 ------------------------------------------------------------------------
 -- Multicast space table

mcastGroup OBJECT IDENTIFIER ::= { switchGroup 27 }

mcastSpaceTable OBJECT-TYPE
	SYNTAX	SEQUENCE OF McastSpaceEntry
	MAX-ACCESS	not-accessible
	STATUS	current
	DESCRIPTION
		"A table containing information on number of multicast
		connections supported on this switch."
	::= { mcastGroup 1 }

mcastSpaceEntry	OBJECT-TYPE
	SYNTAX	McastSpaceEntry
	MAX-ACCESS	not-accessible
	STATUS	current
	DESCRIPTION
		"A table entry containing multicast space information"
	INDEX  { mcastSpaceIndex }
	::= { mcastSpaceTable 1 }

McastSpaceEntry ::=
	SEQUENCE {
		mcastSpaceIndex		Integer32,
		mcastSpaceNumConn       Integer32,
		mcastSpaceName		DisplayString
	}

mcastSpaceIndex OBJECT-TYPE
	SYNTAX	Integer32
	MAX-ACCESS	not-accessible
	STATUS	current
	DESCRIPTION
		"Index of this multicast space entry. This value is
		used to set boardMcastIndex value."
	::= { mcastSpaceEntry 1 }

mcastSpaceNumConn OBJECT-TYPE
	SYNTAX	Integer32
	MAX-ACCESS	read-only
	STATUS	current
	DESCRIPTION
		"Number of multicast connections that this entry
		 represents. When boardMcastIndex is set to
		 mcastSpaceIndex value, the corresponding board will
		 support mcastSpaceNumConn number of multicast connections."
	::= { mcastSpaceEntry 2 }

mcastSpaceName  OBJECT-TYPE
	SYNTAX	DisplayString
	MAX-ACCESS	read-only
	STATUS	current
	DESCRIPTION
		"Name of this multicast space entry."
	::= { mcastSpaceEntry 3 }


------------------------------------------------------------------------
-- Switch Simple Bootp Relay Table

switchSbprServerAddressTable OBJECT-TYPE
     SYNTAX  SEQUENCE OF SwitchSbprServerAddressEntry
     MAX-ACCESS  not-accessible
     STATUS  current
     DESCRIPTION
	  "A table, where each entry consists of a static list of 5
	   bootp address entries."
     ::= { switchGroup 34 }

switchSbprServerAddressEntry OBJECT-TYPE
     SYNTAX  SwitchSbprServerAddressEntry
     MAX-ACCESS  not-accessible
     STATUS  current
     DESCRIPTION
	  "A bootp Ip Address server entry."
     INDEX { sbprServerAddressIndex }
     ::= { switchSbprServerAddressTable 1 }

SwitchSbprServerAddressEntry ::= SEQUENCE {
	  sbprServerAddressIndex       Integer32,
	  sbprServerAddressIndexName   DisplayString,
	  sbprServerMaxHops            INTEGER,
	  sbprServerMinSeconds         INTEGER,
	  sbprServerAddress1           IpAddress,
	  sbprServerAddress2           IpAddress,
	  sbprServerAddress3           IpAddress,
	  sbprServerAddress4           IpAddress,
	  sbprServerAddress5           IpAddress,
	  sbprServerRowStatus          RowStatus
       }

sbprServerAddressIndex  OBJECT-TYPE
       SYNTAX Integer32
       MAX-ACCESS read-write
       STATUS current
       DESCRIPTION
	   "A unique value greater then zero used
	    as an index into the bootp address table."
       ::= { switchSbprServerAddressEntry 1 }

sbprServerAddressIndexName  OBJECT-TYPE
       SYNTAX   DisplayString (SIZE (0..16))
       MAX-ACCESS read-write
       STATUS current
       DESCRIPTION
	   "Name of the Interface index into the bootp address table."
	::= { switchSbprServerAddressEntry 2 }

sbprServerMaxHops OBJECT-TYPE
      SYNTAX  INTEGER (1..16)
      MAX-ACCESS  read-write
      STATUS  current
      DESCRIPTION
	  "The maximum number of hops that a BOOTREQUEST
	  message is permitted to traverse before it must
	  be discarded.  Received BOOTREQUEST messages
	  that have a hopcount greater than this value are
	  discarded by this relay agent.  The default
	  value is 4."
      ::= { switchSbprServerAddressEntry 3 }

sbprServerMinSeconds OBJECT-TYPE
      SYNTAX  INTEGER (0..65535)
      MAX-ACCESS  read-write
      STATUS  current
      DESCRIPTION
	  "The minimum number of seconds that a BOOTP
	  client must have been attempting to boot before
	  the relay agent will relay BOOTREQUESTs from
	  that client.  The default value is 0."
      ::=  { switchSbprServerAddressEntry 4 }

sbprServerAddress1 OBJECT-TYPE
	SYNTAX  IpAddress
	MAX-ACCESS  read-write
	STATUS  current
	DESCRIPTION
		   "The IP address of the BOOTP server."
	::= { switchSbprServerAddressEntry 5 }

sbprServerAddress2 OBJECT-TYPE
	SYNTAX  IpAddress
	MAX-ACCESS  read-write
	STATUS  current
	DESCRIPTION
		   "The IP address of the BOOTP server."
	::= { switchSbprServerAddressEntry 6 }

sbprServerAddress3 OBJECT-TYPE
	SYNTAX  IpAddress
	MAX-ACCESS  read-write
	STATUS  current
	DESCRIPTION
		   "The IP address of the BOOTP server."
	::= { switchSbprServerAddressEntry 7 }

sbprServerAddress4 OBJECT-TYPE
	SYNTAX  IpAddress
	MAX-ACCESS  read-write
	STATUS  current
	DESCRIPTION
		   "The IP address of the BOOTP server."
	::= { switchSbprServerAddressEntry 8 }

sbprServerAddress5 OBJECT-TYPE
	SYNTAX  IpAddress
	MAX-ACCESS  read-write
	STATUS  current
	DESCRIPTION
		   "The IP address of the BOOTP server."
	::= { switchSbprServerAddressEntry 9 }

sbprServerRowStatus OBJECT-TYPE
       SYNTAX RowStatus
       MAX-ACCESS read-write
       STATUS current
       DESCRIPTION
		   "Administrative status of this entry. "
	::= { switchSbprServerAddressEntry 10 }

--------------------------------------------------------------------------
-- The Service Category table

serviceCategoryTable    OBJECT-TYPE
       SYNTAX    SEQUENCE OF ServiceCategoryEntry
       MAX-ACCESS    not-accessible
       STATUS    current
       DESCRIPTION
		" A table of ATM service categories supported."
       ::=  { switchGroup 37 }

serviceCategoryEntry    OBJECT-TYPE
       SYNTAX    ServiceCategoryEntry
       MAX-ACCESS    not-accessible
       STATUS    current
       DESCRIPTION
		" A table entry containing ATM Service Category information."
       INDEX   { serviceCategoryIndex }
       ::=  { serviceCategoryTable 1 }


ServiceCategoryEntry ::= SEQUENCE {
	   serviceCategoryIndex        Integer32,
	   serviceCategoryName         DisplayString
       }

serviceCategoryIndex    OBJECT-TYPE
       SYNTAX    Integer32
       MAX-ACCESS    read-only
       STATUS    current
       DESCRIPTION
		" The ATM service category index."
       ::=  { serviceCategoryEntry 1 }

serviceCategoryName    OBJECT-TYPE
       SYNTAX    DisplayString
       MAX-ACCESS    read-only
       STATUS    current
       DESCRIPTION
		" The name of the ATM service category. The following
		values are supported:
			serviceCategoryIndex      serviceCategoryName
			-----------------      ----------------------
				1                 CBR
				2                 rtVBR
				3                 nrtVBR
				4                 ABR
				5                 UBR
		"
       ::=  { serviceCategoryEntry 2 }



--------------------------------------------------------------------------
--confTopologyGroup

confTopoHelloInterval  OBJECT-TYPE
	SYNTAX   Integer32
	MAX-ACCESS   read-write
	STATUS   current
	DESCRIPTION
		"This is the time interval in milli seconds between
		 successive Hello Indication messages sent by SPANS"
	::= { confTopologyGroup 1 }

confTopoNsapIndInterval  OBJECT-TYPE
	SYNTAX   Integer32
	MAX-ACCESS   read-write
	STATUS   current
	DESCRIPTION
		"This is the time interval in milli seconds between
		 successive NSAP Indication messages sent by SPANS"
	::= { confTopologyGroup 2 }


confTopoStaticUpdateInterval  OBJECT-TYPE
	SYNTAX   Integer32
	MAX-ACCESS   read-write
	STATUS   current
	DESCRIPTION
		"This is the time interval in milli seconds between
		 successive refreshes of NSAP static routes in the
		 NSAP topology"
	::= { confTopologyGroup 3 }

confTopoMaxHopCount  OBJECT-TYPE
	SYNTAX   Integer32
	MAX-ACCESS   read-write
	STATUS   current
	DESCRIPTION
		"This is the upper limit on the number of hops
		 in the source routes computed by the NSAP router"
	::= { confTopologyGroup 4 }

confTopoACRPropMult  OBJECT-TYPE
	SYNTAX   Integer32
	MAX-ACCESS   read-write
	STATUS   current
	DESCRIPTION
		"This is the proportional multiplier expressed as
		 a percentage of Available Cell Rate (ACR). If the
		 percentage change of the ACR of any given link in
		 the NSAP topology exceeds this threshold, then the
		 change is deemed significant"
	::= { confTopologyGroup 5 }

confTopoMinThresh  OBJECT-TYPE
	SYNTAX   Integer32
	MAX-ACCESS   read-write
	STATUS   current
	DESCRIPTION
		"This is the capacity value in Cells per second of the
		 minimum value that the threshold value for determining
		 the significant change can take. This minimum value is
		 used to ensure that the threshold for determining
		 significant changes to ACR does not become a very small
		 value in cases where  product of the ACR and the
		 proportional multiplier is a very small number."
	::= { confTopologyGroup 6 }

confTopoMinVCAvail  OBJECT-TYPE
	SYNTAX   Integer32
	MAX-ACCESS   read-write
	STATUS   current
	DESCRIPTION
		"This is the minimum number of VCs that should be available
		on a link before the state of the link changes from VCs-not-
		available to VCs-available. This state is propagated in the
		link state information. The state changes from VCs-available
		to VCs-not-available when the number of VCs available becomes
		zero from a non-zero value."
	::= { confTopologyGroup 7 }

confTopoSpansAreaID  OBJECT-TYPE
	SYNTAX   Integer32
	MAX-ACCESS   read-write
	STATUS   current
	DESCRIPTION
		"This is the ID of the Area in the SPANS routing
		hierarchy to which this switch belongs. This number
		goes into the most significant byte of the SPANS ATM
		address"
	::= { confTopologyGroup 8 }

confTopoSpansBorderSwitch OBJECT-TYPE
	SYNTAX   INTEGER {
			enabled(1),
			disabled(2)
		 }
	MAX-ACCESS   read-write
	STATUS   current
	DESCRIPTION
		"This variable indicates wherher this switch is
		configured to operate as a SPANS-NNI Border Switch or not"
	::= { confTopologyGroup 9 }

confTopoSwitchPrefix OBJECT-TYPE
	SYNTAX	NsapPrefix
	MAX-ACCESS	read-write
	STATUS	current
	DESCRIPTION
		"The default NSAP (Network Service Access Point) prefix for
		this ATM switch. The NSAP prefix will be used in the ILMI
		address registration message as well as the 'hello-indication'
		SPANS-NNI message."
	::= { confTopologyGroup 10 }

confTopoSwitchPrefixMask OBJECT-TYPE
	SYNTAX   Integer32
	MAX-ACCESS   read-write
	STATUS   current
	DESCRIPTION
		"This mask gives the number of leading bits in the above
		prefix to be used to aggregate the addresses that belong to
		the switch in SPANS-PNNI alias FORE-PNNI"
	::= { confTopologyGroup 11 }

confTopoPeerGroupMask OBJECT-TYPE
	SYNTAX   Integer32
	MAX-ACCESS   read-write
	STATUS   current
	DESCRIPTION
		"This mask gives the number of the leading bits in the above
		prefix to be used to aggregate the addresses that belong to
		the peer group containing this switch in SPANS-PNNI alias
		FORE-PNNI"
	::= { confTopologyGroup 12 }

confTopoSpansPnniBorderSwitch OBJECT-TYPE
	SYNTAX   INTEGER {
			enabled(1),
			disabled(2)
		 }
	MAX-ACCESS   read-write
	STATUS   current
	DESCRIPTION
		"This variable indicates whether this switch is
		configured to operate as a SPANS-PNNI Border Switch or not"
	::= { confTopologyGroup 13 }

confTopoPGSNReachCost OBJECT-TYPE
	SYNTAX   INTEGER (1..4294967295)
	MAX-ACCESS   read-write
	STATUS   current
	DESCRIPTION
		"This is used to indicate cost of link from border node to PGSN"
	::= { confTopologyGroup 14 }

confTopoPGSNReachCostMethod OBJECT-TYPE
	SYNTAX   INTEGER {
			default(1),
			user(2)
		 }
	MAX-ACCESS   read-write
	STATUS   current
	DESCRIPTION
		"This variable indicates the method of computing cost of link
		from border node to PGSN"
	::= { confTopologyGroup 15 }

-- Following FTPNNI variable is deprecated as a part of FT 7.1 

confTopoFtPnniForeArea  OBJECT-TYPE
	SYNTAX   Integer32
	MAX-ACCESS   read-write
	STATUS   deprecated
	DESCRIPTION
		"This variable is the area ID of the FT-PNNI autonomous system
		in the global fore hierarchy of PNNI and FT-PNNI peergroups"
	::= { confTopologyGroup 16 }

-- Following FTPNNI variable is deprecated as a part of FT 7.1 

confTopoFtPnniForeLevel  OBJECT-TYPE
	SYNTAX   Integer32
	MAX-ACCESS   read-write
	STATUS   deprecated
	DESCRIPTION
		"This variable is the level of the FT-PNNI autonomous system
		in the global fore hierarchy of PNNI and FT-PNNI peergroups"
	::= { confTopologyGroup 17 }

confTopoLBUbrLoadBalance OBJECT-TYPE
	SYNTAX   INTEGER {
			enable(1),
			disable(2)
		 }
	MAX-ACCESS   read-write
	STATUS   current
	DESCRIPTION
		"This variable indicates whether this switch is to do
		Load Balanced UBR routing"
	::= { confTopologyGroup 18 }


------------------------------------------------------------------------
-- The Port Group

numberOfPorts OBJECT-TYPE
	SYNTAX	Integer32
	MAX-ACCESS	read-only
	STATUS	current
	DESCRIPTION
		"The number of ports on this ATM switch."
	::= { portGroup 1 }

portTable OBJECT-TYPE
	SYNTAX	SEQUENCE OF PortEntry
	MAX-ACCESS	not-accessible
	STATUS	current
	DESCRIPTION
		"A table of information about the ports on this ATM switch."
	::= { portGroup 2 }

portEntry OBJECT-TYPE
	SYNTAX	PortEntry
	MAX-ACCESS	not-accessible
	STATUS	current
	DESCRIPTION
		"A table entry containing port information."
	INDEX	{ portNumber }
	::= { portTable 1 }

PortEntry ::=
	SEQUENCE {
		portNumber		Integer32,
		portAdminStatus		INTEGER,
		portOperStatus		INTEGER,
		portTime		TimeTicks,
		portRemoteAtmAddress	SpansAddress,
		portRemoteIpAddress	IpAddress,

		portMaxPathsIn		Integer32,
		portNumPathsIn		Gauge32,
		portMaxBandwidthIn	Integer32,
		portAllocBandwidthIn	Gauge32,
		portUsedBandwidthIn	Gauge32,
		portReceivedCells	Counter32,

		portMaxPathsOut		Integer32,
		portNumPathsOut		Gauge32,
		portMaxBandwidthOut	Integer32,
		portAllocBandwidthOut	Gauge32,
		portUsedBandwidthOut	Gauge32,
		portTransmittedCells	Counter32,

		portHwBoard		Integer32,
		portHwModule		Integer32,
		portHwNumber		Integer32,

		portILMIRemoteIpAddress	IpAddress,

		portCDVT                Integer32,
		portInputPolicingStatus	INTEGER,
		portVbrOverbooking      INTEGER,
		portVbrBufferOverb      INTEGER,
		portManagementStatus	INTEGER,
		portAISRDIGeneration	INTEGER,
		portInputCdv            Integer32,
		portInputMaxctd         Integer32,
		portInputDelayMode      INTEGER,
		portOutputCdv           Integer32,
		portOutputMaxctd        Integer32,
		portOutputDelayMode     INTEGER,

		portInputCACErrors	Counter32,
		portInputVPIErrors	Counter32,
		portInputVCIErrors	Counter32,
		portInputSetupErrors	Counter32,

		portOutputCACErrors	Counter32,
		portOutputVPIErrors	Counter32,
		portOutputVCIErrors	Counter32,
		portOutputSetupErrors	Counter32,

		portGCRAPolicingCBR     INTEGER,
		portGCRAPolicingVBR     INTEGER,
		portAAL5PacketDiscardCBR INTEGER,
		portAAL5PacketDiscardVBR INTEGER,
		portAAL5PacketDiscardUBR INTEGER,
		portPPPolicingCBR       INTEGER,
		portPPPolicingVBR	INTEGER,
		portUBRTagging		INTEGER,
		portCACStatus		INTEGER,
		portCounterResetTime    TimeStamp,
		portCounterReset        INTEGER,
		portName		DisplayString,
		portGCRAPolicingRTVBR     INTEGER,
		portGCRAPolicingNRTVBR     INTEGER,
		portAAL5PacketDiscardRTVBR INTEGER,
		portAAL5PacketDiscardNRTVBR INTEGER,
		portPPPolicingRTVBR	INTEGER,
		portPPPolicingNRTVBR	INTEGER,
		portNrtVbrOverbooking   INTEGER,
		portNrtVbrBufferOverb   INTEGER,
		portRtVbrOverbooking    INTEGER,
		portRtVbrBufferOverb    INTEGER,
		portPathOverbooking     INTEGER
	}

portNumber OBJECT-TYPE
	SYNTAX	Integer32
	MAX-ACCESS	read-only
	STATUS	current
	DESCRIPTION
		"The value of this object identifies the port."
	::= { portEntry 1 }

portAdminStatus OBJECT-TYPE
	SYNTAX	INTEGER {
			-- unused(1) deprecated
			down(2),
			up(3)
		}
	MAX-ACCESS	read-write
	STATUS	current
	DESCRIPTION
		"The desired state of this port.  The up(3) state
		indicates that SPANS (Simple Protocol for ATM Network Signalling),
		FORE's link signalling protocol, is used to determine the
		operational status of the port. The down(2) state dictates
		that the operational status of the port should not be determined
		by SPANS."
	::= { portEntry 2 }

portOperStatus OBJECT-TYPE
	SYNTAX	INTEGER {
			up(1),
			down(2)
		}
	MAX-ACCESS	read-only
	STATUS	current
	DESCRIPTION
		"The current operational state of this port,
		as determined either by administrative action,
		when the value of portAdminStatus is down(2),
		or by SPANS (Simple Protocol for ATM Network Signalling),
		FORE's link signalling protocol, when the value of
		porAdminStatus is up(3). For FRAM netmod, it
		is equivalent to the ifOperStatus of the same port"
	::= { portEntry 3 }

portTime OBJECT-TYPE
	SYNTAX	TimeTicks
	MAX-ACCESS	read-only
	STATUS	current
	DESCRIPTION
		"The length of time this port has been in its current state,
		in hundredths of a second."
	::= { portEntry 4 }

portRemoteAtmAddress OBJECT-TYPE
	SYNTAX	SpansAddress
	MAX-ACCESS	read-only
	STATUS	current
	DESCRIPTION
		"The ATM address of the entity connected to this port."
	::= { portEntry 5 }

portRemoteIpAddress OBJECT-TYPE
	SYNTAX	IpAddress
	MAX-ACCESS	read-only
	STATUS	current
	DESCRIPTION
		"The IP address of the entity connected to this port."
	::= { portEntry 6 }

portMaxPathsIn OBJECT-TYPE
	SYNTAX	Integer32
	MAX-ACCESS	read-only
	STATUS	current
	DESCRIPTION
		"The maximum number of incoming virtual paths
		supported by this port."
	::= { portEntry 7 }

portNumPathsIn OBJECT-TYPE
	SYNTAX	Gauge32
	MAX-ACCESS	read-only
	STATUS	current
	DESCRIPTION
		"The number of incoming virtual paths on this port."
	::= { portEntry 8 }

portMaxBandwidthIn OBJECT-TYPE
	SYNTAX	Integer32
	MAX-ACCESS	read-only
	STATUS	current
	DESCRIPTION
		"The maximum incoming bandwidth of this port,
		in cells per second."
	::= { portEntry 9 }

portAllocBandwidthIn OBJECT-TYPE
	SYNTAX	Gauge32
	MAX-ACCESS	read-only
	STATUS	current
	DESCRIPTION
		"The allocated incoming bandwidth of this port,
		in cells per second."
	::= { portEntry 10 }

portUsedBandwidthIn OBJECT-TYPE
	SYNTAX	Gauge32
	MAX-ACCESS	read-only
	STATUS	deprecated
	DESCRIPTION
		"The incoming bandwidth being used on this port,
		in cells per second."
	::= { portEntry 11 }

portReceivedCells OBJECT-TYPE
	SYNTAX	Counter32
	MAX-ACCESS	read-only
	STATUS	current
	DESCRIPTION
		"The number of cells received on this port."
	::= { portEntry 12 }

portMaxPathsOut OBJECT-TYPE
	SYNTAX	Integer32
	MAX-ACCESS	read-only
	STATUS	current
	DESCRIPTION
		"The maximum number of outgoing virtual paths
		supported by this port."
	::= { portEntry 13 }

portNumPathsOut OBJECT-TYPE
	SYNTAX	Gauge32
	MAX-ACCESS	read-only
	STATUS	current
	DESCRIPTION
		"The number of outgoing virtual paths on this port."
	::= { portEntry 14 }

portMaxBandwidthOut OBJECT-TYPE
	SYNTAX	Integer32
	MAX-ACCESS	read-only
	STATUS	current
	DESCRIPTION
		"The maximum outgoing bandwidth of this port,
		in cells per second."
	::= { portEntry 15 }

portAllocBandwidthOut OBJECT-TYPE
	SYNTAX	Gauge32
	MAX-ACCESS	read-only
	STATUS	current
	DESCRIPTION
		"The allocated outgoing bandwidth of this port,
		in cells per second."
	::= { portEntry 16 }

portUsedBandwidthOut OBJECT-TYPE
	SYNTAX	Gauge32
	MAX-ACCESS	read-only
	STATUS	deprecated
	DESCRIPTION
		"The outgoing bandwidth being used on this port,
		in cells per second."
	::= { portEntry 17 }

portTransmittedCells OBJECT-TYPE
	SYNTAX	Counter32
	MAX-ACCESS	read-only
	STATUS	current
	DESCRIPTION
		"The number of cells transmitted on this port."
	::= { portEntry 18 }

portHwBoard OBJECT-TYPE
	SYNTAX	Integer32
	MAX-ACCESS	read-only
	STATUS	current
	DESCRIPTION
		"The hardware board number of this port."
	::= { portEntry 19 }

portHwModule OBJECT-TYPE
	SYNTAX	Integer32
	MAX-ACCESS	read-only
	STATUS	current
	DESCRIPTION
		"The hardware module number of this port. For a control port
		(a software port), the value of this object is the maximun
		number of hardware modules plus one."
	::= { portEntry 20 }

portHwNumber OBJECT-TYPE
	SYNTAX	Integer32
	MAX-ACCESS	read-only
	STATUS	deprecated
	DESCRIPTION
		"The hardware port number of this port. For a control port
		(a software port), the value of this object is 0."
	::= { portEntry 21 }

portILMIRemoteIpAddress OBJECT-TYPE
	SYNTAX	IpAddress
	MAX-ACCESS	read-only
	STATUS	current
	DESCRIPTION
		"The IP address of the entity connected to this port that
		was discovered using ILMI on path 0. If there is no q2931
		siganlling path on VPI 0 that uses ILMI, the value of this
		object is 255.255.255.255."
	::= { portEntry 22 }

portCDVT OBJECT-TYPE
	SYNTAX  Integer32
	MAX-ACCESS  read-write
	STATUS  current
	DESCRIPTION
		"The Cell Delay Variation Tolerance associated with this
		 physical port.  Connections take their default value
		 for CDVT from the input side port."
	::= { portEntry 23 }

portInputPolicingStatus OBJECT-TYPE
	SYNTAX	INTEGER {
			enabled(1),
			disabled(2)
		}
	MAX-ACCESS	read-write
	STATUS	deprecated
	DESCRIPTION
		"The state of policing on this input port.  Enabled(1)
		 forces every connection on this input port to be policed.
		 Disabled(2) turns policing off for every connection on
		 this input port.
		 The functions of this variable have been subsumed by
		 the new GCRAPolicingCBR and GCRAPolicingVBR variables
		 below. Now, writing 'disabled' to this MIB variable has
		 the effect of setting GCRAPolicingCBR=allOff and
		 GCRAPolicingVBR=allOff. On read, this variable reports
		 'enabled', if either of the GCRAPolicing*BR options are
		 in an 'On' setting. Use of this variable should be avoided,
		 in favor of the two GCRA variables."
	::= { portEntry 24 }

portVbrOverbooking OBJECT-TYPE
	SYNTAX	INTEGER (1..32767)
	MAX-ACCESS	read-write
	STATUS	deprecated
	DESCRIPTION
		"The percentage of overbooking for nrtVBR connections.
		The default value is 100 (no overbooking). "
	::= { portEntry 25 }

portVbrBufferOverb OBJECT-TYPE
	SYNTAX	INTEGER (1..32767)
	MAX-ACCESS	read-write
	STATUS	deprecated
	DESCRIPTION
		"The percentage of buffer overbooking for nrtVBR connections.
		The default value is 100 (no overbooking)."
	::= { portEntry 26 }

portManagementStatus OBJECT-TYPE
	SYNTAX	INTEGER {
			managed(1),
			un-managed(2)
		}
	MAX-ACCESS	read-write
	STATUS	current
	DESCRIPTION
		"The visibility of this port in the management station's
		view.  The default value is 1 (managed)."
	::= { portEntry 27 }

portAISRDIGeneration OBJECT-TYPE
	SYNTAX  INTEGER {
			disabled(1),
			enabled(2)
		}
	MAX-ACCESS  read-write
	STATUS  current
	DESCRIPTION
		"The port ATM layer AIS and RDI generation status."
	::= { portEntry 28 }

portGCRAPolicingCBR OBJECT-TYPE
	SYNTAX  INTEGER {
		    allOn(1),
		    allOff(2),
		    svcOn(3),
		    svcOff(4),
		    default(5)
		}
	MAX-ACCESS  read-write
	STATUS  current
	DESCRIPTION
		"This variable defines the per-port policing configuration for
		CBR connections. The states mean the following:
		allOn:  ALL CBR connections arriving on this port will be
			    subjected to GCRA policing.
		allOff: NO CBR connections arriving on this port will be
			    subjected to GCRA policing.
		svcOn:  ALL CRB SVCs arriving on this port will be
			    subjected to GCRA policing
		svcOff: NO CBR SVCs arriving on this port will be
			subjected to GCRA policing. CBR PVCs will be
			GCRA policed based on the state of their UPC contract.
		default: ALL CBR UNI SVCs/SVPs arriving at this port will be
			 subject to GCRA policing and NO CBR NNI SVCs/SVPs
			 arriving at this port will be subject to GCRA policing.
			 CBR PVCs/PVPs arriving at this port will be policed
			 based on the state of their UPC contract."
	DEFVAL { default }
	::= { portEntry 33 }


portGCRAPolicingVBR OBJECT-TYPE
	SYNTAX  INTEGER {
		    allOn(1),
		    allOff(2),
		    svcOn(3),
		    svcOff(4),
		    default(5)
		}
	MAX-ACCESS  read-write
	STATUS  deprecated
	DESCRIPTION
		"This variable defines the per-port policing configuration for
		nrtVBR connections. The states mean the following:
		allOn:  ALL nrtVBR connections arriving on this port will be
			    subjected to GCRA policing.
		allOff: NO nrtVBR connections arriving on this port will be
			    subjected to GCRA policing.
		svcOn:  ALL nrtVBR SVCs arriving on this port will be
			    subjected to GCRA policing
		svcOff: NO nrtVBR SVCs arriving on this port will be
			subjected to GCRA policing. nrtVBR PVCs will be
			GCRA policed based on the state of their UPC contract.
		default: ALL nrtVBR UNI SVCs/SVPs arriving at this port will
			 be subject to GCRA policing and NO nrtVBR NNI SVCs/SVPs
			 arriving at this port will be subject to GCRA policing.
			 nrtVBR PVCs/PVPs arriving at this port will be policed
			 based on the state of their UPC contract."
	DEFVAL { default }
	::= { portEntry 34 }


portAAL5PacketDiscardCBR OBJECT-TYPE
	SYNTAX	INTEGER {
		    allOn(1),
		    allOff(2),
		    svcOn(3), --default
		    svcOff(4)
		}
	MAX-ACCESS  read-write
	STATUS  current
	DESCRIPTION
		"This variable defines the per-port AAL5 packet discard
		configuration for CBR connections.  The states mean the
		following:
		allOn:   All CBR AAL5 connections have packet discard
			 performed on them.
		allOff:  AAL5 packet discard is not performed on any
			 CBR connections.
		svcOn:   Any CBR SVC that 'requests' packet discard will
			 have it performed.  For CBR PVC's, AAL5
			 packet discard is enabled based on the UPC
			 contract of the connection.
		svcOff:  AAL5 packet discard is not performed on any
			 CBR SVC's.For CBR PVC's, AAL5 packet discard
			 is enabled based on the UPC contract of the
			 connection."
	DEFVAL { svcOn }
	::= { portEntry 35 }

portAAL5PacketDiscardVBR OBJECT-TYPE
	SYNTAX  INTEGER {
			allOn(1),
			allOff(2),
			svcOn(3),  -- default
			svcOff(4)
		}
	MAX-ACCESS  read-write
	STATUS  deprecated
	DESCRIPTION
		"This variable defines the per-port AAL5 packet discard
		configuration for nrtVBR connections.  The states mean the
		following:
		allOn:   All nrtVBR AAL5 connections have packet discard
			 performed on them.
		allOff:  AAL5 packet discard is not performed on any
			 nrtVBR connections.
		svcOn:   Any nrtVBR SVC that 'requests' packet discard will
			 have it performed.  For nrtVBR PVC's, AAL5
			 packet discard is enabled based on the UPC
			 contract of the connection.
		svcOff:  AAL5 packet discard is not performed on any
			 nrtVBR SVC's.For nrtVBR PVC's, AAL5 packet discard
			 is enabled based on the UPC contract of the
			 connection."
	DEFVAL { svcOn }
	::= { portEntry 36 }

portAAL5PacketDiscardUBR OBJECT-TYPE
	SYNTAX  INTEGER {
			allOn(1),
			allOff(2),
			svcOn(3),  -- default
			svcOff(4)
		}
	MAX-ACCESS  read-write
	STATUS  current
	DESCRIPTION
		"This variable defines the per-port AAL5 packet discard
		configuration for UBR connections.  The states mean the
		following:
		allOn:   All UBR AAL5 connections have packet discard
			 performed on them.
		allOff:  AAL5 packet discard is not performed on any
			 UBR connections.
		svcOn:   Any UBR SVC that 'requests' packet discard will
			 have it performed.  For UBR PVC's, AAL5
			 packet discard is enabled based on the UPC
			 contract of the connection.
		svcOff:  AAL5 packet discard is not performed on any
			 UBR SVC's.For UBR PVC's, AAL5 packet discard
			 is enabled based on the UPC contract of the
			 connection."
	DEFVAL { svcOn }
	::= { portEntry 37 }

portInputCACErrors OBJECT-TYPE
	SYNTAX  Counter32
	MAX-ACCESS  read-only
	STATUS  current
	DESCRIPTION
		"The number of input CAC (Call Admission Control)
		failures on this port."
	::= { portEntry 38 }

portInputVPIErrors OBJECT-TYPE
	SYNTAX  Counter32
	MAX-ACCESS  read-only
	STATUS  current
	DESCRIPTION
		"The number of input VPI allocation failures on this port."
	::= { portEntry 39 }

portInputVCIErrors OBJECT-TYPE
	SYNTAX  Counter32
	MAX-ACCESS  read-only
	STATUS  current
	DESCRIPTION
		"The number of input VCI allocation failures on this port."
	::= { portEntry 40 }

portInputSetupErrors OBJECT-TYPE
	SYNTAX  Counter32
	MAX-ACCESS  read-only
	STATUS  current
	DESCRIPTION
		"The number of input connection setup failures on this port."
	::= { portEntry 41 }

portOutputCACErrors OBJECT-TYPE
	SYNTAX  Counter32
	MAX-ACCESS  read-only
	STATUS  current
	DESCRIPTION
		"The number of output CAC (Call Admission Control)
		failures on this port."
	::= { portEntry 42 }

portOutputVPIErrors OBJECT-TYPE
	SYNTAX  Counter32
	MAX-ACCESS  read-only
	STATUS  current
	DESCRIPTION
		"The number of output VPI allocation failures on this port."
	::= { portEntry 43 }

portOutputVCIErrors OBJECT-TYPE
	SYNTAX  Counter32
	MAX-ACCESS  read-only
	STATUS  current
	DESCRIPTION
		"The number of output VCI allocation failures on this port."
	::= { portEntry 44 }

portOutputSetupErrors OBJECT-TYPE
	SYNTAX  Counter32
	MAX-ACCESS  read-only
	STATUS  current
	DESCRIPTION
		"The number of output connection setup failures on this port."
	::= { portEntry 45 }

portPPPolicingCBR OBJECT-TYPE
	SYNTAX  INTEGER {
			allOn(1),
			allOff(2),
			svcOn(3),
			svcOff(4)
		}
	MAX-ACCESS  read-write
	STATUS  current
	DESCRIPTION
		"This variable defines the per-port AAL5 Partial Packet
		Policing configuration for CBR connections.  The states
		of this variable mean the following:
		allOn:   All CBR AAL5 connections have partial packet
			 policing performed on them.
		allOff:  AAL5 partial packet policing is not performed
			 on any CBR connections.
		svcOn:   Any CBR SVC that uses AAL5 will have partial
			 packet policing performed on it.  For CBR PVC's,
			 partial packet policing will be performed
			 based on the UPC contract of the connection.
		svcOff:  Partial packet policing will not be performed on
			 any CBR SVC's.  For CBR PVC's, partial packet
			 policing is enabled based on the UPC contract of
			 the connection."
	DEFVAL { svcOn }
	::= { portEntry 46 }

portPPPolicingVBR OBJECT-TYPE
	SYNTAX  INTEGER {
			allOn(1),
			allOff(2),
			svcOn(3),
			svcOff(4)
		}
	MAX-ACCESS  read-write
	STATUS  deprecated
	DESCRIPTION
		"This variable defines the per-port AAL5 Partial Packet
		Policing configuration for nrtVBR connections.  The states
		of this variable mean the following:
		allOn:   All nrtVBR AAL5 connections have partial packet
			 policing performed on them.
		allOff:  AAL5 partial packet policing is not performed
			 on any nrtVBR connections.
		svcOn:   Any nrtVBR SVC that uses AAL5 will have partial
			 packet policing performed on it.  For nrtVBR PVC's,
			 partial packet policing will be performed
			 based on the UPC contract of the connection.
		svcOff:  Partial packet policing will not be performed on
			 any nrtVBR SVC's.  For nrtVBR PVC's, partial packet
			 policing is enabled based on the UPC contract of
			 the connection."
	DEFVAL { svcOn }
	::= { portEntry 47 }

portUBRTagging OBJECT-TYPE
	SYNTAX  INTEGER {
			allOn(1),
			allOff(2),
			svcOn(3),
			svcOff(4)
		}
	MAX-ACCESS  read-write
	STATUS  current
	DESCRIPTION
		"This variable defines the per-port configuration for
		tagging (setting CLP=1) of all cells on UBR connections.
		The states of this variable mean the following:
		allOn:   All UBR connections will be tagged.
		allOff:  No UBR connections will be subject to tagging.
		svcOn:   All UBR SVC's will be tagged.  UBR PVC's will
			 be tagged based on their UPC contract.
		svcOff:  No UBR SVC's will be tagged.  UBR PVC's will
			 be tagged based on their UPC contract."
	DEFVAL { svcOff }
	::= { portEntry 48 }

portInputCdv    OBJECT-TYPE
	SYNTAX  Integer32
	MAX-ACCESS  read-write
	STATUS  current
	DESCRIPTION
		"The current value of Cell Delay Variation attributed
		to the input side of this port, which can be either a
		user specified value or the system default, as determined
		by the setting of portInputCdvMode."
	::= { portEntry 49 }

portInputMaxctd OBJECT-TYPE
	SYNTAX  Integer32
	MAX-ACCESS  read-write
	STATUS  current
	DESCRIPTION
		"This variable give the maximum Cell Transfer Delay that
		is being attributed to the input side of this port.  The
		value can be either user specified or a hardware dependant
		system default value."
	::= { portEntry 50 }

portInputDelayMode OBJECT-TYPE
	SYNTAX  INTEGER {
			systemDefault(1),
			userSpecified(2)
		}
	MAX-ACCESS  read-write
	STATUS  current
	DESCRIPTION
		"This variable controls whether the Cell Delay Variation
		and Maximum Cell Transfer Delay values attributed to the
		input side of this port are based on a user defined value
		or the hardware dependant system default values."
	::= { portEntry 51 }

portOutputCdv   OBJECT-TYPE
	SYNTAX  Integer32
	MAX-ACCESS  read-write
	STATUS  current
	DESCRIPTION
		"If portOutputDelayMode == userSpecified then this variable
		contains the constant amount of Cell Delay Variation
		that is being attributed to this output port.   If
		portOutputDelayMode == systemDefault then an actual value
		for the Cell Delay Variation experienced by connections
		traversing this port is being calculated.  In this case
		the value of this variable is meaningless since CDV
		can only be calculated on a per-connection basis."
	::= { portEntry 52 }

portOutputMaxctd OBJECT-TYPE
	SYNTAX  Integer32
	MAX-ACCESS  read-write
	STATUS  current
	DESCRIPTION
		"This variable gives the maximum Cell Transfer Delay that
		is being attributed to the output side of this port.  The
		value can be either user specified or a hardware dependant
		system default value."
	::= { portEntry 53 }

portOutputDelayMode OBJECT-TYPE
	SYNTAX  INTEGER {
			systemDefault(1),
			userSpecified(2)
		}
	MAX-ACCESS  read-write
	STATUS  current
	DESCRIPTION
		"This variable controls whether the Cell Delay Variation
		value contributed by the input side of this port is based
		on a user defined value or the system default value."
	::= { portEntry 54 }

portCACStatus OBJECT-TYPE
	SYNTAX	INTEGER {
			enabled(1),
			disabled(2)
		}
	MAX-ACCESS	read-write
	STATUS	current
	DESCRIPTION
		"The enforcement state of call admission control.  The
		default is enabled(1)."
	::= { portEntry 59 }

portCounterResetTime OBJECT-TYPE
	SYNTAX  TimeStamp
	MAX-ACCESS  read-only
	STATUS  deprecated
	DESCRIPTION
		"Indicates when this port's counters were reset.  The
		 TimeStamp is equal to moduleUptime when the reset
		 occurred.  If this ports counters were never reset,
		 portCounterResetTime will be zero.  This variable is
		 updated whenever portCounterReset or switchCounterReset
		 is written."
	::= { portEntry 60 }

portCounterReset OBJECT-TYPE
	SYNTAX  INTEGER {
		   resetRequest(1),
		   resetTrue(3),
		   resetFalse(4)
		}
	MAX-ACCESS  read-write
	STATUS  deprecated
	DESCRIPTION
		"Writing a value of resetRequest will result in a
		reset of all counters on this port.  VCC indexed
		counters are excluded.  A response value of resetTrue
		indicates a resetRequest has succeeded and is currently
		in effect.  A response value of resetFalse indicates
		a reset is not currently in effect."
	::= { portEntry 61 }

portName OBJECT-TYPE
	SYNTAX  DisplayString
	MAX-ACCESS  read-only
	STATUS  current
	DESCRIPTION
		"The name of this port (BNP format or otherwise)."
	::= { portEntry 62 }

portGCRAPolicingRTVBR OBJECT-TYPE
	SYNTAX  INTEGER {
		    allOn(1),
		    allOff(2),
		    svcOn(3),
		    svcOff(4),
		    default(5)
		}
	MAX-ACCESS  read-write
	STATUS  current
	DESCRIPTION
		"This variable defines the per-port policing configuration for
		rtVBR connections. The states mean the following:
		allOn:  ALL rtVBR connections arriving on this port will be
			    subjected to GCRA policing.
		allOff: NO rtVBR connections arriving on this port will be
			    subjected to GCRA policing.
		svcOn:  ALL rtVBR SVCs arriving on this port will be
			    subjected to GCRA policing
		svcOff: NO rtVBR SVCs arriving on this port will be
			subjected to GCRA policing. rtVBR PVCs will be
			GCRA policed based on the state of their UPC contract.
		default: ALL rtVBR UNI SVCs/SVPs arriving at this port will
			 be subject to GCRA policing and NO rtVBR NNI SVCs/SVPs
			 arriving at this port will be subject to GCRA policing.
			 rtVBR PVCs/PVPs arriving at this port will be policed
			 based on the state of their UPC contract."
	DEFVAL { default }
	::= { portEntry 64 }

portGCRAPolicingNRTVBR OBJECT-TYPE
	SYNTAX  INTEGER {
		    allOn(1),
		    allOff(2),
		    svcOn(3),
		    svcOff(4),
		    default(5)
		}
	MAX-ACCESS  read-write
	STATUS  current
	DESCRIPTION
		"This variable defines the per-port policing configuration for
		nrtVBR connections. The states mean the following:
		allOn:  ALL nrtVBR connections arriving on this port will be
			    subjected to GCRA policing.
		allOff: NO nrtVBR connections arriving on this port will be
			    subjected to GCRA policing.
		svcOn:  ALL nrtVBR SVCs arriving on this port will be
			    subjected to GCRA policing
		svcOff: NO nrtVBR SVCs arriving on this port will be
			subjected to GCRA policing. nrtVBR PVCs will be
			GCRA policed based on the state of their UPC contract.
		default: ALL nrtVBR UNI SVCs/SVPs arriving at this port will
			 be subject to GCRA policing and NO nrtVBR NNI SVCs/SVPs
			 arriving at this port will be subject to GCRA policing.
			 nrtVBR PVCs/PVPs arriving at this port will be policed
			 based on the state of their UPC contract."
	DEFVAL { default }
	::= { portEntry 65 }

portAAL5PacketDiscardRTVBR OBJECT-TYPE
	SYNTAX  INTEGER {
			allOn(1),
			allOff(2),
			svcOn(3),  -- default
			svcOff(4)
		}
	MAX-ACCESS  read-write
	STATUS  current
	DESCRIPTION
		"This variable defines the per-port AAL5 packet discard
		configuration for rtVBR connections.  The states mean the
		following:
		allOn:   All rtVBR AAL5 connections have packet discard
			 performed on them.
		allOff:  AAL5 packet discard is not performed on any
			 rtVBR connections.
		svcOn:   Any rtVBR SVC that 'requests' packet discard will
			 have it performed.  For rtVBR PVC's, AAL5
			 packet discard is enabled based on the UPC
			 contract of the connection.
		svcOff:  AAL5 packet discard is not performed on any
			 rtVBR SVC's.For rtVBR PVC's, AAL5 packet discard
			 is enabled based on the UPC contract of the
			 connection."
	DEFVAL { svcOn }
	::= { portEntry 66 }

portAAL5PacketDiscardNRTVBR OBJECT-TYPE
	SYNTAX  INTEGER {
			allOn(1),
			allOff(2),
			svcOn(3),  -- default
			svcOff(4)
		}
	MAX-ACCESS  read-write
	STATUS  current
	DESCRIPTION
		"This variable defines the per-port AAL5 packet discard
		configuration for nrtVBR connections.  The states mean the
		following:
		allOn:   All nrtVBR AAL5 connections have packet discard
			 performed on them.
		allOff:  AAL5 packet discard is not performed on any
			 nrtVBR connections.
		svcOn:   Any nrtVBR SVC that 'requests' packet discard will
			 have it performed.  For nrtVBR PVC's, AAL5
			 packet discard is enabled based on the UPC
			 contract of the connection.
		svcOff:  AAL5 packet discard is not performed on any
			 nrtVBR SVC's.For nrtVBR PVC's, AAL5 packet discard
			 is enabled based on the UPC contract of the
			 connection."
	DEFVAL { svcOn }
	::= { portEntry 67 }

portPPPolicingNRTVBR OBJECT-TYPE
	SYNTAX  INTEGER {
			allOn(1),
			allOff(2),
			svcOn(3),
			svcOff(4)
		}
	MAX-ACCESS  read-write
	STATUS  current
	DESCRIPTION
		"This variable defines the per-port AAL5 Partial Packet
		Policing configuration for nrtVBR connections.  The states
		of this variable mean the following:
		allOn:   All nrtVBR AAL5 connections have partial packet
			 policing performed on them.
		allOff:  AAL5 partial packet policing is not performed
			 on any nrtVBR connections.
		svcOn:   Any nrtVBR SVC that uses AAL5 will have partial
			 packet policing performed on it.  For nrtVBR PVC's,
			 partial packet policing will be performed
			 based on the UPC contract of the connection.
		svcOff:  Partial packet policing will not be performed on
			 any nrtVBR SVC's.  For nrtVBR PVC's, partial packet
			 policing is enabled based on the UPC contract of
			 the connection."
	DEFVAL { svcOn }
	::= { portEntry 68 }

portPPPolicingRTVBR OBJECT-TYPE
	SYNTAX  INTEGER {
			allOn(1),
			allOff(2),
			svcOn(3),
			svcOff(4)
		}
	MAX-ACCESS  read-write
	STATUS  current
	DESCRIPTION
		"This variable defines the per-port AAL5 Partial Packet
		Policing configuration for rtVBR connections.  The states
		of this variable mean the following:
		allOn:   All rtVBR AAL5 connections have partial packet
			 policing performed on them.
		allOff:  AAL5 partial packet policing is not performed
			 on any rtVBR connections.
		svcOn:   Any rtVBR SVC that uses AAL5 will have partial
			 packet policing performed on it.  For rtVBR PVC's,
			 partial packet policing will be performed
			 based on the UPC contract of the connection.
		svcOff:  Partial packet policing will not be performed on
			 any rtVBR SVC's.  For rtVBR PVC's, partial packet
			 policing is enabled based on the UPC contract of
			 the connection."
	DEFVAL { svcOn }
	::= { portEntry 69 }

portNrtVbrOverbooking OBJECT-TYPE
	SYNTAX	INTEGER (1..32767)
	MAX-ACCESS	read-write
	STATUS	current
	DESCRIPTION
		"The percentage of overbooking for nrtVBR connections.
		The default value is 100 (no overbooking). "
	::= { portEntry 70 }

portNrtVbrBufferOverb OBJECT-TYPE
	SYNTAX	INTEGER (1..32767)
	MAX-ACCESS	read-write
	STATUS	current
	DESCRIPTION
		"The percentage of buffer overbooking for nrtVBR connections.
		The default value is 100 (no overbooking)."
	::= { portEntry 71 }

portRtVbrOverbooking OBJECT-TYPE
	SYNTAX	INTEGER (1..32767)
	MAX-ACCESS	read-write
	STATUS	current
	DESCRIPTION
		"The percentage of overbooking for rtVBR connections.
		The default value is 100 (no overbooking). "
	::= { portEntry 72 }

portRtVbrBufferOverb OBJECT-TYPE
	SYNTAX	INTEGER (1..32767)
	MAX-ACCESS	read-write
	STATUS	current
	DESCRIPTION
		"The percentage of buffer overbooking for rtVBR connections.
		The default value is 100 (no overbooking)."
	::= { portEntry 73 }

portPathOverbooking OBJECT-TYPE
	SYNTAX	INTEGER (1..32767)
	MAX-ACCESS	read-write
	STATUS	current
	DESCRIPTION
		"The percentage of overbooking for inelastic originating paths.
		 The default value is 100 (no overbooking)."
	::= { portEntry 74 }

------------------------------------------------------------------------------
---  ATM If level Connection Scheduling Table

atmIfConnSchedTable OBJECT-TYPE
	SYNTAX  SEQUENCE OF AtmIfConnSchedEntry
	MAX-ACCESS  not-accessible
	STATUS  current
	DESCRIPTION
		"A table of connection scheduling information on this ATM If."
	::= { portGroup 3 }

atmIfConnSchedEntry OBJECT-TYPE
	SYNTAX  AtmIfConnSchedEntry
	MAX-ACCESS  not-accessible
	STATUS  current
	DESCRIPTION
		"A table of connection scheduling information on this ATM If."
	INDEX   { atmIfConnSchedLink, atmIfConnSchedServCat }
	::= { atmIfConnSchedTable 1 }

AtmIfConnSchedEntry ::=
	SEQUENCE {
		atmIfConnSchedLink        Integer32,
		atmIfConnSchedServCat     Integer32,
		atmIfConnSchedMode        AtmConnSchedMode,
		atmIfConnSchedOverride    INTEGER
	}

atmIfConnSchedLink OBJECT-TYPE
	SYNTAX  Integer32
	MAX-ACCESS  not-accessible
	STATUS  current
	DESCRIPTION
		"The index of this ATM If."
	::= {atmIfConnSchedEntry 1}

atmIfConnSchedServCat OBJECT-TYPE
	SYNTAX  Integer32
	MAX-ACCESS  not-accessible
	STATUS  current
	DESCRIPTION
		"Index of this service category within serviceCategoryTable."
	::= {atmIfConnSchedEntry 2}

atmIfConnSchedMode OBJECT-TYPE
	SYNTAX  AtmConnSchedMode
	MAX-ACCESS  read-write
	STATUS  current
	DESCRIPTION
		"The scheduling mode used for connections of type
		 atmIfConnSchedServCat on this ATM if. The default
		 choice of AtmConnSchedMode is not allowed at
		 atmIf level."
	::= {atmIfConnSchedEntry 3}

atmIfConnSchedOverride OBJECT-TYPE
	SYNTAX  INTEGER {
		   on(1),
		   off(2)
		}
	MAX-ACCESS  read-write
	STATUS  current
	DESCRIPTION
		"The override option used for connections of type
		 atmIfConnSchedServCat on this ATM if."
	::= {atmIfConnSchedEntry 4}


--------------------------------------------------------------------
-- The IfIndexMap Group --------------------------------------------

ifIndexMapTable OBJECT-TYPE
	SYNTAX	SEQUENCE OF IfIndexMapEntry
	MAX-ACCESS	not-accessible
	STATUS	current
	DESCRIPTION
		"A table containing information about how physical
		 interfaces ifIndexes relate to the b-n-p triplets.
		 Other ifIndices will not have entries in this table."
	::= { ifIndexMapGroup 1 }

ifIndexMapEntry OBJECT-TYPE
	SYNTAX	IfIndexMapEntry
	MAX-ACCESS	not-accessible
	STATUS	current
	DESCRIPTION
		"A table entry containing ifindex/b-n-p information."
	INDEX	{ ifIndexMapIndex }
	::= { ifIndexMapTable 1 }

IfIndexMapEntry ::=
	SEQUENCE {
		ifIndexMapIndex   Integer32,
		ifIndexMapBoard   Integer32,
		ifIndexMapNetmod  Integer32,
		ifIndexMapPort    Integer32
}

ifIndexMapIndex OBJECT-TYPE
	SYNTAX	Integer32
	MAX-ACCESS	read-only
	STATUS	current
	DESCRIPTION
		"The ifIndex of this entry. The ifindex must be that of
		 a physical interface."
	::= { ifIndexMapEntry 1 }

ifIndexMapBoard OBJECT-TYPE
	SYNTAX	Integer32
	MAX-ACCESS	read-only
	STATUS	current
	DESCRIPTION
		"The board number that this ifIndex refers to"
	::= { ifIndexMapEntry 2 }

ifIndexMapNetmod OBJECT-TYPE
	SYNTAX	Integer32
	MAX-ACCESS	read-only
	STATUS	current
	DESCRIPTION
		"The netmod number that this ifIndex refers to"
	::= { ifIndexMapEntry 3 }

ifIndexMapPort OBJECT-TYPE
	SYNTAX	Integer32
	MAX-ACCESS	read-only
	STATUS	current
	DESCRIPTION
		"The port number that this ifIndex refers to"
	::= { ifIndexMapEntry 4 }

cesExtTable OBJECT-TYPE
	SYNTAX  TestAndIncr
	MAX-ACCESS read-only
	STATUS current
	DESCRIPTION
		"This indicates the value of the next available index
		to be used for CES creation"
	::= { cesExtGroup 1 }

cbrctConfTable OBJECT-TYPE
	SYNTAX  SEQUENCE OF CbrctConfEntry
	MAX-ACCESS not-accessible
	STATUS current
	DESCRIPTION
		"A table of CBR Cut-through configuration information."
	::= { cesExtGroup 2 }

cbrctConfEntry OBJECT-TYPE
	SYNTAX  CbrctConfEntry
	MAX-ACCESS  not-accessible
	STATUS  current
	DESCRIPTION
		"A table entry containing CBR Cut-through configuration
		information for each CES connection. "
	INDEX   { ifIndex }
	::= { cbrctConfTable 1 }

CbrctConfEntry ::=
	SEQUENCE {
		cbrctState              INTEGER,
		cbrctIdleDetection      INTEGER,
		cbrctIdleMask           Integer32,
		cbrctNoOfIdlePatterns   Integer32,
		cbrctIdlePatterns       Integer32,
		cbrctIdleIntPeriod      TimeInterval,
		cbrctActiveIntPeriod    TimeInterval
	}

cbrctState OBJECT-TYPE
	SYNTAX  INTEGER {
		enabled(1),
		disabled(2)
	}
	MAX-ACCESS  read-write
	STATUS  current
	DESCRIPTION
		"This variable indicates whether the CBR Cut-through
		feature is enabled or disabled on the ingress connection.
		The values mean:
		enabled         CBR Cut-through enabled
		disabled        CBR Cut-through disabled"
	DEFVAL { disabled }
	::= { cbrctConfEntry 1 }

cbrctIdleDetection OBJECT-TYPE
	SYNTAX  INTEGER {
		idlePattern(1),
		cas(2)
	}
	MAX-ACCESS  read-write
	STATUS  current
	DESCRIPTION
		"This variable identifies the idle detection
		mechanism used on this connection.
		The different values are:
		idlePattern(1)          detection is based on idle
					pattern detection
		cas(2)                  detection is based on CAS
					signalling"
	DEFVAL { idlePattern }
	::= { cbrctConfEntry 2 }

cbrctIdleMask OBJECT-TYPE
	SYNTAX  Integer32
	MAX-ACCESS  read-write
	STATUS  current
	DESCRIPTION
		"This contains the mask pattern for idle detection."
	DEFVAL { 'ff'h }
	::= { cbrctConfEntry 3 }

cbrctNoOfIdlePatterns OBJECT-TYPE
	SYNTAX  Integer32
	MAX-ACCESS  read-write
	STATUS  current
	DESCRIPTION
		"This variable contains the number of idle patterns
		configured for detection."
	DEFVAL { 2 }
	::= { cbrctConfEntry 4 }

cbrctIdlePatterns OBJECT-TYPE
	SYNTAX  Integer32
	MAX-ACCESS  read-write
	STATUS  current
	DESCRIPTION
		"This contains the patterns for idle detection.
		For detection based on both idle and mask patterns
		it contains the idle octet patterns. For detection
		based on signalling it contains the octet value
		of AB signalling bits (eg. 00000010 (02H), the bit
		0 is B bit and bit 1 is A bit). Maximum of 4 idle patterns
		are used. The idle patterns get filled from the
		least significant byte. The cbrctNoOfIdlePatterns gives
		the number of idle patterns."
	DEFVAL { '00007fff'h }
	::= { cbrctConfEntry 5 }

cbrctIdleIntPeriod OBJECT-TYPE
	SYNTAX  TimeInterval
	MAX-ACCESS  read-write
	STATUS  current
	DESCRIPTION
		"This contains the integration period for idle
		detection."
	DEFVAL { 6 }
	::= { cbrctConfEntry 6 }

cbrctActiveIntPeriod OBJECT-TYPE
	SYNTAX  TimeInterval
	MAX-ACCESS  read-write
	STATUS  current
	DESCRIPTION
		"This contains the integration period for active
		detection."
	DEFVAL { 6 }
	::= { cbrctConfEntry 7 }

--------------------------------------------------------------------------------
-- asxAtmIfGroup

asxAtmIfTable OBJECT-TYPE
	SYNTAX  SEQUENCE OF AsxAtmIfEntry
	MAX-ACCESS  not-accessible
	STATUS  current
	DESCRIPTION
		"A table of atm interface information."
	::= {asxAtmIfGroup 1 }

asxAtmIfEntry OBJECT-TYPE
	SYNTAX  AsxAtmIfEntry
	MAX-ACCESS  not-accessible
	STATUS  current
	DESCRIPTION
		"A table entry containing atm interface information."
	INDEX { asxAtmIfName }
	::= { asxAtmIfTable 1 }

AsxAtmIfEntry ::=
	SEQUENCE {
		asxAtmIfName	DisplayString,
		asxAtmIfLinkid	Integer32
	}

asxAtmIfName OBJECT-TYPE
	SYNTAX  DisplayString
	MAX-ACCESS  not-accessible
	STATUS  current
	DESCRIPTION
		"The persistent name of this atm interface. It is
		used to index this atm interface. All letters in the
		asxAtmIfName are always represented in uppercase."
	::= { asxAtmIfEntry 1 }

asxAtmIfLinkid OBJECT-TYPE
	SYNTAX  Integer32
	MAX-ACCESS  read-only
	STATUS  current
	DESCRIPTION
		"The linkid of this atm interface."
	::= { asxAtmIfEntry 2 }

------------------------------------------------------------------------
-- The Path Group

pathTable OBJECT-TYPE
	SYNTAX	SEQUENCE OF PathEntry
	MAX-ACCESS	not-accessible
	STATUS	current
	DESCRIPTION
		"A table of information about the virtual paths
		passing through this ATM switch."
	::= { pathGroup 1 }

pathEntry OBJECT-TYPE
	SYNTAX	PathEntry
	MAX-ACCESS	not-accessible
	STATUS	current
	DESCRIPTION
		"A table entry containing path information."
	INDEX	{ pathPort, pathVPI }
	::= { pathTable 1 }

PathEntry ::=
	SEQUENCE {
		pathPort		Integer32,
		pathVPI			Integer32,
		pathStatus		EntryStatus,
		pathNumOutputs		Gauge32,
		pathMaxChannels		Integer32,
		pathNumChannels		Gauge32,
		pathMaxBandwidth	Integer32,
		pathAllocBandwidth	Gauge32,
		pathUsedBandwidth	Gauge32,
		pathCells		Counter32,
		pathUptime		TimeTicks,
		pathSigProtocol		AtmSigProtocol,
		pathRejectedCells	Counter32,
		pathMinVCI		Integer32,
		pathMaxVCI		Integer32,
		pathCACErrors		Counter32,
		pathVCIErrors		Counter32,
		pathSetupErrors		Counter32
	}

pathPort OBJECT-TYPE
	SYNTAX	Integer32
	MAX-ACCESS	read-only
	STATUS	current
	DESCRIPTION
		"The value of this object identifies the input port
		of this path and is the same as the portNumber."
	::= { pathEntry 1 }

pathVPI OBJECT-TYPE
	SYNTAX	Integer32
	MAX-ACCESS	read-only
	STATUS	current
	DESCRIPTION
		"The input VPI (Virtual Path Identifier) of this path."
	::= { pathEntry 2 }

pathStatus OBJECT-TYPE
	SYNTAX	EntryStatus
	MAX-ACCESS	read-create
	STATUS	current
	DESCRIPTION
		"The status of this path entry."
	::= { pathEntry 3 }

pathNumOutputs OBJECT-TYPE
	SYNTAX	Gauge32
	MAX-ACCESS	read-only
	STATUS	current
	DESCRIPTION
		"The number of output ports to which this path is routed."
	::= { pathEntry 4 }

pathMaxChannels OBJECT-TYPE
	SYNTAX	Integer32
	MAX-ACCESS	read-create
	STATUS	current
	DESCRIPTION
		"The maximum number of virtual channels that
		can be allocated on this path."
	::= { pathEntry 5 }

pathNumChannels OBJECT-TYPE
	SYNTAX	Gauge32
	MAX-ACCESS	read-only
	STATUS	current
	DESCRIPTION
		"The number of virtual channels currently allocated
		on this path."
	::= { pathEntry 6 }

pathMaxBandwidth OBJECT-TYPE
	SYNTAX	Integer32
	MAX-ACCESS	read-create
	STATUS	current
	DESCRIPTION
		"The maximum bandwidth of this path, in cells per second."
	::= { pathEntry 7 }

pathAllocBandwidth OBJECT-TYPE
	SYNTAX	Gauge32
	MAX-ACCESS	read-create
	STATUS	current
	DESCRIPTION
		"The allocated bandwidth of this path, in cells per second."
	::= { pathEntry 8 }

pathUsedBandwidth OBJECT-TYPE
	SYNTAX	Gauge32
	MAX-ACCESS	read-only
	STATUS	deprecated
	DESCRIPTION
		"The bandwidth being used on this path, in cells per second."
	::= { pathEntry 9 }

pathCells OBJECT-TYPE
	SYNTAX	Counter32
	MAX-ACCESS	read-only
	STATUS	current
	DESCRIPTION
		"The number of cells transferred over this path."
	::= { pathEntry 10 }

pathUptime OBJECT-TYPE
	SYNTAX	TimeTicks
	MAX-ACCESS	read-only
	STATUS	current
	DESCRIPTION
		"The time since this path was created,
		in hundredths of a second."
	::= { pathEntry 11 }

pathSigProtocol OBJECT-TYPE
	SYNTAX	AtmSigProtocol
	MAX-ACCESS	read-only
	STATUS	current
	DESCRIPTION
		"The signaling protocol that created this path."
	::= { pathEntry 12 }

pathRejectedCells OBJECT-TYPE
	SYNTAX	Counter32
	MAX-ACCESS	read-only
	STATUS	current
	DESCRIPTION
		"The number of cells over this path that were rejected
		(i.e. dropped) by the policer on the switch fabric.
		This does not include any cells that may have been
		tagged with CLP=1 by the policer, only cells that were
		discarded."
	::= { pathEntry 13 }

pathMinVCI OBJECT-TYPE
	SYNTAX	Integer32
	MAX-ACCESS	read-create
	STATUS	current
	DESCRIPTION
		"The minimum VCI that can be allocated on this path."
	::= { pathEntry 14 }

pathMaxVCI OBJECT-TYPE
	SYNTAX	Integer32
	MAX-ACCESS	read-create
	STATUS	current
	DESCRIPTION
		"The maximum VCI that can be allocated on this path."
	::= { pathEntry 15 }

pathCACErrors OBJECT-TYPE
	SYNTAX  Counter32
	MAX-ACCESS  read-only
	STATUS  current
	DESCRIPTION
		"The number of CAC (Call Admission Control) failures on
		this path."
	::= { pathEntry 16 }

pathVCIErrors OBJECT-TYPE
	SYNTAX  Counter32
	MAX-ACCESS  read-only
	STATUS  current
	DESCRIPTION
		"The number of VCI allocation failures on this path."
	::= { pathEntry 17 }

pathSetupErrors OBJECT-TYPE
	SYNTAX  Counter32
	MAX-ACCESS  read-only
	STATUS  current
	DESCRIPTION
		"The number of connection setup failures on this path."
	::= { pathEntry 18 }

------------------------------------------------------------------------

pathRouteTable OBJECT-TYPE
	SYNTAX	SEQUENCE OF PathRouteEntry
	MAX-ACCESS	not-accessible
	STATUS	current
	DESCRIPTION
		"A table of information about the routing of paths through
		this ATM switch."
	::= { pathGroup 2 }

pathRouteEntry OBJECT-TYPE
	SYNTAX	PathRouteEntry
	MAX-ACCESS	not-accessible
	STATUS	current
	DESCRIPTION
		"A table entry containing path route information."
	INDEX	{ pathrInputPort, pathrInputVPI, pathrOutputPort, pathrOutputVPI }
	::= { pathRouteTable 1 }

PathRouteEntry ::=
	SEQUENCE {
		pathrInputPort			Integer32,
		pathrInputVPI			Integer32,
		pathrOutputPort			Integer32,
		pathrOutputVPI			Integer32,
		pathrStatus			EntryStatus,
		pathrMaxBandwidth		Integer32,
		pathrAllocBandwidth		Gauge32,
		pathrCells			Counter32,
		pathrUptime			TimeTicks,
		pathrSigProtocol		AtmSigProtocol,
		pathrRejectedCells		Counter32,
		pathrLoopVPI			Integer32,
		pathrUpcContract		Integer32,
		pathrName			OCTET STRING,
		pathrConnectionType		ConnectionType,
		pathrServCat			Integer32
	}

pathrInputPort OBJECT-TYPE
	SYNTAX	Integer32
	MAX-ACCESS	read-only
	STATUS	current
	DESCRIPTION
		"The value of this object identifies the input port
		of this path and is the same as the portNumber."
	::= { pathRouteEntry 1 }

pathrInputVPI OBJECT-TYPE
	SYNTAX	Integer32
	MAX-ACCESS	read-only
	STATUS	current
	DESCRIPTION
		"The input VPI  (Virtual Path Identifier) of this path."
	::= { pathRouteEntry 2 }

pathrOutputPort OBJECT-TYPE
	SYNTAX	Integer32
	MAX-ACCESS	read-only
	STATUS	current
	DESCRIPTION
		"The value of this object identifies the output port
		of this path and is the same as the portNumber."
	::= { pathRouteEntry 3 }

pathrOutputVPI OBJECT-TYPE
	SYNTAX	Integer32
	MAX-ACCESS	read-only
	STATUS	current
	DESCRIPTION
		"The output VPI  (Virtual Path Identifier) of this path."
	::= { pathRouteEntry 4 }

pathrStatus OBJECT-TYPE
	SYNTAX	EntryStatus
	MAX-ACCESS	read-create
	STATUS	current
	DESCRIPTION
		"The status of this path entry."
	::= { pathRouteEntry 5 }

pathrMaxBandwidth OBJECT-TYPE
	SYNTAX	Integer32
	MAX-ACCESS	read-only
	STATUS	current
	DESCRIPTION
		"The maximum bandwidth of this path, in cells per second."
	::= { pathRouteEntry 6 }

pathrAllocBandwidth OBJECT-TYPE
	SYNTAX	Gauge32
	MAX-ACCESS	read-create
	STATUS	current
	DESCRIPTION
		"The allocated bandwidth of this path, in cells per second."
	::= { pathRouteEntry 7 }

pathrCells OBJECT-TYPE
	SYNTAX	Counter32
	MAX-ACCESS	read-only
	STATUS	current
	DESCRIPTION
		"The number of cells transferred over this path."
	::= { pathRouteEntry 8 }

pathrUptime OBJECT-TYPE
	SYNTAX	TimeTicks
	MAX-ACCESS	read-only
	STATUS	current
	DESCRIPTION
		"The time since this path was created,
		in hundredths of a second."
	::= { pathRouteEntry 9 }

pathrSigProtocol OBJECT-TYPE
	SYNTAX	AtmSigProtocol
	MAX-ACCESS	read-only
	STATUS	current
	DESCRIPTION
		"The signaling protocol that created this path."
	::= { pathRouteEntry 10 }

pathrRejectedCells OBJECT-TYPE
	SYNTAX	Counter32
	MAX-ACCESS	read-only
	STATUS	current
	DESCRIPTION
		"The number of cells over this through path that
		were rejected (i.e. dropped) by the policer on the
		switch fabric.  This does not include any cells that
		may have been tagged with CLP=1 by the policer, only
		cells that were discarded."
	::= { pathRouteEntry 11 }

pathrLoopVPI OBJECT-TYPE
	SYNTAX	Integer32
	MAX-ACCESS	read-create
	STATUS	current
	DESCRIPTION
		"If this value is other than -1, cells destined for
		pathrOutputPort, pathrOutputVPI will be translated by
		the netmod to pathrLoopVPI before actually being trasmitted.
		This was instituted to facilitate single port loopback."
	::= { pathRouteEntry 12 }

pathrUpcContract OBJECT-TYPE
	SYNTAX	Integer32
	MAX-ACCESS	read-create
	STATUS	current
	DESCRIPTION
		"The UPC contract that will be used to police this through
		path.  This is the number of the row in the upcContractTable."
	::= { pathRouteEntry 13 }

pathrName OBJECT-TYPE
	SYNTAX  OCTET STRING (SIZE(0..32))
	MAX-ACCESS  read-create
	STATUS  current
	DESCRIPTION
		" The value of this object identifies the
		name that has been assigned for this path."
	::= { pathRouteEntry 14 }

pathrConnectionType OBJECT-TYPE
	SYNTAX  ConnectionType
	MAX-ACCESS  read-create
	STATUS  current
	DESCRIPTION
		" This object identifies the type of the path
		endpoints with respect to a particular network."
	::= { pathRouteEntry 15 }

pathrServCat OBJECT-TYPE
	SYNTAX	Integer32
	MAX-ACCESS	read-only
	STATUS	current
	DESCRIPTION
		"Index of this service category within serviceCategoryTable"
	::= { pathRouteEntry 16 }

------------------------------------------------------------------------

outputPathTable OBJECT-TYPE
	SYNTAX	SEQUENCE OF OutputPathEntry
	MAX-ACCESS	not-accessible
	STATUS	current
	DESCRIPTION
		"A table of information about the virtual paths
		originating at this ATM switch."
	::= { pathGroup 3 }

outputPathEntry OBJECT-TYPE
	SYNTAX	OutputPathEntry
	MAX-ACCESS	not-accessible
	STATUS	current
	DESCRIPTION
		"A table entry containing output path information."
	INDEX	{ opathPort, opathVPI }
	::= { outputPathTable 1 }

OutputPathEntry ::=
	SEQUENCE {
		opathPort		Integer32,
		opathVPI		Integer32,
		opathStatus		EntryStatus,
		opathMaxChannels	Integer32,
		opathNumChannels	Gauge32,
		opathMaxBandwidth	Integer32,
		opathAllocBandwidth	Gauge32,
		opathUsedBandwidth	Gauge32,
		opathCells		Counter32,
		opathUptime		TimeTicks,
		opathSigProtocol	AtmSigProtocol,
		opathRejectedCells	Counter32,
		opathTrafficShapeVPI	Integer32,
		opathVbrOverbooking     INTEGER,
		opathVbrBufferOverb     INTEGER,
		opathMinVCI		Integer32,
		opathMaxVCI		Integer32,
		opathCACErrors		Counter32,
		opathVCIErrors		Counter32,
		opathSetupErrors	Counter32,
		opathLoopVPI		Integer32,
		opathSchedMode		AtmOrigPathSchedMode,
		opathNrtVbrOverbooking  INTEGER,
		opathNrtVbrBufferOverb  INTEGER,
		opathRtVbrOverbooking   INTEGER,
		opathRtVbrBufferOverb   INTEGER
	}

opathPort OBJECT-TYPE
	SYNTAX	Integer32
	MAX-ACCESS	read-only
	STATUS	current
	DESCRIPTION
		"The value of this object identifies the output port
		of this path and is the same as the portNumber."
	::= { outputPathEntry 1 }

opathVPI OBJECT-TYPE
	SYNTAX	Integer32
	MAX-ACCESS	read-only
	STATUS	current
	DESCRIPTION
		"The VPI  (Virtual Path Identifier) of this path."
	::= { outputPathEntry 2 }

opathStatus OBJECT-TYPE
	SYNTAX	EntryStatus
	MAX-ACCESS	read-create
	STATUS	current
	DESCRIPTION
		"The status of this path entry."
	::= { outputPathEntry 3 }

opathMaxChannels OBJECT-TYPE
	SYNTAX	Integer32
	MAX-ACCESS	read-create
	STATUS	current
	DESCRIPTION
		"The maximum number of virtual channels that
		can be allocated on this path."
	::= { outputPathEntry 4 }

opathNumChannels OBJECT-TYPE
	SYNTAX	Gauge32
	MAX-ACCESS	read-only
	STATUS	current
	DESCRIPTION
		"The number of virtual channels currently allocated
		on this path."
	::= { outputPathEntry 5 }

opathMaxBandwidth OBJECT-TYPE
	SYNTAX	Integer32
	MAX-ACCESS	read-create
	STATUS	current
	DESCRIPTION
		"The maximum bandwidth of this path, in cells per second."
	::= { outputPathEntry 6 }

opathAllocBandwidth OBJECT-TYPE
	SYNTAX	Gauge32
	MAX-ACCESS	read-create
	STATUS	current
	DESCRIPTION
		"The allocated bandwidth of this path, in cells per second."
	::= { outputPathEntry 7 }

opathUsedBandwidth OBJECT-TYPE
	SYNTAX	Gauge32
	MAX-ACCESS	read-only
	STATUS	deprecated
	DESCRIPTION
		"The bandwidth used on this path, in cells per second."
	::= { outputPathEntry 8 }

opathCells OBJECT-TYPE
	SYNTAX	Counter32
	MAX-ACCESS	read-only
	STATUS	current
	DESCRIPTION
		"The number of cells transmitted on this path."
	::= { outputPathEntry 9 }

opathUptime OBJECT-TYPE
	SYNTAX	TimeTicks
	MAX-ACCESS	read-only
	STATUS	current
	DESCRIPTION
		"The time since this path was created,
		in hundredths of a second."
	::= { outputPathEntry 10 }

opathSigProtocol OBJECT-TYPE
	SYNTAX	AtmSigProtocol
	MAX-ACCESS	read-only
	STATUS	current
	DESCRIPTION
		"The signaling protocol that created this path."
	::= { outputPathEntry 11 }

opathRejectedCells OBJECT-TYPE
	SYNTAX	Counter32
	MAX-ACCESS	read-only
	STATUS	current
	DESCRIPTION
		"The number of cells on this output path that were
		rejected (i.e. dropped) by the policer on the switch fabric.
		This does not include any cells that may have been
		tagged with CLP=1 by the policer, only cells that were
		discarded."
	::= { outputPathEntry 12 }

opathTrafficShapeVPI OBJECT-TYPE
	SYNTAX	Integer32
	MAX-ACCESS	read-create
	STATUS	current
	DESCRIPTION
		"The VPI of shaped cells"
	::= { outputPathEntry 13 }

opathVbrOverbooking OBJECT-TYPE
	SYNTAX	INTEGER (-1..32767)
	MAX-ACCESS	read-create
	STATUS	deprecated
	DESCRIPTION
		"The percentage of overbooking for nrtVBR connections.
		The default value is 100 (no overbooking).  A value of -1
		indicates that the path is elastic, and therefore the
		overbooking factors are meaningless."
	::= { outputPathEntry 14 }

opathVbrBufferOverb OBJECT-TYPE
	SYNTAX	INTEGER (-1..32767)
	MAX-ACCESS	read-create
	STATUS	deprecated
	DESCRIPTION
		"The percentage of buffer overbooking for nrtVBR connections.
		The default value is 100 (no overbooking).  A value of -1
		indicates that the path is elastic, and therefore the
		overbooking factors are meaningless."
	::= { outputPathEntry 15 }

opathMinVCI OBJECT-TYPE
	SYNTAX	Integer32
	MAX-ACCESS	read-create
	STATUS	current
	DESCRIPTION
		"The minimum VCI that can be allocated on this path."
	::= { outputPathEntry 16 }

opathMaxVCI OBJECT-TYPE
	SYNTAX	Integer32
	MAX-ACCESS	read-create
	STATUS	current
	DESCRIPTION
		"The maximum VCI that can be allocated on this path."
	::= { outputPathEntry 17 }

opathCACErrors OBJECT-TYPE
	SYNTAX  Counter32
	MAX-ACCESS  read-only
	STATUS  current
	DESCRIPTION
		"The number of CAC (Call Admission Control) failures on
		this path."
	::= { outputPathEntry 18 }

opathVCIErrors OBJECT-TYPE
	SYNTAX  Counter32
	MAX-ACCESS  read-only
	STATUS  current
	DESCRIPTION
		"The number of VCI allocation failures on this path."
	::= { outputPathEntry 19 }

opathSetupErrors OBJECT-TYPE
	SYNTAX  Counter32
	MAX-ACCESS  read-only
	STATUS  current
	DESCRIPTION
		"The number of connection setup failures on this path."
	::= { outputPathEntry 20 }

opathLoopVPI OBJECT-TYPE
	SYNTAX	Integer32
	MAX-ACCESS	read-create
	STATUS	current
	DESCRIPTION
		"If this value is assigned to other than -1,
		 the netmod will modify cell headers received from
		 the fabric that are destined for opathPort, opathVPI
		 to have the vpi value of opathLoopVPI before being
		 transmitted.  This extra translation can be used to
		 loop cells back onto the fabric using a single port."
	::= { outputPathEntry 21 }

opathSchedMode OBJECT-TYPE
	SYNTAX  AtmOrigPathSchedMode
	MAX-ACCESS  read-create
	STATUS  current
	DESCRIPTION
		"The value of this object identifies the scheduling
		 mode for this originating path."
	DEFVAL  { flat }
	::= { outputPathEntry 22 }

opathNrtVbrOverbooking OBJECT-TYPE
	SYNTAX	INTEGER (-1..32767)
	MAX-ACCESS	read-create
	STATUS	current
	DESCRIPTION
		"The percentage of overbooking for nrtVBR connections.
		The default value is 100 (no overbooking).  A value of -1
		indicates that the path is elastic, and therefore the
		overbooking factors are meaningless."
	::= { outputPathEntry 23 }

opathNrtVbrBufferOverb OBJECT-TYPE
	SYNTAX	INTEGER (-1..32767)
	MAX-ACCESS	read-create
	STATUS	current
	DESCRIPTION
		"The percentage of buffer overbooking for nrtVBR connections.
		The default value is 100 (no overbooking).  A value of -1
		indicates that the path is elastic, and therefore the
		overbooking factors are meaningless."
	::= { outputPathEntry 24 }

opathRtVbrOverbooking OBJECT-TYPE
	SYNTAX	INTEGER (-1..32767)
	MAX-ACCESS	read-create
	STATUS	current
	DESCRIPTION
		"The percentage of overbooking for rtVBR connections.
		The default value is 100 (no overbooking).  A value of -1
		indicates that the path is elastic, and therefore the
		overbooking factors are meaningless."
	::= { outputPathEntry 25 }

opathRtVbrBufferOverb OBJECT-TYPE
	SYNTAX	INTEGER (-1..32767)
	MAX-ACCESS	read-create
	STATUS	current
	DESCRIPTION
		"The percentage of buffer overbooking for rtVBR connections.
		The default value is 100 (no overbooking).  A value of -1
		indicates that the path is elastic, and therefore the
		overbooking factors are meaningless."
	::= { outputPathEntry 26 }

------------------------------------------------------------------------

outputPathStatsTable OBJECT-TYPE
	SYNTAX  SEQUENCE OF OutputPathStatsEntry
	MAX-ACCESS  not-accessible
	STATUS  current
	DESCRIPTION
		"A table of statistics information about the virtual
		 paths originating at this ATM switch."
	::= { pathGroup 4 }

outputPathStatsEntry OBJECT-TYPE
	SYNTAX  OutputPathStatsEntry
	MAX-ACCESS  not-accessible
	STATUS  current
	DESCRIPTION
		"A table entry containing originating channel
		statistics information."
	INDEX  { opathStatsPort, opathStatsVPI }
	::= { outputPathStatsTable 1 }

OutputPathStatsEntry ::= SEQUENCE {
	opathStatsPort                      Integer32,
	opathStatsVPI                       Integer32,
	opathStatsLostCells                 Counter32,
	opathStatsTransmittedCells          Counter32,
	opathStatsIntentionalLostCells      Counter32,
	opathStatsCLP0Cells                 Counter32,
	opathStatsLostPackets               Counter32,
	opathStatsTransmittedPackets        Counter32
}

opathStatsPort OBJECT-TYPE
	SYNTAX  Integer32
	MAX-ACCESS  read-only
	STATUS  current
	DESCRIPTION
		"The value of this object identifies the output port
		of this channel and is the same as the opathPort,
		and portNumber."
	::= { outputPathStatsEntry 1}

opathStatsVPI OBJECT-TYPE
	SYNTAX  Integer32
	MAX-ACCESS  read-only
	STATUS  current
	DESCRIPTION
		"The value of this object identifies the output VPI
		(Virtual Path Identifier) of this channel and is the
		same as the opathVPI."
	::= { outputPathStatsEntry 2}

opathStatsLostCells OBJECT-TYPE
	SYNTAX  Counter32
	MAX-ACCESS  read-only
	STATUS  current
	DESCRIPTION
		"The number of cells on this output path that were dropped
		at the output netmod."
	::= { outputPathStatsEntry 3}

opathStatsTransmittedCells OBJECT-TYPE
	SYNTAX  Counter32
	MAX-ACCESS  read-only
	STATUS  current
	DESCRIPTION
		"The number of cells on this output path that were transmitted."
	::= { outputPathStatsEntry 4 }

opathStatsIntentionalLostCells OBJECT-TYPE
	SYNTAX  Counter32
	MAX-ACCESS  read-only
	STATUS  current
	DESCRIPTION
		"The number of cells on this output path that were dropped
		intentionally at the output netmod."
	::= { outputPathStatsEntry 5}

opathStatsCLP0Cells OBJECT-TYPE
	SYNTAX  Counter32
	MAX-ACCESS  read-only
	STATUS  current
	DESCRIPTION
		"The number of CLP = 0 cells transmitted on this output path."
	::= { outputPathStatsEntry 6}

opathStatsLostPackets OBJECT-TYPE
	SYNTAX  Counter32
	MAX-ACCESS  read-only
	STATUS  current
	DESCRIPTION
		"The number of packets on this output path that were dropped
		at the output netmod."
	::= { outputPathStatsEntry 7}

opathStatsTransmittedPackets OBJECT-TYPE
	SYNTAX  Counter32
	MAX-ACCESS  read-only
	STATUS  current
	DESCRIPTION
		"The number of Packets on this output path that were transmitted."
	::= { outputPathStatsEntry 8 }


------------------------------------------------------------------------
-- output path channel scheduling table

outputPathChannelSchedTable OBJECT-TYPE
	SYNTAX  SEQUENCE OF OutputPathChannelSchedEntry
	MAX-ACCESS  not-accessible
	STATUS  current
	DESCRIPTION
		"A table of connection scheduling information on this output path."
	::= { pathGroup 5 }

outputPathChannelSchedEntry OBJECT-TYPE
	SYNTAX  OutputPathChannelSchedEntry
	MAX-ACCESS  not-accessible
	STATUS  current
	DESCRIPTION
		"A table of connection scheduling information on this output path."
	INDEX  { opathChannelSchedPort, opathChannelSchedVPI, opathChannelSchedServCat }
	::= { outputPathChannelSchedTable 1 }

OutputPathChannelSchedEntry ::= SEQUENCE {
	opathChannelSchedPort                   Integer32,
	opathChannelSchedVPI                    Integer32,
	opathChannelSchedServCat                Integer32,
	opathChannelSchedSchedMode              AtmConnSchedMode,
	opathChannelSchedSchedOverride          INTEGER
}

opathChannelSchedPort OBJECT-TYPE
	SYNTAX  Integer32
	MAX-ACCESS  not-accessible
	STATUS  current
	DESCRIPTION
		"Index of this port"
	::= { outputPathChannelSchedEntry 1}

opathChannelSchedVPI OBJECT-TYPE
	SYNTAX  Integer32
	MAX-ACCESS  not-accessible
	STATUS  current
	DESCRIPTION
		"The value of this object identifies the output VPI
		(Virtual Path Identifier) of this path."
	::= { outputPathChannelSchedEntry 2}

opathChannelSchedServCat OBJECT-TYPE
	SYNTAX  Integer32
	MAX-ACCESS  not-accessible
	STATUS  current
	DESCRIPTION
		"Index of this service category within serviceCategoryTable"
	::= { outputPathChannelSchedEntry 3}

opathChannelSchedSchedMode OBJECT-TYPE
	SYNTAX  AtmConnSchedMode
	MAX-ACCESS  read-write
	STATUS  current
	DESCRIPTION
		"The scheduling mode used for channels of type
		 opathChannelSchedServCat within this path. The default
		 choice of AtmConnSchedMode is not allowed at
		 path level."
	::= { outputPathChannelSchedEntry 4}

opathChannelSchedSchedOverride OBJECT-TYPE
	SYNTAX  INTEGER {
		   on(1),
		   off(2)
		}
	MAX-ACCESS  read-write
	STATUS  current
	DESCRIPTION
		"The override option used for channels of type
		 opathChannelSchedServCat within this path"
	::= { outputPathChannelSchedEntry 5}



------------------------------------------------------------------------
-- The Channel Group

channelTable OBJECT-TYPE
	SYNTAX	SEQUENCE OF ChannelEntry
	MAX-ACCESS	not-accessible
	STATUS	current
	DESCRIPTION
		"A table of information about the virtual channels
		passing through this ATM switch."
	::= { channelGroup 1 }

channelEntry OBJECT-TYPE
	SYNTAX	ChannelEntry
	MAX-ACCESS	not-accessible
	STATUS	current
	DESCRIPTION
		"A table entry containing channel information."
	INDEX	{ chanPort, chanVPI, chanVCI }
	::= { channelTable 1 }

ChannelEntry ::=
	SEQUENCE {
		chanPort			Integer32,
		chanVPI				Integer32,
		chanVCI				Integer32,
		chanStatus			EntryStatus,
		chanNumOutputs			Gauge32,
		chanAllocBandwidth		Gauge32,
		chanUsedBandwidth		Gauge32,
		chanCells			Counter32,
		chanUptime			TimeTicks,
		chanSigProtocol			AtmSigProtocol,
		chanRejectedCells		Counter32,
		chanCDV				Integer32,
		chanPolicingAction		INTEGER,
		chanUpcContract			Integer32,
		chanServCat			Integer32,
		chanQosCDVT                     Integer32,
		chanQosPoliceState              INTEGER,
		chanQosPoliceScheme             INTEGER,
		chanQosPCR                      Integer32,
		chanQosSCR                      Integer32,
		chanQosMBS                      Integer32,
		chanQosIsAAL5                   INTEGER,
		chanQosPerPacketPolicing        INTEGER
	}

chanPort OBJECT-TYPE
	SYNTAX	Integer32
	MAX-ACCESS	read-only
	STATUS	current
	DESCRIPTION
		"The value of this object identifies the input port
		of this channel and is the same as the pathPort and
		portNumber."
	::= { channelEntry 1 }

chanVPI OBJECT-TYPE
	SYNTAX	Integer32
	MAX-ACCESS	read-only
	STATUS	current
	DESCRIPTION
		"The value of this object identifies the input VPI
		(Virtual Path Identifier) of this channel, and is the
		same as the pathVPI."
	::= { channelEntry 2 }

chanVCI OBJECT-TYPE
	SYNTAX	Integer32
	MAX-ACCESS	read-only
	STATUS	current
	DESCRIPTION
		"The input VCI (Virtual Channel Identifier) of this channel."
	::= { channelEntry 3 }

chanStatus OBJECT-TYPE
	SYNTAX	EntryStatus
	MAX-ACCESS	read-create
	STATUS	current
	DESCRIPTION
		"The status of this channel entry."
	::= { channelEntry 4 }

chanNumOutputs OBJECT-TYPE
	SYNTAX	Gauge32
	MAX-ACCESS	read-only
	STATUS	current
	DESCRIPTION
		"The number of output ports to which this channel is routed."
	::= { channelEntry 5 }

chanAllocBandwidth OBJECT-TYPE
	SYNTAX	Gauge32
	MAX-ACCESS	read-create
	STATUS	current
	DESCRIPTION
		"The allocated bandwidth of this channel, in cells per second."
	::= { channelEntry 6 }

chanUsedBandwidth OBJECT-TYPE
	SYNTAX	Gauge32
	MAX-ACCESS	read-only
	STATUS	deprecated
	DESCRIPTION
		"The bandwidth used on this channel, in cells per second."
	::= { channelEntry 7 }

chanCells OBJECT-TYPE
	SYNTAX	Counter32
	MAX-ACCESS	read-only
	STATUS	current
	DESCRIPTION
		"The number of cells transferred on this channel."
	::= { channelEntry 8 }

chanUptime OBJECT-TYPE
	SYNTAX	TimeTicks
	MAX-ACCESS	read-only
	STATUS	current
	DESCRIPTION
		"The time since this channel was created,
		in hundredths of a second."
	::= { channelEntry 9 }

chanSigProtocol OBJECT-TYPE
	SYNTAX	AtmSigProtocol
	MAX-ACCESS	read-only
	STATUS	current
	DESCRIPTION
		"The signaling protocol that created this channel."
	::= { channelEntry 10 }

chanRejectedCells OBJECT-TYPE
	SYNTAX	Counter32
	MAX-ACCESS	read-only
	STATUS	current
	DESCRIPTION
		"The number of cells on this channel that were rejected
		(dropped) by the policer on the switch fabric.
		This does not include any cells that may have been
		tagged with CLP=1 by the policer, only cells that were
		discarded."
	::= { channelEntry 11 }

chanCDV OBJECT-TYPE
	SYNTAX	Integer32
	MAX-ACCESS	read-create
	STATUS	current
	DESCRIPTION
		"The channel Cell Delay Variation Tolerance (CDV),
		specified in microseconds, indicates the time window
		in which a cell may be received on a channel and be
		accepted. A cell that is received on a channel outside
		the CDV window will be dropped or tagged, based on the
		value of chanPolicingAction. The chanCDV value
		overrides the default value inherited from the link."
	::= { channelEntry 12 }

chanPolicingAction OBJECT-TYPE
	SYNTAX	INTEGER {
			tag(1),
			drop(2)
		}
	MAX-ACCESS	read-create
	STATUS	current
	DESCRIPTION
		"This object indicates the action the switch
		will take in case of bandwidth violation on this
		channel."
	::= { channelEntry 13 }

chanUpcContract OBJECT-TYPE
	SYNTAX	Integer32
	MAX-ACCESS	read-create
	STATUS	current
	DESCRIPTION
		"The UPC contract that will be used to police this channel.
		This is the number of the row in the upcContractTable."
	::= { channelEntry 14 }

chanServCat OBJECT-TYPE
	SYNTAX	Integer32
	MAX-ACCESS	read-only
	STATUS	current
	DESCRIPTION
		"Index of this service category within serviceCategoryTable"
	::= { channelEntry 15 }

chanQosPoliceScheme OBJECT-TYPE
	SYNTAX  INTEGER {
			cbr1(1),
			cbr0(2),
			cbr0tag(3),
			vbr1(4),
			vbr2(5),
			vbr3(6),
			abr1(7),
			ubr1(8),
			ubr2(9)
		}
	MAX-ACCESS	read-only
	STATUS	current
	DESCRIPTION
		"It identifies the policing associated with the UPC
		 contract as defined in the ATM Forum TM 4.0
		 specifications. However, the policing schemes cbr0
		 and cbr0tag are specific to FORE switches"
	::= { channelEntry 16 }

chanQosPCR OBJECT-TYPE
	SYNTAX	Integer32
	MAX-ACCESS	read-only
	STATUS	current
	DESCRIPTION
		"The peak cell rate (cells/sec)"
	::= { channelEntry 17 }

chanQosSCR OBJECT-TYPE
	SYNTAX	Integer32
	MAX-ACCESS	read-only
	STATUS	current
	DESCRIPTION
		"The sustained cell rate (cells/sec). It also holds
		 the PCR0 value for cbr0 & cbr0tag contracts"
	::= { channelEntry 18 }

chanQosMBS OBJECT-TYPE
	SYNTAX	Integer32
	MAX-ACCESS	read-only
	STATUS	current
	DESCRIPTION
		"The maximum burst size (cells)"
	::= { channelEntry 19 }

chanQosCDVT OBJECT-TYPE
	SYNTAX	Integer32
	MAX-ACCESS	read-only
	STATUS	current
	DESCRIPTION
		"The channel Cell Delay Variation Tolerance (CDVT),
		specified in microseconds, indicates the time window
		in which a cell may be received on a channel and be
		accepted. A cell that is received on a channel outside
		the CDV window will be dropped or tagged, based on the
		value of chanPolicingAction. The chanCDV value
		overrides the default value inherited from the link."
	::= { channelEntry 20 }


chanQosPoliceState OBJECT-TYPE
	SYNTAX	INTEGER {
			on(1),
			off(2)
		}
	MAX-ACCESS	read-only
	STATUS	current
	DESCRIPTION
	    "Indicates if this connection is policed for traffic violations. 
	     When set to 'on' it overrides the policing status of the atm 
	     interface on which this connection is established."
	::= { channelEntry 21 }

chanQosIsAAL5 OBJECT-TYPE
	SYNTAX	INTEGER {
			on(1),
			off(2)
		}
	MAX-ACCESS	read-only
	STATUS	current
	DESCRIPTION
	    "Indicates if this connection is AAL 5"
	::= { channelEntry 22 }

chanQosPerPacketPolicing OBJECT-TYPE
	SYNTAX  INTEGER {
			on(1),
			off(2)
		}
	MAX-ACCESS  read-only
	STATUS  current
	DESCRIPTION
		"Should we perform AAL5 Partial Packet Policing on
		this UPC contract.  This variable only has meaning if
		the connections is also AAL5."
	::= { channelEntry 23 }

------------------------------------------------------------------------

channelRouteTable OBJECT-TYPE
	SYNTAX	SEQUENCE OF ChannelRouteEntry
	MAX-ACCESS	not-accessible
	STATUS	current
	DESCRIPTION
		"A table of information about the routing of channels through
		this ATM switch."
	::= { channelGroup 2 }

channelRouteEntry OBJECT-TYPE
	SYNTAX	ChannelRouteEntry
	MAX-ACCESS	not-accessible
	STATUS	current
	DESCRIPTION
		"A table entry containing channel route information."
	INDEX	{ chanrInputPort, chanrInputVPI, chanrInputVCI,
		  chanrOutputPort, chanrOutputVPI, chanrOutputVCI }
	::= { channelRouteTable 1 }

ChannelRouteEntry ::= SEQUENCE {
	chanrInputPort			Integer32,
	chanrInputVPI			Integer32,
	chanrInputVCI			Integer32,
	chanrOutputPort			Integer32,
	chanrOutputVPI			Integer32,
	chanrOutputVCI			Integer32,
	chanrStatus			EntryStatus,
	chanrSigProtocol		AtmSigProtocol,
	chanrName	                OCTET STRING,
	chanrConnectionType	        ConnectionType
}

chanrInputPort OBJECT-TYPE
	SYNTAX	Integer32
	MAX-ACCESS	read-only
	STATUS	current
	DESCRIPTION
		"The value of this object identifies the input port
		of this channel and is the same as the chanPort,
		pathPort, and portNumber."
	::= { channelRouteEntry 1 }

chanrInputVPI OBJECT-TYPE
	SYNTAX	Integer32
	MAX-ACCESS	read-only
	STATUS	current
	DESCRIPTION
		"The value of this object identifies the input VPI
		(Virtual Path Identifier) of this channel, and is the
		same as the chanVPI, and pathVPI."
	::= { channelRouteEntry 2 }

chanrInputVCI OBJECT-TYPE
	SYNTAX	Integer32
	MAX-ACCESS	read-only
	STATUS	current
	DESCRIPTION
		"The value of this object identifies the input VCI
		(Virtual Channel Identifier) of this channel, and
		is the same as chanVCI."
	::= { channelRouteEntry 3 }

chanrOutputPort OBJECT-TYPE
	SYNTAX	Integer32
	MAX-ACCESS	read-only
	STATUS	current
	DESCRIPTION
		"The value of this object identifies the output port
		of this channel and is the same as the opathPort,
		and portNumber."
	::= { channelRouteEntry 4 }

chanrOutputVPI OBJECT-TYPE
	SYNTAX	Integer32
	MAX-ACCESS	read-only
	STATUS	current
	DESCRIPTION
		"The value of this object identifies the output VPI
		(Virtual Path Identifier) of this channel and is the
		same as the opathVPI."
	::= { channelRouteEntry 5 }

chanrOutputVCI OBJECT-TYPE
	SYNTAX	Integer32
	MAX-ACCESS	read-only
	STATUS	current
	DESCRIPTION
		"The output VCI (Virtual Channel Identifier) of this channel."
	::= { channelRouteEntry 6 }

chanrStatus OBJECT-TYPE
	SYNTAX	EntryStatus
	MAX-ACCESS	read-create
	STATUS	current
	DESCRIPTION
		"The status of this channel entry."
	::= { channelRouteEntry 7 }

chanrSigProtocol OBJECT-TYPE
	SYNTAX	AtmSigProtocol
	MAX-ACCESS	read-only
	STATUS	current
	DESCRIPTION
		"The signaling protocol that created this channel."
	::= { channelRouteEntry 8 }

chanrName OBJECT-TYPE
	SYNTAX  OCTET STRING (SIZE(0..32))
	MAX-ACCESS  read-create
	STATUS  current
	DESCRIPTION
		" The value of this object identifies the
		name that has been assigned for this channel."
	::= { channelRouteEntry 9 }

chanrConnectionType OBJECT-TYPE
	SYNTAX  ConnectionType
	MAX-ACCESS  read-create
	STATUS  current
	DESCRIPTION
		" This object identifies the type of the channel
		endpoints with respect to a particular network."
	::= { channelRouteEntry 10 }

------------------------------------------------------------------------

reverseChannelRouteTable OBJECT-TYPE
	SYNTAX	SEQUENCE OF ReverseChannelRouteEntry
	MAX-ACCESS	not-accessible
	STATUS	current
	DESCRIPTION
		"A table of information about reverse channel routes
		through	this ATM switch."
	::= { channelGroup 3 }

reverseChannelRouteEntry OBJECT-TYPE
	SYNTAX	ReverseChannelRouteEntry
	MAX-ACCESS	not-accessible
	STATUS	current
	DESCRIPTION
		"A table entry containing reverse channel route information."
	INDEX	{ revChanrOutputPort, revChanrOutputVPI, revChanrOutputVCI,
		  revChanrInputPort, revChanrInputVPI, revChanrInputVCI }
	::= { reverseChannelRouteTable 1 }

ReverseChannelRouteEntry ::= SEQUENCE {
	revChanrOutputPort		Integer32,
	revChanrOutputVPI		Integer32,
	revChanrOutputVCI		Integer32,
	revChanrInputPort		Integer32,
	revChanrInputVPI		Integer32,
	revChanrInputVCI		Integer32,
	revChanrSigProtocol		AtmSigProtocol
}

revChanrOutputPort OBJECT-TYPE
	SYNTAX	Integer32
	MAX-ACCESS	read-only
	STATUS	current
	DESCRIPTION
		"The value of this object identifies the output port
		of this channel and is the same as the chanrOutputPort,
		opathPort and portNumber."
	::= { reverseChannelRouteEntry 1 }

revChanrOutputVPI OBJECT-TYPE
	SYNTAX	Integer32
	MAX-ACCESS	read-only
	STATUS	current
	DESCRIPTION
		"The value of this object identifies the output VPI
		(Virtual Path Identifier) of this channel and is the
		same as the chanrOutputVPI and opathVPI."
	::= { reverseChannelRouteEntry 2 }

revChanrOutputVCI OBJECT-TYPE
	SYNTAX	Integer32
	MAX-ACCESS	read-only
	STATUS	current
	DESCRIPTION
		"The output VCI (Virtual Channel Identifier) of this channel
		and is the same as chanrOutputVCI."
	::= { reverseChannelRouteEntry 3 }

revChanrInputPort OBJECT-TYPE
	SYNTAX	Integer32
	MAX-ACCESS	read-only
	STATUS	current
	DESCRIPTION
		"The value of this object identifies the input port
		of this channel and is the same as the chanPort,
		chanrInputPort, pathPort, and portNumber."
	::= { reverseChannelRouteEntry 4 }

revChanrInputVPI OBJECT-TYPE
	SYNTAX	Integer32
	MAX-ACCESS	read-only
	STATUS	current
	DESCRIPTION
		"The value of this object identifies the input VPI
		(Virtual Path Identifier) of this channel, and is the
		same as the chanVPI, chanrInputVPI and pathVPI."
	::= { reverseChannelRouteEntry 5 }

revChanrInputVCI OBJECT-TYPE
	SYNTAX	Integer32
	MAX-ACCESS	read-only
	STATUS	current
	DESCRIPTION
		"The value of this object identifies the input VCI
		(Virtual Channel Identifier) of this channel, and
		is the same as chanVCI and chanrInputVCI."
	::= { reverseChannelRouteEntry 6 }

revChanrSigProtocol OBJECT-TYPE
	SYNTAX	AtmSigProtocol
	MAX-ACCESS	read-only
	STATUS	current
	DESCRIPTION
		"The signaling protocol that created this channel and is
		the same as chanrSigProtocol."
	::= { reverseChannelRouteEntry 7 }



------------------------------------------------------------------------

outputChannelStatsTable OBJECT-TYPE
	SYNTAX  SEQUENCE OF OutputChannelStatsEntry
	MAX-ACCESS  not-accessible
	STATUS  current
	DESCRIPTION
		"A table of statistics information about the virtual
		 channels originating at this ATM switch."
	::= { channelGroup 4 }

outputChannelStatsEntry OBJECT-TYPE
	SYNTAX  OutputChannelStatsEntry
	MAX-ACCESS  not-accessible
	STATUS  current
	DESCRIPTION
		"A table entry containing originating channel
		statistics information."
	INDEX  { ochanStatsPort, ochanStatsVPI, ochanStatsVCI }
	::= { outputChannelStatsTable 1 }

OutputChannelStatsEntry ::= SEQUENCE {
	ochanStatsPort                      Integer32,
	ochanStatsVPI                       Integer32,
	ochanStatsVCI                       Integer32,
	ochanStatsLostCells                 Counter32,
	ochanStatsTransmittedCells          Counter32,
	ochanStatsIntentionalLostCells      Counter32,
	ochanStatsCLP0Cells                 Counter32,
	ochanStatsLostPackets               Counter32,
	ochanStatsTransmittedPackets        Counter32
}

ochanStatsPort OBJECT-TYPE
	SYNTAX  Integer32
	MAX-ACCESS  read-only
	STATUS  current
	DESCRIPTION
		"The value of this object identifies the output port
		of this channel and is the same as the opathPort,
		and portNumber."
	::= { outputChannelStatsEntry 1}

ochanStatsVPI OBJECT-TYPE
	SYNTAX  Integer32
	MAX-ACCESS  read-only
	STATUS  current
	DESCRIPTION
		"The value of this object identifies the output VPI
		(Virtual Path Identifier) of this channel and is the
		same as the opathVPI."
	::= { outputChannelStatsEntry 2}

ochanStatsVCI OBJECT-TYPE
	SYNTAX  Integer32
	MAX-ACCESS  read-only
	STATUS  current
	DESCRIPTION
		"The output VCI (Virtual Channel Identifier) of this channel."
	::= { outputChannelStatsEntry 3}


ochanStatsLostCells OBJECT-TYPE
	SYNTAX  Counter32
	MAX-ACCESS  read-only
	STATUS  current
	DESCRIPTION
		"The number of cells on this output channel that were
		dropped at the output netmod."
	::= { outputChannelStatsEntry 4}

ochanStatsTransmittedCells OBJECT-TYPE
	SYNTAX  Counter32
	MAX-ACCESS  read-only
	STATUS  current
	DESCRIPTION
		"The number of cells on this output channel that were transmitted."
	::= { outputChannelStatsEntry 5 }

ochanStatsIntentionalLostCells OBJECT-TYPE
	SYNTAX  Counter32
	MAX-ACCESS  read-only
	STATUS  current
	DESCRIPTION
		"The number of cells on this output channel that were
		dropped intentionally."
	::= { outputChannelStatsEntry 6}

ochanStatsCLP0Cells OBJECT-TYPE
	SYNTAX  Counter32
	MAX-ACCESS  read-only
	STATUS  current
	DESCRIPTION
		"The number of CLP = 0 cells transmitted on this output path."
	::= { outputChannelStatsEntry 7}

ochanStatsLostPackets OBJECT-TYPE
	SYNTAX  Counter32
	MAX-ACCESS  read-only
	STATUS  current
	DESCRIPTION
		"The number of packets on this output path that were dropped
		at the output netmod."
	::= { outputChannelStatsEntry 8}

ochanStatsTransmittedPackets OBJECT-TYPE
	SYNTAX  Counter32
	MAX-ACCESS  read-only
	STATUS  current
	DESCRIPTION
		"The number of Packets on this output path that were transmitted."
	::= { outputChannelStatsEntry 9 }

------------------------------------------------------------------------
-- The Topology Group

numberOfLinks OBJECT-TYPE
	SYNTAX	Integer32
	MAX-ACCESS	read-only
	STATUS	current
	DESCRIPTION
		"Current number of links known by this ATM switch."
	::= { topologyGroup 1 }

linkTable OBJECT-TYPE
	SYNTAX	SEQUENCE OF LinkEntry
	MAX-ACCESS	not-accessible
	STATUS	current
	DESCRIPTION
		"A table of links describing this switch's view
		of the ATM network topology."
	::= { topologyGroup 2 }

linkEntry OBJECT-TYPE
	SYNTAX	LinkEntry
	MAX-ACCESS	not-accessible
	STATUS	current
	DESCRIPTION
		"A table entry containing link information."
	INDEX	{ linkSrc, linkDest }
	::= { linkTable 1 }

LinkEntry ::=
	SEQUENCE {
		linkSrc		SpansAddress,
		linkDest	SpansAddress,
		linkCapacity	Integer32,
		linkAge		Integer32
	}

linkSrc OBJECT-TYPE
	SYNTAX	SpansAddress
	MAX-ACCESS	read-only
	STATUS	current
	DESCRIPTION
		"The ATM address of the source switch of this link."
	::= { linkEntry 1 }

linkDest OBJECT-TYPE
	SYNTAX	SpansAddress
	MAX-ACCESS	read-only
	STATUS	current
	DESCRIPTION
		"The ATM address of the destination switch of this link."
	::= { linkEntry 2 }

linkCapacity OBJECT-TYPE
	SYNTAX	Integer32
	MAX-ACCESS	read-only
	STATUS	current
	DESCRIPTION
		"The free capacity of this link in kilobits per second."
	::= { linkEntry 3 }

linkAge OBJECT-TYPE
	SYNTAX	Integer32
	MAX-ACCESS	read-only
	STATUS	current
	DESCRIPTION
		"The freshness of this link information. The actual
		value has no units associated with it. It should be
		used for comparison."
	::= { linkEntry 4 }

------------------------------------------------------------------------
-- The Signaling Group

-- The SPANS Group

sigPathTable OBJECT-TYPE
	SYNTAX	SEQUENCE OF SigPathEntry
	MAX-ACCESS	not-accessible
	STATUS	current
	DESCRIPTION
		"A table of general information about the signaling path."
	::= { spansGroup 1 }

sigPathEntry OBJECT-TYPE
	SYNTAX	SigPathEntry
	MAX-ACCESS	not-accessible
	STATUS	current
	DESCRIPTION
		"A table entry containing signaling path information,
		indexed by port and path."
	INDEX	{ sigPathPort, sigPathVPI }
	::= { sigPathTable 1 }

SigPathEntry ::= SEQUENCE {
	sigPathPort		Integer32,
	sigPathVPI		Integer32,
	sigPathVCI		Integer32,
	sigPathClsVCI		Integer32,
	sigPathAdminStatus	INTEGER,
	sigPathOperStatus	INTEGER,
	sigPathEntryStatus	EntryStatus,
	sigPathAALType		INTEGER,
	sigPathCDV		Integer32,
	sigPathPolicingAction	INTEGER,
	sigPathRemoteAtmAddress	SpansAddress,
	sigPathRemoteIpAddress	IpAddress,
	sigPathType		INTEGER,
	sigPathClsUpcContract   Integer32,
	sigPathSigReservedBW    Integer32,
	sigPathMinVCI		Integer32,
	sigPathMaxVCI		Integer32,
	sigPathOpenTimeout	Integer32,
	sigPathCloseTimeout	Integer32,
	sigPathOutputSigService INTEGER,
	sigPathAALOperType      INTEGER
}

sigPathPort OBJECT-TYPE
	SYNTAX	Integer32
	MAX-ACCESS	read-only
	STATUS	current
	DESCRIPTION
		"The value of this object identifies the port
		of this signalling path, and is the same as the
		portNumber."
	::= { sigPathEntry 1 }

sigPathVPI OBJECT-TYPE
	SYNTAX	Integer32
	MAX-ACCESS	read-only
	STATUS	current
	DESCRIPTION
		"The VPI (Virtual Path Identifier) of this signaling path."
	::= { sigPathEntry 2 }

sigPathVCI OBJECT-TYPE
	SYNTAX	Integer32
	MAX-ACCESS	read-create
	STATUS	current
	DESCRIPTION
		"The VCI (Virtual Channel Identifier) of the signaling
		channel within the signaling path."
	::= { sigPathEntry 3 }

sigPathClsVCI OBJECT-TYPE
	SYNTAX	Integer32
	MAX-ACCESS	read-create
	STATUS	current
	DESCRIPTION
		"The VCI (Virtual Channel Identifier) of the connectionless
		channel within the signaling path."
	::= { sigPathEntry 4 }

sigPathAdminStatus OBJECT-TYPE
	SYNTAX	INTEGER {
			up(1),
			down(2)
		}
	MAX-ACCESS	read-create
	STATUS	current
	DESCRIPTION
		"The desired state of this signaling channel. The up(1) state
		dictates that SPANS (Simple Protocol for ATM Network Siganlling)
		messages are used for signalling. The down(2) state dictates
		the SPANS protocol is not used for signalling."
	::= { sigPathEntry 5 }

sigPathOperStatus OBJECT-TYPE
	SYNTAX	INTEGER {
			up(1),
			down(2)
		}
	MAX-ACCESS	read-only
	STATUS	current
	DESCRIPTION
		"The current operational state of this signaling channel,
		as determined either by administrative action, when the
		value of sigPathAdminStatus is down(2), or by a link
		monitoring protocol, when the value of sigPathAdminStatus
		is up(1)."
	::= { sigPathEntry 6 }

sigPathEntryStatus OBJECT-TYPE
	SYNTAX	EntryStatus
	MAX-ACCESS	read-create
	STATUS	current
	DESCRIPTION
		"The status of this signaling path entry."
	::= { sigPathEntry 7 }

sigPathAALType OBJECT-TYPE
	SYNTAX	INTEGER {
			type34(1),
			type5(2),
			auto(3)
		}
	MAX-ACCESS	read-create
	STATUS	current
	DESCRIPTION
		"The AAL (ATM Adaptation LAyer) type that is used by this
		signaling path."
	::= { sigPathEntry 8 }

sigPathCDV OBJECT-TYPE
	SYNTAX	Integer32
	MAX-ACCESS	read-create
	STATUS	current
	DESCRIPTION
		"The signalling path Cell Delay Variation (CDV) specified
		in microseconds, indicates the time window in which
		a cell may be received on a signalling channel and be
		accepted. A cell that is received on a channel outside the
		CDV window will be dropped. The sigPathCDV value
		overrides the default value of switchCDV."
	::= { sigPathEntry 9 }

sigPathPolicingAction OBJECT-TYPE
	SYNTAX	INTEGER {
			tag(1),
			drop(2)
		}
	MAX-ACCESS	read-create
	STATUS	current
	DESCRIPTION
		"This object indicates the action the switch
		will take in case of bandwidth violation on
		a signalling channel. The value set here overrides
		the default value of switchPolicingAction."
	::= { sigPathEntry 10 }

sigPathRemoteAtmAddress OBJECT-TYPE
	SYNTAX	SpansAddress
	MAX-ACCESS	read-only
	STATUS	current
	DESCRIPTION
		"The ATM address of the entity connected to this
		signalling path."
	::= { sigPathEntry 11 }

sigPathRemoteIpAddress OBJECT-TYPE
	SYNTAX	IpAddress
	MAX-ACCESS	read-only
	STATUS	current
	DESCRIPTION
		"The IP address of the entity connected to this
		signalling path."
	::= { sigPathEntry 12 }

sigPathType OBJECT-TYPE
	SYNTAX	INTEGER {
			uni(1),
			nni(2)
		}
	MAX-ACCESS	read-only
	STATUS	current
	DESCRIPTION
		"The type of the signalling path connection. uni(1)
		(User Network Interface) means that there is a host on
		remote side, while nni(2) (Network Network Interface)
		means there is another switch, that speaks SPANS, on
		the remote side."
	::= { sigPathEntry 13 }

sigPathClsUpcContract OBJECT-TYPE
	SYNTAX  Integer32
	MAX-ACCESS	read-create
	STATUS	current
	DESCRIPTION
		"The UPC contract that will be used to police the
		 connectionless VC.  This is the number of a row in
		 the upcContractTable"
	::= { sigPathEntry 14 }

sigPathSigReservedBW OBJECT-TYPE
	SYNTAX  Integer32
	MAX-ACCESS	read-create
	STATUS	current
	DESCRIPTION
		"Bandwidth reserved for the SPANS Signaling VC, in
		 cells/sec."
	::= { sigPathEntry 15 }

sigPathMinVCI OBJECT-TYPE
	SYNTAX	Integer32
	MAX-ACCESS	read-create
	STATUS	current
	DESCRIPTION
		"The minimum configured VCI (Virtual Channel Identifier)
		 that can be used for SVCs (Signalled Virtual Circuits)."
	::= { sigPathEntry 16 }

sigPathMaxVCI OBJECT-TYPE
	SYNTAX	Integer32
	MAX-ACCESS	read-create
	STATUS	current
	DESCRIPTION
		"The maximum configured VCI (Virtual Channel Identifier)
		 that can be used for SVCs (Signalled Virtual Circuits)."
	::= { sigPathEntry 17 }

sigPathOpenTimeout  OBJECT-TYPE
	SYNTAX  Integer32
	MAX-ACCESS  read-create
	STATUS  current
	DESCRIPTION
		"The timeout in msec for SPANS open requests. "
	DEFVAL { 300 }
	::= { sigPathEntry 18 }

sigPathCloseTimeout  OBJECT-TYPE
	SYNTAX  Integer32
	MAX-ACCESS  read-create
	STATUS  current
	DESCRIPTION
		"The timeout in msec for SPANS close requests."
	DEFVAL { 500 }
	::= { sigPathEntry 19 }

sigPathOutputSigService OBJECT-TYPE
	SYNTAX  INTEGER {
	       vbr(1),
	       ubr(2),
	       oam(3),
	       default(4)
		}
	MAX-ACCESS  read-create
	STATUS  current
	DESCRIPTION
		"Service Queue where the output
		signalling vc should be inserted into."
	DEFVAL { vbr }
	::= { sigPathEntry 20 }

sigPathAALOperType OBJECT-TYPE
	SYNTAX	INTEGER {
			type34(1),
			type5(2)
		}
	MAX-ACCESS	read-only
	STATUS	current
	DESCRIPTION
		"The AAL (ATM Adaptation LAyer) type that is currently being used by
		this signaling path."
	::= { sigPathEntry 21 }


------------------------------------------------------------------------

sigPathStatsTable OBJECT-TYPE
	SYNTAX	SEQUENCE OF SigPathStatsEntry
	MAX-ACCESS	not-accessible
	STATUS	current
	DESCRIPTION
		"A table of statistics about the signaling path."
	::= { spansGroup 2 }

sigPathStatsEntry OBJECT-TYPE
	SYNTAX	SigPathStatsEntry
	MAX-ACCESS	not-accessible
	STATUS	current
	DESCRIPTION
		"A table entry containing signaling path statistics,
		indexed by port and path."
	INDEX	{ sigPathStatsPort, sigPathStatsVPI }
	::= { sigPathStatsTable 1 }

SigPathStatsEntry ::= SEQUENCE {
	sigPathStatsPort		Integer32,
	sigPathStatsVPI			Integer32,
	sigPathVCCs			Gauge32,
	sigPathRestarts			Counter32,
	sigPathCallsCompletions		Counter32,
	sigPathCallsFailures		Counter32,
	sigPathCallsRejections		Counter32,
	sigPathSpansTransmittedMessages	Counter32,
	sigPathSpansReceivedMessages	Counter32,
	sigPathClsTransmittedMessages	Counter32,
	sigPathClsReceivedMessages	Counter32
}

sigPathStatsPort OBJECT-TYPE
	SYNTAX	Integer32
	MAX-ACCESS	read-only
	STATUS	current
	DESCRIPTION
		"The value of this object identifies the port
		of this signalling path, and is the same as
		sigPathPort."
	::= { sigPathStatsEntry 1 }

sigPathStatsVPI OBJECT-TYPE
	SYNTAX	Integer32
	MAX-ACCESS	read-only
	STATUS	current
	DESCRIPTION
		"The value of this object identifies the VPI (Virtual
		Path Identifier) of this signaling path statistics entry,
		and is the same as sigPathVPI."
	::= { sigPathStatsEntry 2 }

sigPathVCCs OBJECT-TYPE
	SYNTAX	Gauge32
	MAX-ACCESS	read-only
	STATUS	current
	DESCRIPTION
		"The number of Virtual Channel Connections (VCCs) on this
		signaling path."
	::= { sigPathStatsEntry 3 }

sigPathRestarts OBJECT-TYPE
	SYNTAX	Counter32
	MAX-ACCESS	read-only
	STATUS	current
	DESCRIPTION
		"The number of times the switch has lost and regained
		contact with the remote signaling entity on this path."
	::= { sigPathStatsEntry 4 }

sigPathCallsCompletions OBJECT-TYPE
	SYNTAX	Counter32
	MAX-ACCESS	read-only
	STATUS	current
	DESCRIPTION
		"The number of successfully completed calls on this
		signaling path."
	::= { sigPathStatsEntry 5 }

sigPathCallsFailures OBJECT-TYPE
	SYNTAX	Counter32
	MAX-ACCESS	read-only
	STATUS	current
	DESCRIPTION
		"The number of call failures on this signaling path."
	::= { sigPathStatsEntry 6 }

sigPathCallsRejections OBJECT-TYPE
	SYNTAX	Counter32
	MAX-ACCESS	read-only
	STATUS	current
	DESCRIPTION
		"The number of connections on this signaling path that were
		rejected by the far end."
	::= { sigPathStatsEntry 7 }

sigPathSpansTransmittedMessages OBJECT-TYPE
	SYNTAX	Counter32
	MAX-ACCESS	read-only
	STATUS	current
	DESCRIPTION
		"The total number of SPANS messages that have been transmitted
		over this signalling path."
	::= { sigPathStatsEntry 8 }

sigPathSpansReceivedMessages OBJECT-TYPE
	SYNTAX	Counter32
	MAX-ACCESS	read-only
	STATUS	current
	DESCRIPTION
		"The total number of SPANS messages that have been received on
		this signalling path."
	::= { sigPathStatsEntry 9 }

sigPathClsTransmittedMessages OBJECT-TYPE
	SYNTAX	Counter32
	MAX-ACCESS	read-only
	STATUS	current
	DESCRIPTION
		"The total number of connectionless messages that have been
		transmitted over this signalling path."
	::= { sigPathStatsEntry 10 }

sigPathClsReceivedMessages OBJECT-TYPE
	SYNTAX	Counter32
	MAX-ACCESS	read-only
	STATUS	current
	DESCRIPTION
		"The total number of connectionless messages that have been
		received on this signalling path."
	::= { sigPathStatsEntry 11 }


------------------------------------------------------------------------

spvcSrcNumberOfSPVCs	OBJECT-TYPE
	SYNTAX	Integer32
	MAX-ACCESS	read-only
	STATUS	current
	DESCRIPTION
		"The number of SPVCs (Smart Permanent Virtual Circuits)
		that are going out of this switch (i.e. this switch is
		their source)."
	::= {spansGroup 3}

spvcSrcTable OBJECT-TYPE
	SYNTAX	SEQUENCE OF SpvcSrcEntry
	MAX-ACCESS	not-accessible
	STATUS	current
	DESCRIPTION
		"This table contains information about SPVCs (Smart
		Permanent Virtual Circuits) that their source is
		this switch."
	::= { spansGroup 4 }

spvcSrcEntry OBJECT-TYPE
	SYNTAX	SpvcSrcEntry
	MAX-ACCESS	not-accessible
	STATUS	current
	DESCRIPTION
		"A table entry containing source SPVC (Smart
		Permanent Virtual Circuits) information."
	INDEX	{ spvcSrcSpvcId }
	::= { spvcSrcTable 1 }

SpvcSrcEntry ::= SEQUENCE {
		spvcSrcSpvcId		Integer32,
		spvcSrcSwitchAddr	SpansAddress,
		spvcSrcDestSpvcId	Integer32,
		spvcSrcDestSwitchAddr	SpansAddress,
		spvcSrcInPort		Integer32,
		spvcSrcInVPI		Integer32,
		spvcSrcInVCI		Integer32,
		spvcSrcAllocBandwidth	Gauge32,
		spvcSrcUpTime		TimeTicks,
		spvcSrcStatus		INTEGER,
		spvcSrcEntryStatus	EntryStatus
	}

spvcSrcSpvcId OBJECT-TYPE
	SYNTAX	Integer32
	MAX-ACCESS	read-only
	STATUS	current
	DESCRIPTION
		"The value of this object uniquely identify
		the SPVC (Smart Permanent Virtual Circuits) that
		this switch is its source."
	::= { spvcSrcEntry 1 }

spvcSrcSwitchAddr OBJECT-TYPE
	SYNTAX	SpansAddress
	MAX-ACCESS	read-only
	STATUS	current
	DESCRIPTION
		"The ATM address of the source switch."
	::= { spvcSrcEntry 2 }

spvcSrcDestSpvcId OBJECT-TYPE
	SYNTAX	Integer32
	MAX-ACCESS	read-create
	STATUS	current
	DESCRIPTION
		"The SPVC (Smart Permanent Virtual Circuits)
		identifier at the destination switch.
		This object should match the spvcDestSpvcId at
		the destination switch."
	::= { spvcSrcEntry 3 }

spvcSrcDestSwitchAddr OBJECT-TYPE
	SYNTAX	SpansAddress
	MAX-ACCESS	read-create
	STATUS	current
	DESCRIPTION
		"The ATM address of the destination switch."
	::= { spvcSrcEntry 4 }

spvcSrcInPort OBJECT-TYPE
	SYNTAX	Integer32
	MAX-ACCESS	read-create
	STATUS	current
	DESCRIPTION
		"The value of this object identifies the input port
		of this SPVC (Smart Permanent Virtual Circuits), and
		is the same as the chanrInputPort, chanPort, pathPort,
		and portNumber."
	::= { spvcSrcEntry 5 }

spvcSrcInVPI OBJECT-TYPE
	SYNTAX	Integer32
	MAX-ACCESS	read-create
	STATUS	current
	DESCRIPTION
		"The value of this object identifies the input VPI
		(Virtual Path Identifier) of this SPVC (Smart Permanent
		Virtual Circuits), and is the same as the chanrInputVPI,
		chanVPI, pathVPI."
	::= { spvcSrcEntry 6 }

spvcSrcInVCI OBJECT-TYPE
	SYNTAX	Integer32
	MAX-ACCESS	read-create
	STATUS	current
	DESCRIPTION
		"The value of this object identifies the input VCI
		(Virtual Channel Identifier) of this SPVC (Smart
		Permanent Virtual Circuits), and is the
		same as the chanrInputVCI."
	::= { spvcSrcEntry 7 }

spvcSrcAllocBandwidth OBJECT-TYPE
	SYNTAX	Gauge32
	MAX-ACCESS	read-create
	STATUS	current
	DESCRIPTION
		"The allocated bandwidth of this SPVC (Smart Permanent
		Virtual Circuits)."
	::= { spvcSrcEntry 8 }

spvcSrcUpTime OBJECT-TYPE
	SYNTAX	TimeTicks
	MAX-ACCESS	read-only
	STATUS	current
	DESCRIPTION
		"The time since this SPVC (Smart Permanent Virtual
		Circuits) was created in hundredths of a second."
	::= { spvcSrcEntry 9 }

spvcSrcStatus OBJECT-TYPE
	SYNTAX	INTEGER {
			up(1),
			down(2)
		}
	MAX-ACCESS	read-only
	STATUS	current
	DESCRIPTION
		"The status of this SPVC (Smart Permanent Virtual
		Circuits)."
	::= { spvcSrcEntry 10 }

spvcSrcEntryStatus OBJECT-TYPE
	SYNTAX	EntryStatus
	MAX-ACCESS	read-create
	STATUS	current
	DESCRIPTION
		"The status of this SPVC (Smart Permanent Virtual
		Circuits) entry."
	::= { spvcSrcEntry 11 }

------------------------------------------------------------------------

spvcDestNumberOfSPVCs	OBJECT-TYPE
	SYNTAX	Integer32
	MAX-ACCESS	read-only
	STATUS	current
	DESCRIPTION
		"The number of SPVCs (Smart Permanent Virtual Circuits)
		that are coming into this switch (i.e. this switch is
		their destination)."
	::= {spansGroup 5}

spvcDestTable OBJECT-TYPE
	SYNTAX	SEQUENCE OF SpvcDestEntry
	MAX-ACCESS	not-accessible
	STATUS	current
	DESCRIPTION
		"This table contains information about SPVCs (Smart
		Permanent Virtual Circuits) that their destination is
		this switch."
	::= { spansGroup 6 }

spvcDestEntry OBJECT-TYPE
	SYNTAX	SpvcDestEntry
	MAX-ACCESS	not-accessible
	STATUS	current
	DESCRIPTION
		"A table entry containing destination SPVC (Smart
		Permanent Virtual Circuits) information."
	INDEX	{ spvcDestSpvcId }
	::= { spvcDestTable 1 }

SpvcDestEntry ::= SEQUENCE {
		spvcDestSpvcId		Integer32,
		spvcDestSwitchAddr	SpansAddress,
		spvcDestSrcSpvcId	Integer32,
		spvcDestSrcSwitchAddr	SpansAddress,
		spvcDestOutPort		Integer32,
		spvcDestOutVPI		Integer32,
		spvcDestOutVCI		Integer32,
		spvcDestAllocBandwidth	Gauge32,
		spvcDestUpTime		TimeTicks,
		spvcDestStatus		INTEGER,
		spvcDestEntryStatus	EntryStatus
	}

spvcDestSpvcId OBJECT-TYPE
	SYNTAX	Integer32
	MAX-ACCESS	read-only
	STATUS	current
	DESCRIPTION
		"The value of this object uniquely identify
		the SPVC (Smart Permanent Virtual Circuits) that
		this switch is its destination. The range of this
		object is [1..spvcDestNumberOfSPVCs]."
	::= { spvcDestEntry 1 }

spvcDestSwitchAddr OBJECT-TYPE
	SYNTAX	SpansAddress
	MAX-ACCESS	read-only
	STATUS	current
	DESCRIPTION
		"The ATM address of this (the destination) switch."
	::= { spvcDestEntry 2 }

spvcDestSrcSpvcId OBJECT-TYPE
	SYNTAX	Integer32
	MAX-ACCESS	read-create
	STATUS	current
	DESCRIPTION
		"The SPVC (Smart Permanent Virtual Circuits)
		identifier at the source switch. This object
		should match the spvcSrcSpvcId at the source
		switch."
	::= { spvcDestEntry 3 }

spvcDestSrcSwitchAddr OBJECT-TYPE
	SYNTAX	SpansAddress
	MAX-ACCESS	read-create
	STATUS	current
	DESCRIPTION
		"The ATM address of the source switch."
	::= { spvcDestEntry 4 }

spvcDestOutPort OBJECT-TYPE
	SYNTAX	Integer32
	MAX-ACCESS	read-create
	STATUS	current
	DESCRIPTION
		"The value of this object identifies the output port
		of this SPVC (Smart Permanent Virtual Circuits)
		and is the same as the chanrOutputPort,
		opathPort, and portNumber."
	::= { spvcDestEntry 5 }

spvcDestOutVPI OBJECT-TYPE
	SYNTAX	Integer32
	MAX-ACCESS	read-create
	STATUS	current
	DESCRIPTION
		"The value of this object identifies the output VPI
		(Virtual Path Identifier) of this SPVC (Smart Permanent
		Virtual Circuits), and is the same as the chanrOutputVPI,
		and opathVPI."
	::= { spvcDestEntry 6 }

spvcDestOutVCI OBJECT-TYPE
	SYNTAX	Integer32
	MAX-ACCESS	read-create
	STATUS	current
	DESCRIPTION
		"The value of this object identifies the output VCI
		(Virtual Channel Identifier) of this SPVC (Smart
		Permanent Virtual Circuits), and is the
		same as the chanrOutputVCI."
	::= { spvcDestEntry 7 }

spvcDestAllocBandwidth OBJECT-TYPE
	SYNTAX	Gauge32
	MAX-ACCESS	read-create
	STATUS	current
	DESCRIPTION
		"The allocated bandwidth of this SPVC (Smart Permanent
		Virtual Circuits)."
	::= { spvcDestEntry 8 }

spvcDestUpTime OBJECT-TYPE
	SYNTAX	TimeTicks
	MAX-ACCESS	read-only
	STATUS	current
	DESCRIPTION
		"The time since this SPVC (Smart Permanent Virtual
		Circuits) was created in hundredths of a second."
	::= { spvcDestEntry 9 }

spvcDestStatus OBJECT-TYPE
	SYNTAX	INTEGER {
			up(1),
			down(2)
		}
	MAX-ACCESS	read-only
	STATUS	current
	DESCRIPTION
		"The status of this SPVC (Smart Permanent Virtual
		Circuits)."
	::= { spvcDestEntry 10 }

spvcDestEntryStatus OBJECT-TYPE
	SYNTAX	EntryStatus
	MAX-ACCESS	read-create
	STATUS	current
	DESCRIPTION
		"The status of this SPVC (Smart Permanent Virtual
		Circuits) entry."
	::= { spvcDestEntry 11 }

------------------------------------------------------------------------
--
-- PNNI SPVC source-side definitions
--

pnniSpvcSrcNumberOfSPVCs OBJECT-TYPE
	SYNTAX  Integer32
	MAX-ACCESS  read-only
	STATUS  current
	DESCRIPTION
		"The number of SPVCs (Smart Permanent Virtual Circuits)
		that have their source at this switch."
	::= { q2931Group 2 }

pnniSpvcSrcTable OBJECT-TYPE
	SYNTAX  SEQUENCE OF PnniSpvcSrcEntry
	MAX-ACCESS  not-accessible
	STATUS  current
	DESCRIPTION
		"This table contains information about SPVCs (Smart
		Permanent Virtual Circuits) that have their source
		at this switch."
	::= { q2931Group 3 }

pnniSpvcSrcEntry OBJECT-TYPE
	SYNTAX  PnniSpvcSrcEntry
	MAX-ACCESS  not-accessible
	STATUS  current
	DESCRIPTION
		"A table entry containing source SPVC (Smart
		Permanent Virtual Circuits) information."
	INDEX   { pnniSpvcSrcIndex }
	::= { pnniSpvcSrcTable 1 }

PnniSpvcSrcEntry ::= SEQUENCE {
		pnniSpvcSrcIndex                Integer32,
		pnniSpvcSrcCallingPort          Integer32,
		pnniSpvcSrcCallingVPI           Integer32,
		pnniSpvcSrcCallingVCI           Integer32,
		pnniSpvcSrcCalledAtmAddr        NsapAddr,
		pnniSpvcSrcCalledPort           Integer32,
		pnniSpvcSrcCalledVPVCSel        INTEGER,
		pnniSpvcSrcCalledVPI            Integer32,
		pnniSpvcSrcCalledVCI            Integer32,
		pnniSpvcSrcCalledAssignedVPI    Integer32,
		pnniSpvcSrcCalledAssignedVCI    Integer32,
		pnniSpvcSrcFwdUpcKey            Integer32,
		pnniSpvcSrcBckUpcKey            Integer32,
		pnniSpvcSrcBearerClass          INTEGER,
		pnniSpvcSrcTrafficType          INTEGER,
		pnniSpvcSrcTimingReq            INTEGER,
		pnniSpvcSrcSusceptClip          INTEGER,
		pnniSpvcSrcFwdQoSClass          INTEGER,
		pnniSpvcSrcBckQoSClass          INTEGER,
		pnniSpvcSrcTransitNetSel        TransitNetwork,
		pnniSpvcSrcLastFailCause        DisplayString,
		pnniSpvcSrcRetryCount           Integer32,
		pnniSpvcSrcLastChangeTime       TimeTicks,
		pnniSpvcSrcStatus               INTEGER,
		pnniSpvcSrcName			OCTET STRING,
		pnniSpvcSrcEntryStatus          EntryStatus,
		pnniSpvcSrcRouteCost		Integer32,
		pnniSpvcSrcDtlIndex		Integer32,
		pnniSpvcSrcActiveDtlIndex	Integer32,
		pnniSpvcSrcRerouteStatus	INTEGER,
		pnniSpvcSrcCallingDomain	Integer32,
		pnniSpvcSrcQosIndex		Integer32,
		pnniSpvcSrcDtlIndex1		Integer32,
		pnniSpvcSrcDtlIndex2		Integer32,
		pnniSpvcSrcDtlIndex3		Integer32,
		pnniSpvcSrcDtlIndex4		Integer32,
		pnniSpvcSrcDtlWeight1		Integer32,
		pnniSpvcSrcDtlWeight2		Integer32,
		pnniSpvcSrcDtlWeight3		Integer32,
		pnniSpvcSrcDtlWeight4		Integer32,
		pnniSpvcSrcBackoffStatus	INTEGER,
		pnniSpvcSrcPriority		Integer32,
		pnniSpvcSrcLastLocation	        DisplayString,
		pnniSpvcSrcOldRouteCost		Integer32,
		pnniSpvcSrcDownReason		INTEGER,
		pnniSpvcSrcActiveDtlNodeIndex   Integer32,
		pnniSpvcSrcDtlTag               Integer32,
		pnniSpvcSrcAutoDtlStatus        INTEGER,
		pnniSpvcSrcRGroupIndex          INTEGER,
		pnniSpvcSrcSecondaryVPI         Integer32,
		pnniSpvcSrcSecondaryVCI         Integer32
	}

pnniSpvcSrcIndex OBJECT-TYPE
	SYNTAX  Integer32
	MAX-ACCESS  read-create
	STATUS  current
	DESCRIPTION
		"The value of this object uniquely identify the
		SPVCs (Smart Permanent Virtual Circuits) that
		have this switch as their source."
	::= { pnniSpvcSrcEntry 1 }

pnniSpvcSrcCallingPort OBJECT-TYPE
	SYNTAX  Integer32
	MAX-ACCESS  read-create
	STATUS  current
	DESCRIPTION
		"The value of this object identifies the input port
		of this SPVC (Smart Permanent Virtual Circuits), and
		is the same as the chanrInputPort, chanPort, pathPort,
		and portNumber."
	::= { pnniSpvcSrcEntry 2 }

pnniSpvcSrcCallingVPI OBJECT-TYPE
	SYNTAX  Integer32
	MAX-ACCESS  read-create
	STATUS  current
	DESCRIPTION
		"The VPI to be used at the Calling NI
		for this SPVC."
	::= { pnniSpvcSrcEntry 3 }

pnniSpvcSrcCallingVCI OBJECT-TYPE
	SYNTAX  Integer32
	MAX-ACCESS  read-create
	STATUS  current
	DESCRIPTION
		"The VCI to be used at the Calling NI
		SPVC."
	::= { pnniSpvcSrcEntry 4 }


pnniSpvcSrcCalledAtmAddr OBJECT-TYPE
	SYNTAX  NsapAddr
	MAX-ACCESS  read-create
	STATUS  current
	DESCRIPTION
		"The ATM address of the distant end NI (remote
		switch) for this SPVC."
	::= { pnniSpvcSrcEntry 5 }

pnniSpvcSrcCalledPort OBJECT-TYPE
	SYNTAX  Integer32
	MAX-ACCESS  read-only
	STATUS  current
	DESCRIPTION
		"The value of this object identifies the port
		of this SPVC (Smart Permanent Virtual Circuits) at
		the destination end. It has a value of -1 if the
		port at the destination switch cannot be determined."
	::= { pnniSpvcSrcEntry 6 }

pnniSpvcSrcCalledVPVCSel OBJECT-TYPE
	SYNTAX  INTEGER {
			    noPref(1),
			    require(2)
			}
	MAX-ACCESS  read-create
	STATUS  current
	DESCRIPTION
		"The Called VPI/VCI value selection qualifier."
	::= { pnniSpvcSrcEntry 7 }

pnniSpvcSrcCalledVPI OBJECT-TYPE
	SYNTAX  Integer32
	MAX-ACCESS  read-create
	STATUS  current
	DESCRIPTION
		"The VPI to be used at the Called NI
		for this SPVC."
	::= { pnniSpvcSrcEntry 8 }

pnniSpvcSrcCalledVCI OBJECT-TYPE
	SYNTAX  Integer32
	MAX-ACCESS  read-create
	STATUS  current
	DESCRIPTION
		"The VCI to be used at the Called NI
		for this SPVC."
	::= { pnniSpvcSrcEntry 9 }

pnniSpvcSrcCalledAssignedVPI OBJECT-TYPE
	SYNTAX  Integer32
	MAX-ACCESS  read-only
	STATUS  current
	DESCRIPTION
		"The VPI assigned at the Called NI for this
		SPVC.  This value is only meaningful if the SPVC
		status is up."
	::= { pnniSpvcSrcEntry 10 }

pnniSpvcSrcCalledAssignedVCI OBJECT-TYPE
	SYNTAX  Integer32
	MAX-ACCESS  read-only
	STATUS  current
	DESCRIPTION
		"The VCI assigned at the Called NI for this
		SPVC.  This value is only meaningful if the SPVC
		status is up."
	::= { pnniSpvcSrcEntry 11 }

pnniSpvcSrcFwdUpcKey OBJECT-TYPE
	SYNTAX  Integer32
	MAX-ACCESS  read-create
	STATUS  current
	DESCRIPTION
		"The forward UPC traffic contract key for this SPVC.
		This key must be defined in the upcContractTable."
	::= { pnniSpvcSrcEntry 12 }

pnniSpvcSrcBckUpcKey OBJECT-TYPE
	SYNTAX  Integer32
	MAX-ACCESS  read-create
	STATUS  current
	DESCRIPTION
		"The forward UPC traffic contract key for this SPVC.
		This key must be defined in the upcContractTable."
	::= { pnniSpvcSrcEntry 13 }

pnniSpvcSrcBearerClass OBJECT-TYPE
	SYNTAX  INTEGER {
			    classA(1),
			    classC(2),
			    classX(3)
			}
	MAX-ACCESS  read-create
	STATUS  current
	DESCRIPTION
		"The requested broadband bearer class for this
		SPVC."
	::= { pnniSpvcSrcEntry 14 }

pnniSpvcSrcTrafficType OBJECT-TYPE
	SYNTAX  INTEGER {
			    noIndication(1),
			    cbr(2),
			    vbr(3)
			}
	MAX-ACCESS  read-create
	STATUS  obsolete
	DESCRIPTION
		"The requested broadband bearer traffic type for
		this SPVC."
	::= { pnniSpvcSrcEntry 15 }

pnniSpvcSrcTimingReq OBJECT-TYPE
	SYNTAX  INTEGER {
			    noIndication(1),
			    end2endRequired(2),
			    end2endNotReqd(3)
			}
	MAX-ACCESS  read-create
	STATUS  obsolete
	DESCRIPTION
		"The requested broadband bearer timing requirements
		 for this SPVC."
	::= { pnniSpvcSrcEntry 16 }

pnniSpvcSrcSusceptClip OBJECT-TYPE
	SYNTAX  INTEGER {
			    no(1),
			    yes(2)
			}
	MAX-ACCESS  read-create
	STATUS  current
	DESCRIPTION
		"The requested broadband bearer susceptability to
		 for this SPVC."
	::= { pnniSpvcSrcEntry 17 }

--
-- Should be made read-write when supported.
--
pnniSpvcSrcFwdQoSClass OBJECT-TYPE
	SYNTAX  INTEGER {
			    class0(1),
			    class1(2),
			    class2(3),
			    class3(4),
			    class4(5)
			}
	MAX-ACCESS  read-create
	STATUS  current
	DESCRIPTION
		"The requested quality of service for this SPVC in
		the forward (calling to called) direction."
	::= { pnniSpvcSrcEntry 18 }

--
-- Should be made read-write when supported.
--
pnniSpvcSrcBckQoSClass OBJECT-TYPE
	SYNTAX  INTEGER {
			    class0(1),
			    class1(2),
			    class2(3),
			    class3(4),
			    class4(5)
			}
	MAX-ACCESS  read-create
	STATUS  current
	DESCRIPTION
		"The requested quality of service for this SPVC in
		the backward (called to calling) direction."
	::= { pnniSpvcSrcEntry 19 }

--
-- Should be made read-write when supported.
--
pnniSpvcSrcTransitNetSel OBJECT-TYPE
	SYNTAX  TransitNetwork
	MAX-ACCESS  read-only
	STATUS  current
	DESCRIPTION
		"The optional transit network selection for this
		SPVC."
	::= { pnniSpvcSrcEntry 20 }

pnniSpvcSrcLastFailCause OBJECT-TYPE
	SYNTAX  DisplayString
	MAX-ACCESS  read-only
	STATUS  current
	DESCRIPTION
		"The last call setup failure cause code for this
		SPVC."
	::= { pnniSpvcSrcEntry 21 }

pnniSpvcSrcRetryCount OBJECT-TYPE
	SYNTAX  Integer32
	MAX-ACCESS  read-only
	STATUS  current
	DESCRIPTION
		"The number of times the call setup has been
		attempted since the SPVC creation or the last
		successful call setup."
	::= { pnniSpvcSrcEntry 22 }

pnniSpvcSrcLastChangeTime OBJECT-TYPE
	SYNTAX  TimeTicks
	MAX-ACCESS  read-only
	STATUS  current
	DESCRIPTION
		"The time since this SPVC (Smart Permanent Virtual
		Circuits) has been up/down in hundredths of a second."
	::= { pnniSpvcSrcEntry 23 }

pnniSpvcSrcStatus OBJECT-TYPE
	SYNTAX  INTEGER {
			up(1),
			down(2),
			failed(3)
		}
	MAX-ACCESS  read-only
	STATUS  current
	DESCRIPTION
		"The operational status of this SPVC (Smart Permanent
		Virtual Circuit)."
	::= { pnniSpvcSrcEntry 24 }

pnniSpvcSrcName OBJECT-TYPE
	 SYNTAX  OCTET STRING (SIZE(0..32))
	 MAX-ACCESS  read-create
	 STATUS  current
	 DESCRIPTION
		 " The value of this object identifies the
		 name that has been assigned for this SPVC."
	 ::= { pnniSpvcSrcEntry 25 }

pnniSpvcSrcEntryStatus OBJECT-TYPE
	SYNTAX  EntryStatus
	MAX-ACCESS  read-create
	STATUS  current
	DESCRIPTION
		"The status of this SPVC (Smart Permanent Virtual
		Circuits) entry."
	::= { pnniSpvcSrcEntry 26 }

pnniSpvcSrcRouteCost OBJECT-TYPE
	SYNTAX  Integer32
	MAX-ACCESS  read-only
	STATUS  current
	DESCRIPTION
		"The cumulative route cost for the current route
		of this SPVC (Smart Permanent Virtual Circuits)."
	::= { pnniSpvcSrcEntry 27 }

pnniSpvcSrcDtlIndex OBJECT-TYPE
	SYNTAX	Integer32
	MAX-ACCESS  read-create
	STATUS  obsolete
	DESCRIPTION
		"The Designated Transit List (DTL) index for this
		SPVC (Smart Permanent Virtual Circuit).  This variable
		has been deprecated. Any writes to this variable will
		be treated as writes to pnniSpvcSrcDtlIndex1. This value
		must be defined in the ftPnniDTLTable.  The DTL
		specifies a preferred call routing for the SVC
		portion of the SPVC."
	::= { pnniSpvcSrcEntry 28 }

pnniSpvcSrcActiveDtlIndex OBJECT-TYPE
	SYNTAX	Integer32
	MAX-ACCESS  read-only
	STATUS  current
	DESCRIPTION
		"The Active Designated Transit List (DTL) index for
		this SPVC (Smart Permanent Virtual Circuit).  This
		value along with pnniSpvcSrcActiveDtlNodeIndex
		uniquely identifies the DTL that is currently
		used by the SVC portion of the SPVC."
	::= { pnniSpvcSrcEntry 29 }

pnniSpvcSrcRerouteStatus OBJECT-TYPE
	SYNTAX	INTEGER {
			enabled(1),
			disabled(2)
		}
	MAX-ACCESS	read-create
	STATUS	current
	DESCRIPTION
		"The status of the reroute function for this SPVC
		(Smart Permanent Virtual Circuit).  If set to disabled(2),
		no rerouting will be attempted for this SPVC."
	DEFVAL	{ disabled }
	::= { pnniSpvcSrcEntry 30 }

pnniSpvcSrcCallingDomain OBJECT-TYPE
	SYNTAX  Integer32
	MAX-ACCESS  read-create
	STATUS  current
	DESCRIPTION
		"The Domain ID to be used at the Calling NI
		SPVC."
	::= { pnniSpvcSrcEntry 31 }

pnniSpvcSrcQosIndex OBJECT-TYPE
	SYNTAX  Integer32
	MAX-ACCESS  read-create
	STATUS  current
	DESCRIPTION
		"The index for the QOS Class Expansion Table to be used for
		 this spvc."
	::= { pnniSpvcSrcEntry 32 }

pnniSpvcSrcDtlIndex1 OBJECT-TYPE
	SYNTAX	Integer32
	MAX-ACCESS  read-create
	STATUS  obsolete
	DESCRIPTION
		"The first Designated Transit List (DTL) index for this
		SPVC (Smart Permanent Virtual Circuit).  This value
		must be defined in the ftPnniDTLTable.  The DTL
		specifies a preferred call routing for the SVC
		portion of the SPVC."
	::= { pnniSpvcSrcEntry 33 }

pnniSpvcSrcDtlIndex2 OBJECT-TYPE
	SYNTAX	Integer32
	MAX-ACCESS  read-create
	STATUS  obsolete
	DESCRIPTION
		"The second Designated Transit List (DTL) index for this
		SPVC (Smart Permanent Virtual Circuit).  This value
		must be defined in the ftPnniDTLTable.  The DTL
		specifies a preferred call routing for the SVC
		portion of the SPVC."
	::= { pnniSpvcSrcEntry 34 }

pnniSpvcSrcDtlIndex3 OBJECT-TYPE
	SYNTAX	Integer32
	MAX-ACCESS  read-create
	STATUS  obsolete
	DESCRIPTION
		"The third Designated Transit List (DTL) index for this
		SPVC (Smart Permanent Virtual Circuit).  This value
		must be defined in the ftPnniDTLTable.  The DTL
		specifies a preferred call routing for the SVC
		portion of the SPVC."
	::= { pnniSpvcSrcEntry 35 }

pnniSpvcSrcDtlIndex4 OBJECT-TYPE
	SYNTAX	Integer32
	MAX-ACCESS  read-create
	STATUS  obsolete
	DESCRIPTION
		"The fourth Designated Transit List (DTL) index for this
		SPVC (Smart Permanent Virtual Circuit).  This value
		must be defined in the ftPnniDTLTable.  The DTL
		specifies a preferred call routing for the SVC
		portion of the SPVC."
	::= { pnniSpvcSrcEntry 36 }

pnniSpvcSrcDtlWeight1 OBJECT-TYPE
	SYNTAX	Integer32
	MAX-ACCESS  read-create
	STATUS  obsolete
	DESCRIPTION
		"The weight of the first Designated Transit List (DTL)
		index for this SPVC (Smart Permanent Virtual Circuit).
		The weight specifies the priority of this DTL index
		among the four DTL indices that can be specified for
		a particular SPVC."
	DEFVAL	{ 0 }
	::= { pnniSpvcSrcEntry 37 }

pnniSpvcSrcDtlWeight2 OBJECT-TYPE
	SYNTAX	Integer32
	MAX-ACCESS  read-create
	STATUS  obsolete
	DESCRIPTION
		"The weight of the second Designated Transit List (DTL)
		index for this SPVC (Smart Permanent Virtual Circuit).
		The weight specifies the priority of this DTL index
		among the four DTL indices that can be specified for
		a particular SPVC."
	DEFVAL	{ 0 }
	::= { pnniSpvcSrcEntry 38 }

pnniSpvcSrcDtlWeight3 OBJECT-TYPE
	SYNTAX	Integer32
	MAX-ACCESS  read-create
	STATUS  obsolete
	DESCRIPTION
		"The weight of the third Designated Transit List (DTL)
		index for this SPVC (Smart Permanent Virtual Circuit).
		The weight specifies the priority of this DTL index
		among the four DTL indices that can be specified for
		a particular SPVC."
	DEFVAL	{ 0 }
	::= { pnniSpvcSrcEntry 39 }

pnniSpvcSrcDtlWeight4 OBJECT-TYPE
	SYNTAX	Integer32
	MAX-ACCESS  read-create
	STATUS  obsolete
	DESCRIPTION
		"The weight of the fourth Designated Transit List (DTL)
		index for this SPVC (Smart Permanent Virtual Circuit).
		The weight specifies the priority of this DTL index
		among the four DTL indices that can be specified for
		a particular SPVC."
	DEFVAL	{ 0 }
	::= { pnniSpvcSrcEntry 40 }

pnniSpvcSrcBackoffStatus OBJECT-TYPE
	SYNTAX	INTEGER {
			enabled(1),
			disabled(2)
		}
	MAX-ACCESS	read-create
	STATUS	current
	DESCRIPTION
		"The status of the backoff function for this SPVC
		(Smart Permanent Virtual Circuit).  If set to disabled(2),
		directed dtls configured for this SPVC will be continually
		retried on failure."
	DEFVAL	{ enabled }
	::= { pnniSpvcSrcEntry 41 }

pnniSpvcSrcPriority OBJECT-TYPE
	SYNTAX  Integer32
	MAX-ACCESS  read-create
	STATUS  current
	DESCRIPTION
		"Priority of this SPVCC for connection"
	::= { pnniSpvcSrcEntry 42 }

pnniSpvcSrcLastLocation OBJECT-TYPE
	SYNTAX  DisplayString
	MAX-ACCESS  read-only
	STATUS  current
	DESCRIPTION
		"The last call setup failure location code for this
		SPVC. This indicates the switch that initiated the
		clearing for the call. This is formatted as a text
		string with the fields:
		   FMT: Indicates diagnostic format
		   RMT: Indicates whether a remote switch is the source of the
			failure or this switch inserted the location diag
		   LINK:Link id that clear pertains to
		   VPI: VPI that clear pertains to
		   The remaining fields are format specific"
	::= { pnniSpvcSrcEntry 43 }

pnniSpvcSrcOldRouteCost  OBJECT-TYPE
	SYNTAX  Integer32
	MAX-ACCESS  read-only
	STATUS  current
	DESCRIPTION
		"This OID is specified only to be included the the
		pnniSpvcUp trap. It specifies the
		path cost of the call the previous time this call
		was up. If the call has not been up, this will
		report a value of -1."
	::= { pnniSpvcSrcEntry 44 }

pnniSpvcSrcDownReason  OBJECT-TYPE
	SYNTAX  INTEGER {
			reroute(1),
			failure(2),
			deletion(3)
		}
	MAX-ACCESS  read-only
	STATUS  current
	DESCRIPTION
		"This OID is specified only to be included the the
		pnniSpvccDown and pnniSpvccFail traps.
		This specifies whether the SPVC call was cleared due to
		a better route being found, a network failure,
		or SPVC deletion."
	::= { pnniSpvcSrcEntry 45 }

pnniSpvcSrcActiveDtlNodeIndex OBJECT-TYPE
	SYNTAX	Integer32
	MAX-ACCESS  read-only
	STATUS  current
	DESCRIPTION
		"The Node index of the Active Designated Transit List
		for this SPVC (Smart Permanent Virtual Circuit).
		The active DTL indexed by the node index and DTL index
		identifies the DTL that is currently used by the SVC
		portion of the SPVC. The value of this object is 65535
		for FTPNNI nodes."
	::= { pnniSpvcSrcEntry 46 }

pnniSpvcSrcDtlTag OBJECT-TYPE
	SYNTAX  Integer32
	MAX-ACCESS  read-create
	STATUS  current
	DESCRIPTION
		"This value specifies an index into a table of DTLs,
		the DTL entries in this table will be used to setup
		the SPVC."
	::= { pnniSpvcSrcEntry 47 }

pnniSpvcSrcAutoDtlStatus OBJECT-TYPE
	SYNTAX	INTEGER {
			enabled(1),
			disabled(2)
		}
	MAX-ACCESS	read-create
	STATUS  current
	DESCRIPTION
		"The status of the dynamic path selection function for this
		SPVC (Smart Permanent Virtual Circuit). If set to disabled(2),
		auto path selection will not be used."
	DEFVAL	{ enabled }
	::= { pnniSpvcSrcEntry 48 }

pnniSpvcSrcRGroupIndex OBJECT-TYPE
	SYNTAX        INTEGER (1..65535)
	MAX-ACCESS        read-create
	STATUS  current
	DESCRIPTION
		"This specifies the entry in the Spvxc Redundancy Group
		 table for information regarding the secondary port to
		 be used as the redundant port"
	::= { pnniSpvcSrcEntry 49 }

pnniSpvcSrcSecondaryVPI OBJECT-TYPE
	SYNTAX  Integer32
	MAX-ACCESS  read-create
	STATUS  current
	DESCRIPTION
		"The Secondary VPI to be used at the originating switch for
		 the redundant permanent portion of this SPVC. "
	::= { pnniSpvcSrcEntry 50 }

pnniSpvcSrcSecondaryVCI OBJECT-TYPE
	SYNTAX  Integer32
	MAX-ACCESS  read-create
	STATUS  current
	DESCRIPTION
		"The Secondary VCI to be used at the originating switch for
		 the redundant permanent portion of this SPVC."
	::= { pnniSpvcSrcEntry 51 }



------------------------------------------------------------------------

--
-- PNNI SPVC destination-side definitions
--

pnniSpvcDestNumberOfSPVCs OBJECT-TYPE
	SYNTAX  Integer32
	MAX-ACCESS  read-only
	STATUS  current
	DESCRIPTION
		"The number of connected SPVCs (Smart Permanent Virtual
		Circuits) that have their destination at this switch."
	::= { q2931Group 4 }

pnniSpvcDestTable OBJECT-TYPE
	SYNTAX  SEQUENCE OF PnniSpvcDestEntry
	MAX-ACCESS  not-accessible
	STATUS  current
	DESCRIPTION
		"This table contains information about SPVCs (Smart
		Permanent Virtual Circuits) that have their destination
		at this switch."
	::= { q2931Group 5 }

pnniSpvcDestEntry OBJECT-TYPE
	SYNTAX  PnniSpvcDestEntry
	MAX-ACCESS  not-accessible
	STATUS  current
	DESCRIPTION
		"A table entry containing destination SPVC (Smart
		Permanent Virtual Circuits) information."
	INDEX   { pnniSpvcDestIndex }
	::= { pnniSpvcDestTable 1 }

PnniSpvcDestEntry ::= SEQUENCE {
		pnniSpvcDestIndex               Integer32,
		pnniSpvcDestCallingAtmAddr      NsapAddr,
		pnniSpvcDestCallingPort         Integer32,
		pnniSpvcDestCallingVPI          Integer32,
		pnniSpvcDestCallingVCI          Integer32,
		pnniSpvcDestCalledAtmAddr       NsapAddr,
		pnniSpvcDestCalledPort          Integer32,
		pnniSpvcDestAssignedVPI         Integer32,
		pnniSpvcDestAssignedVCI         Integer32,
		pnniSpvcDestBearerClass         INTEGER,
		pnniSpvcDestTrafficType         INTEGER,
		pnniSpvcDestTimingReq           INTEGER,
		pnniSpvcDestSusceptClip         INTEGER,
		pnniSpvcDestUpTime              TimeTicks,
		pnniSpvcDestFwdQoSClass         INTEGER,
		pnniSpvcDestBckQoSClass         INTEGER,
		pnniSpvcDestTransitNetSel	TransitNetwork,
		pnniSpvcDestStatus		INTEGER,
		pnniSpvcDestRGroupIndex         INTEGER
	}

pnniSpvcDestIndex OBJECT-TYPE
	SYNTAX  Integer32
	MAX-ACCESS  read-only
	STATUS  current
	DESCRIPTION
	       "The value of this object uniquely identify the
		SPVCs (Smart Permanent Virtual Circuits) that
		have this switch as their source."
	::= { pnniSpvcDestEntry 1 }

pnniSpvcDestCallingAtmAddr OBJECT-TYPE
	SYNTAX  NsapAddr
	MAX-ACCESS  read-only
	STATUS  current
	DESCRIPTION
		"The ATM address of the local end NI (on this
		switch) for this SPVC."
	::= { pnniSpvcDestEntry 2 }

pnniSpvcDestCallingPort OBJECT-TYPE
	SYNTAX  Integer32
	MAX-ACCESS  read-only
	STATUS  current
	DESCRIPTION
		"The value of this object identifies the port
		of this terminating SPVC (Smart Permanent Virtual Circuits)
		at the source end. It has a value of -1 if the
		port at the destination switch cannot be determined."
	::= { pnniSpvcDestEntry 3 }

pnniSpvcDestCallingVPI OBJECT-TYPE
	SYNTAX  Integer32
	MAX-ACCESS  read-only
	STATUS  current
	DESCRIPTION
		"The VPI to be used at the Calling NI for this
		SPVC."
       ::= { pnniSpvcDestEntry 4 }

pnniSpvcDestCallingVCI OBJECT-TYPE
	SYNTAX  Integer32
	MAX-ACCESS  read-only
	STATUS  current
	DESCRIPTION
		"The VCI to be used at the Calling NI for this
		SPVC."
	::= { pnniSpvcDestEntry 5 }

pnniSpvcDestCalledAtmAddr OBJECT-TYPE
	SYNTAX  NsapAddr
	MAX-ACCESS  read-only
	STATUS  current
	DESCRIPTION
		"The ATM address of the distant end NI (remote
		switch) for this SPVC."
	::= { pnniSpvcDestEntry 6 }

pnniSpvcDestCalledPort OBJECT-TYPE
	SYNTAX  Integer32
	MAX-ACCESS  read-only
	STATUS  current
	DESCRIPTION
		"The value of this object identifies the port
		of this terminating SPVC (Smart Permanent Virtual Circuits)
		at the destination end. It has a value os -1 if the
		port at the destination switch cannot be determined."
	::= { pnniSpvcDestEntry 7 }

pnniSpvcDestAssignedVPI OBJECT-TYPE
	SYNTAX  Integer32
	MAX-ACCESS  read-only
	STATUS  current
	DESCRIPTION
		"The VPI assigned at the Called NI for this
		SPVC.  This value is only meaningful if the SPVC
		status is up."
	::= { pnniSpvcDestEntry 8 }

pnniSpvcDestAssignedVCI OBJECT-TYPE
       SYNTAX  Integer32
	MAX-ACCESS  read-only
	STATUS  current
	DESCRIPTION
		"The VCI assigned at the Called NI for this
		SPVC.  This value is only meaningful if the SPVC
		status is up."
	::= { pnniSpvcDestEntry 9 }

pnniSpvcDestBearerClass OBJECT-TYPE
	SYNTAX  INTEGER {
			    classA(1),
			    classC(2),
			    classX(3)
			}
	MAX-ACCESS  read-only
	STATUS  current
	DESCRIPTION
		"The broadband bearer class for this
		SPVC."
	::= { pnniSpvcDestEntry 10 }

pnniSpvcDestTrafficType OBJECT-TYPE
	SYNTAX  INTEGER {
			    noIndication(1),
			    cbr(2),
			    vbr(3)
			}
	MAX-ACCESS  read-only
	STATUS  deprecated
	DESCRIPTION
		"The broadband bearer traffic type for
		this SPVC."
	::= { pnniSpvcDestEntry 11 }

pnniSpvcDestTimingReq OBJECT-TYPE
	SYNTAX  INTEGER {
			    noIndication(1),
			    end2endRequired(2),
			    end2endNotReqd(3)
			}
	MAX-ACCESS  read-only
	STATUS  deprecated
	DESCRIPTION
		"The broadband bearer timing requirements
		 for this SPVC."
	::= { pnniSpvcDestEntry 12 }

pnniSpvcDestSusceptClip OBJECT-TYPE
	SYNTAX  INTEGER {
			    no(1),
			    yes(2)
			}
	MAX-ACCESS  read-only
	STATUS  current
	DESCRIPTION
		"The broadband bearer susceptability to
		clipping for this SPVC."
	::= { pnniSpvcDestEntry 13 }

pnniSpvcDestUpTime OBJECT-TYPE
	SYNTAX  TimeTicks
	MAX-ACCESS  read-only
	STATUS  current
	DESCRIPTION
		"The time since this SPVC (Smart Permanent Virtual
		Circuits) was created in hundredths of a second."
	::= { pnniSpvcDestEntry 14 }

pnniSpvcDestFwdQoSClass OBJECT-TYPE
	SYNTAX  INTEGER {
			    class0(1),
			    class1(2),
			    class2(3),
			    class3(4),
			    class4(5)
			}
	MAX-ACCESS  read-only
	STATUS  current
	DESCRIPTION
		"The requested quality of service for this SPVC in
		the forward (calling to called) direction."
	::= { pnniSpvcDestEntry 15 }

pnniSpvcDestBckQoSClass OBJECT-TYPE
	SYNTAX  INTEGER {
			    class0(1),
			    class1(2),
			    class2(3),
			    class3(4),
			    class4(5)
			}
	MAX-ACCESS  read-only
	STATUS  current
	DESCRIPTION
		"The requested quality of service for this SPVC in
		the backward (called to calling) direction."
	::= { pnniSpvcDestEntry 16 }

pnniSpvcDestTransitNetSel OBJECT-TYPE
	SYNTAX  TransitNetwork
	MAX-ACCESS  read-only
	STATUS  current
	DESCRIPTION
		"The optional transit network selection for this
		SPVC."
	::= { pnniSpvcDestEntry 17 }

pnniSpvcDestStatus OBJECT-TYPE
	SYNTAX  INTEGER {
			up(1),
			down(2),
			failed(3)
		}
	MAX-ACCESS  read-only
	STATUS  current
	DESCRIPTION
		"The operational status of this SPVC (Smart Permanent
		Virtual Circuit)."
	::= { pnniSpvcDestEntry 18 }

pnniSpvcDestRGroupIndex OBJECT-TYPE
	SYNTAX        INTEGER (1..65535)
	MAX-ACCESS        read-only
	STATUS  current
	DESCRIPTION
		"This specifies the entry in the Spvxc Redundancy Group
		 table for information regarding the secondary port to
		 be used as the redundant port. This will used at the
		 terminating PVC end."
	::= { pnniSpvcDestEntry 19 }

------------------------------------------------------------------------

--
-- PNNI SPVC Configuration Parameters
--

pnniSpvcParamGroup	OBJECT IDENTIFIER ::=  { q2931Group 7 }

pnniSpvcPaceInterval  OBJECT-TYPE
	SYNTAX	TimeInterval
	MAX-ACCESS	read-write
	STATUS	current
	DESCRIPTION
		"The time interval between successive callbacks
		to the SPVC controller to open to the destinations
		of a batch of SPVCs"
	DEFVAL	{ 200 }
	::= { pnniSpvcParamGroup 1 }


pnniSpvcPaceNumSpvcs  OBJECT-TYPE
	SYNTAX	Integer32
	MAX-ACCESS	read-write
	STATUS	current
	DESCRIPTION
		"The max number of SPVCs that each batch of
		SPVCs that the SPVC controller tries to open
		to per pnniSpvcPaceInterval"
	DEFVAL	{ 20 }
	::= { pnniSpvcParamGroup 2 }


pnniSpvcRerouteInterval OBJECT-TYPE
	SYNTAX	TimeInterval
	MAX-ACCESS	read-write
	STATUS	current
	DESCRIPTION
		"The time interval between successive callbacks to
		the SPVC controller to reroute existing SPVC connection
		if a better path is available to the destination"
	DEFVAL	{ 1000 }
	::= { pnniSpvcParamGroup 3 }


pnniSpvcRerouteNumSpvcs OBJECT-TYPE
	SYNTAX	Integer32
	MAX-ACCESS	read-write
	STATUS	current
	DESCRIPTION
		"The number of SPVCs that are attempted to be
		rerouted by the SPVC controller per pnniSpvcRerouteInterval"
	DEFVAL	{ 20 }
	::= { pnniSpvcParamGroup 4 }


pnniSpvcRerouteThreshold OBJECT-TYPE
	SYNTAX	Integer32
	MAX-ACCESS	read-write
	STATUS	current
	DESCRIPTION
		"The percentage improvement in the cost that
		the new SPVC path must have over the current
		SPVC path before a reroute will be performed."
	DEFVAL	{ 50 }
	::= { pnniSpvcParamGroup 5 }

pnniSpvcLowestPriority  OBJECT-TYPE
	SYNTAX  Integer32
	MAX-ACCESS  read-write
	STATUS  current
	DESCRIPTION
		"The value of lowest priority for SPVCCs"
	DEFVAL  { 10 }
	::= { pnniSpvcParamGroup 6 }

pnniSpvcDefaultUbrBandwidth  OBJECT-TYPE
	SYNTAX  INTEGER (0..65534)
	MAX-ACCESS  read-write
	STATUS  current
	DESCRIPTION
		"The default bandwidth in Kilo-CPS to be used for UBR SPVCs"
	DEFVAL  { 1 }
	::= { pnniSpvcParamGroup 7 }

pnniSpvcBackoffInterval  OBJECT-TYPE
	SYNTAX	TimeInterval
	MAX-ACCESS	read-write
	STATUS	current
	DESCRIPTION
		"The time interval to backoff a DTL that failed
		call setup.  The DTL will not be used again until
		this interval has elapsed.  The interval will not
		be applicable if backoff is disabled on the SPVC."
	DEFVAL	{ 60000 }
	::= { pnniSpvcParamGroup 9 }

pnniSpvcTrapMode  OBJECT-TYPE
	SYNTAX  INTEGER {
			reroute(1),
			failure(2),
			all(3),
			none(4)
		}
	MAX-ACCESS  read-write
	STATUS  current
	DESCRIPTION
		"This configuration item specifies whether the
		 switch should send the:
		 spvcRerouteInitiated
			OR
		 pnniSpvccUp and pnniSpvccFail
			OR
		 pnniSpvccDown, pnniSpvccFail, and pnniSpvccUp
		traps."
	DEFVAL { reroute }
	::= { pnniSpvcParamGroup 8 }


pnniPmpSpvcPartyPaceNum  OBJECT-TYPE
	   SYNTAX  Integer32
	   MAX-ACCESS  read-write
	   STATUS  current
	   DESCRIPTION
	       "The maximum number parties within a PMP SPVC that are activated
		per SpvcPacingInterval."
	   DEFVAL { 10 }
	   ::= { pnniSpvcParamGroup 10 }

------------------------------------------------------------------------
-- PNNI SPVPC Control parameters : This sub-group contains all the MIB
-- variables used for configuring and managing the SPVPC control
-- parameters like pacing interval, reroute interval etc.
------------------------------------------------------------------------

pnniSpvpcParamGroup         OBJECT IDENTIFIER ::=  { q2931Group 8 }

pnniSpvpcPaceInterval  OBJECT-TYPE
	SYNTAX    TimeInterval
	MAX-ACCESS    read-write
	STATUS    current
	DESCRIPTION
		"The time interval between successive callbacks
		 to the SPVPC controller to open connections to the
		 destinations of a batch of SPVPCs. This parameter along
		 with pnniSpvpcPaceNumSpvpcs control the rate at which the
		 SPVPCs that are down are established. Analogous SPVCC
		 variable is pnniSpvcPaceInterval."
	DEFVAL   { 200 }
	::= { pnniSpvpcParamGroup 1 }


pnniSpvpcPaceNumSpvpcs  OBJECT-TYPE
	SYNTAX    INTEGER (0..1000)
	MAX-ACCESS    read-write
	STATUS    current
	DESCRIPTION
		"The max number of SPVPCs that the SPVPC controller
		 tries to activate per pnniSpvpcPaceInterval. This controls
		 the rate at which SPVPCs that are down are established. The
		 corresponding SPVCC variable is pnniSpvcPaceNumSpvcs."
	DEFVAL   { 20 }
	::= { pnniSpvpcParamGroup 2 }


pnniSpvpcRerouteInterval OBJECT-TYPE
	SYNTAX    TimeInterval
	MAX-ACCESS    read-write
	STATUS    current
	DESCRIPTION
		"The time interval between successive callbacks to
		 the SPVPC controller to reroute existing SPVPC connections
		 if a better path is available to the destination. This
		 is one of the parameters that control the rate at which
		 rerouting is attempted. The analogous SPVCC variable is
		 pnniSpvcRerouteInterval."
	DEFVAL   { 1500 }
	::= { pnniSpvpcParamGroup 3 }


pnniSpvpcRerouteNumSpvpcs OBJECT-TYPE
	SYNTAX   INTEGER (0..1000)
	MAX-ACCESS   read-write
	STATUS   current
	DESCRIPTION
		"The number of SPVPCs that are attempted to be
		 rerouted by the SPVPC controller per
		 pnniSpvpcRerouteInterval. Thus it determines the
		 rerouting rate. The analogous SPVCC variable is
		 pnniSpvcRerouteNumSpvcs."
	DEFVAL   { 15 }
	::= { pnniSpvpcParamGroup 4 }


pnniSpvpcRerouteThreshold OBJECT-TYPE
	SYNTAX   INTEGER (0..100)
	MAX-ACCESS   read-write
	STATUS   current
	DESCRIPTION
		"The percentage improvement in the cost that
		 the new SPVPC path must have over the current
		 SPVPC path before a reroute will be performed. This
		 is analogous to the pnniSpvcRerouteThreshold variable
		 for SPVCCs."
	DEFVAL   { 75 }
	::= { pnniSpvpcParamGroup 5 }

pnniSpvpcLowestPriority  OBJECT-TYPE
	SYNTAX  Integer32
	MAX-ACCESS  read-write
	STATUS  current
	DESCRIPTION
		"The value of lowest priority for SPVPCs"
	DEFVAL  { 10 }
	::= { pnniSpvpcParamGroup 6 }

pnniSpvpcTrapMode  OBJECT-TYPE
	SYNTAX  INTEGER {
			reroute(1),
			failure(2),
			all(3),
			none(4)
		}
	MAX-ACCESS  read-write
	STATUS  current
	DESCRIPTION
		"This configuration item specifies whether the
		 switch should send the:
		 spvcRerouteInitiated
			OR
		 pnniSpvpcUp and pnniSpvpcFail
			OR
		 pnniSpvpcDown, pnniSpvpcFail, and pnniSpvpcUp
		 traps."
	DEFVAL { reroute }
	::= { pnniSpvpcParamGroup 7 }

pnniSpvpcBackoffInterval  OBJECT-TYPE
	SYNTAX	TimeInterval
	MAX-ACCESS	read-write
	STATUS	current
	DESCRIPTION
		"The time interval to backoff a DTL that failed
		call setup.  The DTL will not be used again until
		this interval has elapsed.  The interval will not
		be applicable if backoff is disabled on the SPVPC."
	DEFVAL	{ 60000 }
	::= { pnniSpvpcParamGroup 8 }

------------------------------------------------------------------------
-- The source side table for configuring originating SPVPCs
------------------------------------------------------------------------

pnniSpvpcSrcTable OBJECT-TYPE
	SYNTAX  SEQUENCE OF PnniSpvpcSrcEntry
	MAX-ACCESS  not-accessible
	STATUS  current
	DESCRIPTION
		"This table contains information about SPVPCs (Smart
		 Permanent Virtual Path Connections) that have their
		 source at this switch. This table serves the same
		 function that the pnniSpvcSrcTable serves for SPVCCs."
	::= { q2931Group 9 }

pnniSpvpcSrcEntry OBJECT-TYPE
	SYNTAX  PnniSpvpcSrcEntry
	MAX-ACCESS  not-accessible
	STATUS  current
	DESCRIPTION
		"A table entry containing source SPVPC (Smart
		 Permanent Virtual Path Connection) information."
	INDEX   { pnniSpvpcSrcIndex }
	::= { pnniSpvpcSrcTable 1 }

PnniSpvpcSrcEntry ::= SEQUENCE {
		pnniSpvpcSrcIndex                INTEGER,
		pnniSpvpcSrcCallingPort          INTEGER,
		pnniSpvpcSrcCallingVPI           Integer32,
		pnniSpvpcSrcCalledAtmAddr        NsapAddr,
		pnniSpvpcSrcCalledPort           Integer32,
		pnniSpvpcSrcCalledVPVCSel        INTEGER,
		pnniSpvpcSrcCalledVPI            INTEGER,
		pnniSpvpcSrcCalledAssignedVPI    INTEGER,
		pnniSpvpcSrcFwdUpcKey            INTEGER,
		pnniSpvpcSrcBckUpcKey            INTEGER,
		pnniSpvpcSrcSusceptClip          INTEGER,
		pnniSpvpcSrcFwdQoSClass          INTEGER,
		pnniSpvpcSrcBckQoSClass          INTEGER,
		pnniSpvpcSrcLastFailCause        DisplayString,
		pnniSpvpcSrcRetryCount           Integer32,
		pnniSpvpcSrcLastChangeTime       TimeTicks,
		pnniSpvpcSrcStatus               INTEGER,
		pnniSpvpcSrcName                 OCTET STRING,
		pnniSpvpcSrcRowStatus            RowStatus,
		pnniSpvpcSrcRouteCost            Integer32,
		pnniSpvpcSrcRerouteStatus        INTEGER,
		pnniSpvpcSrcCallingDomain        Integer32,
		pnniSpvpcSrcQosIndex             Integer32,
		pnniSpvpcSrcPriority             Integer32,
		pnniSpvpcSrcLastLocation	 DisplayString,
		pnniSpvpcSrcOldRouteCost         Integer32,
		pnniSpvpcSrcDownReason           INTEGER,
		pnniSpvpcSrcBackoffStatus        INTEGER,
		pnniSpvpcSrcActiveDtlNodeIndex   Integer32,
		pnniSpvpcSrcActiveDtlIndex       Integer32,
		pnniSpvpcSrcDtlTag               Integer32,
		pnniSpvpcSrcAutoDtlStatus        INTEGER,
		pnniSpvpcSrcRGroupIndex          INTEGER,
		pnniSpvpcSrcSecondaryVPI         Integer32
	}

pnniSpvpcSrcIndex OBJECT-TYPE
	SYNTAX  INTEGER (1..65535)
	MAX-ACCESS  not-accessible
	STATUS  current
	DESCRIPTION
		"The value of this object uniquely identify the
		 SPVPCs (Smart Permanent Virtual Path Connections)
		 that have this switch as their source."
	::= { pnniSpvpcSrcEntry 1 }

pnniSpvpcSrcCallingPort OBJECT-TYPE
	SYNTAX  INTEGER (0..1025)
	MAX-ACCESS  read-create
	STATUS  current
	DESCRIPTION
		"The value of this object identifies the input port
		 of this SPVPC (Smart Permanent Virtual Path Connection),
		 and is the same as the chanrInputPort, chanPort, pathPort,
		 and portNumber. The maximum value of this variable
		 depends on the type of the switch. The upper bound given is
		 the highest possible as of now. In some switches the range
		 will be much narrower."
	::= { pnniSpvpcSrcEntry 2 }

pnniSpvpcSrcCallingVPI OBJECT-TYPE
	SYNTAX  Integer32
	MAX-ACCESS  read-create
	STATUS  current
	DESCRIPTION
		"The VPI to be used at the originating switch for the
		 permanent portion of this SPVPC (Smart Permanent Virtual
		 Path Connection)."
	::= { pnniSpvpcSrcEntry 3 }

pnniSpvpcSrcCalledAtmAddr OBJECT-TYPE
	SYNTAX  NsapAddr
	MAX-ACCESS  read-create
	STATUS  current
	DESCRIPTION
		"The ATM address of the distant end NI (destination
		 switch) for this SPVPC (Smart Permanent Virtual Path
		 Connection). Distant end NI is the network interface at
		 the destination switch at which the switched portion of
		 this SPVPC terminates."
	::= { pnniSpvpcSrcEntry 4 }

pnniSpvpcSrcCalledPort OBJECT-TYPE
	SYNTAX  Integer32
	MAX-ACCESS  read-only
	STATUS  current
	DESCRIPTION
		"The value of this object identifies the port where
		 the permanent portion of this SPVPC (Smart Permanent
		 Virtual Path Connection) resides at the destination
		 switch. It has a value of -1 if this port at the
		 destination switch cannot be determined."
	::= { pnniSpvpcSrcEntry 5 }

pnniSpvpcSrcCalledVPVCSel OBJECT-TYPE
	SYNTAX  INTEGER {
			    noPref(1),
			    require(2)
			}
	MAX-ACCESS  read-create
	STATUS  current
	DESCRIPTION
		"The originating switch for a SPVPC can specify the VPI to
		 be used for the permanent portion of this SPVPC at the
		 destination switch. The value of this object indicates
		 whether the SPVPC was configured with a specific value for
		 this VPI or not. require(2) indicates that the user
		 configured a specific value for this VPI and noPref(1)
		 indicates that the user did not specify any."
	::= { pnniSpvpcSrcEntry 6 }

pnniSpvpcSrcCalledVPI OBJECT-TYPE
	SYNTAX  INTEGER (0..4096)
	MAX-ACCESS  read-create
	STATUS  current
	DESCRIPTION
		"The VPI to be used at the destination switch for the
		 permanent portion of this SPVPC (Smart Permanent Virtual
		 Path Connection). The range given above is the maximum
		 possible. The upperbound varies with the type of netmod."
	::= { pnniSpvpcSrcEntry 7 }

pnniSpvpcSrcCalledAssignedVPI OBJECT-TYPE
	SYNTAX  INTEGER (0..4096)
	MAX-ACCESS  read-only
	STATUS  current
	DESCRIPTION
		"The VPI that is assigned at the destination switch for
		 the permanent portion of this SPVPC (Smart Permanent
		 Virtual Path Connection).  This value is only meaningful
		 if the SPVPC status is up."
	::= { pnniSpvpcSrcEntry 8 }

pnniSpvpcSrcFwdUpcKey OBJECT-TYPE
	SYNTAX  INTEGER (0..32767)
	MAX-ACCESS  read-create
	STATUS  current
	DESCRIPTION
		"The forward UPC traffic contract key for this SPVPC.
		 This traffic contract will be used for the data traffic
		 flow from the originating switch to the destination switch.
		 This key must be defined in the upcContractTable."
	::= { pnniSpvpcSrcEntry 9 }

pnniSpvpcSrcBckUpcKey OBJECT-TYPE
	SYNTAX  INTEGER (0..32767)
	MAX-ACCESS  read-create
	STATUS  current
	DESCRIPTION
		"The backward UPC traffic contract key for this SPVPC.
		 This traffic contract will be used for the data flow
		 in the direction from the destination switch to the
		 originating switch. This key must be defined in the
		 upcContractTable."
	::= { pnniSpvpcSrcEntry 10 }

pnniSpvpcSrcSusceptClip OBJECT-TYPE
	SYNTAX  INTEGER {
			    no(1),
			    yes(2)
			}
	MAX-ACCESS  read-create
	STATUS  current
	DESCRIPTION
		"The requested broadband bearer susceptibility to
		 clipping for this SPVPC. This object will be used to fill
		 the broadband bearer capability information element in the
		 call setup message for this SPVPC."
	::= { pnniSpvpcSrcEntry 11 }

pnniSpvpcSrcFwdQoSClass OBJECT-TYPE
	SYNTAX  INTEGER {
			    class0(1),
			    class1(2),
			    class2(3),
			    class3(4),
			    class4(5)
			}
	MAX-ACCESS  read-create
	STATUS  current
	DESCRIPTION
		"The requested quality of service class for this SPVPC in
		 the forward (source to destination) direction. This
		 determines the QoS objectives for the data path from the
		 originating switch to the destination switch."
	::= { pnniSpvpcSrcEntry 12 }

pnniSpvpcSrcBckQoSClass OBJECT-TYPE
	SYNTAX  INTEGER {
			    class0(1),
			    class1(2),
			    class2(3),
			    class3(4),
			    class4(5)
			}
	MAX-ACCESS  read-create
	STATUS  current
	DESCRIPTION
		"The requested quality of service class for this SPVPC in
		 the backward (destination to source) direction. This object
		 determines the QoS objectives for the data flow in the
		 reverse direction (from the destination switch to the
		 originating switch)."
	::= { pnniSpvpcSrcEntry 13 }

pnniSpvpcSrcLastFailCause OBJECT-TYPE
	SYNTAX  DisplayString (SIZE (0..80))
	MAX-ACCESS  read-only
	STATUS  current
	DESCRIPTION
		"The last call setup failure cause code for this
		 SPVPC."
	::= { pnniSpvpcSrcEntry 14 }

pnniSpvpcSrcRetryCount OBJECT-TYPE
	SYNTAX  Integer32
	MAX-ACCESS  read-only
	STATUS  current
	DESCRIPTION
		"The number of times the call setup has been
		 attempted since the SPVPC creation or the last
		 successful call setup for this SPVPC."
	::= { pnniSpvpcSrcEntry 15 }

pnniSpvpcSrcLastChangeTime OBJECT-TYPE
	SYNTAX  TimeTicks
	MAX-ACCESS  read-only
	STATUS  current
	DESCRIPTION
		"The time since this SPVPC (Smart Permanent Virtual
		 Path Connection) has been up/down in hundredths of a
		 second."
	::= { pnniSpvpcSrcEntry 16 }

pnniSpvpcSrcStatus OBJECT-TYPE
	SYNTAX  INTEGER {
			 up(1),
			 down(2)
			}
	MAX-ACCESS  read-only
	STATUS  current
	DESCRIPTION
		"The operational status of this SPVPC (Smart Permanent
		 Virtual Path Connection). The value of up(1) indicates
		 that this SPVPC is operational and down(2) indicates
		 that the SPVPC is not-operational."
	::= { pnniSpvpcSrcEntry 17 }

pnniSpvpcSrcName OBJECT-TYPE
	 SYNTAX  OCTET STRING (SIZE(0..32))
	 MAX-ACCESS  read-create
	 STATUS  current
	 DESCRIPTION
		 "The value of this object identifies the
		  name that has been assigned for this SPVPC."
	 ::= { pnniSpvpcSrcEntry 18 }

pnniSpvpcSrcRowStatus OBJECT-TYPE
	SYNTAX  RowStatus
	MAX-ACCESS  read-create
	STATUS  current
	DESCRIPTION
		"The status of this SPVPC (Smart Permanent Virtual
		 Path Connection) entry."
	::= { pnniSpvpcSrcEntry 19 }

pnniSpvpcSrcRouteCost OBJECT-TYPE
	SYNTAX  Integer32
	MAX-ACCESS  read-only
	STATUS  current
	DESCRIPTION
		"The cumulative route cost for the current route
		 of this SPVPC (Smart Permanent Virtual Path
		 Connection)."
	::= { pnniSpvpcSrcEntry 20 }

pnniSpvpcSrcRerouteStatus OBJECT-TYPE
	SYNTAX  INTEGER {
			 enabled(1),
			 disabled(2)
			}
	MAX-ACCESS  read-create
	STATUS  current
	DESCRIPTION
		"The status of the reroute function for this SPVPC
		 (Smart Permanent Virtual Path Connection). If set to
		 disabled(2), no rerouting will be attempted for this
		 SPVPC."
	DEFVAL    { disabled }
	::= { pnniSpvpcSrcEntry 21 }

pnniSpvpcSrcCallingDomain OBJECT-TYPE
	SYNTAX  Integer32
	MAX-ACCESS  read-create
	STATUS  current
	DESCRIPTION
		"The Domain ID identifying the routing domain to be used
		 at the Originating Switch for this SPVPC."
	::= { pnniSpvpcSrcEntry 22 }

pnniSpvpcSrcQosIndex OBJECT-TYPE
	SYNTAX  Integer32
	MAX-ACCESS  read-create
	STATUS  current
	DESCRIPTION
		"The index for the QOS Class Expansion Table to be used for
		 QoS class values into QoS parameter objectives for this
		 SPVPC. The corresponding expansion table should be defined
		 in the qosClassExpansionTable."
	::= { pnniSpvpcSrcEntry 23 }

pnniSpvpcSrcPriority OBJECT-TYPE
	SYNTAX  Integer32
	MAX-ACCESS  read-create
	STATUS  current
	DESCRIPTION
		"Priority of this SPVPC for connection"
	::= { pnniSpvpcSrcEntry 24 }

pnniSpvpcSrcLastLocation OBJECT-TYPE
	SYNTAX  DisplayString
	MAX-ACCESS  read-only
	STATUS  current
	DESCRIPTION
		"The last call setup failure location code for this
		SPVPC. This indicates the switch that initiated the
		clearing for the call. This is formatted as a text
		string with the fields:
		   FMT: Indicates diagnostic format
		   RMT: Indicates whether a remote switch is the source of the
			failure or this switch inserted the location diag
		   LINK:Link id that clear pertains to
		   VPI: VPI that clear pertains to
		   The remaining fields are format specific"
	::= { pnniSpvpcSrcEntry 25 }

pnniSpvpcSrcOldRouteCost  OBJECT-TYPE
	SYNTAX  Integer32
	MAX-ACCESS  read-only
	STATUS  current
	DESCRIPTION
		"This OID is specified only to be included the the
		pnniSpvcUp trap. It specifies the
		path cost of the call the previous time this call
		was up. If the call has not been up, this will
		report a value of -1."
	::= { pnniSpvpcSrcEntry 26 }

pnniSpvpcSrcDownReason  OBJECT-TYPE
	SYNTAX  INTEGER {
			reroute(1),
			failure(2),
			deletion(3)
		}
	MAX-ACCESS  read-only
	STATUS  current
	DESCRIPTION
		"This OID is specified only to be included the the
		pnniSpvccDown and pnniSpvccFail traps.
		This specifies whether the SPVC call was cleared due to
		a better route being found, a network failure,
		or SPVPC deletion."
	::= { pnniSpvpcSrcEntry 27 }

pnniSpvpcSrcBackoffStatus OBJECT-TYPE
	SYNTAX	INTEGER {
			enabled(1),
			disabled(2)
		}
	MAX-ACCESS	read-create
	STATUS	current
	DESCRIPTION
		"The status of the backoff function for this SPVC
		(Smart Permanent Virtual Path Circuit).  If set to disabled(2),
		directed dtls configured for this SPVPC will be continually
		retried on failure."
	DEFVAL	{ enabled }
	::= { pnniSpvpcSrcEntry 28 }

pnniSpvpcSrcActiveDtlIndex OBJECT-TYPE
	SYNTAX	Integer32
	MAX-ACCESS  read-only
	STATUS  current
	DESCRIPTION
		"The Active Designated Transit List (DTL) index for
		this SPVPC (Smart Permanent Virtual Path Circuit).
		This value along with pnniSpvcSrcActiveDtlNodeIndex
		uniquely identifies the DTL that is currently
		used by the SVC portion of the SPVPC."
	::= { pnniSpvpcSrcEntry 29 }

pnniSpvpcSrcActiveDtlNodeIndex OBJECT-TYPE
	SYNTAX	Integer32
	MAX-ACCESS  read-only
	STATUS  current
	DESCRIPTION
		"The Node index of the Active Designated Transit List
		for this SPVPC (Smart Permanent Virtual Path Circuit).
		The active DTL indexed by the node index and DTL index
		identifies the DTL that is currently used by the SVC
		portion of the SPVPC. The value of this object is 65535
		for FTPNNI nodes."
	::= { pnniSpvpcSrcEntry 30 }

pnniSpvpcSrcDtlTag OBJECT-TYPE
	SYNTAX  Integer32
	MAX-ACCESS  read-create
	STATUS  current
	DESCRIPTION
		"This value specifies an index into a table of DTLs,
		the DTL entries in this table will be used to setup
		the SPVPC."
	::= { pnniSpvpcSrcEntry 31 }

pnniSpvpcSrcAutoDtlStatus OBJECT-TYPE
	SYNTAX	INTEGER {
			enabled(1),
			disabled(2)
		}
	MAX-ACCESS	read-create
	STATUS  current
	DESCRIPTION
		"The status of the dynamic path selection function for this
		SPVPC (Smart Permanent Virtual Path Circuit). If set to disabled(2),
		auto path selection will not be used."
	DEFVAL	{ enabled }
	::= { pnniSpvpcSrcEntry 32 }

pnniSpvpcSrcRGroupIndex OBJECT-TYPE
	SYNTAX        INTEGER (1..65535)
	MAX-ACCESS        read-create
	STATUS  current
	DESCRIPTION
		"This specifies the entry in the Spvxc Redundancy Group
		 table for information regarding the secondary port to
		 be used as the redundant port"
	::= { pnniSpvpcSrcEntry 33 }

pnniSpvpcSrcSecondaryVPI OBJECT-TYPE
	SYNTAX  Integer32
	MAX-ACCESS  read-create
	STATUS  current
	DESCRIPTION
		"The Secondary VPI to be used at the originating switch for the
		 redundant permanent portion of this SPVPC. "
	::= { pnniSpvpcSrcEntry 34 }


------------------------------------------------------------------------
-- This is the group common to source and destination switches that
-- contains some statistics and gauges
------------------------------------------------------------------------

pnniSpvpcStatsGroup  OBJECT IDENTIFIER ::=  { q2931Group 10 }

------------------------------------------------------------------------
-- This variable is for the number of source SPVPCs that originate on
-- a switch.
------------------------------------------------------------------------

pnniSpvpcSrcNumberOfSPVPCs OBJECT-TYPE
	SYNTAX  Gauge32
	MAX-ACCESS  read-only
	STATUS  current
	DESCRIPTION
		"The number of SPVPCs (Smart Permanent Virtual Path
		 Connections) that have their source at this switch. This
		 object is analogous to the pnniSpvcSrcNumberOfSPVCs
		 object defined for SPVCCs."
	::= { pnniSpvpcStatsGroup 1 }

------------------------------------------------------------------------
-- The following variable gives the number of terminating SPVPCs that
-- terminate on a given switch
------------------------------------------------------------------------

pnniSpvpcDestNumberOfSPVPCs OBJECT-TYPE
	SYNTAX  Gauge32
	MAX-ACCESS  read-only
	STATUS  current
	DESCRIPTION
		"The number of connected SPVPCs (Smart Permanent Virtual
		 Path Connections) that have their destination at this
		 switch. This object is analogous to the
		 pnniSpvcDestNumberOfSPVCs object for SPVCCs."
	::= { pnniSpvpcStatsGroup 2 }

------------------------------------------------------------------------
-- This is the table for the SPVPC that terminate at a given
-- switch. This table is a read-only table and it allows the user to
-- gather information about the terminating SPVPCs.
------------------------------------------------------------------------

pnniSpvpcDestTable OBJECT-TYPE
	SYNTAX  SEQUENCE OF PnniSpvpcDestEntry
	MAX-ACCESS  not-accessible
	STATUS  current
	DESCRIPTION
		"This table contains information about SPVPCs (Smart
		 Permanent Virtual Path Connections) that have their
		 destination at this switch. This table provides the same
		 functions that the pnniSpvcDestTable provides for SPVCCs."
	::= { q2931Group 11 }

pnniSpvpcDestEntry OBJECT-TYPE
	SYNTAX  PnniSpvpcDestEntry
	MAX-ACCESS  not-accessible
	STATUS  current
	DESCRIPTION
		"A table entry containing destination SPVPC (Smart
		 Permanent Virtual Path Connection) information."
	INDEX   { pnniSpvpcDestIndex }
	::= { pnniSpvpcDestTable 1 }

PnniSpvpcDestEntry ::= SEQUENCE {
		pnniSpvpcDestIndex               INTEGER,
		pnniSpvpcDestCallingAtmAddr      NsapAddr,
		pnniSpvpcDestCallingPort         INTEGER,
		pnniSpvpcDestCallingVPI          INTEGER,
		pnniSpvpcDestCalledAtmAddr       NsapAddr,
		pnniSpvpcDestCalledPort          INTEGER,
		pnniSpvpcDestAssignedVPI         INTEGER,
		pnniSpvpcDestSusceptClip         INTEGER,
		pnniSpvpcDestUpTime              TimeTicks,
		pnniSpvpcDestFwdQoSClass         INTEGER,
		pnniSpvpcDestBckQoSClass         INTEGER,
		pnniSpvpcDestStatus              INTEGER,
		pnniSpvpcDestRGroupIndex         INTEGER
	      }

pnniSpvpcDestIndex OBJECT-TYPE
	SYNTAX  INTEGER (1..65535)
	MAX-ACCESS  read-only
	STATUS  current
	DESCRIPTION
	       "The value of this object uniquely identifies the
		SPVPCs (Smart Permanent Virtual Path Connections) that
		have this switch as their destination."
	::= { pnniSpvpcDestEntry 1 }

pnniSpvpcDestCallingAtmAddr OBJECT-TYPE
	SYNTAX  NsapAddr
	MAX-ACCESS  read-only
	STATUS  current
	DESCRIPTION
		"The ATM address of the calling end NI at the originating
		 switch for this SPVPC (Smart Permanent Virtual Path
		 Connection). Calling end NI is the network interface at
		 the originating switch from which the switched portion of
		 SPVPC originates."
	::= { pnniSpvpcDestEntry 2 }

pnniSpvpcDestCallingPort OBJECT-TYPE
	SYNTAX  INTEGER (0..1025)
	MAX-ACCESS  read-only
	STATUS  current
	DESCRIPTION
		"The value of this object identifies the port
		 of this terminating SPVPC (Smart Permanent Virtual Path
		 Connection) at the source switch in which the permanent
		 portion of the SPVPC resides. It has a value of -1 if the
		 port at the source switch cannot be determined."
	::= { pnniSpvpcDestEntry 3 }

pnniSpvpcDestCallingVPI OBJECT-TYPE
	SYNTAX  INTEGER (0..4096)
	MAX-ACCESS  read-only
	STATUS  current
	DESCRIPTION
		"The VPI to be used at the originating switch for the
		 permanent portion of this SPVPC."
       ::= { pnniSpvpcDestEntry 4 }

pnniSpvpcDestCalledAtmAddr OBJECT-TYPE
	SYNTAX  NsapAddr
	MAX-ACCESS  read-only
	STATUS  current
	DESCRIPTION
		"The ATM address of the local end NI (at this
		 destination switch) for this SPVPC. Local end NI is
		 network interface at this destination switch where the
		 switched portion of this SPVPC terminates."
	::= { pnniSpvpcDestEntry 5 }

pnniSpvpcDestCalledPort OBJECT-TYPE
	SYNTAX  INTEGER (0..1025)
	MAX-ACCESS  read-only
	STATUS  current
	DESCRIPTION
		"The value of this object identifies the port
		 of this terminating SPVPC (Smart Permanent Virtual Path
		 Connection) at this destination switch where the permanent
		 portion of this SPVPC resides. It has a value of -1 if the
		 port at the destination switch cannot be determined."
	::= { pnniSpvpcDestEntry 6 }

pnniSpvpcDestAssignedVPI OBJECT-TYPE
	SYNTAX  INTEGER (0..4096)
	MAX-ACCESS  read-only
	STATUS  current
	DESCRIPTION
		"The VPI assigned at this destination switch for the
		 permanent portion of this SPVPC.  This value is only
		 meaningful if the SPVPC status is up."
	::= { pnniSpvpcDestEntry 7 }

pnniSpvpcDestSusceptClip OBJECT-TYPE
	SYNTAX  INTEGER {
			    no(1),
			    yes(2)
			}
	MAX-ACCESS  read-only
	STATUS  current
	DESCRIPTION
		"The value of this object identifies if the SPVPC was
		 setup with the broadband bearer susceptibility to
		 clipping set or not."
	::= { pnniSpvpcDestEntry 8 }

pnniSpvpcDestUpTime OBJECT-TYPE
	SYNTAX  TimeTicks
	MAX-ACCESS  read-only
	STATUS  current
	DESCRIPTION
		"The time since this SPVPC (Smart Permanent Virtual
		 Path Connection) was created in hundredths of a second."
	::= { pnniSpvpcDestEntry 9 }

pnniSpvpcDestFwdQoSClass OBJECT-TYPE
	SYNTAX  INTEGER {
			    class0(1),
			    class1(2),
			    class2(3),
			    class3(4),
			    class4(5)
			}
	MAX-ACCESS  read-only
	STATUS  current
	DESCRIPTION
		"The requested quality of service class for this SPVPC
		 in the direction from the source switch to the
		 destination switch. This value determines the QoS
		 parameter objectives for this SPVPC in that direction."
	::= { pnniSpvpcDestEntry 10 }

pnniSpvpcDestBckQoSClass OBJECT-TYPE
	SYNTAX  INTEGER {
			    class0(1),
			    class1(2),
			    class2(3),
			    class3(4),
			    class4(5)
			}
	MAX-ACCESS  read-only
	STATUS  current
	DESCRIPTION
		"The requested quality of service class for this SPVPC in
		 the direction from the destination switch to the source
		 switch. This value determines the QoS objectives for the
		 data flow in that direction."
	::= { pnniSpvpcDestEntry 11 }

pnniSpvpcDestStatus OBJECT-TYPE
	SYNTAX  INTEGER {
			 up(1),
			 down(2)
			}
	MAX-ACCESS  read-only
	STATUS  current
	DESCRIPTION
		"The operational status of this SPVPC (Smart Permanent
		 Virtual Path Connection). up(1) indicates that this
		 SPVPC is operational while down(2) indicates that it is
		 not."
	::= { pnniSpvpcDestEntry 12 }

pnniSpvpcDestRGroupIndex OBJECT-TYPE
	SYNTAX        INTEGER (1..65535)
	MAX-ACCESS        read-only
	STATUS  current
	DESCRIPTION
		"This specifies the entry in the Spvxc Redundancy Group
		 table for information regarding the secondary port to
		 be used as the redundant port. This will used at the
		 terminating PVC end."
	::= { pnniSpvpcDestEntry 13 }


-----------------------------------------------------------------------
--*********************************************************************
--
--         PNNI PMP SPVCC GROUP
--
--*********************************************************************
-----------------------------------------------------------------------
--  The pnniPmpSpvcc implements all the relevant MIBs for the PMP SPVCC
--  feature. Both the RootTable and PartyTable are under this group.
-----------------------------------------------------------------------

pnniPmpSpvccGroup       OBJECT IDENTIFIER ::= { q2931Group 12 }

------------------------------------------------------------------------
--   PNNI PMP SPVCC MIB Definitions.
------------------------------------------------------------------------
--   The parameters are divided into two  Tables(both at the source and
--   destination):
--
--   "RootTable" maintains information about the root of the PMP SPVC and
--   other connection parameters that are common to all the parties(such as
--   QoS index, UPC, Timing Requirements, Traffic Type etc.).
--
--   "PartyTable" keeps track of party related information such as, Called
--   NSAP, VPI, VCI, status etc.
--
--   Priority information is maintained on a "per PMP SPVCC" basis
--   implying that all the parties of a given PMP SPVCC have the same
--   priority.
--
--   Rerouting is not "automatic" for PMP SPVCCs. Instead, it can be
--   triggered administratively by setting pnniPmpSpvccSrcPartyRerouteStatus
--   of pnniPmpSpvccSrcPartyTable to an appropriate value.
------------------------------------------------------------------------
--
-- PNNI PMP SPVCC source-side definitions
--
pnniPmpSpvccSrcNextRootIndex OBJECT-TYPE
	SYNTAX	TestAndIncr
	MAX-ACCESS	read-write
	STATUS	current
	DESCRIPTION
		"The index of the next free root index in the
		 pnniPmpSpvcSrcRootTable. Client is responsible for
		 implementing a policy when a set on this variable fails.
		 E.g. Keep testing this variable until a free index is
		 found or choose a random number or a combination of the two."
	::= {pnniPmpSpvccGroup 1}

pnniPmpSpvccSrcNumberOfSpvccs OBJECT-TYPE
	SYNTAX  Integer32
	MAX-ACCESS  read-only
	STATUS  current
	DESCRIPTION
		"The number of PMP SPVCCs (Smart Permanent Virtual Circuits)
		that have their source at this switch."
	::= { pnniPmpSpvccGroup 2 }

pnniPmpSpvccSrcRootTable OBJECT-TYPE
	SYNTAX  SEQUENCE OF PnniPmpSpvccSrcRootEntry
	MAX-ACCESS  not-accessible
	STATUS  current
	DESCRIPTION
		"This table contains information about the root side of PMP
		 SPVCCs (Smart Permanent Virtual Circuits) that have their
		 source at this switch. It also contains the connection
		 parameters that are common to all the parties"
	::= { pnniPmpSpvccGroup 3 }

pnniPmpSpvccSrcRootEntry OBJECT-TYPE
	SYNTAX  PnniPmpSpvccSrcRootEntry
	MAX-ACCESS  not-accessible
	STATUS  current
	DESCRIPTION
		"A table entry containing source PMP SPVCC (Smart
		 Permanent Virtual Circuits) information."
	INDEX   { pnniPmpSpvccSrcRootIndex }
	::= { pnniPmpSpvccSrcRootTable 1 }

PnniPmpSpvccSrcRootEntry ::= SEQUENCE {
		pnniPmpSpvccSrcRootIndex            Integer32,
		pnniPmpSpvccSrcRootPort             Integer32,
		pnniPmpSpvccSrcRootVPI              Integer32,
		pnniPmpSpvccSrcRootVCI              Integer32,
		pnniPmpSpvccSrcRootFwdUpcKey        Integer32,
		pnniPmpSpvccSrcRootBearerClass      INTEGER,
		pnniPmpSpvccSrcRootSusceptClip      INTEGER,
		pnniPmpSpvccSrcRootFwdQoSClass      INTEGER,
		pnniPmpSpvccSrcRootStatus           INTEGER,
		pnniPmpSpvccSrcRootName             OCTET STRING,
		pnniPmpSpvccSrcRootPriority         Integer32,
		pnniPmpSpvccSrcRootNumberOfParties  Integer32,
		pnniPmpSpvccSrcRootNextPartyIndex   TestAndIncr,
		pnniPmpSpvccSrcRootCallingDomain    Integer32,
		pnniPmpSpvccSrcRootRowStatus        RowStatus,
		pnniPmpSpvccSrcRootRGroupIndex      INTEGER,
		pnniPmpSpvccSrcRootSecondaryVPI     Integer32,
		pnniPmpSpvccSrcRootSecondaryVCI     Integer32
	}

pnniPmpSpvccSrcRootIndex OBJECT-TYPE
	SYNTAX  Integer32
	MAX-ACCESS  not-accessible
	STATUS  current
	DESCRIPTION
		"The value of this object uniquely identify the
		 PMP SPVCCs (Smart Permanent Virtual Circuits) that
		 have this switch as their source(root)."
	::= { pnniPmpSpvccSrcRootEntry 1 }

pnniPmpSpvccSrcRootPort OBJECT-TYPE
	SYNTAX  Integer32
	MAX-ACCESS  read-create
	STATUS  current
	DESCRIPTION
		"The value of this object identifies the input port
		 of this PMP SPVCC (Smart Permanent Virtual Circuits), and
		 is the same as the chanrInputPort, chanPort, pathPort,
		 and portNumber."
	::= { pnniPmpSpvccSrcRootEntry 2 }

pnniPmpSpvccSrcRootVPI OBJECT-TYPE
	SYNTAX  Integer32
	MAX-ACCESS  read-create
	STATUS  current
	DESCRIPTION
		"The VPI to be used at the Calling(root) NI
		 for this PMP SPVCC."
	::= { pnniPmpSpvccSrcRootEntry 3 }

pnniPmpSpvccSrcRootVCI OBJECT-TYPE
	SYNTAX  Integer32
	MAX-ACCESS  read-create
	STATUS  current
	DESCRIPTION
		"The VCI to be used at the Calling(root) NI
		 for this PMP SPVCC."
	::= { pnniPmpSpvccSrcRootEntry 4 }

pnniPmpSpvccSrcRootFwdUpcKey OBJECT-TYPE
	SYNTAX  Integer32
	MAX-ACCESS  read-create
	STATUS  current
	DESCRIPTION
		"The forward UPC traffic contract key for this PMP SPVCC.
		 This key must be defined in the upcContractTable. Backward
		 UPC traffic contract does not apply to PMP SPVCCs."
	::= { pnniPmpSpvccSrcRootEntry 5 }

pnniPmpSpvccSrcRootBearerClass OBJECT-TYPE
	SYNTAX  INTEGER {
			    classA(1),
			    classC(2),
			    classX(3)
			}
	MAX-ACCESS  read-create
	STATUS  current
	DESCRIPTION
		"The requested broadband bearer class for this PMP SPVCC."
	::= { pnniPmpSpvccSrcRootEntry 6 }

pnniPmpSpvccSrcRootSusceptClip OBJECT-TYPE
	SYNTAX  INTEGER {
			    no(1),
			    yes(2)
			}
	MAX-ACCESS  read-create
	STATUS  current
	DESCRIPTION
		"The requested broadband bearer susceptability to for
		 this PMP SPVCC."
	::= { pnniPmpSpvccSrcRootEntry 7 }


pnniPmpSpvccSrcRootFwdQoSClass OBJECT-TYPE
	SYNTAX  INTEGER {
			    class0(1),
			    class1(2),
			    class2(3),
			    class3(4),
			    class4(5)
			}
	MAX-ACCESS  read-create
	STATUS  current
	DESCRIPTION
		"The requested quality of service for this PMP SPVCC in
		 the forward (calling to called) direction. Backward
		 direction does not apply to PMP SPVCCs."
	::= { pnniPmpSpvccSrcRootEntry 8 }

pnniPmpSpvccSrcRootStatus OBJECT-TYPE
	SYNTAX  INTEGER {
			up(1),
			down(2),
			wait(3)
		}
	MAX-ACCESS  read-only
	STATUS  current
	DESCRIPTION
		"The operational status of this PMP SPVCC (Smart Permanent
		 Virtual Circuit)."
	::= { pnniPmpSpvccSrcRootEntry 9 }

pnniPmpSpvccSrcRootName OBJECT-TYPE
	 SYNTAX  OCTET STRING (SIZE(0..32))
	 MAX-ACCESS  read-create
	 STATUS  current
	 DESCRIPTION
		 "The value of this object identifies the
		  name that has been assigned for this PMP SPVCC."
	 ::= { pnniPmpSpvccSrcRootEntry 10 }

pnniPmpSpvccSrcRootPriority OBJECT-TYPE
	SYNTAX  Integer32
	MAX-ACCESS  read-create
	STATUS  current
	DESCRIPTION
		"Priority of this PMP SPVCC for connection. This priority is
		 shared with any point-to-point SPVCCs configured on this
		 switch."
	::= { pnniPmpSpvccSrcRootEntry 11 }

pnniPmpSpvccSrcRootNumberOfParties OBJECT-TYPE
	SYNTAX  Integer32
	MAX-ACCESS  read-only
	STATUS  current
	DESCRIPTION
		"Number of parties currently configured with this PMP SPVCC"
	::= { pnniPmpSpvccSrcRootEntry 12 }

pnniPmpSpvccSrcRootNextPartyIndex OBJECT-TYPE
	SYNTAX	TestAndIncr
	MAX-ACCESS	read-create
	STATUS	current
	DESCRIPTION
		"This indicates the next allocatable party index"
	::= { pnniPmpSpvccSrcRootEntry 13 }


pnniPmpSpvccSrcRootCallingDomain OBJECT-TYPE
	SYNTAX  Integer32
	MAX-ACCESS  read-create
	STATUS  current
	DESCRIPTION
		"The Domain ID to be used at the Calling NI for this PMP SPVCC."
	::= { pnniPmpSpvccSrcRootEntry 14 }

pnniPmpSpvccSrcRootRowStatus OBJECT-TYPE
	SYNTAX  RowStatus
	MAX-ACCESS  read-create
	STATUS  current
	DESCRIPTION
		"The status of this SPVCC (Smart Permanent Virtual Circuits) entry."
	::= { pnniPmpSpvccSrcRootEntry 15 }

pnniPmpSpvccSrcRootRGroupIndex OBJECT-TYPE
	SYNTAX        INTEGER (1..65535)
	MAX-ACCESS        read-create
	STATUS  current
	DESCRIPTION
		"This specifies the entry in the Spvxc Redundancy Group
		 table for information regarding the secondary port to
		 be used as the redundant port"
	::= { pnniPmpSpvccSrcRootEntry 16 }

pnniPmpSpvccSrcRootSecondaryVPI OBJECT-TYPE
	SYNTAX  Integer32
	MAX-ACCESS  read-create
	STATUS  current
	DESCRIPTION
		"The Secondary VPI to be used at the originating switch for
		 the redundant permanent portion of this SPVC. "
	::= { pnniPmpSpvccSrcRootEntry 17 }

pnniPmpSpvccSrcRootSecondaryVCI OBJECT-TYPE
	SYNTAX  Integer32
	MAX-ACCESS  read-create
	STATUS  current
	DESCRIPTION
		"The Secondary VCI to be used at the originating switch for
		 the redundant permanent portion of this SPVC."
	::= { pnniPmpSpvccSrcRootEntry 18 }


----------------------------------------------------------------------------
--  PMP SPVCC Source Side Party Table
--

pnniPmpSpvccSrcPartyTable OBJECT-TYPE
	SYNTAX  SEQUENCE OF PnniPmpSpvccSrcPartyEntry
	MAX-ACCESS  not-accessible
	STATUS  current
	DESCRIPTION
		"This table contains information about the parties of
		 PMP SPVCCs (Smart Permanent Virtual Circuits) that have
		 their source at this switch."
	::= { pnniPmpSpvccGroup 4 }

pnniPmpSpvccSrcPartyEntry OBJECT-TYPE
	SYNTAX  PnniPmpSpvccSrcPartyEntry
	MAX-ACCESS  not-accessible
	STATUS  current
	DESCRIPTION
		"A table entry containing information about parties in a PMP
		 SPVCC (Smart Permanent Virtual Circuits) at the source."
	INDEX   { pnniPmpSpvccSrcRootIndex, pnniPmpSpvccSrcPartyIndex }
	::= { pnniPmpSpvccSrcPartyTable 1 }

PnniPmpSpvccSrcPartyEntry ::= SEQUENCE {
		pnniPmpSpvccSrcPartyIndex           Integer32,
		pnniPmpSpvccSrcPartyAtmAddr         NsapAddr,
		pnniPmpSpvccSrcPartyVPVCSel         INTEGER,
		pnniPmpSpvccSrcPartyVPI             Integer32,
		pnniPmpSpvccSrcPartyVCI             Integer32,
		pnniPmpSpvccSrcPartyAssignedVPI     Integer32,
		pnniPmpSpvccSrcPartyAssignedVCI     Integer32,
		pnniPmpSpvccSrcPartyStatus          INTEGER,
		pnniPmpSpvccSrcPartyName            OCTET STRING,
		pnniPmpSpvccSrcPartyLastFailCause   DisplayString,
		pnniPmpSpvccSrcPartyRetryCount      Integer32,
		pnniPmpSpvccSrcPartyLastChangeTime  TimeTicks,
		pnniPmpSpvccSrcPartyFtDtlIndex      Integer32,
		pnniPmpSpvccSrcPartyRerouteStatus   INTEGER,
		pnniPmpSpvccSrcPartyQosIndex        Integer32,
		pnniPmpSpvccSrcPartyRowStatus       RowStatus,
		pnniPmpSpvccSrcPartyLastLocation    DisplayString,
		pnniPmpSpvccSrcPartyAutoDtlStatus   INTEGER,
		pnniPmpSpvccSrcPartyDownReason	    INTEGER,
		pnniPmpSpvccSrcPartyRouteCost	    Integer32
	}

pnniPmpSpvccSrcPartyIndex OBJECT-TYPE
	SYNTAX  Integer32
	MAX-ACCESS  not-accessible
	STATUS  current
	DESCRIPTION
		"The value of this object uniquely identifies a
		 party within a PMP SPVCC identified by pnniPmpSpvccSrcRootIndex.
		 Root's parameters and commmon connection parameters
		 for this party are availabe in pnniPmpSpvccSrcRootTable,
		 indexed by pnniPmpSpvccSrcRootIndex."
	::= { pnniPmpSpvccSrcPartyEntry 1 }

pnniPmpSpvccSrcPartyAtmAddr OBJECT-TYPE
	SYNTAX  NsapAddr
	MAX-ACCESS  read-create
	STATUS  current
	DESCRIPTION
		"The ATM address of the distant end NI (remote
		 switch) for this party."
	::= { pnniPmpSpvccSrcPartyEntry 2 }

pnniPmpSpvccSrcPartyVPVCSel OBJECT-TYPE
	SYNTAX  INTEGER {
			    noPref(1),
			    require(2)
			}
	MAX-ACCESS  read-create
	STATUS  current
	DESCRIPTION
		"The Called VPI/VCI value selection qualifier."
	::= { pnniPmpSpvccSrcPartyEntry 3 }

pnniPmpSpvccSrcPartyVPI OBJECT-TYPE
	SYNTAX  Integer32
	MAX-ACCESS  read-create
	STATUS  current
	DESCRIPTION
		"The VPI to be used at the Called NI for this party."
	::= { pnniPmpSpvccSrcPartyEntry 4 }

pnniPmpSpvccSrcPartyVCI OBJECT-TYPE
	SYNTAX  Integer32
	MAX-ACCESS  read-create
	STATUS  current
	DESCRIPTION
		"The VCI to be used at the Called NI for this party."
	::= { pnniPmpSpvccSrcPartyEntry 5 }

pnniPmpSpvccSrcPartyAssignedVPI OBJECT-TYPE
	SYNTAX  Integer32
	MAX-ACCESS  read-only
	STATUS  current
	DESCRIPTION
		"The VPI assigned at the Called NI for this
		 party. This value is only meaningful if the party status is up."
	::= { pnniPmpSpvccSrcPartyEntry 6 }

pnniPmpSpvccSrcPartyAssignedVCI OBJECT-TYPE
	SYNTAX  Integer32
	MAX-ACCESS  read-only
	STATUS  current
	DESCRIPTION
		"The VCI assigned at the Called NI for this
		 party. This value is only meaningful if the party status is up."
	::= { pnniPmpSpvccSrcPartyEntry 7 }

pnniPmpSpvccSrcPartyStatus OBJECT-TYPE
	SYNTAX  INTEGER {
		 up(1),
		 down(2),
		 connecting(3)
	}
	MAX-ACCESS  read-only
	STATUS  current
	DESCRIPTION
		"Operational status of this party in the PMP SPVCC."
	::= { pnniPmpSpvccSrcPartyEntry 8 }

pnniPmpSpvccSrcPartyName OBJECT-TYPE
	 SYNTAX  OCTET STRING (SIZE(0..32))
	 MAX-ACCESS  read-create
	 STATUS  current
	 DESCRIPTION
		 " The value of this object identifies the
		   name that has been assigned for this party."
	 ::= { pnniPmpSpvccSrcPartyEntry 9 }

pnniPmpSpvccSrcPartyLastFailCause OBJECT-TYPE
	SYNTAX  DisplayString
	MAX-ACCESS  read-only
	STATUS  current
	DESCRIPTION
		"The last setup(addparty) failure cause code for this party."
	::= { pnniPmpSpvccSrcPartyEntry 10 }

pnniPmpSpvccSrcPartyRetryCount OBJECT-TYPE
	SYNTAX  Integer32
	MAX-ACCESS  read-only
	STATUS  current
	DESCRIPTION
		"The number of times the party setup/addparty has been
		 attempted since the party creation or the last
		 successful setup/addparty."
	::= { pnniPmpSpvccSrcPartyEntry 11 }

pnniPmpSpvccSrcPartyLastChangeTime OBJECT-TYPE
	SYNTAX  TimeTicks
	MAX-ACCESS  read-only
	STATUS  current
	DESCRIPTION
		"The time since this party has been up/down in
		 hundredths of a second."
	::= { pnniPmpSpvccSrcPartyEntry 12 }

--
-- Should be made read-write when supported.
--
--pnniPmpSpvccSrcPartyTransitNetSel OBJECT-TYPE
--        SYNTAX  TransitNetwork
--        ACCESS  read-only
--        STATUS  mandatory
--        DESCRIPTION
--                "The optional transit network selection for this party."
--        ::= { pnniPmpSpvccSrcPartyEntry 14 }
--

pnniPmpSpvccSrcPartyFtDtlIndex OBJECT-TYPE
	SYNTAX  Integer32
	MAX-ACCESS  read-create
	STATUS  current
	DESCRIPTION
		 "The Designated Transit List (DTL) index for this
		  party. This value must be defined in the ftPnniDTLTable.
		  The DTL specifies a preferred call routing for the SVC
		  portion of the party. If a DTL is specified, this party will not be
		  rerouted when rerouting is requested administratively. "
	::= { pnniPmpSpvccSrcPartyEntry 13 }

pnniPmpSpvccSrcPartyRerouteStatus OBJECT-TYPE
	SYNTAX  INTEGER {
			rerouteNotRequested(1),
			rerouteRequested(2),
			rerouteCompleted(3),
			rerouteNotApplicable(4)
		 }
	MAX-ACCESS  read-create
	STATUS  current
	DESCRIPTION
		"The status of the reroute function for this party. Rerouting can be
		 administratively requested, for active parties, by setting this variable to
		 reroute_requested(2). On successful completion of rerouting,
		 it will be set to reroute_completed(3). When a DTL is specified for a
		 party, rerouting will not be performed for that party and this variable will
		 set to reroute_not_applicable. "
	DEFVAL  { rerouteNotRequested }
	::= { pnniPmpSpvccSrcPartyEntry 14 }


pnniPmpSpvccSrcPartyQosIndex OBJECT-TYPE
	SYNTAX  Integer32
	MAX-ACCESS  read-create
	STATUS  current
	DESCRIPTION
		"The index for the QOS Class Expansion Table to be used for
		 this PMP SPVCC."
	::= {  pnniPmpSpvccSrcPartyEntry 15 }

pnniPmpSpvccSrcPartyRowStatus OBJECT-TYPE
	SYNTAX  RowStatus
	MAX-ACCESS  read-create
	STATUS  current
	DESCRIPTION
		"The status of this party entry."
	::= { pnniPmpSpvccSrcPartyEntry 16 }

pnniPmpSpvccSrcPartyLastLocation OBJECT-TYPE
	SYNTAX  DisplayString
	MAX-ACCESS  read-only
	STATUS  current
	DESCRIPTION
		"The last call setup failure location code for this
		SPVC. This indicates the switch that initiated the
		clearing for the call. This is formatted as a text
		string with the fields:
		   FMT: Indicates diagnostic format
		   RMT: Indicates whether a remote switch is the source of the
			failure or this switch inserted the location diag
		   LINK:Link id that clear pertains to
		   VPI: VPI that clear pertains to
		   The remaining fields are format specific"
	::= { pnniPmpSpvccSrcPartyEntry 17 }

pnniPmpSpvccSrcPartyAutoDtlStatus OBJECT-TYPE
	SYNTAX	INTEGER {
			enabled(1),
			disabled(2)
		}
	MAX-ACCESS	read-create
	STATUS  current
	DESCRIPTION
		"The status of the dynamic path selection function for this
		SPVC (Smart Permanent Virtual Circuit). If set to disabled(2),
		auto path selection will not be used."
	DEFVAL	{ enabled }
	::= { pnniPmpSpvccSrcPartyEntry 18 }

pnniPmpSpvccSrcPartyDownReason OBJECT-TYPE
	SYNTAX	INTEGER {
			reroute(1),
			failure(2),
			deletion(3)
		}
	MAX-ACCESS 	read-only
	STATUS	current
	DESCRIPTION
		"The reason for the spvc down is set accordingly"
	::= { pnniPmpSpvccSrcPartyEntry 19 }

pnniPmpSpvccSrcPartyRouteCost	OBJECT-TYPE
	SYNTAX	Integer32
	MAX-ACCESS	read-only
	STATUS	current
	DESCRIPTION
		"The link cost associated for the party isset here"
	::= { pnniPmpSpvccSrcPartyEntry 20 }
------------------------------------------------------------------------

--
-- PNNI SPVCC destination-side definitions
--

pnniPmpSpvccDestNumberOfSpvccs OBJECT-TYPE
	SYNTAX  Integer32
	MAX-ACCESS  read-only
	STATUS  current
	DESCRIPTION
		"The number of connected PMP SPVCCs (Smart Permanent Virtual
		 Circuits) that have their parties terminating at this switch."
	::= { pnniPmpSpvccGroup 5 }

pnniPmpSpvccDestRootTable OBJECT-TYPE
	SYNTAX  SEQUENCE OF PnniPmpSpvccDestRootEntry
	MAX-ACCESS  not-accessible
	STATUS  current
	DESCRIPTION
		"This table contains information about the root of PMP
		 SPVCCs (Smart Permanent Virtual Circuits) that have their
		 parties terminating at this switch."
	::= { pnniPmpSpvccGroup 6 }

pnniPmpSpvccDestRootEntry OBJECT-TYPE
	SYNTAX  PnniPmpSpvccDestRootEntry
	MAX-ACCESS  not-accessible
	STATUS  current
	DESCRIPTION
		"A table entry containing destination SPVCC (Smart
		 Permanent Virtual Circuits) information."
	INDEX   { pnniPmpSpvccDestRootIndex }
	::= { pnniPmpSpvccDestRootTable 1 }

PnniPmpSpvccDestRootEntry ::= SEQUENCE {
		pnniPmpSpvccDestRootIndex               Integer32,
		pnniPmpSpvccDestRootAtmAddr             NsapAddr,
		pnniPmpSpvccDestRootPort                Integer32,
		pnniPmpSpvccDestRootVPI                 Integer32,
		pnniPmpSpvccDestRootVCI                 Integer32,
		pnniPmpSpvccDestRootBearerClass         INTEGER,
		pnniPmpSpvccDestRootSusceptClip         INTEGER,
		pnniPmpSpvccDestRootFwdQoSClass         INTEGER,
		pnniPmpSpvccDestRootNumberOfParties     Integer32
	}

pnniPmpSpvccDestRootIndex OBJECT-TYPE
	SYNTAX  Integer32
	MAX-ACCESS  read-only
	STATUS  current
	DESCRIPTION
	       "The value of this object uniquely identifies the
		PMP SPVCCs (Smart Permanent Virtual Circuits) that
		has one or more parties terminating at this switch."
	::= { pnniPmpSpvccDestRootEntry 1 }

pnniPmpSpvccDestRootAtmAddr OBJECT-TYPE
	SYNTAX  NsapAddr
	MAX-ACCESS  read-only
	STATUS  current
	DESCRIPTION
		"The ATM address of the root of the PMP SPVCC that has
		 one or more parties terminating at this switch."
	::= { pnniPmpSpvccDestRootEntry 2 }

pnniPmpSpvccDestRootPort OBJECT-TYPE
	SYNTAX  Integer32
	MAX-ACCESS  read-only
	STATUS  current
	DESCRIPTION
		"The value of this object identifies the port
		 of this terminating PMP SPVCC (Smart Permanent Virtual Circuits)
		 at the source end. It has a value of -1 if the
		 port at the destination switch cannot be determined."
	::= { pnniPmpSpvccDestRootEntry 3 }

pnniPmpSpvccDestRootVPI OBJECT-TYPE
	SYNTAX  Integer32
	MAX-ACCESS  read-only
	STATUS  current
	DESCRIPTION
		"The VPI used for the PVCC portion of the connection at the
		 root of the PMP SPVCC. The root switch is identified by
		 pnniPmpSpvccDestCallingAtmAddr."
       ::= { pnniPmpSpvccDestRootEntry 4 }

pnniPmpSpvccDestRootVCI OBJECT-TYPE
	SYNTAX  Integer32
	MAX-ACCESS  read-only
	STATUS  current
	DESCRIPTION
		"The VCI used for the PVCC portion of the connection at the
		 root of the PMP SPVCC. The root switch is identified by
		 pnniPmpSpvccDestCallingAtmAddr."
	::= { pnniPmpSpvccDestRootEntry 5 }

pnniPmpSpvccDestRootBearerClass OBJECT-TYPE
	SYNTAX  INTEGER {
			    classA(1),
			    classC(2),
			    classX(3)
			}
	MAX-ACCESS  read-only
	STATUS  current
	DESCRIPTION
		"The broadband bearer class signalled for the first party
		 of this PMP SPVCC. All subsequent parties should have the same
		 value."
	::= { pnniPmpSpvccDestRootEntry 6 }

pnniPmpSpvccDestRootSusceptClip OBJECT-TYPE
	SYNTAX  INTEGER {
			    no(1),
			    yes(2)
			}
	MAX-ACCESS  read-only
	STATUS  current
	DESCRIPTION
		"The broadband bearer susceptability to clipping signalled for
		 the first party of this PMP SPVCC. All subsequent parties should
		 have the same value."
	::= { pnniPmpSpvccDestRootEntry 7 }

pnniPmpSpvccDestRootFwdQoSClass OBJECT-TYPE
	SYNTAX  INTEGER {
			    class0(1),
			    class1(2),
			    class2(3),
			    class3(4),
			    class4(5)
			}
	MAX-ACCESS  read-only
	STATUS  current
	DESCRIPTION
		"The requested quality of service for this PMP SPVCC in
		 the forward (from root to leaves) direction. Backward QoS
		 requirements do not apply to PMP SPVCCs."
	::= { pnniPmpSpvccDestRootEntry 8 }

pnniPmpSpvccDestRootNumberOfParties OBJECT-TYPE
	SYNTAX  Integer32
	MAX-ACCESS  read-only
	STATUS  current
	DESCRIPTION
		"Number of parties currently terminating at this switch
		 within this PMP SPVCC"
	::= { pnniPmpSpvccDestRootEntry 9 }


------------------------------------------------------------------------
pnniPmpSpvccDestPartyTable OBJECT-TYPE
	SYNTAX  SEQUENCE OF PnniPmpSpvccDestPartyEntry
	MAX-ACCESS  not-accessible
	STATUS  current
	DESCRIPTION
		"This table contains information about the parties of PMP
		 SPVCCs (Smart Permanent Virtual Circuits) that terminate
		 at this switch."
	::= { pnniPmpSpvccGroup 7 }

pnniPmpSpvccDestPartyEntry OBJECT-TYPE
	SYNTAX  PnniPmpSpvccDestPartyEntry
	MAX-ACCESS  not-accessible
	STATUS  current
	DESCRIPTION
		"A table entry containing destination information about
		 parties in a PMP SPVCC (Smart Permanent Virtual Circuits)."
	INDEX   { pnniPmpSpvccDestRootIndex, pnniPmpSpvccDestPartyIndex }
	::= { pnniPmpSpvccDestPartyTable 1 }

PnniPmpSpvccDestPartyEntry ::= SEQUENCE {
		pnniPmpSpvccDestPartyIndex         Integer32,
		pnniPmpSpvccDestPartyAtmAddr       NsapAddr,
		pnniPmpSpvccDestPartyPort          Integer32,
		pnniPmpSpvccDestPartyAssignedVPI   Integer32,
		pnniPmpSpvccDestPartyAssignedVCI   Integer32,
		pnniPmpSpvccDestPartyUpTime        TimeTicks,
		pnniPmpSpvccDestPartyTransitNetSel TransitNetwork,
		pnniPmpSpvccDestPartyStatus        INTEGER,
		pnniPmpSpvccDestPartyRGroupIndex   INTEGER
}


pnniPmpSpvccDestPartyIndex OBJECT-TYPE
	SYNTAX  Integer32
	MAX-ACCESS  read-only
	STATUS  current
	DESCRIPTION
	       "The value of this object uniquely identifies a
		party of PMP SPVCCs (Smart Permanent Virtual Circuits) that
		have one or more parties terminating at this switch. This
		value is unique within a PMP SPVCC represented by
		pnniPmpSpvccDestRootIndex"
	::= { pnniPmpSpvccDestPartyEntry 1 }

pnniPmpSpvccDestPartyAtmAddr OBJECT-TYPE
	SYNTAX  NsapAddr
	MAX-ACCESS  read-only
	STATUS  current
	DESCRIPTION
		"The ATM address of the switch where this party
		 of a PMP SPVCC terminates."
	::= { pnniPmpSpvccDestPartyEntry 2 }

pnniPmpSpvccDestPartyPort OBJECT-TYPE
	SYNTAX  Integer32
	MAX-ACCESS  read-only
	STATUS  current
	DESCRIPTION
		"The value of this object identifies the port
		 where this party of a PMP  SPVCC (Smart Permanent Virtual
		 Circuits) terminates.It has a value os -1 if the
		 port at the destination switch cannot be determined."
	::= { pnniPmpSpvccDestPartyEntry 3 }

pnniPmpSpvccDestPartyAssignedVPI OBJECT-TYPE
	SYNTAX  Integer32
	MAX-ACCESS  read-only
	STATUS  current
	DESCRIPTION
		"The value of this object identifies the VPI assigned
		 for this party of a PMP SPVCC (Smart Permanent Virtual
		 Circuits) at the terminating switch. This value is only
		 meaningful if the party status, identified by
		 pnniPmpSpvccDestStatus, is up."
	::= { pnniPmpSpvccDestPartyEntry 4 }

pnniPmpSpvccDestPartyAssignedVCI OBJECT-TYPE
       SYNTAX  Integer32
	MAX-ACCESS  read-only
	STATUS  current
	DESCRIPTION
		"The value of this object identifies the VCI assigned
		 for this party of a PMP SPVCC (Smart Permanent Virtual
		 Circuits) at the terminating switch. This value is only
		 meaningful if the party status, identified by
		 pnniPmpSpvccDestStatus, is up."
	::= { pnniPmpSpvccDestPartyEntry 5 }

pnniPmpSpvccDestPartyUpTime OBJECT-TYPE
	SYNTAX  TimeTicks
	MAX-ACCESS  read-only
	STATUS  current
	DESCRIPTION
		"The time since this party of PMP SPVCC (Smart Permanent Virtual
		 Circuits) was created in hundredths of a second."
	::= { pnniPmpSpvccDestPartyEntry 6 }

pnniPmpSpvccDestPartyTransitNetSel OBJECT-TYPE
	SYNTAX  TransitNetwork
	MAX-ACCESS  read-only
	STATUS  current
	DESCRIPTION
		"The optional transit network selection for this
		 party of PMP SPVCC."
	::= { pnniPmpSpvccDestPartyEntry 7 }

pnniPmpSpvccDestPartyStatus OBJECT-TYPE
	SYNTAX  INTEGER {
			up(1),
			down(2),
			failed(3)
		}
	MAX-ACCESS  read-only
	STATUS  current
	DESCRIPTION
		"The operational status of this party of PMP SPVCC (Smart
		 Permanent Virtual Circuit)."
	::= { pnniPmpSpvccDestPartyEntry 8 }

pnniPmpSpvccDestPartyRGroupIndex OBJECT-TYPE
	SYNTAX        INTEGER (1..65535)
	MAX-ACCESS        read-only
	STATUS        current
	DESCRIPTION
		"This specifies the entry in the Spvxc Redundancy Group
		 table for information regarding the secondary port to
		 be used as the redundant port. This will used at the
		 terminating PVC end."
	::= {  pnniPmpSpvccDestPartyEntry 9 }


----------------------------------------------------------------------------
----------------------------------------------------------------------------
-- PNNI SPVxC Redundancy Table Group
--
-- The mapping of primary and secondary ports for the
-- Permanent portion of SPVxCs.
--

pnniSpvxcRGroupTable OBJECT-TYPE
	SYNTAX  SEQUENCE OF PnniSpvxcRGroupEntry
	MAX-ACCESS  not-accessible
	STATUS  current
	DESCRIPTION
		"A table of Primary to Secondary  Port mappings that
		 will be used for redundancy in permanent portion of SPVxCs. "
	::= {  q2931Group 14 }

pnniSpvxcRGroupEntry OBJECT-TYPE
	SYNTAX        PnniSpvxcRGroupEntry
	MAX-ACCESS        not-accessible
	STATUS        current
	DESCRIPTION
		"A table entry containing the primary to secondary
		 port mappings."
	INDEX   { pnniSpvxcRGroupIndex }
	::= { pnniSpvxcRGroupTable 1 }

PnniSpvxcRGroupEntry ::= SEQUENCE {
	    pnniSpvxcRGroupIndex                        INTEGER,
	    pnniSpvxcRGroupPrimaryPort                  Integer32,
	    pnniSpvxcRGroupSecondaryPort                Integer32,
	    pnniSpvxcRGroupNsapAddr                     NsapAddr,
	    pnniSpvxcRGroupSwitchoverCmd                INTEGER,
	    pnniSpvxcRGroupActivePort                   Integer32,
	    pnniSpvxcRGroupPacingNumber                 Integer32,
	    pnniSpvxcRGroupPacingInterval               Integer32,
	    pnniSpvxcRGroupAutoPVCSwitchover            INTEGER,
	    pnniSpvxcRGroupName                         OCTET STRING,
	    pnniSpvxcRGroupState                        INTEGER,
	    pnniSpvxcRGroupRowStatus                    RowStatus
	}

pnniSpvxcRGroupIndex OBJECT-TYPE
	SYNTAX        INTEGER (1..65535)
	MAX-ACCESS        not-accessible
	STATUS        current
	DESCRIPTION
		"The value of this object identifies the Group Index
		 associated with this entry."
	::= { pnniSpvxcRGroupEntry 1 }

pnniSpvxcRGroupPrimaryPort OBJECT-TYPE
	SYNTAX  Integer32
	MAX-ACCESS  read-write
	STATUS  current
	DESCRIPTION
		"The value of this object identifies the primary port
		 of this entry. This will used as the primary PVC port
		 for the SPVC created with this group index. "
	::= { pnniSpvxcRGroupEntry 2 }

pnniSpvxcRGroupSecondaryPort OBJECT-TYPE
	SYNTAX  Integer32
	MAX-ACCESS  read-write
	STATUS  current
	DESCRIPTION
		"The value of this object identifies the secondary port
		 of this group. This will used as the redundant PVC port
		 for the SPVC created with this group index. During a
		 switch command, the PVCs will be switched from primary
		 port to this port."
	::= { pnniSpvxcRGroupEntry 3 }

pnniSpvxcRGroupNsapAddr OBJECT-TYPE
	SYNTAX  NsapAddr
	MAX-ACCESS  read-only
	STATUS  current
	DESCRIPTION
		"This shows the default nsap address associated with
		 this group using the default domain's prefix. This is
		 a read-only variable available to view the default nsap
		 address associated with this group."
	::= { pnniSpvxcRGroupEntry 4 }

pnniSpvxcRGroupSwitchoverCmd  OBJECT-TYPE
	SYNTAX  INTEGER {
			switch2primary(1),
			switch2secondary(2)
		}
	MAX-ACCESS  read-write
	STATUS  current
	DESCRIPTION
		"The value of this MIB defines the switchover command.
		 The value of 1 is used to switch over the permanent
		 PVC portion to the primary port. The value of 2 is
		 used to switch over the permanent PVC portion to the
		 secondary port. If the permanent portions are already on
		 the specified port, no action is taken "
	::= { pnniSpvxcRGroupEntry 5 }

pnniSpvxcRGroupActivePort  OBJECT-TYPE
	SYNTAX  Integer32
	MAX-ACCESS  read-only
	STATUS  current
	DESCRIPTION
		"This specifies the port that is active. This can take
		 any one of the primary or secondary port values. This
		 is a read only variable useful to check the currently
		 active port."
	::= { pnniSpvxcRGroupEntry 6 }

pnniSpvxcRGroupPacingNumber  OBJECT-TYPE
	SYNTAX  Integer32
	MAX-ACCESS  read-write
	STATUS  current
	DESCRIPTION
		"This specifies the pacing number for this group. During a
		 pacing interval, pacing number of SPVCs will be attempted
		 for PVC switch over. "
	::= { pnniSpvxcRGroupEntry 7 }

pnniSpvxcRGroupPacingInterval  OBJECT-TYPE
	SYNTAX  Integer32
	MAX-ACCESS  read-write
	STATUS  current
	DESCRIPTION
		"This specifies the pacing interval in units of milliseconds
		 for this group. Every time a switchover command is issued,
		 pacing number of SPVCs will be attempted for PVC
		 switch over every Pacing Interval."
	::= { pnniSpvxcRGroupEntry 8 }

pnniSpvxcRGroupAutoPVCSwitchover  OBJECT-TYPE
	SYNTAX  INTEGER {
		enabled(1),
		disabled(2)
	}
	MAX-ACCESS  read-write
	STATUS  current
	DESCRIPTION
		"The value of this MIB defines if automatic switchover
		 of the PVC portion is enable dor disabled. The
		 default value is disabled(2)."
       DEFVAL { disabled }
	::= { pnniSpvxcRGroupEntry 9 }

pnniSpvxcRGroupName OBJECT-TYPE
	 SYNTAX  OCTET STRING (SIZE(0..16))
	 MAX-ACCESS  read-write
	 STATUS  current
	 DESCRIPTION
		 " The value of this object identifies the
		 name that has been assigned for this Rgroup."
	::= { pnniSpvxcRGroupEntry 10 }

pnniSpvxcRGroupState  OBJECT-TYPE
	SYNTAX  INTEGER {
		operational(1),
		switchoverInProgress(2)
	}
	MAX-ACCESS  read-only
	STATUS  current
	DESCRIPTION
		"This specifies the state of the Redundancy
		 Group. State operational(1) indicates that this group is
		 in the normal state and switchover is not going on.
		 State switchover_in_progress(2) indicates that
		 switchover is presently going on for this group. In
		 this state no new SPVCs can be added to this group."
	::= { pnniSpvxcRGroupEntry 11 }

pnniSpvxcRGroupRowStatus   OBJECT-TYPE
	SYNTAX        RowStatus
	MAX-ACCESS        read-write
	STATUS        current
	DESCRIPTION
		"The status of this pnniSpvxcRGroup entry."
	::= { pnniSpvxcRGroupEntry 12 }


------------------------------------------------------------------------
-- The Q2931 Group

-- The implementation of the group is mandatory for
-- FORE switches that supports Q2931 signalling.

-- The Q2931 Layer Group

q2931AdminTable OBJECT-TYPE
	SYNTAX	SEQUENCE OF Q2931AdminEntry
	MAX-ACCESS	not-accessible
	STATUS	current
	DESCRIPTION
		"A table of general information about the Q2931 signaling path."
	::= { q2931LayerGroup 1 }

q2931AdminEntry OBJECT-TYPE
	SYNTAX	Q2931AdminEntry
	MAX-ACCESS	not-accessible
	STATUS	current
	DESCRIPTION
		"A table entry containing Q2931Admin signaling administration information,
		indexed by port and path."
	INDEX	{ q2931AdminPort, q2931AdminVPI }
	::= { q2931AdminTable 1 }

Q2931AdminEntry ::= SEQUENCE {
	q2931AdminPort			Integer32,
	q2931AdminVPI			Integer32,
	q2931AdminVCI			Integer32,
	q2931AdminStatus		INTEGER,
	q2931OperStatus			INTEGER,
	q2931SSCOPOperStatus		INTEGER,
	q2931ILMIAdminStatus		INTEGER,
	q2931ILMIOperStatus		INTEGER,
	q2931AdminAALType		INTEGER,
	q2931AdminUNISide		INTEGER,
	q2931AdminConfigType		INTEGER,
	q2931AdminOperType		INTEGER,
	q2931AdminEntryStatus		EntryStatus,
	q2931AdminRemoteIpAddress	IpAddress,
	q2931SigReservedBW              Integer32,
	q2931ILMIReservedBW             Integer32,
	q2931ILMIAdminVCI		Integer32,
	q2931AdminMinVCI		Integer32,
	q2931AdminMaxVCI		Integer32,
	q2931MinVCI			Integer32,
	q2931MaxVCI			Integer32,
	q2931UNIConfigVersion           INTEGER,
	q2931UNIOperVersion             INTEGER,
	q2931ILMIRegistration		INTEGER,
	q2931CallingPDefaultAddress	NsapAddr,
	q2931AdminUseNativeE164		INTEGER,
	q2931AdminNativeE164Address	E164Address,
	q2931AdminE164AddressResolution	INTEGER,
	q2931AdminFtPnniOrigCost	INTEGER,
	q2931AdminFtPnniTermCost	Integer32,
	q2931AdminAVPresentation	Integer32,
	q2931AdminSigMode		INTEGER,
	q2931AdminSigAlloc		INTEGER,
	q2931PeerPort			Integer32,
	q2931InputSigContract           Integer32,
	q2931OutputSigService           INTEGER,
	q2931SSCOPNoRespTimer		Integer32,
--      q2931AdminCDASActivation        INTEGER,
--      q2931EcacPerSvcMaxBwForward     INTEGER,
--      q2931EcacPerSvcMaxBwBackward    INTEGER,
--      q2931EcacUbrRepBwForward        INTEGER,
--      q2931EcacUbrRepBwBackward       INTEGER,
--      q2931EcacMaxUbrVCsForward       INTEGER,
--      q2931EcacMaxUbrVCsBackward      INTEGER,
	q2931AdminIncomingNSAPFilterIndex Integer32,
	q2931AdminOutgoingNSAPFilterIndex Integer32,
	q2931AdminIEFilter		Integer32,
	q2931SendCallProc		INTEGER,
--	q2931LogMessage			INTEGER,
	q2931VCIRangeStatus             INTEGER,
	q2931ClearOnCarrierLoss		INTEGER,
	q2931QosClassExpansionKey       Integer32,
	q2931AtmrConfDomainID           Integer32,
	q2931AtmrPnniNodeIndex          Integer32,
	q2931AdminOperSigMode		INTEGER,
--      q2931AdminTrafficType           INTEGER,
	q2931AdminOperSigAlloc		INTEGER,
	q2931OutputSigUpc		Integer32,
	q2931AdminPlanType		INTEGER,
	q2931AdminMaxVPI		INTEGER,
	q2931MaxSvccVPI			INTEGER,
	q2931LastChangeTime		TimeStamp,
	q2931MaxSvpcVPI			INTEGER,
	q2931VpCapability		INTEGER,
	q2931NNIProto	                INTEGER,
	q2931VpciGroupIndex		INTEGER,
        q2931ProxyDirGroupIndex         INTEGER,
	q2931AcceleratedClear          INTEGER,
        q2931OutputIlmiUpc              Integer32,
        q2931OutputRccUpc               Integer32,
	q2931SupplementaryServicesStatus      INTEGER,
	q2931CallingPAddressPresentation      INTEGER,
	q2931CallingPAddressRestriction       INTEGER,
	q2931ConnectedPAddressPresentation    INTEGER,
	q2931ConnectedPAddressRestriction     INTEGER,
	q2931ConnectedPDefaultAddress         NsapAddr,
	q2931SubaddressingAdminStatus         INTEGER,
	q2931UserUserSignallingAdminStatus    INTEGER,
        q2931PnniRccVci                       Integer32,
        q2931AdminubrCalls                    INTEGER,
        q2931AdmincbrCalls                    INTEGER,
        q2931AdminabrCalls                    INTEGER,
        q2931AdminrtvbrCalls                  INTEGER,
        q2931AdminnrtvbrCalls                 INTEGER

}

q2931AdminPort OBJECT-TYPE
	SYNTAX	Integer32
	MAX-ACCESS	read-only
	STATUS	current
	DESCRIPTION
		"The value of this object identifies the port
		of this signalling path, and is the same as the
		portNumber."
	::= { q2931AdminEntry 1 }

q2931AdminVPI OBJECT-TYPE
	SYNTAX	Integer32
	MAX-ACCESS	read-only
	STATUS	current
	DESCRIPTION
		"The VPI (Virtual Path Identifier) of this signaling path."
	::= { q2931AdminEntry 2 }

q2931AdminVCI OBJECT-TYPE
	SYNTAX	Integer32
	MAX-ACCESS	read-create
	STATUS	current
	DESCRIPTION
		"The VCI (Virtual Channel Identifier) of the signaling
		channel within the signaling path."
	::= { q2931AdminEntry 3 }

q2931AdminStatus OBJECT-TYPE
	SYNTAX	INTEGER {
			up(1),
			down(2)
		}
	MAX-ACCESS	read-create
	STATUS	current
	DESCRIPTION
		"The desired state of this signaling channel. The up(1) state
		dictates that Q2931 messages are used for signalling. The down(2)
		state dictates that Q2931 protocol is not used for signalling."
	::= { q2931AdminEntry 4 }

q2931OperStatus OBJECT-TYPE
	SYNTAX	INTEGER {
			up(1),
			down(2)
		}
	MAX-ACCESS	read-only
	STATUS	current
	DESCRIPTION
		"The current operational state of this signaling channel,
		as determined either by administrative action, when the
		value of q2931AdminStatus is down(2), or by a link
		monitoring protocol, when the value of q2931AdminStatus
		is up(1)."
	::= { q2931AdminEntry 5 }

q2931SSCOPOperStatus OBJECT-TYPE
	SYNTAX	INTEGER {
			up(1),
			down(2)
		}
	MAX-ACCESS	read-only
	STATUS	current
	DESCRIPTION
		"The current operational state of the underlying SSCOP
		(Service Specific Connection Orientedd Protocol) on this
		channel. SSCOP's function is to provide a reliable data
		link layer for the exchange of Q.2931 signalling messages.
		The value up(1) reflects the value dataTransReady(4) for
		the SSCOPOperStatus object in the SSCOP Administration
		table (sscopAdminTable). All other values of that object
		are reflected as the value down(2) for this object."
	::= { q2931AdminEntry 6 }

q2931ILMIAdminStatus OBJECT-TYPE
	SYNTAX	INTEGER {
			up(1),
			down(2)
		}
	MAX-ACCESS	read-create
	STATUS	current
	DESCRIPTION
		"The desired state of the underlying ILMI (Interim Local
		Manageemnt Interface) status and configuration channel.
		The up(1) state dictates that ILMI messages are used for
		status and configuration information. The down(2) state
		dictates that ILMI protocol is not used."
	::= { q2931AdminEntry 7 }

q2931ILMIOperStatus OBJECT-TYPE
	SYNTAX	INTEGER {
			up(1),
			down(2)
		}
	MAX-ACCESS	read-only
	STATUS	current
	DESCRIPTION
		"The current operational state of the underlying ILMI
		(Interim Local Manageemnt Interface) status and configuration
		channel, as determined either by administrative action, when
		the value of q2931ILMIAdminStatus is down(2), or by a link
		monitoring protocol, when the value of q2931ILMIAdminStatus
		is up(1)."
	::= { q2931AdminEntry 8 }

q2931AdminAALType OBJECT-TYPE
	SYNTAX	INTEGER {
			type34(1),
			type5(2)
		}
	MAX-ACCESS	read-create
	STATUS	current
	DESCRIPTION
		"The AAL (ATM Adaptation Layer) type that is used by this
		Q2931 signaling path."
	::= { q2931AdminEntry 9 }

q2931AdminUNISide OBJECT-TYPE
	SYNTAX	INTEGER {
			user(1),
			network(2)
		}
	MAX-ACCESS	read-create
	STATUS	current
	DESCRIPTION
		"This object detemines the role this port takes in the
		UNI (User Network Interface). If this port is connected
		to a host via the private UNI, this port is on the network(2)
		side of the UNI, whilst if this port is connected to the
		Public UNI the port may be required to be the user(1) side
		of the connection."
	::= { q2931AdminEntry 10 }

q2931AdminConfigType OBJECT-TYPE
	SYNTAX	INTEGER {
			publicUNI(1),
			automode(2),
			iisp(3),
			ftPNNI(4),
			privateNNI(5),
			privateUNI(6)
		}
	MAX-ACCESS	read-create
	STATUS	current
	DESCRIPTION
		"The configuration of the UNI (User Network Interface)
		at initialization. Configuring the UNI to publicUNI(1)
		means that this link will be used between the switch and
		a public switch. Configuring the UNI to automode(2) means that
		the operational type will be determined dynamically.
		Configuring the UNI to iisp(3) (Interim Inter-Switch
		Signalling Protocol) indicates that this link is used for
		static routing NNI (Network to Network Interface). Configuring
		the type to privateNNI allows the interface to come up as
		PNNI type and running the PNNI routing protocol. Configuring
		the type as privateUNI indicates that the interface should
		comeup as a user-network interface UNI."
	::= { q2931AdminEntry 11 }

q2931AdminOperType OBJECT-TYPE
	SYNTAX	INTEGER {
			publicUNI(1),
			privateUNI(2),
			iisp(3),
			ftPNNI(4),
			privateNNI(5)
		}
	MAX-ACCESS	read-only
	STATUS	current
	DESCRIPTION
		"The operational configuration of the UNI (User Network
		Interface). publicUNI(1) is used between the switch and
		a public switch. privateUNI(2) is used between the switch
		and a host. IISP, iisp(3), stands for Interim Inter-Switch
		Signalling Protocol, is used between two switches using
		static routing. And spansNNI(4) is used between two switches
		using SPANS mapping messages for dynamic routing. If the
		q2931AdminConfigType is set to auto(2), the value of this
		object may be either privateUNI(2), or spansNNI(4)."
	::= { q2931AdminEntry 12 }

q2931AdminEntryStatus OBJECT-TYPE
	SYNTAX	EntryStatus
	MAX-ACCESS	read-create
	STATUS	current
	DESCRIPTION
		"The status of this signaling path entry. Setting this object
		to invalid(4) causes the q2931 path to be destroyed."
	::= { q2931AdminEntry 13 }

q2931AdminRemoteIpAddress OBJECT-TYPE
	SYNTAX	IpAddress
	MAX-ACCESS	read-only
	STATUS	current
	DESCRIPTION
		"The IP address of the entity connected to this q2931
		signalling path. The remote IP address is derived using
		ILMI on this interface."
	::= { q2931AdminEntry 14 }

q2931SigReservedBW OBJECT-TYPE
	SYNTAX  Integer32
	MAX-ACCESS	read-create
	STATUS	deprecated
	DESCRIPTION
		"Bandwidth reserved for the UNI Signaling VC, in
		 cells/sec."
	::= { q2931AdminEntry 15 }

q2931ILMIReservedBW OBJECT-TYPE
	SYNTAX  Integer32
	MAX-ACCESS	read-create
	STATUS	deprecated
	DESCRIPTION
		"Bandwidth reserved for the UNI ILMI VC, in
		 cells/sec."
	::= { q2931AdminEntry 16 }

q2931ILMIAdminVCI OBJECT-TYPE
	SYNTAX	Integer32
	MAX-ACCESS	read-create
	STATUS	current
	DESCRIPTION
		"The VCI (Virtual Channel Identifier) of the ILMI
		 signalling channel."
	::= { q2931AdminEntry 17 }

q2931AdminMinVCI OBJECT-TYPE
	SYNTAX	Integer32
	MAX-ACCESS	read-create
	STATUS	current
	DESCRIPTION
		"The minimum configured VCI (Virtual Channel Identifier)
		 used for SVCs (Signalling Virtual Circuits)."
	::= { q2931AdminEntry 18 }

q2931AdminMaxVCI OBJECT-TYPE
	SYNTAX	Integer32
	MAX-ACCESS	read-create
	STATUS	current
	DESCRIPTION
		"The maximum configured VCI (Virtual Channel Identifier)
		 used for SVCs (Signalling Virtual Circuits)."
	::= { q2931AdminEntry 19 }

q2931MinVCI OBJECT-TYPE
	SYNTAX	Integer32
	MAX-ACCESS	read-only
	STATUS	current
	DESCRIPTION
		"The minimum actual VCI (Virtual Channel Identifier)
		 used for SVCs (Signalling Virtual Circuits)."
	::= { q2931AdminEntry 20 }

q2931MaxVCI OBJECT-TYPE
	SYNTAX	Integer32
	MAX-ACCESS	read-only
	STATUS	current
	DESCRIPTION
		"The maximum actual VCI (Virtual Channel Identifier)
		 used for SVCs (Signalling Virtual Circuits)."
	::= { q2931AdminEntry 21 }

q2931UNIConfigVersion OBJECT-TYPE
	SYNTAX	INTEGER {
			auto(1),
			uni30(2),
			uni31(3),
			pnni10(4),
			uni40(5)
		}
	MAX-ACCESS	read-create
	STATUS	current
	DESCRIPTION
		"The configuration version of the UNI protocol to use at
		initialization. Configuring the UNI to auto(1), means that
		the UNI will attempt to automatically determine which version
		of the UNI protocol to use by reading the value of ILMI
		variable atmfAtmLayerUniVersion. Configuring the UNI to
		uni30(2) means that this link will use version 30 of the UNI
		protocol, likewise for uni31(3). If the nni interface has to
		be brought up as pnni then pnni10 version isspecified.
		To bring the interface as uni40 version then sepcify uni40."
	::= { q2931AdminEntry 22 }

q2931UNIOperVersion OBJECT-TYPE
	SYNTAX	INTEGER {
			auto(0),
			uni30(1),
			uni31(2),
			pnni10(3),
			uni40(4)
		}
	MAX-ACCESS	read-only
	STATUS	current
	DESCRIPTION
		"The version of the UNI that is currently being used on
		this link, i.e. the operational version of the UNI."
	::= { q2931AdminEntry 23 }


q2931ILMIRegistration		OBJECT-TYPE
	SYNTAX	INTEGER {
		enable(1),
		disable(2),
		ignore(3)	-- net-side only
		}
	MAX-ACCESS	read-create
	STATUS	current
	DESCRIPTION
		"Whether to do ILMI Address and Prefix Registration
		 across this UNI.  If disabled, no prefix registration
		messages are sent by the network-side, and no address
		registration messages are generated by the user-side.

		If set to ignore, then the network-side performs as it
		normally would, except that addresses registered are
		not published into the routing database.  This setting
		is not recommended except in Public Network situations
		where CPE equipment requires ILMI Address registration
		in order to function correctly.

		The default value of this variable is different
		depending on the type of UNI being created. If
		creating a public UNI, this variable defaults to
		disable, while it defaults to enable for all other
		types."
	::= { q2931AdminEntry 24 }


q2931CallingPDefaultAddress	OBJECT-TYPE
	SYNTAX	NsapAddr
	MAX-ACCESS	read-create
	STATUS	current
	DESCRIPTION
		"The calling party address to be inserted in Connection
		Setup messages which do not contain Calling Party
		Addresses."
	::= { q2931AdminEntry 25 }

q2931AdminUseNativeE164	OBJECT-TYPE
	SYNTAX	INTEGER {
		enable(1),
		disable(2)	-- default
	}
	MAX-ACCESS	read-create
	STATUS	current
	DESCRIPTION
		"Whether to use Native Form of E164 Addresses across
		this link. Used by Public UNI."
	::= { q2931AdminEntry 26 }

q2931AdminNativeE164Address OBJECT-TYPE
	SYNTAX	E164Address
	MAX-ACCESS	read-create
	STATUS	current
	DESCRIPTION
		"Native E164 Address for this uni. "
	::= { q2931AdminEntry 27 }

q2931AdminE164AddressResolution OBJECT-TYPE
	SYNTAX	INTEGER {
		enable(1),
		disable(2) -- default
	}
	MAX-ACCESS	read-create
	STATUS	current
	DESCRIPTION
		"Whether to resolve Private NSAPs into Native E164
		addresses (using the Q2931E164AddrResTable).  If
		disabled, but if q2931AdminUseNativeE164 is enabled,
		then the only address conversion performed at this
		UNI will be of Private NSAPs in E.164 format."
	::= { q2931AdminEntry 28 }

-- Following FTPNNI variable is deprecated as a part of FT 7.1 

q2931AdminFtPnniOrigCost OBJECT-TYPE
	SYNTAX	INTEGER (1..4294967295)
	MAX-ACCESS	read-create
	STATUS	deprecated
	DESCRIPTION
		"The cost of each pnni orig loglink. It is configured at
		 originating end of sigpath"
	::= { q2931AdminEntry 29 }

-- Following FTPNNI variable is deprecated as a part of FT 7.1 

q2931AdminFtPnniTermCost OBJECT-TYPE
	SYNTAX	Integer32
	MAX-ACCESS	read-only
	STATUS	deprecated
	DESCRIPTION
		"The cost of each pnni term loglink.  The originating
		 side of a link informs the terminating side of the
		 configured q2931AdminFtPnniOrigCost in a hello message.
		 The terminating side then uses the cost value in the
		 hello message as the q2931AdminFtPnniTermCost for
		 topology advertisement."
	::= { q2931AdminEntry 30 }

q2931AdminAVPresentation     OBJECT-TYPE
	SYNTAX  Integer32
	MAX-ACCESS  read-create
	STATUS  deprecated
	DESCRIPTION
		"The set of Address Validation interface options as follows:
		(The bits in this integer have the following meanings:)

		Bit		     Significance			Default
		========             =============			========
		0x0001               Address Validation Enabled		disabled
		0x0002               insertCallingPDefaultAddress	disabled
		0x0004               CallingP_delivery			enabled
		0x0008               CallingPSubAddr_trxf		enabled
		0x0010               CalledPSubAddr_trxf		enabled
		0x0020               BHLI_TRXF				enabled
		0x0040               BLLI_TRXF				enabled
		0x0080               BLLI_selection_TRXF		enabled
		0x0100               AAL_INFO_TRXF			enabled
		---                  Not used presently.		----
		"
	::= { q2931AdminEntry 31 }

q2931AdminSigMode		OBJECT-TYPE
	SYNTAX	INTEGER {
			vpAssoc(1),
			nonAssoc(2),
			auto(3)
		}
	MAX-ACCESS	read-create
	STATUS	current
	DESCRIPTION
		"The configured mode for signalling: VP-associated,
		Non-Associated or auto mode. vpAssoc(1) stands for
		VP-associated signalling, if set to this value, the uni
		encodes the connection identifier with the VP-associated
		signalling bits. nonAssoc(2) is for Non-associated signalling,
		if set to this value the connection identifier is encoded with
		non-associated signalling bits. auto(3) stands for
		auto-configured signalling mode, if set to this value, the
		operating mode will be determined dynamically and will either
		be VP-associated or Non-associated depending on the operating
		type of the signalling link"
	DEFVAL	{ auto }
	::= { q2931AdminEntry 32 }

q2931AdminSigAlloc		OBJECT-TYPE
	SYNTAX	INTEGER {
			allocVP(1),
			allocLink(2),
			auto(3),
			allocVpBundle(4),
			allocProxy(5)
		}
	MAX-ACCESS	read-create
	STATUS	current
	DESCRIPTION
		"The current configured allocation policy for a network side
		uni. If set to allocVP(1), the signalling entity will allocate
		connections within the containing VP only. If set to
		allocLink(2), the signalling entity will allocate connections
		in its containing VP and may allocate connections in other VPS
		that are available to it. If set to allocVpBundle, the uni
		will allocate connections in its containing VP and a bundle of
		other VPs which are pre-created. If set to auto(3), the operating
		allocation policy will be determined based on the operating
		type of the signalling entity and the VPI value of the VP in
		which the signalling channel is present. Based on these, it
		might be allocLink or allocVP or allocVpBundle"
	DEFVAL	{ auto }
	::= { q2931AdminEntry 33 }

q2931PeerPort OBJECT-TYPE
	SYNTAX	Integer32
	MAX-ACCESS	read-only
	STATUS	current
	DESCRIPTION
		"The value of this object identifies the port
		of the peer's signalling path. The value starts
		at zero."
	::= { q2931AdminEntry 34 }

q2931InputSigContract OBJECT-TYPE
	SYNTAX  Integer32
	MAX-ACCESS	read-create
	STATUS	current
	DESCRIPTION
		"Traffic Contract to be applied to the input signalling channel."
	::= { q2931AdminEntry 35 }

q2931OutputSigService OBJECT-TYPE
	SYNTAX  INTEGER {
	       vbr(1),
	       ubr(2),
	       unknown(3)
	}
	MAX-ACCESS	read-create
	STATUS	deprecated
	DESCRIPTION
		"Service Queue where the output signalling vc should be inserted into."
	DEFVAL { unknown }
	::= { q2931AdminEntry 36 }

q2931SSCOPNoRespTimer OBJECT-TYPE
	SYNTAX  Integer32
	MAX-ACCESS  read-create
	STATUS  current
	DESCRIPTION
		"The Value to be set for the duration of
		 the SSCOP No response timer. This is the
		 time in seconds that we will wait before
		 bringing the SSCOP link down. If no value
		 is specified by the user, a default value
		 of 10 seconds is used if the oper version
		 is uni30 and a default value of 7 secs is
		 used if the oper version is uni31."
	::= { q2931AdminEntry 37 }

-- Vector Mib variables. Commented out here to save space.
-- q2931AdminCDASActivation OBJECT-TYPE
--        SYNTAX  INTEGER {
--                enable(1),
--                disable(2)
--        }
--        ACCESS  read-write
--        STATUS  mandatory
--        DESCRIPTION
--                "The actication status (enabled/disabled) indicator for
--                 called address screening feature"
--        ::= { q2931AdminEntry 38 }

-- VR2.1 Redundancy modifications for ECAC feature
-- q2931EcacPerSvcMaxBwForward  OBJECT-TYPE
--        SYNTAX  INTEGER
--        ACCESS  read-write
--        STATUS  mandatory
--        DESCRIPTION
--                "The maximum allowable bandwidth in the user to network
--		  direction which can be allocated to each and every SVC
--                connection at this UNI (for both CBR and VBR)."
--      ::= { q2931AdminEntry 40 }

-- q2931EcacPerSvcMaxBwBackward  OBJECT-TYPE
--        SYNTAX  INTEGER
--        ACCESS  read-write
--        STATUS  mandatory
--        DESCRIPTION
--                "The maximum allowable bandwidth in the network to user
--                direction which can be allocated to each and every SVC
--                connection at this UNI (for both CBR and VBR).
--        ::= { q2931AdminEntry 41 }

-- q2931EcacUbrRepBwForward OBJECT-TYPE
--        SYNTAX  INTEGER
--        ACCESS  read-write
--        STATUS  mandatory
--        DESCRIPTION
--                "A representative bandwidth in the user to network
--                direction for UBR connections which will be deducted from the
--                maximum aggregate SVC bandwidth at this UNI."
--        ::= { q2931AdminEntry 42}

-- q2931EcacUbrRepBwBackward OBJECT-TYPE
--        SYNTAX  INTEGER
--        ACCESS  read-write
--        STATUS  mandatory
--        DESCRIPTION
--                "A representative bandwidth in the network to user
--                direction for UBR connections which will be deducted from
--                the maximum aggregate SVC bandwidth at this UNI."
--        ::= { q2931AdminEntry 43}

-- q2931EcacMaxUbrVCsForward OBJECT-TYPE
--        SYNTAX  INTEGER
--        ACCESS  read-write
--        STATUS  mandatory
--        DESCRIPTION
--                "The maximum number of allowable UBR connections in the
--                user to network direction which can be established at
--                this UNI."
--        ::= { q2931AdminEntry 44 }

-- q2931EcacMaxUbrVCsBackward OBJECT-TYPE
--        SYNTAX  INTEGER
--        ACCESS  read-write
--        STATUS  mandatory
--        DESCRIPTION
--               "The maximum number of allowable UBR connections in the
--		 network to user direction which can be established at this
--		 UNI."
--        ::= { q2931AdminEntry 45 }

q2931AdminIncomingNSAPFilterIndex	OBJECT-TYPE
	SYNTAX	Integer32
	MAX-ACCESS	read-create
	STATUS	current
	DESCRIPTION
		"The Filter Index of the NSAP Address Filter used to
		 filter incoming calls.  If this variable is set to
		 zero, all incoming calls on this UNI will be
		 accepted."
	::= { q2931AdminEntry 46 }

q2931AdminOutgoingNSAPFilterIndex	OBJECT-TYPE
	SYNTAX	Integer32
	MAX-ACCESS	read-create
	STATUS	current
	DESCRIPTION
		"The Filter Index of the NSAP Address Filter used to
		 filter outgoing calls.  If this variable is set to
		 zero, all incoming calls on this UNI will be
		 accepted."
	::= { q2931AdminEntry 47 }

q2931AdminIEFilter           OBJECT-TYPE
	SYNTAX  Integer32
	MAX-ACCESS  read-create
	STATUS  current
	DESCRIPTION
		"The set of Information Element Filtering interface options
		 as follows:
		(The bits in this integer have the following meanings:)

		Bit             Significance                    Default
		========        =============                   ========
		0x0001          IE Filtering enabled            disabled
		0x0002          InsertCallingPDefaultAddress    disabled
		0x0004          CallingP_delivery               enabled
		0x0008          CallingPSubAddr_trxf            enabled
		0x0010          CalledPSubAddr_trxf             enabled
		0x0020          BHLI_trxf                       enabled
		0x0040          BLLI_trxf                       enabled
		0x0080          BLLI_selection_trxf             enabled
		0x0100          AAL_Info_trxf                   enabled
		---             not used presently              ----

		The valid combinations of bits 0x40 (BLLI_TRXF) and
		0x80 (BLLI_selection_TRXF) are:

		0xc0 (1 1)      transfer all BLLIs              default
		0x80 (1 0)      **invalid**
		0x40 (0 1)      transfer only the first BLLI
		0x00 (0 0)      remove all BLLIs
		"
	::= { q2931AdminEntry 48 }

q2931SendCallProc OBJECT-TYPE
	SYNTAX	INTEGER {
			on(1),
			off(2)
		}
	MAX-ACCESS	read-create
	STATUS	deprecated
	DESCRIPTION
		"A flag which allows the user to specify at creation
		time if CALL PROCEEDING should be sent on this
		particular interface. If set to on(1), a CALL
		PROCEEDING message is sent out that interface for
		every SETUP received on that interface that is
		successfully forwarded. If set to off(2), no CALL
		PROCEEDING messages are sent on this interface."
	DEFVAL { on }
	::= { q2931AdminEntry 49 }

-- Vector switch MIB variable.
-- q2931LogMessage OBJECT-TYPE
--        SYNTAX  INTEGER {
--               on(1),
--               off(2)
--        }
--        ACCESS  read-write
--        STATUS  mandatory
--        DESCRIPTION
--                "To enable or disable the Logging of q2931 Messages
--                 when a call is rejected"
--        DEFVAL { off }
--        ::= { q2931AdminEntry 50 }

q2931VCIRangeStatus OBJECT-TYPE
	SYNTAX INTEGER {
			valid(1),
			invalid(2)
	       }
	MAX-ACCESS read-only
	STATUS current
	DESCRIPTION
		"A flag which indicates the status of Min/MaxVCI range
		 with respect to whether or not the range values are assigned
		 after negotiating with the peer through ILMI process.
		 This variable is set to valid if ILMI is up and range
		 negotiation with the peer is completed, except if a UNI
		 (link) is configured as IISP or ILMI-down, then
		 the value of this MIB value is always set to valid."
	::= { q2931AdminEntry 51 }

q2931ClearOnCarrierLoss OBJECT-TYPE
	SYNTAX INTEGER {
			noClear(1),
			clearCalls(2)
		}
	MAX-ACCESS read-create
	STATUS obsolete
	DESCRIPTION
		"This object indicates whether to clear calls when
		carrier is lost on the link associated with this
		signalling channel. The default value is noClear(1).
		This follows the ATM Forum specification which requires
		the specific signalling timers to expire before clearing
		the connections. Setting this value to clearCalls(2)
		will result in the connections being torn down as soon
		as carrier loss is detected (not compliant with ATM
		Forum signalling specifications)."
	DEFVAL { noClear }
	::= { q2931AdminEntry 52 }

q2931QosClassExpansionKey OBJECT-TYPE
	SYNTAX  Integer32
	MAX-ACCESS  read-create
	STATUS  current
	DESCRIPTION
		"The key for the QOS Class Expansion Table to be used for
		 this UNI."
	::= { q2931AdminEntry 54 }

q2931AtmrConfDomainID  OBJECT-TYPE
	SYNTAX  Integer32
	MAX-ACCESS  read-create
	STATUS  current
	DESCRIPTION
		"This is the ID of the routing domain to which this interface
		belongs if this uni is operating as a private UNI, public UNI
		or IISP"
	::= { q2931AdminEntry 55 }

q2931AtmrPnniNodeIndex  OBJECT-TYPE
	SYNTAX  Integer32
	MAX-ACCESS  read-only
	STATUS  current
	DESCRIPTION
		"This is the index of the node to which this interface
		attaches for FT-PNNI and PNNI interfaces. The value is
		always 0xffff for FT-PNNI interfaces."
	::= { q2931AdminEntry 56 }

q2931AdminOperSigMode OBJECT-TYPE
	SYNTAX	INTEGER {
			vpAssoc(1),
			nonAssoc(2)
		}
	MAX-ACCESS	read-only
	STATUS	current
	DESCRIPTION
		"The operating mode for signalling: VP-associated or
		Non-associated. vpAssoc(1) stands for VP-associated
		signalling, if set to this value, the uni encodes the
		conn_id with the VP-associated signalling bits. nonAssoc(2)
		stands for Non-associated signalling, if set to this value,
		the uni encodes the conn_id with Non-associated signalling
		bits."
	::= { q2931AdminEntry 57 }

q2931AdminOperSigAlloc OBJECT-TYPE
	SYNTAX	INTEGER {
			allocVP(1),
			allocLink(2),
			allocVpBundle(4),
			allocProxy(5)
		}
	MAX-ACCESS	read-only
	STATUS	current
	DESCRIPTION
		"The operating allocation policy for a network side uni. If
		set to allocVP, the network side uni will allocate connections
		in its containing VP only. If set to allocLink, the uni will
		allocate connections in its containing VP and may allocate
		connections in other VPS that are available to it. If set
		to allocVpBundle, the uni will allocate connections in its
		containing VP and a bundle of other VPs which are pre-created."
	::= { q2931AdminEntry 58 }

-- Vector switch MIB variable
-- q2931AdminTrafficType OBJECT-TYPE
--        SYNTAX  INTEGER {
--                cbr(1),
--                vbr(2),
--                ubr(3),
--                mixed(4)
--        }
--        ACCESS   read-write
--        STATUS  mandatory
--        DESCRIPTION
--                "This mib definition is strictly for Traffic Class Routing
--                 feature. It is the type of traffic that a particular VP
--                 can support. cbr, vbr, and ubr means the created VPs can
--                 only support cbr, vbr, and ubr traffic type respectively.
--                 mixed means that the particular VP can support all
--                 traffic types."
--        DEFVAL { 4 }
--        ::= { q2931AdminEntry 59}

q2931OutputSigUpc OBJECT-TYPE
	SYNTAX Integer32
	MAX-ACCESS read-create
	STATUS current
	DESCRIPTION
		"Traffic contract to be applied to the output side of
		the signalling channel. If this is not specified,
		signalling will be put in the vbr queue with no
		bandwidth reservation and no policing."
	::= { q2931AdminEntry 60}


q2931AdminPlanType      OBJECT-TYPE
	SYNTAX  INTEGER {
			 unknown (1),
			 international(2),
			 national(3),
			 subscriber(4)
		 }
	MAX-ACCESS read-create
	STATUS current
	DESCRIPTION
		"This is the plan type to be used in calling party number
		 and called party number IEs in the signalling messages.
		 The value of this variable is dependent on whether
		 q2931AdminUseNativeE164 is set to enable or disable.
		 Further, q2931AdminPlanType can be set in conjunction with
		 q2931AdminUseNativeE164. When q2931AdminUseNativeE164 is
		 set to disable, q2931AdminPlanType takes a default value
		 of 1(unknown). All other values are invalid. When
		 q2931AdminUseNativeE164 is set to enable, q2931AdminPlanType
		 takes a default value of 2(international). Other valid
		 values are 3(national) and 4(subscriber)."
	::= { q2931AdminEntry 61 }

q2931AdminMaxVPI OBJECT-TYPE
	SYNTAX	INTEGER (0..4096)
	MAX-ACCESS	read-create
	STATUS	current
	DESCRIPTION
		"The maximum configured VPI (Virtual Path Identifier)
		 that is used for SVPs (Signalling Virtual Paths) when
		 this interface sets up SVP Connections and also the
		 Max VPI that is used to create dynamic paths for
		 SVCs (Signalling Virtual Circuit) connections."
	::= { q2931AdminEntry 62 }

q2931MaxSvccVPI OBJECT-TYPE
	SYNTAX	INTEGER (0..4096)
	MAX-ACCESS	read-only
	STATUS	current
	DESCRIPTION
		"The maximum actual VPI (Virtual Path Identifier)
		 that will be used for SVCs (Signalling Virtual
		 Circuit) dynamic paths. This variable denotes the
		 operating value for the maximum VPI value that
		 can be used for setting up dynamic path SVPS.
		 The operating value can differ from the
		 configured value (q2931AdminMaxVPI) as the operating
		 value depends on the outcome of possible ILMI based
		 VPI range negotiation procedure."
	::= { q2931AdminEntry 63 }
q2931LastChangeTime OBJECT-TYPE
	SYNTAX  TimeStamp
	MAX-ACCESS  read-only
	STATUS  current
	DESCRIPTION
		"The time the Signalling entity
		was created in hundredths of a second."
	::= { q2931AdminEntry 64 }

q2931MaxSvpcVPI OBJECT-TYPE
	SYNTAX	INTEGER (0..4096)
	MAX-ACCESS	read-only
	STATUS	current
	DESCRIPTION
		"The maximum actual VPI (Virtual Path Identifier)
		 that will be used for SVPs (Signalling Virtual
		 Paths). This variable denotes the operating
		 value for the maximum VPI value that
		 can be used for setting up dynamic path SVPS.
		 The operating value can differ from the
		 configured value (q2931AdminMaxVPI) as the operating
		 value depends on the outcome of possible ILMI based
		 VPI range negotiation procedure."
	::= { q2931AdminEntry 67 }

q2931VpCapability OBJECT-TYPE
	SYNTAX  INTEGER {
			 undefined (1),
			 vpCapable(2),
			 notVpCapable(3)
		 }
	MAX-ACCESS	read-only
	STATUS	current
	DESCRIPTION
		"This mib variable is used to determine if this
		 interface is capable of supporting Switched VPs.
		 For UNI3.x and VP Scope Signalling Interfaces,
		 SVPs (Switch Virtual Paths) cannot be created and hence
		 undefined(1). For UNI40 & PNNI Link Scope interfaces,
		 if there is a non-zero VPI range intersection with
		 the peer, the interface is vpCapable(2), else
		 notVpCapable(3)"
	::= { q2931AdminEntry 68 }


q2931NNIProto OBJECT-TYPE
	SYNTAX INTEGER {
		       none(1),
		       ftpnni(2),
		       forum-pnni(3),
		       iisp(4)
	       }
	MAX-ACCESS read-only
	STATUS current
	DESCRIPTION
		"The NNI protocol being run on this link"
	::= { q2931AdminEntry 66 }

q2931AcceleratedClear OBJECT-TYPE
	SYNTAX INTEGER {
			disable(1),
			enable(2)
		}
	MAX-ACCESS read-create
	STATUS current
	DESCRIPTION
		"This object indicates whether to clear calls when
		 carrier is lost on the link associated with this
		signalling channel or the Virtual Path goes down.
	  The default value is noClear(1).
		This follows the ATM Forum specification which requires
		the specific signalling timers to expire before clearing
		the connections. Setting this value to clearCalls(2)
		will result in the connections being torn down as soon
		as carrier loss/VP failure is detected (not compliant with ATM
		Forum signalling specifications)."
	DEFVAL { disable }
	::= { q2931AdminEntry 70 }

q2931VpciGroupIndex OBJECT-TYPE
	SYNTAX INTEGER (1..99999)
	MAX-ACCESS read-create
	STATUS current
	DESCRIPTION
		"The index into the VPCI Mapping Group Table to use
		for this signalling interface."
	::= { q2931AdminEntry 69 }

q2931ProxyDirGroupIndex OBJECT-TYPE
        SYNTAX INTEGER (1..99999)
        MAX-ACCESS read-create
        STATUS current
        DESCRIPTION
                "The index into the proxy address group table to use
                for this signalling interface."
        ::= { q2931AdminEntry 87 }

q2931SupplementaryServicesStatus   OBJECT-TYPE
	SYNTAX INTEGER {
	       enable(1),
	       disable(2),
	       undefined(3) --- readonly value
	}
	MAX-ACCESS        read-create
	STATUS        current
	DESCRIPTION
	    "This MIB variable is used to enable or disable all the
	     supplementary services features for this interface. This
	     acts as a global switch for this interface to disable or
	     enable all of the supplementary services. The MIB
	     variables defined for all supplementary services will be
	     used only when this is enabled. The supplementary
	     services is disabled by default. The value of
	     undefined(3) is a read-only value used for interfaces
	     where supplementary services are not applicable."
	DEFVAL { disable }
	::= { q2931AdminEntry 71 }

q2931CallingPAddressPresentation   OBJECT-TYPE
	SYNTAX INTEGER {
	       enable(1),
	       disable(2),
	       undefined(3) -- readonly value
	}
	MAX-ACCESS        read-create
	STATUS        current
	DESCRIPTION
		"The Calling party address presentation can be set to
		one of the two values as described above. The CLIP MIB
		variable is used when this interface is acting as a
		called party for a call setup message. When set to
		enable(1), while a call setup  message is forwarded
		through this interface, the calling party number is
		provided. When set to disable(2), the calling party
		number is not provided in the call setup message.
		The value of undefined(3) is a read-only value used
		for interfaces where supplementary services are not
		applicable."
	    DEFVAL { disable }
	::= { q2931AdminEntry 72 }

q2931CallingPAddressRestriction   OBJECT-TYPE
	SYNTAX INTEGER {
	      enable(1),
	      disable(2),
	      undefined(3) --- readonly value
	}
	MAX-ACCESS        read-create
	STATUS        current
	DESCRIPTION
		"The Calling party address restriction can be set to
		one of the two values as described above. The CLIR MIB
		variable is used when this interface is acting as a
		calling party for a call setup message. When set to
		enable(1), while a call setup mes-sage is received
		from this interface and forwarded out, the calling
		party number is not provided to called user. When set
		to disable(2), the calling party number is provided to
		the called user.
		The value of undefined(3) is a read-only value used
		for interfaces where supplementary services are not
		applicable."
	DEFVAL { disable }
	::= { q2931AdminEntry 73 }

q2931ConnectedPAddressPresentation   OBJECT-TYPE
	SYNTAX INTEGER {
	       enable(1),
	       disable(2),
	       undefined(3) --- readonly value
	}
	MAX-ACCESS        read-create
	STATUS        current
	DESCRIPTION
		"The Connected party address presentation can be set
		to one of the two values as described above. The COLP
		MIB variable is used when the interface is acting as a
		calling party to a call setup message. When set to
		enable(1), while a call establish-ment response
		message is forwarded through this interface, the connected party
		number is provided to the calling user. When set to
		disable(2), while a call establishment response
		message is forwarded through this interface, the
		connected party number is not provided to the calling
		user.
		The value of undefined(3) is a read-only value used
		for interfaces where supplementary services are not
		applicable."
       DEFVAL { disable }
       ::= { q2931AdminEntry 74 }

q2931ConnectedPAddressRestriction   OBJECT-TYPE
	SYNTAX INTEGER {
	       enable(1),
	       disable(2),
	       undefined(3) --- readonly value
	}
	MAX-ACCESS        read-create
	STATUS        current
	DESCRIPTION
		"The Connected party address restriction can be set to
		one of the two values as described above. The COLR MIB
		variable is used when the interface is acting as a
		called party to a call setup message. When set to
		enable(1), while a call establishment response message
		is forwarded from this interface, the connected party
		number is not provided to the calling user. When set
		to disable(2),while a call establishment response
		message is forwarded from this interface, the
		connected party number is provided to the calling
		user.
		The value of undefined(3) is a read-only value used
		for interfaces where supplementary services are not
		applicable."
       DEFVAL { disable }
       ::= { q2931AdminEntry 75 }

q2931ConnectedPDefaultAddress     OBJECT-TYPE
       SYNTAX        NsapAddr
       MAX-ACCESS        read-create
       STATUS        current
       DESCRIPTION
		"The connected party address to be used in Connection
		Acceptance (connect, add party ack etc.) messages that
		do not contain Connected Party Addresses."
	   ::= { q2931AdminEntry 76 }

q2931SubaddressingAdminStatus     OBJECT-TYPE
       SYNTAX  INTEGER {
		 enable(1),
		 disable(2),
		 undefined(3) --- readonly value
       }
       MAX-ACCESS        read-create
       STATUS        current
       DESCRIPTION
		"This is used to enable or disable the sub-addressing
		capability. If this is set to enable(1), the called
		party sub-address IE is passed along. Ifthis is set to
		disbale(2), this IE is removed while forwarding the
		messages.
		The value of undefined(3) is a read-only value used
		for interfaces where supplementary services are not
		applicable."
       DEFVAL { disable }
	  ::= { q2931AdminEntry 77 }

q2931UserUserSignallingAdminStatus     OBJECT-TYPE
       SYNTAX  INTEGER {
	       enable(1),
	       disable(2),
	       undefined(3) --- readonly value
       }
       MAX-ACCESS        read-create
       STATUS        current
       DESCRIPTION
		"This is used to enable or disable the User to User
		Signalling capability. If this is set to enable(1),
		the UUS IE is passed along. If this is set to
		disbale(2), this IE is removed while forwarding the
		messages.
		The value of undefined(3) is a read-only value used
		for interfaces where supplementary services are not
		applicable."
       DEFVAL { disable }
	  ::= { q2931AdminEntry 78 }

q2931OutputIlmiUpc OBJECT-TYPE
	SYNTAX 	     Integer32 
	MAX-ACCESS   read-create
	STATUS       current
        DESCRIPTION
                "The index into the UPC table for the ILMI channel"
        ::= {q2931AdminEntry 79 }

q2931OutputRccUpc OBJECT-TYPE
        SYNTAX       Integer32 
        MAX-ACCESS   read-create
        STATUS       current
        DESCRIPTION
                "The index into the UPC table for the RCC channel"
        ::= {q2931AdminEntry 80 }

q2931PnniRccVci	OBJECT-TYPE
       SYNTAX  Integer32 
       MAX-ACCESS   read-create
       STATUS       current
       DESCRIPTION
		" This is used to specify the PVC RCC VCI used by PNNI.
		  Normally this will always be 18, but if a user creates
		  a VPT with a VCI range that does not contain 18, then this
		  field is used to specify the PNNI PVC RCC VCI."
	DEFVAL {18}
	  ::= { q2931AdminEntry 81 }

q2931AdminubrCalls           OBJECT-TYPE
        SYNTAX  INTEGER {
                  on(1),
                  off(2)
                }
        MAX-ACCESS  read-create
        STATUS  current
        DESCRIPTION
                " This flag is used to disable processing of UBR calls."
        DEFVAL {on}
        ::= { q2931AdminEntry 82 }

q2931AdmincbrCalls           OBJECT-TYPE
        SYNTAX  INTEGER {
                  on(1),
                  off(2)
                }
        MAX-ACCESS  read-create
        STATUS  current
        DESCRIPTION
                " This flag is used to disable processing of CBR calls."
        DEFVAL {on}
        ::= { q2931AdminEntry 83 }

q2931AdminabrCalls           OBJECT-TYPE
        SYNTAX  INTEGER {
                  on(1),
                  off(2)
                }
        MAX-ACCESS  read-create
        STATUS  current
        DESCRIPTION
                " This flag is used to disable processing of ABR calls."
        DEFVAL {on}
        ::= { q2931AdminEntry 84 }

q2931AdminrtvbrCalls           OBJECT-TYPE
        SYNTAX  INTEGER {
                  on(1),
                  off(2)
                }
        MAX-ACCESS  read-create
        STATUS  current
        DESCRIPTION
                " This flag is used to disable processing of RT-VBR calls."
        DEFVAL {on}
        ::= { q2931AdminEntry 85 }

q2931AdminnrtvbrCalls           OBJECT-TYPE
        SYNTAX  INTEGER {
                  on(1),
                  off(2)
                }
        MAX-ACCESS  read-create
        STATUS  current
        DESCRIPTION
                " This flag is used to disable processing of NRT-VBR calls."
        DEFVAL {on}
        ::= { q2931AdminEntry 86 }
------------------------------------------------------------------------


q2931StatsTable OBJECT-TYPE
	SYNTAX	SEQUENCE OF Q2931StatsEntry
	MAX-ACCESS	not-accessible
	STATUS	current
	DESCRIPTION
		"A table of statistics about the Q2931 signaling path."
	::= { q2931LayerGroup 2 }

q2931StatsEntry OBJECT-TYPE
	SYNTAX	Q2931StatsEntry
	MAX-ACCESS	not-accessible
	STATUS	current
	DESCRIPTION
		"A table entry containing signaling path statistics,
		indexed by port and path."
	INDEX	{ q2931StatsPort, q2931StatsVPI }
	::= { q2931StatsTable 1 }

Q2931StatsEntry ::= SEQUENCE {
	q2931StatsPort		        Integer32,
	q2931StatsVPI			Integer32,
	q2931VCCs			Gauge32,
	q2931Restarts			Counter32,
	q2931CallsCompletions		Counter32,
	q2931CallsFailures		Counter32,
	q2931CallsRejections		Counter32,
	q2931TransmittedMessages	Counter32,
	q2931ReceivedMessages		Counter32
}

q2931StatsPort OBJECT-TYPE
	SYNTAX	Integer32
	MAX-ACCESS	read-only
	STATUS	current
	DESCRIPTION
		"The value of this object identifies the port
		of this signalling path, and is the same as
		q2931Port."
	::= { q2931StatsEntry 1 }

q2931StatsVPI OBJECT-TYPE
	SYNTAX	Integer32
	MAX-ACCESS	read-only
	STATUS	current
	DESCRIPTION
		"The value of this object identifies the VPI (Virtual
		Path Identifier) of this signaling path statistics entry,
		and is the same as q2931VPI."
	::= { q2931StatsEntry 2 }

q2931VCCs OBJECT-TYPE
	SYNTAX	Gauge32
	MAX-ACCESS	read-only
	STATUS	current
	DESCRIPTION
		"The number of Virtual Channel Connections (VCCs) on this
		signaling path."
	::= { q2931StatsEntry 3 }

q2931Restarts OBJECT-TYPE
	SYNTAX	Counter32
	MAX-ACCESS	read-only
	STATUS	current
	DESCRIPTION
		"The number of times the switch has lost and regained
		contact with the remote signaling entity on this path."
	::= { q2931StatsEntry 4 }

q2931CallsCompletions OBJECT-TYPE
	SYNTAX	Counter32
	MAX-ACCESS	read-only
	STATUS	current
	DESCRIPTION
		"The number of successfully completed calls on this
		signaling path."
	::= { q2931StatsEntry 5 }

q2931CallsFailures OBJECT-TYPE
	SYNTAX	Counter32
	MAX-ACCESS	read-only
	STATUS	current
	DESCRIPTION
		"The number of call failures on this signaling path."
	::= { q2931StatsEntry 6 }

q2931CallsRejections OBJECT-TYPE
	SYNTAX	Counter32
	MAX-ACCESS	read-only
	STATUS	current
	DESCRIPTION
		"The number of connections on this signaling path that were
		rejected by the far end."
	::= { q2931StatsEntry 7 }

q2931TransmittedMessages OBJECT-TYPE
	SYNTAX	Counter32
	MAX-ACCESS	read-only
	STATUS	current
	DESCRIPTION
		"The total number of Q2931 messages that have been transmitted
		over this signalling path."
	::= { q2931StatsEntry 8 }

q2931ReceivedMessages OBJECT-TYPE
	SYNTAX	Counter32
	MAX-ACCESS	read-only
	STATUS	current
	DESCRIPTION
		"The total number of Q2931 messages that have been received on
		this signalling path."
	::= { q2931StatsEntry 9 }

------------------------------------------------------------------------
--
-- Native E164 Address Resolution
--

q2931PublicGroup	OBJECT IDENTIFIER ::=  { q2931Group 6 }

q2931E164AddrResTable OBJECT-TYPE
	SYNTAX  SEQUENCE OF Q2931E164AddrResEntry
	MAX-ACCESS	not-accessible
	STATUS	current
	DESCRIPTION
		"A table of E164 Address Resolution entries."
	::= { q2931PublicGroup 1 }

q2931E164AddrResEntry OBJECT-TYPE
	SYNTAX	Q2931E164AddrResEntry
	MAX-ACCESS	not-accessible
	STATUS	current
	DESCRIPTION
		"A table entry containing E164 Address Resolution
		information, indexed by Nsap."
	INDEX	{ q2931E164Port, q2931E164VPI,
		  q2931E164Nsap, q2931E164NsapMask }
	::= { q2931E164AddrResTable 1 }

Q2931E164AddrResEntry ::= SEQUENCE {
	q2931E164Port		Integer32,
	q2931E164VPI		Integer32,
	q2931E164Nsap		NsapAddr,
	q2931E164NsapMask	Integer32,
	q2931E164Address	E164Address,
	q2931E164AddrResStatus	EntryStatus
}

q2931E164Port	OBJECT-TYPE
	SYNTAX	Integer32
	MAX-ACCESS	read-only
	STATUS	current
	DESCRIPTION
			""
	::= { q2931E164AddrResEntry 1 }

q2931E164VPI	OBJECT-TYPE
	SYNTAX	Integer32
	MAX-ACCESS	read-only
	STATUS	current
	DESCRIPTION
			""
	::= { q2931E164AddrResEntry 2 }
q2931E164Nsap	OBJECT-TYPE
	SYNTAX	NsapAddr
	MAX-ACCESS	read-only
	STATUS	current
	DESCRIPTION
			""
	::= { q2931E164AddrResEntry 3 }

q2931E164NsapMask	OBJECT-TYPE
	SYNTAX	Integer32
	MAX-ACCESS	read-only
	STATUS	current
	DESCRIPTION
			""
	::= { q2931E164AddrResEntry 4 }

q2931E164Address	OBJECT-TYPE
	SYNTAX	E164Address
	MAX-ACCESS	read-create
	STATUS	current
	DESCRIPTION
			""
	::= { q2931E164AddrResEntry 5 }

q2931E164AddrResStatus	OBJECT-TYPE
	SYNTAX	EntryStatus
	MAX-ACCESS	read-create
	STATUS	current
	DESCRIPTION
			""
	::= { q2931E164AddrResEntry 6 }

------------------------------------------------------------------------


--
-- q2931 Calling Party Address Validation.
--
--
--	A per-UNI 3.x table of "valid" addresses, expected to be
--	used on the Network Side of a Public UNI connection
--	to filter incoming calls.
--
-- This group has been made obsolete with the introduction of
-- the q2931AddressFilterGroup.
--
--
--q2931AddrValidationGroup OBJECT IDENTIFIER ::= { q2931LayerGroup 3 }
--
--
-- The following single-instance variables are necessary to
-- support trap generation when too many CPN address validation
-- failures have occurred.
--
--
--q2931AVRejectTrapThreshold	OBJECT-TYPE
--	SYNTAX	INTEGER
--	ACCESS	read-write
--	STATUS	mandatory
--	DESCRIPTION
--		"Maximum number of CPN Rejections before a CPN REJECT
--		trap is generated."
--	::= { q2931AddrValidationGroup 1 }
--
--q2931AVRejectTrapPeriod	OBJECT-TYPE
--	SYNTAX	TimeTicks
--	ACCESS	read-write
--	STATUS	mandatory
--	DESCRIPTION
--		"Used in conjuction with above counter:  a cpnRejectTrap
--		will be generated for any UNI if address validation
--		is enabled and more than cpnRejectTrapThreshold rejects
--		occur in any given cpnRejectTrapPeriod."
--	::= { q2931AddrValidationGroup 2 }
--
--q2931AVTable OBJECT-TYPE
--	SYNTAX	SEQUENCE OF Q2931AVTableEntry
--	ACCESS	not-accessible
--	STATUS	mandatory
--	DESCRIPTION
--		"A table of allowable(rejectable) CPN addresses for
--		 a given UNI ."
--	::= { q2931AddrValidationGroup 3 }
--
--q2931AVTableEntry OBJECT-TYPE
--	SYNTAX	Q2931AVTableEntry
--	ACCESS	not-accessible
--	STATUS	mandatory
--	DESCRIPTION
--		"A table entry containing CPN address validation info."
--	INDEX	{ q2931AVTablePort, q2931AVTableVPI, q2931AVTableNsap,
--		  q2931AVTableNsapMask }
--	::= { q2931AVTable 1 }
--
--Q2931AVTableEntry ::= SEQUENCE {
--	q2931AVTablePort		INTEGER,
--	q2931AVTableVPI		INTEGER,
--	q2931AVTableNsap		NsapAddr,
--	q2931AVTableNsapMask		INTEGER,
--	q2931AVTableStatus		INTEGER,
--	q2931AVTableAction		INTEGER
--}
--
--q2931AVTablePort OBJECT-TYPE
--	SYNTAX	INTEGER
--	ACCESS	read-only
--	STATUS	mandatory
--	DESCRIPTION
--		"The value of this object identifies the port
--		of this signalling path, and is the same as the
--		portNumber."
--	::= { q2931AVTableEntry 1 }
--
--q2931AVTableVPI OBJECT-TYPE
--	SYNTAX	INTEGER
--	ACCESS	read-only
--	STATUS	mandatory
--	DESCRIPTION
--		"The VPI (Virtual Path Identifier) of this signaling path."
--	::= { q2931AVTableEntry 2 }
--
--q2931AVTableNsap OBJECT-TYPE
--	SYNTAX	NsapAddr
--	ACCESS	read-write
--	STATUS	mandatory
--	DESCRIPTION
--		"The NSAP address filtered by this table entry."
--	::= { q2931AVTableEntry 3 }
--
--q2931AVTableNsapMask	OBJECT-TYPE
--	SYNTAX	INTEGER
--	ACCESS	read-write
--	STATUS	mandatory
--	DESCRIPTION
--		"The mask applied to CPN address in order to compare against
--		the above q2931AVTableNsap."
--	::= { q2931AVTableEntry 4 }
--
--q2931AVTableStatus OBJECT-TYPE
--	SYNTAX	EntryStatus
--	ACCESS	read-write
--	STATUS	mandatory
--	DESCRIPTION
--		"The status of this table entry."
--	::= { q2931AVTableEntry 5 }
--
--q2931AVTableAction	OBJECT-TYPE
--	SYNTAX	INTEGER {
--		accept(1),
--		reject(2)
--		}
--	ACCESS	read-write
--	STATUS	mandatory
--	DESCRIPTION
--		"What to do with CPN's that match this entry."
--	::= { q2931AVTableEntry 6 }
--
--------------------------------
-- Address Validation Statistics
--
--q2931AVStatsTable OBJECT-TYPE
--	SYNTAX	SEQUENCE OF Q2931AVStatsEntry
--	ACCESS	not-accessible
--	STATUS	mandatory
--	DESCRIPTION
--		"A table of address validation statistics for a given
--		Q2931 signaling path."
--	::= { q2931AddrValidationGroup 4 }
--
--q2931AVStatsEntry OBJECT-TYPE
--	SYNTAX	Q2931AVStatsEntry
--	ACCESS	not-accessible
--	STATUS	mandatory
--	DESCRIPTION
--		"A table entry containing address validation statistics,
--		indexed by port and path."
--	INDEX	{ q2931AVStatsPort, q2931AVStatsVPI }
--	::= { q2931AVStatsTable 1 }
--
--Q2931AVStatsEntry ::= SEQUENCE {
--	q2931AVStatsPort		INTEGER,
--	q2931AVStatsVPI			INTEGER,
--	q2931AVAcceptCount		Counter,
--	q2931AVRejectKnownCount		Counter,
--	q2931AVRejectUnknownCount	Counter,
--	q2931AVCurrentRejectUnknownCount Counter
--}
--
--q2931AVStatsPort OBJECT-TYPE
--	SYNTAX	INTEGER
--	ACCESS	read-only
--	STATUS	mandatory
--	DESCRIPTION
--		"The value of this object identifies the port
--		of this signalling path, and is the same as
--		q2931Port."
--	::= { q2931AVStatsEntry 1 }
--
--q2931AVStatsVPI OBJECT-TYPE
--	SYNTAX	INTEGER
--	ACCESS	read-only
--	STATUS	mandatory
--	DESCRIPTION
--		"The value of this object identifies the VPI (Virtual
--		Path Identifier) of this signaling path statistics entry,
--		and is the same as q2931VPI."
--	::= { q2931AVStatsEntry 2 }
--
--q2931AVAcceptCount OBJECT-TYPE
--	SYNTAX	Counter
--	ACCESS	read-only
--	STATUS	mandatory
--	DESCRIPTION
--		"The total number of Q2931 messages that have been accepted
--		by Address Validation on this UNI."
--	::= { q2931AVStatsEntry 3 }
--
--q2931AVRejectKnownCount OBJECT-TYPE
--	SYNTAX	Counter
--	ACCESS	read-only
--	STATUS	mandatory
--	DESCRIPTION
--		"The total number of Q2931 messages that have been rejected
--		because the supplied address matched a rule in the address
--		validation table where the action was to reject the call."
--	::= { q2931AVStatsEntry 4 }
--
--q2931AVRejectUnknownCount OBJECT-TYPE
--	SYNTAX	Counter
--	ACCESS	read-only
--	STATUS	mandatory
--	DESCRIPTION
--		"The total number of Q2931 messages that have been rejected
--		because the supplied address matched no rule in the address
--		validation table."
--	::= { q2931AVStatsEntry 5 }
--
--q2931AVCurrentRejectUnknownCount OBJECT-TYPE
--	SYNTAX	Counter
--	ACCESS	read-only
--	STATUS	mandatory
--	DESCRIPTION
--		"The number of Q2931 messages that have been rejected
--		because the supplied address matched no rule in the address
--		validation table since the last Address validation
--		trap was generated."
--	::= { q2931AVStatsEntry 6 }

------------------------------------------------------------------------
--
--
-- q2931 NSAP PING Call table
--
--
--      A table of called addresses, call parameters ,
--      expected to be used to make a test call to test
--      the reachability of NSAP addresses.
--

q2931NSAPPingGroup OBJECT IDENTIFIER ::= { q2931LayerGroup 7 }


q2931NPCallTable OBJECT-TYPE
	SYNTAX  SEQUENCE OF Q2931NPCallEntry
	MAX-ACCESS  not-accessible
	STATUS  current
	DESCRIPTION
		"A table of NSAP addressed and call parameters to be used
		 in testing the reachability of destination addresses."
	::= { q2931NSAPPingGroup 1 }

q2931NPCallEntry OBJECT-TYPE
	SYNTAX  Q2931NPCallEntry
	MAX-ACCESS  not-accessible
	STATUS  current
	DESCRIPTION
		"A table entry containing NSAP address, call parameter
		 information."
	INDEX   { q2931NPCallIndex }
	::= { q2931NPCallTable 1 }

Q2931NPCallEntry ::= SEQUENCE {
	q2931NPCallIndex                Integer32,
	q2931NPCallDstNsap              NsapAddr,
	q2931NPCallState                INTEGER,
	q2931NPCallClientType           INTEGER,
	q2931NPCallFwdUpcKey            Integer32,
	q2931NPCallBckUpcKey            Integer32,
	q2931NPCallCallingDomain        Integer32,
	q2931NPCallQosIndex             Integer32,
	q2931NPCallQosClassFwd          INTEGER,
	q2931NPCallQosClassBwd          INTEGER,
	q2931NPCallBearerClass          INTEGER,
	q2931NPCallVerbose              INTEGER,
	q2931NPCallCauseCode            Integer32,
	q2931NPPingState                INTEGER,
	q2931NPPingPktCount             Integer32,
	q2931NPPingStatsPktsSent        Integer32,
	q2931NPPingStatsPktsReceived    Integer32,
	q2931NPPingStatsAverageDelay    Integer32,
	q2931NPPingStatsMinimumDelay    Integer32,
	q2931NPPingStatsMaximumDelay    Integer32,
	q2931NPMeasureRoundTripDelay    INTEGER,
	q2931NPCallStatus               RowStatus
}

q2931NPCallIndex                OBJECT-TYPE
	SYNTAX  Integer32
	MAX-ACCESS  not-accessible
	STATUS  current
	DESCRIPTION
		"The value of this object identifies an entry in the
		 q2931NPCallTable."
	::= { q2931NPCallEntry 1 }

q2931NPCallDstNsap              OBJECT-TYPE
	SYNTAX  NsapAddr
	MAX-ACCESS  read-write
	STATUS  current
	DESCRIPTION
		"The Destination NSAP address used by this table
		 entry."
	::= { q2931NPCallEntry 2 }

q2931NPCallState           OBJECT-TYPE
	SYNTAX  INTEGER {
		down(1),
		inprogress(2),
		up(3),
		err(4),
		locpref(5),
		lochost(6)
		}
	MAX-ACCESS  read-write
	STATUS  current
	DESCRIPTION
		"This field keeps the state of the nsap call. This
		 field is set to inprogress by default. 
		 'up' means call was successful,
		 'down' means call was rejected by the destination,
		 'err' means call was not attempted primarily because no route
		 to destination was available,
		 'locpref', 'lochost' mean that the address is local"

	::= { q2931NPCallEntry 3 }

q2931NPCallClientType           OBJECT-TYPE
	SYNTAX  INTEGER {
		noIndication(1),
		lecs(2),
		lec(3),
		bus(4),
		les(5)
		}
	MAX-ACCESS  read-write
	STATUS  current
	DESCRIPTION
		 "Holds the type of the client expected to answer the call
		  at destination.  Set to noIndication by default."
	::= { q2931NPCallEntry 4 }

q2931NPCallFwdUpcKey            OBJECT-TYPE
	SYNTAX  Integer32
	MAX-ACCESS  read-write
	STATUS  current
	DESCRIPTION
		"UPC table entry to be used in the forward direction
		 of the call is stored here. Set to ZERO by default."
	::= { q2931NPCallEntry 6 }

q2931NPCallBckUpcKey            OBJECT-TYPE
	SYNTAX  Integer32
	MAX-ACCESS  read-write
	STATUS  current
	DESCRIPTION
		"UPC table entry to be used in the backward direction
		 of the call is stored here. Set to ZERO by default."
	::= { q2931NPCallEntry 7 }

q2931NPCallCallingDomain        OBJECT-TYPE
	SYNTAX  Integer32
	MAX-ACCESS  read-write
	STATUS  current
	DESCRIPTION
		"The domain at the originating switch on which the call
		 has to be routed.  By default this is set to the default
		 domain, control port domain."
	::= { q2931NPCallEntry 8 }

q2931NPCallQosIndex            OBJECT-TYPE
	SYNTAX  Integer32
	MAX-ACCESS  read-write
	STATUS  current
	DESCRIPTION
		"QOS Index entry to be used in the forward direction
		 of the call is stored here. Set to ZERO by default."
	::= { q2931NPCallEntry 9 }

q2931NPCallQosClassFwd            OBJECT-TYPE
	SYNTAX  INTEGER {
	   class0(1),
	   class1(2),
	   class2(3),
	   class3(4),
	   class4(5)
	}
	MAX-ACCESS  read-write
	STATUS  current
	DESCRIPTION
		"QOS Class for forward direction of the call.
		 Set to ZERO by default."
	::= { q2931NPCallEntry 10 }

q2931NPCallQosClassBwd            OBJECT-TYPE
	SYNTAX  INTEGER {
	   class0(1),
	   class1(2),
	   class2(3),
	   class3(4),
	   class4(5)
	}
	MAX-ACCESS  read-write
	STATUS  current
	DESCRIPTION
		"QOS Class for backward direction of the call.
		 Set to ZERO by default."
	::= { q2931NPCallEntry 11 }

q2931NPCallBearerClass         OBJECT-TYPE
	SYNTAX  INTEGER {
	   classA(1),
	   classC(2),
	   classX(3)
	}
	MAX-ACCESS  read-write
	STATUS  current
	DESCRIPTION
		"Bearer Class to be used for the NSAP Ping call.
		 Set to classX by default."
	::= { q2931NPCallEntry 12 }

q2931NPCallVerbose        OBJECT-TYPE
	SYNTAX  INTEGER {
	    on  (1),
	    off (2)
	}
	MAX-ACCESS  read-write
	STATUS  current
	DESCRIPTION
		"Holds the info, whether the call setup messages
		 have to be displayed on user console or not.
		 By default set to off."
	::= { q2931NPCallEntry 13 }

q2931NPCallStatus               OBJECT-TYPE
	SYNTAX  RowStatus
	MAX-ACCESS  read-write
	STATUS  current
	DESCRIPTION
		"The status of this table entry.  This entry may not
		 be destroyed if there are any filter entries that
		 refer to it."
	::= { q2931NPCallEntry 14 }

q2931NPPingState           OBJECT-TYPE
	SYNTAX  INTEGER {
		invalid(0),
		inprogress(1),
		complete(2)
		}
	MAX-ACCESS  read-only
	STATUS  current
	DESCRIPTION
		"This field tracks the state of the ping process. Invalid
		is the initial state, when the connection is made the state
		changes to 'inprogress' and when the ping is complete the state
		changes to 'complete'."
	::= { q2931NPCallEntry 15 }

q2931NPCallCauseCode        OBJECT-TYPE
	SYNTAX  Integer32
	MAX-ACCESS  read-only
	STATUS  current
	DESCRIPTION
		"The UNI call setup failure cause code.
		 This value is valid only if the call state is 'down'"
	::= { q2931NPCallEntry 16 }

q2931NPPingPktCount        OBJECT-TYPE
	SYNTAX  Integer32
	MAX-ACCESS  read-write
	STATUS  current
	DESCRIPTION
		"The number of ping packets used in the ping process"
	::= { q2931NPCallEntry 17 }

q2931NPPingStatsPktsSent        OBJECT-TYPE
	SYNTAX  Integer32
	MAX-ACCESS  read-only
	STATUS  current
	DESCRIPTION
		"The number of ping packets actually sent"
	::= { q2931NPCallEntry 18 }

q2931NPPingStatsPktsReceived    OBJECT-TYPE
	SYNTAX  Integer32
	MAX-ACCESS  read-only
	STATUS  current
	DESCRIPTION
		"The number of ping packets replied to by the destination "
	::= { q2931NPCallEntry 19 }

q2931NPPingStatsAverageDelay    OBJECT-TYPE
	SYNTAX  Integer32
	MAX-ACCESS  read-only
	STATUS  current
	DESCRIPTION
		"The average round trip delay expressed in milli seconds."
	::= { q2931NPCallEntry 20 }

q2931NPMeasureRoundTripDelay        OBJECT-TYPE
	SYNTAX  INTEGER {
	    on  (1),
	    off (2)
	}
	MAX-ACCESS  read-write
	STATUS  current
	DESCRIPTION
		"Holds the info, whether the ping process has to be done
		 after the connection is made, By default set to off"
	::= { q2931NPCallEntry 21 }

q2931NPPingStatsMaximumDelay    OBJECT-TYPE
	SYNTAX  Integer32
	MAX-ACCESS  read-only
	STATUS  current
	DESCRIPTION
		"The maximum round trip delay expressed in milli seconds."
	::= { q2931NPCallEntry 22 }

q2931NPPingStatsMinimumDelay    OBJECT-TYPE
	SYNTAX  Integer32
	MAX-ACCESS  read-only
	STATUS  current
	DESCRIPTION
		"The minimum round trip delay expressed in milli seconds."
	::= { q2931NPCallEntry 23 }

q2931NPCallNextIndex OBJECT-TYPE
	SYNTAX  TestAndIncr
	MAX-ACCESS  read-write
	STATUS  current
	DESCRIPTION
		"The index of the next free row in the
		 q2931NPCallTable."
	::= { q2931NSAPPingGroup 2 }

------------------------------------------------------------------------
--
-- q2931 Call Address Filtering
--
--
--	A table of combinations of calling and called addresses,
--	expected to be used on the network side of a Public
--	UNI connection to filter NSAP addresses in calls.
--

q2931AddressFilterGroup OBJECT IDENTIFIER ::= { q2931LayerGroup 6 }

q2931AFTemplateTable OBJECT-TYPE
	SYNTAX	SEQUENCE OF Q2931AFTemplateEntry
	MAX-ACCESS	not-accessible
	STATUS	current
	DESCRIPTION
		"A table of allowable (or rejectable) NSAP source and
		 destination addresses."
	::= {  q2931AddressFilterGroup 1 }

q2931AFTemplateEntry OBJECT-TYPE
	SYNTAX	Q2931AFTemplateEntry
	MAX-ACCESS	not-accessible
	STATUS	current
	DESCRIPTION
		"A table entry containing NSAP address filtering
		 information."
	INDEX	{ q2931AFTemplateIndex }
	::= { q2931AFTemplateTable 1 }

Q2931AFTemplateEntry ::= SEQUENCE {
	q2931AFTemplateIndex		Integer32,
	q2931AFTemplateSrcPort		Integer32,
	q2931AFTemplateSrcVPI		Integer32,
	q2931AFTemplateSrcNsap		NsapAddr,
	q2931AFTemplateSrcNsapMask	Integer32,
	q2931AFTemplateDstPort		Integer32,
	q2931AFTemplateDstVPI		Integer32,
	q2931AFTemplateDstNsap		NsapAddr,
	q2931AFTemplateDstNsapMask	Integer32,
	q2931AFTemplateAction		INTEGER,
	q2931AFTemplateName		OCTET STRING,
	q2931AFTemplateStatus		RowStatus
}

q2931AFTemplateIndex		OBJECT-TYPE
	SYNTAX	Integer32
	MAX-ACCESS	not-accessible
	STATUS	current
	DESCRIPTION
		"The value of this object identifies the NSAP Address
		 Filter Template to which this entry belongs."
	::= { q2931AFTemplateEntry 1 }

q2931AFTemplateSrcPort		OBJECT-TYPE
	SYNTAX	Integer32
	MAX-ACCESS	read-write
	STATUS	current
	DESCRIPTION
		"The source UNI port matched by this entry.
		 A value of -1 matches all ports."
	::= { q2931AFTemplateEntry 2 }

q2931AFTemplateSrcVPI		OBJECT-TYPE
	SYNTAX	Integer32
	MAX-ACCESS	read-write
	STATUS	current
	DESCRIPTION
		"The source UNI VPI matched by this entry.
		 A value of -1 matches all VPIs."
	::= { q2931AFTemplateEntry 3 }

q2931AFTemplateSrcNsap		OBJECT-TYPE
	SYNTAX	NsapAddr
	MAX-ACCESS	read-write
	STATUS	current
	DESCRIPTION
		"The Source NSAP address filtered by this table entry."
	::= { q2931AFTemplateEntry 4 }

q2931AFTemplateSrcNsapMask	OBJECT-TYPE
	SYNTAX	Integer32
	MAX-ACCESS	read-write
	STATUS	current
	DESCRIPTION
		"The mask applied to the source address in order to
		 compare against the above q2931AFTemplateEntrySrcNsap.
		 A mask of 0 bits matches all source addresses."
	::= { q2931AFTemplateEntry 5 }

q2931AFTemplateDstPort		OBJECT-TYPE
	SYNTAX	Integer32
	MAX-ACCESS	read-write
	STATUS	current
	DESCRIPTION
		"The destination UNI port matched by this entry.
		 A value of -1 matches all ports."
	::= { q2931AFTemplateEntry 6 }

q2931AFTemplateDstVPI		OBJECT-TYPE
	SYNTAX	Integer32
	MAX-ACCESS	read-write
	STATUS	current
	DESCRIPTION
		"The destination UNI VPI matched by this entry.
		 A value of -1 matches all VPIs."
	::= { q2931AFTemplateEntry 7 }

q2931AFTemplateDstNsap		OBJECT-TYPE
	SYNTAX	NsapAddr
	MAX-ACCESS	read-write
	STATUS	current
	DESCRIPTION
		"The Destination NSAP address filtered by this table
		 entry."
	::= { q2931AFTemplateEntry 8 }

q2931AFTemplateDstNsapMask	OBJECT-TYPE
	SYNTAX	Integer32
	MAX-ACCESS	read-write
	STATUS	current
	DESCRIPTION
		"The mask applied to the destination address in order
		 to compare against the above q2931AFTemplateDstNsap.
		 A mask of 0 bits matches all destination addresses."
	::= { q2931AFTemplateEntry 9 }

q2931AFTemplateAction		OBJECT-TYPE
	SYNTAX	INTEGER {
		accept(1),
		reject(2)
		}
	MAX-ACCESS	read-write
	STATUS	current
	DESCRIPTION
		"What to do with addresses that match this entry."
	::= { q2931AFTemplateEntry 10 }

q2931AFTemplateName		OBJECT-TYPE
        SYNTAX  OCTET STRING (SIZE(0..32))
	MAX-ACCESS	read-write
	STATUS	current
	DESCRIPTION
		"An optional text name for the template."
	::= { q2931AFTemplateEntry 11 }

q2931AFTemplateStatus		OBJECT-TYPE
	SYNTAX	RowStatus
	MAX-ACCESS	read-write
	STATUS	current
	DESCRIPTION
		"The status of this table entry.  This entry may not
		 be destroyed if there are any filter entries that
		 refer to it."
	::= { q2931AFTemplateEntry 12 }


q2931AFTemplateNextIndex OBJECT-TYPE
	SYNTAX	TestAndIncr
	MAX-ACCESS	read-write
	STATUS	current
	DESCRIPTION
		"The index of the next free row in the
		 q2931AFTemplateTable."
	::= { q2931AFTemplateTable 2 }

-----------------------
-- Filter Table

-- q2931AFFilterTableGroup OBJECT IDENTIFIER ::= { q2931AddressFilterGroup 2 }

q2931AFFilterTable OBJECT-TYPE
	SYNTAX	SEQUENCE OF Q2931AFFilterEntry
	MAX-ACCESS	not-accessible
	STATUS	current
	DESCRIPTION
		"A table of filters, each composed of an ordered list
		 of address filtering templates."
	::= { q2931AddressFilterGroup 2 }

q2931AFFilterEntry OBJECT-TYPE
	SYNTAX	Q2931AFFilterEntry
	MAX-ACCESS	not-accessible
	STATUS	current
	DESCRIPTION
		"A table entry for one filter."
	INDEX	{ q2931AFFilterIndex }
	::= { q2931AFFilterTable 1 }

Q2931AFFilterEntry ::= SEQUENCE {
	q2931AFFilterIndex		Integer32,
	q2931AFFilterName		OCTET STRING,
	q2931AFFilterStatus		RowStatus
}

q2931AFFilterIndex		OBJECT-TYPE
	SYNTAX	Integer32
	MAX-ACCESS	not-accessible
	STATUS	current
	DESCRIPTION
		"The value of this object identifies the NSAP Address
		 Filter to which this entry belongs."
	::= { q2931AFFilterEntry 1 }

q2931AFFilterName		OBJECT-TYPE
        SYNTAX  OCTET STRING (SIZE(0..31))
	MAX-ACCESS	read-write
	STATUS	current
	DESCRIPTION
		"An optional text name for the filter."
	::= { q2931AFFilterEntry 2 }

q2931AFFilterStatus		OBJECT-TYPE
	SYNTAX	RowStatus
	MAX-ACCESS	read-write
	STATUS	current
	DESCRIPTION
		"The status of this table entry.  Setting this variable
		 to destroy removes this row from the q2931AFFilterTable,
		 and removes the corresponding entries from the
		 q2931AFFilterTListTable."
	::= { q2931AFFilterEntry 3 }


q2931AFFilterNextIndex OBJECT-TYPE
 	SYNTAX	TestAndIncr
 	MAX-ACCESS	read-write
 	STATUS	current
 	DESCRIPTION
 		"The index of the next free row in the
 		 q2931AFFilterTable."
 	::= { q2931AFFilterTable 2 }

--------------------------------
-- Filter Template List Table

q2931AFFilterTListTable OBJECT-TYPE
	SYNTAX	SEQUENCE OF Q2931AFFilterTListEntry
	MAX-ACCESS	not-accessible
	STATUS	current
	DESCRIPTION
		"A table of template lists for filters.  A template
		 list is composed of an ordered list of address
		 filtering templates.  All objects with the same
		 value for q2931AFFilterIndex are conceptually part
		 of the corresponding q2931AFFilterEntry."
	::= { q2931AddressFilterGroup 3 }

q2931AFFilterTListEntry OBJECT-TYPE
	SYNTAX	Q2931AFFilterTListEntry
	MAX-ACCESS	not-accessible
	STATUS	current
	DESCRIPTION
		"A table entry holding one template in a filter's
		 template list."
	INDEX	{ q2931AFFilterIndex, q2931AFFilterTListIndex }
	::= { q2931AFFilterTListTable 1 }

Q2931AFFilterTListEntry ::= SEQUENCE {
	q2931AFFilterTListIndex		Integer32,
	q2931AFFilterTListTemplateIndex	Integer32,
	q2931AFFilterTListStatus	RowStatus
}

q2931AFFilterTListIndex		OBJECT-TYPE
	SYNTAX	Integer32
	MAX-ACCESS	not-accessible
	STATUS	current
	DESCRIPTION
		"The value of this object identifies the order in this
		 NSAP Address Filter in which this template is applied."
	::= { q2931AFFilterTListEntry 1 }

q2931AFFilterTListTemplateIndex	OBJECT-TYPE
	SYNTAX	Integer32
	MAX-ACCESS	read-write
	STATUS	current
	DESCRIPTION
		"The value of this object identifies the NSAP Address
		 Filter Template for this entry."
	::= { q2931AFFilterTListEntry 2 }

q2931AFFilterTListStatus	OBJECT-TYPE
	SYNTAX	RowStatus
	MAX-ACCESS	read-write
	STATUS	current
	DESCRIPTION
		"The status of this table entry."
	::= { q2931AFFilterTListEntry 3 }


--------------------------------
-- Address Filtering Statistics

q2931AFStatsTable OBJECT-TYPE
	SYNTAX	SEQUENCE OF Q2931AFStatsEntry
	MAX-ACCESS	not-accessible
	STATUS	current
	DESCRIPTION
		"A table of address filtering statistics."
	::= { q2931AddressFilterGroup 4 }

q2931AFStatsEntry OBJECT-TYPE
	SYNTAX	Q2931AFStatsEntry
	MAX-ACCESS	not-accessible
	STATUS	current
	DESCRIPTION
		"An entry in the table of address filtering statistics.
		 There are two entries for each UNI: one for incoming
		 call setup attempts, and one for outgoing call setup
		 attempts."
	INDEX	{ q2931AdminPort, q2931AdminVPI, q2931AFDirection }
	::= { q2931AFStatsTable 1 }

Q2931AFStatsEntry ::= SEQUENCE {
	q2931AFDirection			INTEGER,
	q2931AFAccepts				Counter32,
	q2931AFRejectKnowns			Counter32,
	q2931AFRejectUnknowns			Counter32
}

q2931AFDirection		OBJECT-TYPE
	SYNTAX	INTEGER {
		incoming(1),
		outgoing(2)
		}
	MAX-ACCESS	not-accessible
	STATUS	current
	DESCRIPTION
		"The value of this object identifies whether this
		 row of the statistics table applies to incoming
		 or outgoing call attempts."
	::= { q2931AFStatsEntry 1 }

q2931AFAccepts			OBJECT-TYPE
	SYNTAX	Counter32
	MAX-ACCESS	read-only
	STATUS	current
	DESCRIPTION
		"The total number of Q2931 messages that have been
		 accepted by Address Filtering on this UNI."
	::= { q2931AFStatsEntry 2 }

q2931AFRejectKnowns		OBJECT-TYPE
	SYNTAX	Counter32
	MAX-ACCESS	read-only
	STATUS	current
	DESCRIPTION
		"The total number of Q2931 messages that have been
		 rejected because the supplied address matched a
		 template in the address filtering table where the
		 action was to reject the call."
	::= { q2931AFStatsEntry 3 }

q2931AFRejectUnknowns		OBJECT-TYPE
	SYNTAX	Counter32
	MAX-ACCESS	read-only
	STATUS	current
	DESCRIPTION
		"The total number of Q2931 messages that have been
		 rejected because the supplied address matched no
		 template in the address filtering table."
	::= { q2931AFStatsEntry 4 }


--------------------------------------------------------
--
-- The AFLookup facility allows a management station to
-- test the filters applied to a collection of UNIs without
-- sending actual setup messages to the switch.  When a
-- row's rowStatus is set to 'active', the source and
-- destination addresses in that row are filtered by the
-- specified NSAP address filter.
--

q2931AFLookupTable OBJECT-TYPE
	SYNTAX	SEQUENCE OF Q2931AFLookupEntry
	MAX-ACCESS	not-accessible
	STATUS	current
	DESCRIPTION
		"The Lookup facility for NSAP address filtering."
	::= { q2931AddressFilterGroup 5 }

q2931AFLookupEntry OBJECT-TYPE
	SYNTAX	Q2931AFLookupEntry
	MAX-ACCESS	not-accessible
	STATUS	current
	DESCRIPTION
		"The result of an inquiry to the Lookup facility."
	INDEX	{ q2931AFLookupIndex }
	::= { q2931AFLookupTable 1 }

Q2931AFLookupEntry ::= SEQUENCE {
	q2931AFLookupIndex		Integer32,
	q2931AFLookupNSAPFilterIndex	Integer32,
	q2931AFLookupSrcPort		Integer32,
	q2931AFLookupSrcVPI		Integer32,
	q2931AFLookupSrcNsap		NsapAddr,
	q2931AFLookupDstPort		Integer32,
	q2931AFLookupDstVPI		Integer32,
	q2931AFLookupDstNsap		NsapAddr,
	q2931AFLookupResult		INTEGER,
	q2931AFLookupTemplate		Integer32,
	q2931AFLookupStatus		RowStatus
}

q2931AFLookupIndex		OBJECT-TYPE
	SYNTAX	Integer32
	MAX-ACCESS	not-accessible
	STATUS	current
	DESCRIPTION
		"The value of this object identifies this entry
		 in the Filter Lookup table."
	::= { q2931AFLookupEntry 1 }

q2931AFLookupNSAPFilterIndex	OBJECT-TYPE
	SYNTAX	Integer32
	MAX-ACCESS	read-write
	STATUS	current
	DESCRIPTION
		"The index of the NSAP address filter for this lookup."
	::= { q2931AFLookupEntry 2 }

q2931AFLookupSrcPort		OBJECT-TYPE
	SYNTAX	Integer32
	MAX-ACCESS	read-write
	STATUS	current
	DESCRIPTION
		"The simulated incoming Port for this filter lookup."
	::= { q2931AFLookupEntry 3 }

q2931AFLookupSrcVPI		OBJECT-TYPE
	SYNTAX	Integer32
	MAX-ACCESS	read-write
	STATUS	current
	DESCRIPTION
		"The simulated incoming VPI for this filter lookup."
	::= { q2931AFLookupEntry 4 }

q2931AFLookupSrcNsap		OBJECT-TYPE
	SYNTAX	NsapAddr
	MAX-ACCESS	read-write
	STATUS	current
	DESCRIPTION
		"The Source NSAP address for this filter lookup."
	::= { q2931AFLookupEntry 5 }

q2931AFLookupDstPort		OBJECT-TYPE
	SYNTAX	Integer32
	MAX-ACCESS	read-write
	STATUS	current
	DESCRIPTION
		"The simulated outgoing Port for this filter lookup."
	::= { q2931AFLookupEntry 6 }

q2931AFLookupDstVPI		OBJECT-TYPE
	SYNTAX	Integer32
	MAX-ACCESS	read-write
	STATUS	current
	DESCRIPTION
		"The simulated outgoing VPI for this filter lookup."
	::= { q2931AFLookupEntry 7 }

q2931AFLookupDstNsap		OBJECT-TYPE
	SYNTAX	NsapAddr
	MAX-ACCESS	read-write
	STATUS	current
	DESCRIPTION
		"The Destination NSAP address for this filter lookup."
	::= { q2931AFLookupEntry 8 }

q2931AFLookupResult		OBJECT-TYPE
	SYNTAX	INTEGER {
		accept(1),
		reject(2)
	}
	MAX-ACCESS	read-only
	STATUS	current
	DESCRIPTION
		"The result of a filter Lookup on the selected values:
		 1	Accepted
		 2	Rejected"
	::= { q2931AFLookupEntry 9 }

q2931AFLookupTemplate		OBJECT-TYPE
	SYNTAX	Integer32
	MAX-ACCESS	read-only
	STATUS	current
	DESCRIPTION
		"The index of the template in the address filter that
		 either accepted or rejected the call.  It is zero if
		 the address was unknown."
	::= { q2931AFLookupEntry 10 }

q2931AFLookupStatus		OBJECT-TYPE
	SYNTAX	RowStatus
	MAX-ACCESS	read-write
	STATUS	current
	DESCRIPTION
		"The status of this table entry."
	::= { q2931AFLookupEntry 11 }


------------------------------------------------------------------------------
-- Last Failed Call Attempt

q2931AFLastFailureGroup	OBJECT IDENTIFIER ::= { q2931AddressFilterGroup 6 }

q2931AFLastFailureSrcPort	OBJECT-TYPE
	SYNTAX	Integer32
	MAX-ACCESS	read-only
	STATUS	current
	DESCRIPTION
		"The incoming port for this failed call attempt."
	::= { q2931AFLastFailureGroup 1 }

q2931AFLastFailureSrcVPI	OBJECT-TYPE
	SYNTAX	Integer32
	MAX-ACCESS	read-only
	STATUS	current
	DESCRIPTION
		"The incoming VPI for this failed call attempt."
	::= { q2931AFLastFailureGroup 2 }

q2931AFLastFailureSrcNsap	OBJECT-TYPE
	SYNTAX	NsapAddr
	MAX-ACCESS	read-only
	STATUS	current
	DESCRIPTION
		"The source address of this failed call attempt."
	::= { q2931AFLastFailureGroup 3 }

q2931AFLastFailureDstPort	OBJECT-TYPE
	SYNTAX	Integer32
	MAX-ACCESS	read-only
	STATUS	current
	DESCRIPTION
		"The outgoing port for this failed call attempt."
	::= { q2931AFLastFailureGroup 4 }

q2931AFLastFailureDstVPI	OBJECT-TYPE
	SYNTAX	Integer32
	MAX-ACCESS	read-only
	STATUS	current
	DESCRIPTION
		"The outgoing VPI for this failed call attempt."
	::= { q2931AFLastFailureGroup 5 }

q2931AFLastFailureDstNsap	OBJECT-TYPE
	SYNTAX	NsapAddr
	MAX-ACCESS	read-only
	STATUS	current
	DESCRIPTION
		"The destination address of this failed call attempt."
	::= { q2931AFLastFailureGroup 6 }

q2931AFLastFailureTemplateIndex	OBJECT-TYPE
	SYNTAX	Integer32
	MAX-ACCESS	read-only
	STATUS	current
	DESCRIPTION
		"The index of the template which rejected this call
		 attempt.  If this call was rejected because its
		 addresses were not known, this field is set to zero."
	::= { q2931AFLastFailureGroup 7 }

q2931AFLastFailureDirection	OBJECT-TYPE
	SYNTAX  INTEGER {
		incoming(1),
		outgoing(2)
		}
	MAX-ACCESS  read-only
	STATUS  current
	DESCRIPTION
		"The value of this object identifies whether the
		 incoming (source) or outgoing (destination) filter
		 rejected the call.  Its value is irrelevant for
		 accepted calls."
	::= { q2931AFLastFailureGroup 8 }


------------------------------------------------------------------------

--
-- The Proxy client address to VPCI mapping table
--
-- An entry in this table contains the necessary information for
-- a single ATM End system address and VPCI mapping. Each entry in this
-- table associated an ATM end system address with a VPCI for a single
-- proxy address group.  Each proxy address group is associated with a
-- VPCI group mapping.
--

proxyDirMapEntryGroup OBJECT IDENTIFIER ::= { q2931Group 15 }

proxyDirMapEntryTable OBJECT-TYPE
      SYNTAX  SEQUENCE OF ProxyDirMapEntry
      MAX-ACCESS      not-accessible
      STATUS  current
      DESCRIPTION
              "A table of ATM End system address, Proxy address
              directory and VPCI mappings. "
      ::= { proxyDirMapEntryGroup 1 }

proxyDirMapEntry OBJECT-TYPE
      SYNTAX  ProxyDirMapEntry
      MAX-ACCESS      not-accessible
      STATUS  current
      DESCRIPTION
              "A table entry containing ATM End System Address, proxy
              directory group index and VPCI. "
      INDEX   { proxyDirMapIndex }
      ::= { proxyDirMapEntryTable 1 }

ProxyDirMapEntry ::= SEQUENCE {
      proxyDirMapIndex        INTEGER,
      proxyDirMapAESA         OCTET STRING,
      proxyDirMapGroup        Integer32,
      proxyDirMapVPCI         Integer32,
      proxyDirMapPort         Integer32,
      proxyDirMapVp           Integer32,
      proxyDirMapStatus       RowStatus
      }

proxyDirMapIndex OBJECT-TYPE
      SYNTAX  INTEGER (1..99999)
      MAX-ACCESS      not-accessible
      STATUS  current
      DESCRIPTION
              "The value of this object identifies the
               mapping associated with this entry."
      ::= { proxyDirMapEntry 1 }

proxyDirMapAESA OBJECT-TYPE
      SYNTAX  OCTET STRING
      MAX-ACCESS      read-write
      STATUS  current
      DESCRIPTION
              "The ATM End System Address associated with this entry"
      ::= { proxyDirMapEntry 2 }

proxyDirMapGroup OBJECT-TYPE
      SYNTAX  Integer32
      MAX-ACCESS      read-write
      STATUS  current
      DESCRIPTION
              "The proxy directory address group identifier associated with
              this mapping"
      ::= { proxyDirMapEntry 3 }

proxyDirMapVPCI OBJECT-TYPE
      SYNTAX  Integer32
      MAX-ACCESS      read-write
      STATUS  current
      DESCRIPTION
              "The VPCI value associated with this entry"
      ::= { proxyDirMapEntry 4 }

proxyDirMapStatus OBJECT-TYPE
      SYNTAX  RowStatus
      MAX-ACCESS      read-write
      STATUS  current
      DESCRIPTION
              "The status of this mapping entry."
      ::= { proxyDirMapEntry 5 }

proxyDirMapVp OBJECT-TYPE
      SYNTAX  Integer32
      MAX-ACCESS      read-only
      STATUS  current
      DESCRIPTION
              "The VP value associated with this entry"
      ::= { proxyDirMapEntry 6 }

proxyDirMapPort OBJECT-TYPE
      SYNTAX  Integer32
      MAX-ACCESS      read-only
      STATUS  current
      DESCRIPTION
              "The port associated with this entry"
      ::= { proxyDirMapEntry 7 }


------------------------------------------------------------------------
--
-- The Proxy client address groups
--
-- An entry in this table contains the necessary information for
-- a proxy interface to create a mapping between client addresses
-- and their port number, VP and VPCI values.  This table should be
-- used with VPCI group table to derive all the necessary information
-- for a complete maaping.
--

proxyDirGroupGroup OBJECT IDENTIFIER ::= { q2931Group 16 }

proxyDirGroupTable OBJECT-TYPE
      SYNTAX  SEQUENCE OF ProxyDirGroup
      MAX-ACCESS      not-accessible
      STATUS  current
      DESCRIPTION
              "A group of ATM End system address and VPCI mappings"
      ::= { proxyDirGroupGroup 1 }

proxyDirGroupEntry OBJECT-TYPE
      SYNTAX  ProxyDirGroup
      MAX-ACCESS      not-accessible
      STATUS  current
      DESCRIPTION
              "A group of ATM End system address and VPCI mappings"
      INDEX   { proxyDirGroupIndex }
      ::= { proxyDirGroupTable 1 }

ProxyDirGroup ::= SEQUENCE {
      proxyDirGroupIndex      INTEGER,
      proxyDirGroupPrefix     Integer32,
      proxyDirGroupVPCIGroup  Integer32,
      proxyDirGroupStatus     RowStatus
      }

proxyDirGroupIndex OBJECT-TYPE
      SYNTAX  INTEGER (1..99999)
      MAX-ACCESS      not-accessible
      STATUS  current
      DESCRIPTION
              "The value of this object identifies the
               mapping associated with this entry."
      ::= { proxyDirGroupEntry 1 }

proxyDirGroupPrefix OBJECT-TYPE
      SYNTAX  Integer32
      MAX-ACCESS      read-write
      STATUS  current
      DESCRIPTION
              "The prefix of the ATM End System Address that is used in
              mapping to a VPCI"
      ::= { proxyDirGroupEntry 2 }

proxyDirGroupVPCIGroup OBJECT-TYPE
      SYNTAX  Integer32
      MAX-ACCESS      read-write
      STATUS  current
      DESCRIPTION
              "The VPCI group index associated with this entry"
      ::= { proxyDirGroupEntry 3 }

proxyDirGroupStatus OBJECT-TYPE
      SYNTAX  RowStatus
      MAX-ACCESS      read-write
      STATUS  current
      DESCRIPTION
              "The status of this mapping entry."
      ::= { proxyDirGroupEntry 4 }

--
-- q2931 VPCI Mapping Table Group
--
-- The mapping of VPCI, VPI and Port values
-- to be used for implementing Virtual UNIs, VP Groups
-- and for Proxy Signalling
--

vpciMappingTableGroup OBJECT IDENTIFIER ::= { q2931Group 13 }

--
-- The VPCI Map Table
--
-- An entry in this table contains the necessary information for
-- a single VPCI-VPI-Port mapping. Each entry in this table can
-- be a part of one or more entries in the vmtVpciMapGroupTable
--

vmtVpciMapTable OBJECT-TYPE
	SYNTAX  SEQUENCE OF VmtVpciMapEntry
	MAX-ACCESS	not-accessible
	STATUS	current
	DESCRIPTION
		"A table of VPCI, VPI and Port mappings. "
	::= { vpciMappingTableGroup 1 }

vmtVpciMapEntry OBJECT-TYPE
	SYNTAX	VmtVpciMapEntry
	MAX-ACCESS	not-accessible
	STATUS	current
	DESCRIPTION
		"A table entry containing a VPCI, VPI and
		Port mappings. "
	INDEX   { vmtVpciMapIndex }
	::= { vmtVpciMapTable 1 }

VmtVpciMapEntry ::= SEQUENCE {
	vmtVpciMapIndex		INTEGER,
	vmtVpciMapVPCI		Integer32,
	vmtVpciMapVPI		Integer32,
	vmtVpciMapPort		Integer32,
	vmtVpciMapStatus	RowStatus
	}

vmtVpciMapIndex OBJECT-TYPE
	SYNTAX	INTEGER (1..99999)
	MAX-ACCESS	not-accessible
	STATUS	current
	DESCRIPTION
		"The value of this object identifies the VPCI
		 mapping associated with this entry."
	::= { vmtVpciMapEntry 1 }

vmtVpciMapVPCI OBJECT-TYPE
	SYNTAX	Integer32
	MAX-ACCESS	read-write
	STATUS	current
	DESCRIPTION
		"The VPCI associated with this VPCI mapping entry."
	DEFVAL  { 0 }
	::= { vmtVpciMapEntry 2 }

vmtVpciMapVPI OBJECT-TYPE
	SYNTAX	Integer32
	MAX-ACCESS	read-write
	STATUS	current
	DESCRIPTION
		"The VPI associated with this VPCI mapping entry.
		A value of -1 indicates that the VPI is the same
		as the VPI associated with the signalling interface
		using this VPCI mapping entry."
	DEFVAL  { -1 }
	::= { vmtVpciMapEntry 3 }

vmtVpciMapPort OBJECT-TYPE
	SYNTAX	Integer32
	MAX-ACCESS	read-write
	STATUS	current
	DESCRIPTION
		"The Port associated with this VPCI mapping entry.
		A value of -1 indicates that the Port is the same
		as the Port associated with the signalling interface
		using this VPCI mapping entry."
	DEFVAL  { -1 }
	::= { vmtVpciMapEntry 4 }

vmtVpciMapStatus OBJECT-TYPE
	SYNTAX	RowStatus
	MAX-ACCESS	read-write
	STATUS	current
	DESCRIPTION
		"The status of this VPCI mapping entry.
		The status cannot be set to destroy if there are any
		vmtVpciMapGroupTable entries that refer to it."
	::= { vmtVpciMapEntry 5 }

--
-- The VPCI Map Group Table
--
-- An entry in this table contains the common information for
-- a VPCI mapping group.
--

vmtVpciMapGroupTable OBJECT-TYPE
	SYNTAX	SEQUENCE OF VmtVpciMapGroupEntry
	MAX-ACCESS	not-accessible
	STATUS	current
	DESCRIPTION
		"A table of VPCI mapping groups. Each VPCI mapping
		group consists of a list if VPCI mapping entries."
	::= { vpciMappingTableGroup 2 }

vmtVpciMapGroupEntry OBJECT-TYPE
	SYNTAX	VmtVpciMapGroupEntry
	MAX-ACCESS	not-accessible
	STATUS	current
	DESCRIPTION
		"A table entry for one VPCI mapping group."
	INDEX   { vmtVpciMapGroupIndex }
	::= { vmtVpciMapGroupTable 1 }

VmtVpciMapGroupEntry ::= SEQUENCE {
	vmtVpciMapGroupIndex	INTEGER,
	vmtVpciMapGroupStatus	RowStatus
	}

vmtVpciMapGroupIndex OBJECT-TYPE
	SYNTAX	INTEGER (1..99999)
	MAX-ACCESS	not-accessible
	STATUS	current
	DESCRIPTION
		"The value of this object identifies the VPCI
		 mapping group associated with this entry."
	::= { vmtVpciMapGroupEntry 1 }

vmtVpciMapGroupStatus OBJECT-TYPE
	SYNTAX	RowStatus
	MAX-ACCESS	read-write
	STATUS	current
	DESCRIPTION
		"The status of the VPCI mapping group entry. This
		object cannot be transitioned from the Active state
		to any other state if there are any signalling
		interfaces using this VPCI mapping group.
		Setting this variable to destroy will remove this
		row from the vmtVpciMapGroupTable and also
		remove the corresponding entries from the
		vmtVpciMapListTable."
	::= { vmtVpciMapGroupEntry 2 }

--
-- The VPCI Map List Table
--
-- An entry in this table contains a VPCI mapping entry
-- belonging to a VPCI mapping group.
--

vmtVpciMapListTable OBJECT-TYPE
	SYNTAX	SEQUENCE OF VmtVpciMapListEntry
	MAX-ACCESS	not-accessible
	STATUS	current
	DESCRIPTION
		"A table of VPCI mapping entries for VPCI mapping
		groups. A VPCI mapping list is composed of a list
		of VPCI mapping entries. All objects with the same
		value for vmtVpciMapGroupIndex are conceptually
		part of the same vmtVpciMapGroupEntry. Entries in this
		table may be added, deleted or modified only if the
		corresponding vpcigroup index is not being used by
		any signalling interface."
	::= { vpciMappingTableGroup 3 }

vmtVpciMapListEntry OBJECT-TYPE
	SYNTAX	VmtVpciMapListEntry
	MAX-ACCESS	not-accessible
	STATUS	current
	DESCRIPTION
		"A table entry holding one VPCI mapping entry in a
		VPCI mapping group."
	INDEX	{ vmtVpciMapGroupIndex, vmtVpciMapListIndex }
	::= { vmtVpciMapListTable 1 }

VmtVpciMapListEntry ::= SEQUENCE {
	vmtVpciMapListIndex		INTEGER,
	vmtVpciMapListMEIndex		Integer32,
	vmtVpciMapListStatus		RowStatus
}

vmtVpciMapListIndex OBJECT-TYPE
	SYNTAX        INTEGER (1..99999)
	MAX-ACCESS        not-accessible
	STATUS        current
	DESCRIPTION
		"The value of this object identifies the order of a
		VPCI mapping entry in the VPCI mapping group in
		which it is used."
	::= { vmtVpciMapListEntry 1 }

vmtVpciMapListMEIndex OBJECT-TYPE
	SYNTAX        Integer32
	MAX-ACCESS        read-write
	STATUS        current
	DESCRIPTION
		"The value of this object identifies the VPCI
		mapping entry in the vmtVpciMapTable for this
		entry."
	::= { vmtVpciMapListEntry 2 }

vmtVpciMapListStatus OBJECT-TYPE
	SYNTAX        RowStatus
	MAX-ACCESS        read-write
	STATUS        current
	DESCRIPTION
		"The status of this entry.  This object can be
		set to destroy only if the corresponding
		vmtVpciMapGroupStatus is not Active."
	::= { vmtVpciMapListEntry 3 }

------------------------------------------------------------------------
-- Per Call Debugging Filter Group
--
--  The following mib definations define the filters that are to be
-- used by the Per Call Debugging Filter, which will be compared to
-- incoming calls to determine if the PCD feature should be enabled.
------------------------------------------------------------------------

perCallDbgFilterGroup OBJECT IDENTIFIER ::= { q2931LayerGroup 8 }

perCallDbgFilterTable OBJECT-TYPE
	SYNTAX	 SEQUENCE OF PerCallDbgFilterEntry
	MAX-ACCESS	 not-accessible
	STATUS	 current
	DESCRIPTION
		" A table of Per Call Debugging Filter entries."
	::=  { perCallDbgFilterGroup 1 }

perCallDbgFilterEntry OBJECT-TYPE
	SYNTAX	 PerCallDbgFilterEntry
	MAX-ACCESS	 not-accessible
	STATUS	 current
	DESCRIPTION
		"A table entry containing a Per Call Debugging filter."
	INDEX   { perCallDbgFilterIndex }
	::= { perCallDbgFilterTable 1}

PerCallDbgFilterEntry ::= SEQUENCE {
	perCallDbgFilterIndex		Integer32,
	perCallDbgFilterTemplateId	Integer32,
	perCallDbgFilterName		OCTET STRING,
	perCallDbgFilterFlavor		Integer32,
	perCallDbgFilterMatches		Counter32,
	perCallDbgFilterRowStatus	RowStatus
}

perCallDbgFilterIndex	       OBJECT-TYPE
	SYNTAX	 Integer32
	MAX-ACCESS	 not-accessible
	STATUS	 current
	DESCRIPTION
		"The value of the object indicates the index of
		   this entry in the PCD table.  A limit will be set
		   as a constant to limit the number of filter that can
		   exist at once."
	::= { perCallDbgFilterEntry 1 }

perCallDbgFilterTemplateId       OBJECT-TYPE
	SYNTAX	Integer32
	MAX-ACCESS	read-write
	STATUS	current
	DESCRIPTION
		"The value of this object reflects the index of the
		  template to be used for this filter"
	::= { perCallDbgFilterEntry 2 }

perCallDbgFilterName	       OBJECT-TYPE
        SYNTAX  OCTET STRING (SIZE(0..16))
	MAX-ACCESS	read-write
	STATUS	current
	DESCRIPTION
		"The value of this object reflects a name that will
		   be printed out with the debug messages generated
		   by this feature."
	::= { perCallDbgFilterEntry 3 }

perCallDbgFilterFlavor	 OBJECT-TYPE
	SYNTAX	Integer32
	MAX-ACCESS  read-write
	STATUS	current
	DESCRIPTION
		"The value of this object reflects the type of debugging
		   that has been enabled."
	::= { perCallDbgFilterEntry 4 }


perCallDbgFilterMatches	       OBJECT-TYPE
	SYNTAX	Counter32
	MAX-ACCESS	read-only
	STATUS	current
	DESCRIPTION
		"The value of this object reflects the
		   number of SVC setup messages matches that
		   have been found for this filter."
	::= { perCallDbgFilterEntry 5 }

perCallDbgFilterRowStatus      OBJECT-TYPE
	SYNTAX	RowStatus
	MAX-ACCESS	read-write
	STATUS	current
	DESCRIPTION
		"The status of this PCD filter entry."
	::= { perCallDbgFilterEntry 6 }

-------------------

-----------------------------------
-- switchperCallDbgTransFlag  A flag which will indicate whether
--   a switch will generate Per Call Debuggging messages as a
--   Transient Switch.
-----------------------------------
perCallDbgTransFlag OBJECT-TYPE
	SYNTAX	INTEGER {
			disabled(1),
			enabled(2)
		}
	MAX-ACCESS	read-write
	STATUS	current
	DESCRIPTION
		"Enables a switch to generate and print PCD debugging
		information when a switch receives a PCD GIT IE.  The
		default value will be enabled."
	::= { perCallDbgFilterGroup 2  }

------------------------------------------------------------------------
-- The NSAP Routing Group

-- Implementation of this group is mandatory
-- for all asxd applications that support
-- NSAP routing.


nsapNetworkPrefixTable OBJECT-TYPE
	SYNTAX  SEQUENCE OF NsapNetworkPrefixEntry
	MAX-ACCESS  not-accessible
	STATUS  current
	DESCRIPTION
		"A table of Network Prefix addresses"
	::= { nsapGroup 1 }

nsapNetworkPrefixEntry OBJECT-TYPE
	SYNTAX	NsapNetworkPrefixEntry
	MAX-ACCESS	not-accessible
	STATUS	current
	DESCRIPTION
		"An entry in the Network Prefix table."
	INDEX	{ nsapNetworkPrefixPort, nsapNetworkPrefixVPI, nsapNetworkPrefixValue }
	::= { nsapNetworkPrefixTable 1 }

NsapNetworkPrefixEntry ::= SEQUENCE {
	nsapNetworkPrefixPort		Integer32,
	nsapNetworkPrefixVPI		Integer32,
	nsapNetworkPrefixValue		NsapPrefix,
	nsapNetworkPrefixStatus		EntryStatus
}

nsapNetworkPrefixPort OBJECT-TYPE
	SYNTAX	Integer32
	MAX-ACCESS	read-only
	STATUS	current
	DESCRIPTION
		"The value of this object identifies the port
		of this signalling path, and is the same as
		nsapPort."
	::= { nsapNetworkPrefixEntry 1 }

nsapNetworkPrefixVPI OBJECT-TYPE
	SYNTAX	Integer32
	MAX-ACCESS	read-only
	STATUS	current
	DESCRIPTION
		"The value of this object identifies the VPI (Virtual
		Path Identifier) of this signaling path statistics entry,
		and is the same as nsapVPI."
	::= { nsapNetworkPrefixEntry 2 }

nsapNetworkPrefixValue  OBJECT-TYPE
	SYNTAX  NsapPrefix
	MAX-ACCESS  read-only
	STATUS  current
	DESCRIPTION
		"The network prefix for ATM addresses which is in
		effect on the user-side of the ATM UNI port."
	::= { nsapNetworkPrefixEntry 3 }

nsapNetworkPrefixStatus OBJECT-TYPE
	SYNTAX	EntryStatus
	MAX-ACCESS	read-create
	STATUS	current
	DESCRIPTION
		"The status of this Network Prefix entry. Setting this object
		to invalid(4) causes this Network to disappear."
	::= { nsapNetworkPrefixEntry 4 }


------------------------------------------------------------------------
--
-- nsapAddrAdminTable OBJECT-TYPE
--        SYNTAX  SEQUENCE OF NsapAddrAdminEntry
--        ACCESS  not-accessible
--        STATUS  deprecated
--        DESCRIPTION
--                "A table for NSAP (Network Service Access Point) address
--		administration."
--        ::= { nsapGroup 2 }
--
------------------------------------------------------------------------

nsapTopologyTable OBJECT-TYPE
	SYNTAX  SEQUENCE OF NsapTopologyEntry
	MAX-ACCESS  not-accessible
	STATUS  current
	DESCRIPTION
		"A table for NSAP (Network Service Access Point) topology,
		based on NSAP routing."
	::= { nsapGroup 3 }

nsapTopologyEntry OBJECT-TYPE
	SYNTAX	NsapTopologyEntry
	MAX-ACCESS	not-accessible
	STATUS	current
	DESCRIPTION
		"An entry in the NSAP (Network Service Access Point) topology
		table."
	INDEX	{ nsapTopoBoard, nsapTopoLinkSrc, nsapTopoLinkSrcMask, nsapTopoLinkSrcPort,
		  nsapTopoLinkSrcVpi, nsapTopoLinkDest, nsapTopoLinkDestMask,
		  nsapTopoLinkDestPort, nsapTopoLinkDestVpi }
	::= { nsapTopologyTable 1 }

NsapTopologyEntry ::= SEQUENCE {
	nsapTopoBoard				Integer32,
	nsapTopoLinkSrc				NsapAddr,
	nsapTopoLinkSrcMask			Integer32,
	nsapTopoLinkSrcPort			Integer32,
	nsapTopoLinkSrcVpi			Integer32,
	nsapTopoLinkDest			NsapAddr,
	nsapTopoLinkDestMask			Integer32,
	nsapTopoLinkDestPort			Integer32,
	nsapTopoLinkDestVpi			Integer32,
	nsapTopoLinkCost			Integer32,
	nsapTopoLinkUbrVCs			Gauge32,
	nsapTopoLinkCbrCapacity			Integer32,
	nsapTopoLinkCbrFifo			Integer32,
	nsapTopoLinkVbrCapacity			Integer32,
	nsapTopoLinkVbrFifo			Integer32,
	nsapTopoLinkOrig			INTEGER,
	nsapTopoLinkCapabilitySet		Integer32,
	nsapTopoLinkFreshness			Integer32,
	nsapTopoLinkUbrEstimatedBandwidth	Integer32
}

nsapTopoBoard OBJECT-TYPE
	SYNTAX	Integer32
	MAX-ACCESS	read-only
	STATUS	current
	DESCRIPTION
		"The index of the switch board within the ATM switch cluster.
		This object is the same as the swBoardIndex."
	::= { nsapTopologyEntry 1 }

nsapTopoLinkSrc OBJECT-TYPE
	SYNTAX	NsapAddr
	MAX-ACCESS	read-only
	STATUS	current
	DESCRIPTION
		"The value of this object identifies the source NSAP
		(Network Service Access Point) address of this link."
	::= { nsapTopologyEntry 2 }

nsapTopoLinkSrcMask OBJECT-TYPE
	SYNTAX	Integer32
	MAX-ACCESS	read-only
	STATUS	current
	DESCRIPTION
		"The value of this object identifies the mask that is
		used for the link source NSAP (Network Service Access Point)
		address. The mask identifies the number of bits in the
		NSAP address that are valid. The value of the mask object
		is in the range 0-160 (160 bits is the size of an NSAP
		address)."
	::= { nsapTopologyEntry 3 }

nsapTopoLinkSrcPort OBJECT-TYPE
	SYNTAX	Integer32
	MAX-ACCESS	read-only
	STATUS	current
	DESCRIPTION
		"This object identifies the physical port of the link source."
	::= { nsapTopologyEntry 4 }

nsapTopoLinkSrcVpi OBJECT-TYPE
	SYNTAX	Integer32
	MAX-ACCESS	read-only
	STATUS	current
	DESCRIPTION
		"This object identifies the virtual path identifier of the link source."
	::= { nsapTopologyEntry 5 }

nsapTopoLinkDest OBJECT-TYPE
	SYNTAX	NsapAddr
	MAX-ACCESS	read-only
	STATUS	current
	DESCRIPTION
		"The value of this object identifies the destination NSAP
		(Network Service Access Point) address of this link."
	::= { nsapTopologyEntry 6 }

nsapTopoLinkDestMask OBJECT-TYPE
	SYNTAX	Integer32
	MAX-ACCESS	read-only
	STATUS	current
	DESCRIPTION
		"The value of this object identifies the mask that is
		used for the link destination NSAP (Network Service Access
		Point) address. The mask identifies the number of bits in the
		NSAP address that are valid. The value of the mask object
		is in the range 0-160 (160 bits is the size of an NSAP
		address)."
	::= { nsapTopologyEntry 7 }

nsapTopoLinkDestPort OBJECT-TYPE
	SYNTAX	Integer32
	MAX-ACCESS	read-only
	STATUS	current
	DESCRIPTION
		"This object identifies the physical  port of the link
		destination."
	::= { nsapTopologyEntry 8 }

nsapTopoLinkDestVpi OBJECT-TYPE
	SYNTAX	Integer32
	MAX-ACCESS	read-only
	STATUS	current
	DESCRIPTION
		"This object identifies the virtual path identifier of the
		link destination."
	::= { nsapTopologyEntry 9 }

nsapTopoLinkCost OBJECT-TYPE
	SYNTAX	Integer32
	MAX-ACCESS	read-only
	STATUS	current
	DESCRIPTION
		"The routing metric for this link."
	::= { nsapTopologyEntry 10 }

nsapTopoLinkUbrVCs OBJECT-TYPE
	SYNTAX	Gauge32
	MAX-ACCESS	read-only
	STATUS	deprecated
	DESCRIPTION
		"The number of UBR vcs."
	::= { nsapTopologyEntry 11 }

nsapTopoLinkCbrCapacity OBJECT-TYPE
	SYNTAX	Integer32
	MAX-ACCESS	read-only
	STATUS	current
	DESCRIPTION
		"The available capacity for additional CBR (Constant Bit Rate)
		connections. The available capacity is measured in Kbps."
	::= { nsapTopologyEntry 12 }

nsapTopoLinkCbrFifo OBJECT-TYPE
	SYNTAX	Integer32
	MAX-ACCESS	read-only
	STATUS	current
	DESCRIPTION
		"The size of the FIFO queue that is used for transmitting CBR
		(Constant Bit Rate) traffic. The size of the fifo is measured
		in number of cells."
	::= { nsapTopologyEntry 13 }

nsapTopoLinkVbrCapacity OBJECT-TYPE
	SYNTAX	Integer32
	MAX-ACCESS	read-only
	STATUS	current
	DESCRIPTION
		"The available capacity for additional VBR (Variable Bit Rate)
		connections. The available capacity is measured in Kbps."
	::= { nsapTopologyEntry 14 }

nsapTopoLinkVbrFifo OBJECT-TYPE
	SYNTAX	Integer32
	MAX-ACCESS	read-only
	STATUS	current
	DESCRIPTION
		"The size of the FIFO queue that is used for transmitting VBR
		(Variable Bit Rate) traffic. The size of the fifo is measured
		in number of cells."
	::= { nsapTopologyEntry 15 }

nsapTopoLinkOrig OBJECT-TYPE
	SYNTAX	INTEGER {
			static-route(1),
			spans-pnni(2),
			ilmi-registered(3),
			pnni(4),
			external(5)
		}
	MAX-ACCESS	read-only
	STATUS	current
	DESCRIPTION
		"The source of this route information."
	::= { nsapTopologyEntry 16 }

nsapTopoLinkCapabilitySet OBJECT-TYPE
	SYNTAX	Integer32
	MAX-ACCESS	read-only
	STATUS	current
	DESCRIPTION
		"A bitmap indicate the capabilities of this link. For example,
		whether the link support ABR (Available Bit Rate) traffic."
	::= { nsapTopologyEntry 17 }

nsapTopoLinkFreshness OBJECT-TYPE
	SYNTAX	Integer32
	MAX-ACCESS	read-only
	STATUS	current
	DESCRIPTION
		"This object indicates the freshness (or staleness) of this
		NSAP (Network Service Access Point) link. As the number increases,
		the link becomes stale."
	::= { nsapTopologyEntry 18 }

nsapTopoLinkUbrEstimatedBandwidth OBJECT-TYPE
	SYNTAX	Integer32
	MAX-ACCESS	read-only
	STATUS	current
	DESCRIPTION
		"The estimated UBR bandwidth on this link."
	::= { nsapTopologyEntry 19 }


------------------------------------------------------------------------


nsapStaticRouteTable OBJECT-TYPE
	SYNTAX  SEQUENCE OF NsapStaticRouteEntry
	MAX-ACCESS  not-accessible
	STATUS  current
	DESCRIPTION
		"A table for static NSAP (Network Service Access Point) route
		administration."
	::= { nsapGroup 4 }

nsapStaticRouteEntry OBJECT-TYPE
	SYNTAX	NsapStaticRouteEntry
	MAX-ACCESS	not-accessible
	STATUS	current
	DESCRIPTION
		"An entry in the NSAP (Network Service Access Point) static route
		administration table."
	INDEX	{ nsapStaticRouteAddress, nsapStaticRouteMask,
		  nsapStaticRoutePort, nsapStaticRouteVPI }
	::= { nsapStaticRouteTable 1 }

NsapStaticRouteEntry ::= SEQUENCE {
	nsapStaticRouteAddress		NsapAddr,
	nsapStaticRouteMask		Integer32,
	nsapStaticRoutePort		Integer32,
	nsapStaticRouteVPI		Integer32,
	nsapStaticRouteCost		Integer32,
	nsapStaticRouteMaxCbrCap        Integer32,
	nsapStaticRouteMaxVbrCap        Integer32,
	nsapStaticRouteAbrSupport       INTEGER,
	nsapStaticRouteEpdSupport       INTEGER,
	nsapStaticRouteStatus		EntryStatus
}

nsapStaticRouteAddress OBJECT-TYPE
	SYNTAX	NsapAddr
	MAX-ACCESS	read-only
	STATUS	current
	DESCRIPTION
		"The value of this object identifies the destination NSAP address"
	::= { nsapStaticRouteEntry 1 }

nsapStaticRouteMask OBJECT-TYPE
	SYNTAX	Integer32
	MAX-ACCESS	read-only
	STATUS	current
	DESCRIPTION
		"The value of this object identifies the mask that is
		used for this NSAP (Network Service Access Point) address."
	::= { nsapStaticRouteEntry 2 }

nsapStaticRoutePort OBJECT-TYPE
	SYNTAX	Integer32
	MAX-ACCESS	read-create
	STATUS	current
	DESCRIPTION
		"The value of this object identifies the port through which
		this NSAP (Network Service Access Point) address can be
		reached."
	::= { nsapStaticRouteEntry 3 }

nsapStaticRouteVPI OBJECT-TYPE
	SYNTAX	Integer32
	MAX-ACCESS	read-create
	STATUS	current
	DESCRIPTION
		"The value of this object identifies the path through which
		this NSAP (Network Service Access Point) address can be
		reached."
	::= { nsapStaticRouteEntry 4 }

nsapStaticRouteCost OBJECT-TYPE
	SYNTAX	Integer32
	MAX-ACCESS	read-create
	STATUS	current
	DESCRIPTION
		"The value of this object identifies the cost
		 associated with this Static Route. This cost is
		 to be used as a metric while routing"
	::= { nsapStaticRouteEntry 5 }

nsapStaticRouteMaxCbrCap OBJECT-TYPE
	SYNTAX	Integer32
	MAX-ACCESS	read-create
	STATUS	current
	DESCRIPTION
		"The value of this object identifies the maximum capacity
		 available on this route for CBR connections"
	::= { nsapStaticRouteEntry 6 }

nsapStaticRouteMaxVbrCap OBJECT-TYPE
	SYNTAX	Integer32
	MAX-ACCESS	read-create
	STATUS	current
	DESCRIPTION
		"The value of this object identifies the maximum capacity
		 available on this route for VBR connections"
	::= { nsapStaticRouteEntry 7 }

nsapStaticRouteAbrSupport OBJECT-TYPE
	SYNTAX	INTEGER {
			  supported (1),
			  unsupported (2)
			}
	MAX-ACCESS	read-create
	STATUS	current
	DESCRIPTION
		"The value identifies the capability to support
		 ABR traffic on this route"
	::= { nsapStaticRouteEntry 8 }

nsapStaticRouteEpdSupport OBJECT-TYPE
	SYNTAX	INTEGER {
			  supported (1),
			  unsupported (2)
			}
	MAX-ACCESS	read-create
	STATUS	current
	DESCRIPTION
		"The value identifies the capability to support
		 Early Packet Discard (EPD) on this route"
	::= { nsapStaticRouteEntry 9 }


nsapStaticRouteStatus OBJECT-TYPE
	SYNTAX	EntryStatus
	MAX-ACCESS	read-create
	STATUS	current
	DESCRIPTION
		"The status of this NSAP (Network Service Access Point) address.
		Setting this object to invalid(4) causes this NSAP address to
		disappear."
	::= { nsapStaticRouteEntry 10 }

----------------------------------------------------------------------------


-- Following FTPNNI Table and its constituents are deprecated as a part of 
-- FT 7.1

-- Table for FT-PNNI Designated Transit Lists

-- This table is used for configuring Designated Transit Lists (DTLs)
-- for the FT-PNNI router. DTLs are static source routes for the FT-PNNI
-- router. The only application that uses this table currently is the
-- directed SPVC feature. Other uses are conceivable.

ftPnniDTLTable  OBJECT-TYPE
	SYNTAX  SEQUENCE OF FtPnniDTLEntry
	MAX-ACCESS  not-accessible
	STATUS  deprecated
	DESCRIPTION
		"A table of Designated Transit List entries.
		The DTLs represent statically configured FT-PNNI
		routes"
	::= { nsapGroup 5}

ftPnniDTLEntry OBJECT-TYPE
	SYNTAX	FtPnniDTLEntry
	MAX-ACCESS	not-accessible
	STATUS	deprecated
	DESCRIPTION
		"An entry in the FT-PNNI DTLble. A DTL is formed
		by concatenating rows of the table for which the
		ftPnniDTLIndex is the same"
	INDEX	{ ftPnniDTLIndex, ftPnniDTLEntryIndex }
	::= { ftPnniDTLTable 1 }

FtPnniDTLEntry ::= SEQUENCE {
		ftPnniDTLIndex              Integer32,
		ftPnniDTLEntryIndex         Integer32,
		ftPnniDTLNodePrefix         NsapPrefix,
		ftPnniDTLNodeMask           INTEGER,
		ftPnniDTLPort               Integer32,
		ftPnniDTLVPI                Integer32,
		ftPnniDTLStatus             EntryStatus
	}

ftPnniDTLIndex OBJECT-TYPE
	SYNTAX	Integer32
	MAX-ACCESS	read-only
	STATUS	deprecated
	DESCRIPTION
	"The value of this object identifies the index of a (FT-PNNI) DTL in
	the table. A DTL (Designated Transit List) is a source route of entries
	comprising a  FT-PNNI node and the corresponding logical output port at
	that node. The FT-PNNI node is given by the node's NSAP Prefix and
	mask. The logical port is given by the linkid and the VPI."
	::= { ftPnniDTLEntry 1 }

ftPnniDTLEntryIndex OBJECT-TYPE
	SYNTAX	Integer32
	MAX-ACCESS	read-only
	STATUS	deprecated
	DESCRIPTION
	"The value of this object identifies the Index of an entry within a
	given DTL. A DTL is a source route and each entry in the DTL represents
	a single hop in the source route. Each hop is represented by a
	FT-PNNI node and the logical output port at that node. An entry in
	the DTL is given an index equal to its position in the source
	route. Thus the entry corresponding to the first hop is given an
	index of 1, the second hop an index of 2 and so on."
	::= { ftPnniDTLEntry 2 }

ftPnniDTLNodePrefix OBJECT-TYPE
	SYNTAX	NsapPrefix
	MAX-ACCESS	read-create
	STATUS	deprecated
	DESCRIPTION
		"This the Prefix part of the Node ID of this DTL entry.
		In FT-PNNI, The Node IDs are represented as prefixes,
		that represents both the ID of the node and a summary
		of reachable addresses"
	::= { ftPnniDTLEntry 3 }

ftPnniDTLNodeMask OBJECT-TYPE
	SYNTAX	INTEGER (0..104)
	MAX-ACCESS	read-create
	STATUS	deprecated
	DESCRIPTION
		"This the Mask corresponding to the ftPnniDTLNodePrefix.
		This gives the length of the above prefix in number of
		bits. This can vary from 0 to 104 (13 bytes)."
	::= { ftPnniDTLEntry 4 }

ftPnniDTLPort OBJECT-TYPE
	SYNTAX	Integer32
	MAX-ACCESS	read-create
	STATUS	deprecated
	DESCRIPTION
		"This is the output port at the Node given by the above
		Node ID. This is also the port to which the next node in
		the DTL (if there is one) is connected."
	::= { ftPnniDTLEntry 5 }

ftPnniDTLVPI OBJECT-TYPE
	SYNTAX	Integer32
	MAX-ACCESS	read-create
	STATUS	deprecated
	DESCRIPTION
		"This is the output path in the output port above that
		is the signalling path to the peer given by the next
		node in the DTL."
	::= { ftPnniDTLEntry 6 }

ftPnniDTLStatus OBJECT-TYPE
	SYNTAX	EntryStatus
	MAX-ACCESS	read-create
	STATUS	deprecated
	DESCRIPTION
		"The entry status of this entry in the table."
	::= { ftPnniDTLEntry 7 }


----------------------------------------------------------------------------

-- Following FTPNNI Table and its constituents are deprecated as a part of 
-- FT 7.1

ftPnniSummaryTable   OBJECT-TYPE
	SYNTAX  SEQUENCE OF FtPnniSummaryEntry
	MAX-ACCESS  not-accessible
	STATUS  deprecated
	DESCRIPTION
		"A table of Prefixes that are used for either summarizing
		or suppressing internal and exterior reachability information
		by the FT-PNNI routing protocol"
	::= { nsapGroup 6 }

ftPnniSummaryEntry OBJECT-TYPE
	SYNTAX	FtPnniSummaryEntry
	MAX-ACCESS	not-accessible
	STATUS	deprecated
	DESCRIPTION
		"An entry in the FT-PNNI Summary table."
	INDEX	{ ftPnniSummaryAddress, ftPnniSummaryPrefixLength }
	::= { ftPnniSummaryTable 1 }

FtPnniSummaryEntry ::= SEQUENCE {
		ftPnniSummaryAddress        Integer32,
		ftPnniSummaryPrefixLength   Integer32,
		ftPnniSummaryType           INTEGER,
		ftPnniSummarySuppress       INTEGER,
		ftPnniSummaryState          INTEGER,
		ftPnniSummaryStatus         EntryStatus
}

ftPnniSummaryAddress OBJECT-TYPE
	SYNTAX	Integer32
	MAX-ACCESS	read-only
	STATUS	deprecated
	DESCRIPTION
		"The address prefix that is to be either summarized
		or suppressed by the FT-PNNI routing protocol"
	::= { ftPnniSummaryEntry 1 }

ftPnniSummaryPrefixLength OBJECT-TYPE
	SYNTAX	Integer32
	MAX-ACCESS	read-only
	STATUS	deprecated
	DESCRIPTION
		"This value is the mask for the address. This gives
		length of the address prefix in number of bits"
	::= { ftPnniSummaryEntry 2 }

ftPnniSummaryType  OBJECT-TYPE
	SYNTAX	INTEGER { internal(1), exterior(2) }
	MAX-ACCESS	read-create
	STATUS	deprecated
	DESCRIPTION
		"This value identifies the type of the summary
		being described"
	::= { ftPnniSummaryEntry 3 }

ftPnniSummarySuppress  OBJECT-TYPE
	SYNTAX	INTEGER { no(1), yes(2) }
	MAX-ACCESS	read-create
	STATUS	deprecated
	DESCRIPTION
		"The Suppress flag determinces what is to be done with
		this address. The default value (no) will indicate that
		the summary should be propagated. If the value is yes,
		this summary and any reachable address it summarizes are
		suppressed for being propagated"
	::= { ftPnniSummaryEntry 4 }

ftPnniSummaryState  OBJECT-TYPE
	SYNTAX	INTEGER { advertising(1),
			  suppressing(2),
			  inactive(3)
			}
	MAX-ACCESS	read-only
	STATUS	deprecated
	DESCRIPTION
		"This value indicates whether the summary is currently
		being advertised by the FT-PNNI routing protocol"
	::= { ftPnniSummaryEntry 5 }

ftPnniSummaryStatus  OBJECT-TYPE
	SYNTAX	EntryStatus
	MAX-ACCESS	read-create
	STATUS	deprecated
	DESCRIPTION
		"The entry status of this entry in the table."
	::= { ftPnniSummaryEntry 6 }

----------------------------------------------------------------------------

-- The UPC Configuration Group

-- This table contains a variable number of valid, user defined UPC
-- traffic policing contracts.  Other tables, for instance the SPANS
-- sigPathTable, can use this table as a common place for retrieving
-- valid traffic contracts.  SPANS looks into this table to find the
-- traffic contract to be used for policing the connectionless VC.


upcContractTable OBJECT-TYPE
	SYNTAX	SEQUENCE OF UpcContractEntry
	MAX-ACCESS	not-accessible
	STATUS	current
	DESCRIPTION
		"A table of user defined UPC traffic contracts."
	::= { upcContractGroup 1 }

upcContractEntry OBJECT-TYPE
	SYNTAX	UpcContractEntry
	MAX-ACCESS	not-accessible
	STATUS	current
	DESCRIPTION
		"A table entry containing a user defined UPC traffic contract."
	INDEX	{ upcContractKey }
	::= { upcContractTable 1 }

UpcContractEntry ::=
	SEQUENCE {
		upcContractKey				INTEGER,
		upcContractEntryStatus			EntryStatus,
		upcContractPCR01			Integer32,
		upcContractSCR01			Integer32,
		upcContractMBS01			Integer32,
		upcContractPCR0				Integer32,
		upcContractSCR0				Integer32,
		upcContractMBS0				Integer32,
		upcContractCDVT				Integer32,
		upcContractTagReq			Integer32,
		upcContractAal5Epd			Integer32,
		upcContractName				DisplayString,
		upcContractDoGCRAPolicing		INTEGER,
		upcContractIsAAL5			INTEGER,
		upcContractDoPacketDiscard		INTEGER,
		upcContractDoPPPolicing			INTEGER,
		upcContractDoUBRTagging			INTEGER,
		upcContractSchedMode			AtmConnSchedMode,
		upcContractUseAltCLPThreshold		INTEGER,
		upcContractMCR				Integer32,
		upcContractEstimatedUbrBandwidth	Integer32,
		upcContractAAL5CountingMode             AAL5CountingMode,
		upcContractServiceCategory		Integer32,
		upcContractPoliceScheme			INTEGER,
		upcContractPCR				Integer32,
		upcContractSCR				Integer32,
		upcContractMBS				Integer32,
		upcContractServiceSubCategory           INTEGER,
		upcContractCongestionBasedPeakBw	Integer32,
		upcContractBehaviorClassSelector	Integer32
	}

upcContractKey OBJECT-TYPE
	SYNTAX	INTEGER (1..32767)
	MAX-ACCESS	read-only
	STATUS	current
	DESCRIPTION
		"The key of this UPC configuration."
	::= { upcContractEntry 1 }

upcContractEntryStatus OBJECT-TYPE
	SYNTAX	EntryStatus
	MAX-ACCESS	read-create
	STATUS	current
	DESCRIPTION
		"The SNMP status of this upcContract entry."
	::= { upcContractEntry 2 }

upcContractPCR01 OBJECT-TYPE
	SYNTAX	Integer32
	MAX-ACCESS	read-create
	STATUS	deprecated
	DESCRIPTION
		"The peak cell rate (cells/sec) for cell loss priority 0+1"
	::= { upcContractEntry 3 }

upcContractSCR01 OBJECT-TYPE
	SYNTAX	Integer32
	MAX-ACCESS	read-create
	STATUS	deprecated
	DESCRIPTION
		"The sustained cell rate (cells/sec) for cell loss priority 0+1"
	::= { upcContractEntry 4 }

upcContractMBS01 OBJECT-TYPE
	SYNTAX	Integer32
	MAX-ACCESS	read-create
	STATUS	deprecated
	DESCRIPTION
		"The maximum burst size (cells) for cell loss priority 0+1"
	::= { upcContractEntry 5 }

upcContractPCR0 OBJECT-TYPE
	SYNTAX	Integer32
	MAX-ACCESS	read-create
	STATUS	deprecated
	DESCRIPTION
		"The peak cell rate (cells/sec) for cell loss priority 0"
	::= { upcContractEntry 6 }


upcContractSCR0 OBJECT-TYPE
	SYNTAX	Integer32
	MAX-ACCESS	read-create
	STATUS	deprecated
	DESCRIPTION
		"The sustained cell rate (cells/sec) for cell loss priority 0"
	::= { upcContractEntry 7 }

upcContractMBS0 OBJECT-TYPE
	SYNTAX	Integer32
	MAX-ACCESS	read-create
	STATUS	deprecated
	DESCRIPTION
		"The maximum burst size (cells) for cell loss priority 0."
	::= { upcContractEntry 8 }

upcContractCDVT OBJECT-TYPE
	SYNTAX  Integer32
	MAX-ACCESS  read-create
	STATUS  current
	DESCRIPTION
		"The Cell Delay Variation Tolerance associated with PCR's.
		 The Default CDVT values (in microseconds) for the various
		 physical media are:
		 DS1_DEFAULT_LINK_CDVT         -      5000
		 DS3_DEFAULT_LINK_CDVT         -      2500
		 E1_DEFAULT_LINK_CDVT          -      5000
		 E3_DEFAULT_LINK_CDVT          -      2500
		 J2_DEFAULT_LINK_CDVT          -      5000
		 SONET_OC3_LINK_DEFAULT_CDVT   -       250
		 SONET_OC12_LINK_DEFAULT_CDVT  -       250
		 SONET_OC48_LINK_DEFAULT_CDVT  -       250
		 TAXI_DEFAULT_LINK_CDVT        -      1000
		 TP25_DEFAULT_LINK_CDVT        -      5000
		 CTRLPORT_DEFAULT_LINK_CDVT    -      5000
		 BACKPLANE_DEFAULT_LINK_CDVT   -       100"
	::= { upcContractEntry 9 }

upcContractTagReq OBJECT-TYPE
	SYNTAX  Integer32
	MAX-ACCESS  read-create
	STATUS  deprecated
	DESCRIPTION
		"Should we tag (instead of drop) non-compliant CLP=0 cells?."
	::= { upcContractEntry 10 }

upcContractAal5Epd OBJECT-TYPE
	SYNTAX  Integer32
	MAX-ACCESS  read-create
	STATUS  deprecated
	DESCRIPTION
		"Should we do AAL5 EPD on this connection?.
		This variable has been subsumed by the two new variables
		upcContractIsAAL5 and upcContractdoPacketDiscard. These
		new variables allow us to decouple the AAL5'ness of a
		connection from whether we are going to do
		packet discard on it if it is AAL5."
	::= { upcContractEntry 11 }

upcContractName OBJECT-TYPE
	SYNTAX	DisplayString (SIZE (0..19))
	MAX-ACCESS	read-create
	STATUS	current
	DESCRIPTION
		"The name associated with this UPC traffic contract."
	::= { upcContractEntry 12 }

upcContractDoGCRAPolicing OBJECT-TYPE
	SYNTAX  INTEGER {
		  on(1),
		  off(2)
		}
	MAX-ACCESS  read-create
	STATUS  current
	DESCRIPTION
		"Should we suppress GCRA policing on connections
		using this UPC Contract ?"
	DEFVAL { on }
	::= { upcContractEntry 13 }

upcContractIsAAL5 OBJECT-TYPE
	SYNTAX  INTEGER {
		  true(1),
		  false(2)
		}
	MAX-ACCESS  read-create
	STATUS  current
	DESCRIPTION
		"Is this UPC contract using AAL5?"
	DEFVAL { false }
	::= { upcContractEntry 14 }


upcContractDoPacketDiscard OBJECT-TYPE
	SYNTAX  INTEGER {
		  on(1),
		  off(2)
		}
	MAX-ACCESS  read-create
	STATUS  current
	DESCRIPTION
		"Should we perform AAL5 Packet Discard (EPD/PPD) on this
		UPC contract. This variable only has meaning if the
		connection is also AAL5"
	DEFVAL { on }
	::= { upcContractEntry 15 }

upcContractDoPPPolicing OBJECT-TYPE
	SYNTAX  INTEGER {
			on(1),
			off(2)
		}
	MAX-ACCESS  read-create
	STATUS  current
	DESCRIPTION
		"Should we perform AAL5 Partial Packet Policing on
		this UPC contract.  This variable only has meaning if
		the connections is also AAL5."
	DEFVAL { off }
	::= { upcContractEntry 16 }

upcContractDoUBRTagging OBJECT-TYPE
	SYNTAX  INTEGER {
			on(1),
			off(2)
		}
	MAX-ACCESS  read-create
	STATUS  deprecated
	DESCRIPTION
		"Should we perform tagging (set CLP=1) of all cells of
		connections that use this UBR traffic contract?"
	DEFVAL { off }
	::= { upcContractEntry 17 }

upcContractSchedMode OBJECT-TYPE
       SYNTAX  AtmConnSchedMode
       MAX-ACCESS  read-create
       STATUS  current
       DESCRIPTION
		"This variable indicates the scheduling mode that
		 is  requested for connections that use this UPC
		 contract."
       DEFVAL { default }
       ::= { upcContractEntry 18}

upcContractUseAltCLPThreshold OBJECT-TYPE
	SYNTAX  INTEGER {
			on(1),
			off(2)
		}
	MAX-ACCESS  read-create
	STATUS  current
	DESCRIPTION
		"This flag determines whether the Series-DW per-VC
		Alternate CLP Threshold should be used for all
		non-ABR VC's created with this UPC contract."
	DEFVAL { off }
	::= { upcContractEntry 19 }

upcContractMCR OBJECT-TYPE
	SYNTAX  Integer32
	MAX-ACCESS  read-create
	STATUS  current
	DESCRIPTION
		"The minimum cell rate (cells/sec) for ABR connections."
	::= { upcContractEntry 20 }

upcContractEstimatedUbrBandwidth OBJECT-TYPE
	SYNTAX  Integer32
	MAX-ACCESS  read-create
	STATUS  current
	DESCRIPTION
		"The estimated UBR bandwidth in Kilo-CPS associated with
		this UPC contract"
	::= { upcContractEntry 21 }

upcContractAAL5CountingMode OBJECT-TYPE
	SYNTAX  AAL5CountingMode
	MAX-ACCESS  read-create
	STATUS  current
	DESCRIPTION
		"The Counter mode for an AAL5 connection"
	DEFVAL { default }
	::= { upcContractEntry 22 }

upcContractServiceCategory OBJECT-TYPE
	SYNTAX  Integer32
	MAX-ACCESS  read-create
	STATUS  current
	DESCRIPTION
		"Index of this service category within serviceCategoryTable"
	::= { upcContractEntry 23 }

upcContractPoliceScheme OBJECT-TYPE
	SYNTAX  INTEGER {
			cbr1(1),
			cbr0(2),
			cbr0tag(3),
			vbr1(4),
			vbr2(5),
			vbr3(6),
			abr1(7),
			ubr1(8),
			ubr2(9)
		}
	MAX-ACCESS  read-create
	STATUS  current
	DESCRIPTION
		"It identifies the policing associated with the UPC
		 contract as defined in the ATM Forum TM 4.0
		 specifications. However, the policing schemes cbr0
		 and cbr0tag are specific to FORE switches"
	::= { upcContractEntry 24 }

upcContractPCR OBJECT-TYPE
	SYNTAX	Integer32
	MAX-ACCESS	read-create
	STATUS	current
	DESCRIPTION
		"The peak cell rate (cells/sec)"
	::= { upcContractEntry 25 }

upcContractSCR OBJECT-TYPE
	SYNTAX	Integer32
	MAX-ACCESS	read-create
	STATUS	current
	DESCRIPTION
		"The sustained cell rate (cells/sec). It also holds
		 the PCR0 value for cbr0 & cbr0tag contracts"
	::= { upcContractEntry 26 }

upcContractMBS OBJECT-TYPE
	SYNTAX	Integer32
	MAX-ACCESS	read-create
	STATUS	current
	DESCRIPTION
		"The maximum burst size (cells)"
	::= { upcContractEntry 27 }

upcContractServiceSubCategory OBJECT-TYPE
	SYNTAX  INTEGER (1..16)
	MAX-ACCESS  read-create
	STATUS  current
	DESCRIPTION
		"The Service subcategory for this connection.Default value is 1."
	DEFVAL { 1 }
	::= { upcContractEntry 28 }

upcContractCongestionBasedPeakBw OBJECT-TYPE
	SYNTAX	Integer32
	MAX-ACCESS	read-create
	STATUS	current
	DESCRIPTION
		"The expected peak bandwidth for this congestion
		 based UPC contract"
	::= { upcContractEntry 29 }

upcContractBehaviorClassSelector OBJECT-TYPE
        SYNTAX  Integer32
        MAX-ACCESS  read-create
        STATUS  current
        DESCRIPTION
                "The behavior class selector (BCS) for this UPC contract"
        ::= { upcContractEntry 30 }

------------------------------------------------------------------------

-- The QOS Class Expansion Group

-- This table contains a user defined expansion of the various QOS classes
--

qosClassExpansionTable OBJECT-TYPE
       SYNTAX  SEQUENCE OF QosClassExpansionEntry
       MAX-ACCESS  not-accessible
       STATUS  current
       DESCRIPTION
		"A table of user defined QOS Class Expansions."
       ::= { qosClassExpansionGroup 1 }


qosClassExpansionEntry OBJECT-TYPE
       SYNTAX  QosClassExpansionEntry
       MAX-ACCESS  not-accessible
       STATUS  current
       DESCRIPTION
		"A table entry containing a user defined QOS Class Expansion."
       INDEX   { qosClassExpansionKey, qosClassValue }
       ::= { qosClassExpansionTable 1 }


QosClassExpansionEntry ::=
       SEQUENCE {
	       qosClassExpansionKey		Integer32,
	       qosClassValue			INTEGER,
	       qosClassExpansionEntryStatus	EntryStatus,
	       qosClassFwdCtd			INTEGER,
	       qosClassFwdCdv			INTEGER,
	       qosClassBackCdv			INTEGER,
	       qosClassFwdClr			INTEGER,	
	       qosClassBackClr			INTEGER,
	       qosClassName                     DisplayString
	}

qosClassExpansionKey OBJECT-TYPE
       SYNTAX  Integer32
       MAX-ACCESS  not-accessible
       STATUS  current
       DESCRIPTION
	       "The unique key for the set of entries in this table that
		make up a QOS Class Mapping table.  Only one entry for
		each Class is allowed per key."
       ::= { qosClassExpansionEntry 1 }

qosClassValue OBJECT-TYPE
       SYNTAX  INTEGER {
		       class0(1),
		       class1(2),
		       class2(3),
		       class3(4),
		       class4(5)
	       }
       MAX-ACCESS  not-accessible
       STATUS  current
       DESCRIPTION
	       "QOS Class which needs to be expanded. If a class does not
		exist for a specific Expansion Key, all qos parameters
		will be interpreted as any acceptable qos parameter
		value."
       ::= { qosClassExpansionEntry 2 }

qosClassExpansionEntryStatus OBJECT-TYPE
       SYNTAX  EntryStatus
       MAX-ACCESS  read-create
       STATUS  current
       DESCRIPTION
	       "The SNMP status of this Expansion entry."
       ::= { qosClassExpansionEntry 3 }

--
-- QOS Expansions
--

qosClassFwdCtd OBJECT-TYPE
       SYNTAX  INTEGER (0..16777215)
       MAX-ACCESS  read-create
       STATUS  current
       DESCRIPTION
	       "The maximum acceptable forward Cell Transfer Delay in
		microseconds to be used for this expansion.
		A value of 16777215 will signify any acceptable forward CTD
		value."
       DEFVAL { 16777215 }
       ::= { qosClassExpansionEntry 4 }

qosClassFwdCdv OBJECT-TYPE
       SYNTAX  INTEGER (0..16777215)
       MAX-ACCESS  read-create
       STATUS  current
       DESCRIPTION
	       "The maximum acceptable peak to peak forward Cell Delay
		Variation in micro-seconds to be used for this
		expansion. A value of 16777215 will signify any acceptable
		forward CDV value."
       DEFVAL { 16777215 }
       ::= { qosClassExpansionEntry 5 }

qosClassBackCdv OBJECT-TYPE
       SYNTAX  INTEGER (0..16777215)
       MAX-ACCESS  read-create
       STATUS  current
       DESCRIPTION
	       "The maximum acceptable peak to peak backward Cell Delay
		Variation in micro-seconds to be used for this
		expansion. A value of 16777215 will signify any acceptable
		backward CDV value."
       DEFVAL { 16777215 }
       ::= { qosClassExpansionEntry 6 }

qosClassFwdClr OBJECT-TYPE
       SYNTAX  INTEGER (1..255)
       MAX-ACCESS  read-create
       STATUS  current
       DESCRIPTION
	       "10 raised to the power of this value signifies the
		maximum acceptable forward Cell Loss Ratio
		value to be used for this expansion. The valid values
		are from 1 to 15 (both inclusive) and 255. A value of
		255 will signify any acceptable forward CLR value."
       DEFVAL { 255 }
       ::= { qosClassExpansionEntry 7 }

qosClassBackClr OBJECT-TYPE
       SYNTAX  INTEGER (1..255)
       MAX-ACCESS  read-create
       STATUS  current
       DESCRIPTION
	       "10 raised to the power of this value signifies the
		maximum acceptable backward Cell Loss Ratio
		value to be used for this expansion. The valid values
		are from 1 to 15 (both inclusive) and 255. A value of
		255 will signify any acceptable backward CLR value."
       DEFVAL { 255 }
       ::= { qosClassExpansionEntry 8 }

qosClassName OBJECT-TYPE
       SYNTAX  DisplayString (SIZE (0..19))
       MAX-ACCESS  read-create
       STATUS  current
       DESCRIPTION
	       "A name associated with this entry in the qos class table"
       ::= { qosClassExpansionEntry 9 }


-----------------------------------------------------------------------
-- Qos Metric Table

pathExtQosMetricTable OBJECT-TYPE
	SYNTAX  SEQUENCE OF PathExtQosMetricEntry
	MAX-ACCESS  not-accessible
	STATUS  current
	DESCRIPTION
		"Qos metric table for path extension"
	::= { pathExtGroup 1 }

pathExtQosMetricEntry OBJECT-TYPE
	SYNTAX  PathExtQosMetricEntry
	MAX-ACCESS  not-accessible
	STATUS  current
	DESCRIPTION
		""
	INDEX   { pathExtQosMetricIndex }
	::= { pathExtQosMetricTable 1 }

PathExtQosMetricEntry ::= SEQUENCE {
	pathExtQosMetricIndex       Integer32,
	pathExtQosMetricMaxCtd      Integer32,
	pathExtQosMetricMaxCdv      Integer32,
	pathExtQosMetricMaxClr      Integer32,
	pathExtQosMetricEntryStatus EntryStatus
	}

pathExtQosMetricIndex OBJECT-TYPE
	SYNTAX  Integer32
	MAX-ACCESS  not-accessible
	STATUS  current
	DESCRIPTION
		""
	::= { pathExtQosMetricEntry 1 }

pathExtQosMetricMaxCtd OBJECT-TYPE
	SYNTAX  Integer32
	MAX-ACCESS  read-create
	STATUS  current
	DESCRIPTION
		"cell transfer delay in microseconds"
	::= { pathExtQosMetricEntry 2 }

pathExtQosMetricMaxCdv OBJECT-TYPE
	SYNTAX  Integer32
	MAX-ACCESS  read-create
	STATUS  current
	DESCRIPTION
		"cell delay variation in microseconds"
	::= { pathExtQosMetricEntry 3 }

pathExtQosMetricMaxClr OBJECT-TYPE
	SYNTAX  Integer32
	MAX-ACCESS  read-create
	STATUS  current
	DESCRIPTION
		"cell loss ratio. 10**(-n) where n is the returned value"
	::= { pathExtQosMetricEntry 4 }

pathExtQosMetricEntryStatus OBJECT-TYPE
	SYNTAX  EntryStatus
	MAX-ACCESS  read-create
	STATUS  current
	DESCRIPTION
		""
	::= { pathExtQosMetricEntry 5 }


------------------------------------------------------------------------

-- Term Path extension table

pathExtTable OBJECT-TYPE
	SYNTAX  SEQUENCE OF PathExtEntry
	MAX-ACCESS  not-accessible
	STATUS  current
	DESCRIPTION
		"path extension table"
	::= { pathExtGroup 2 }

pathExtEntry OBJECT-TYPE
	SYNTAX  PathExtEntry
	MAX-ACCESS  not-accessible
	STATUS  current
	DESCRIPTION
		"A table entry containing path Qos Metric information."
	INDEX   { pathPort, pathVPI }
	::= { pathExtTable 1 }

PathExtEntry ::=
	SEQUENCE {
	pathExtCbrMetric	Integer32,
	pathExtRtVbrMetric	Integer32,
	pathExtNrtVbrMetric	Integer32,
	pathExtAbrMetric	Integer32,
	pathExtUbrMetric	Integer32,
	pathExtEntryStatus      EntryStatus
	}

pathExtCbrMetric OBJECT-TYPE
	SYNTAX  Integer32
	MAX-ACCESS  read-create
	STATUS  current
	DESCRIPTION
		"index to the path ext qos metric table"
	::= { pathExtEntry 1 }

pathExtRtVbrMetric OBJECT-TYPE
	SYNTAX  Integer32
	MAX-ACCESS  read-create
	STATUS  current
	DESCRIPTION
		"index to the path ext qos metric table"
	::= { pathExtEntry 2 }

pathExtNrtVbrMetric OBJECT-TYPE
	SYNTAX  Integer32
	MAX-ACCESS  read-create
	STATUS  current
	DESCRIPTION
		"index to the path ext qos metric table"
	::= { pathExtEntry 3 }

pathExtAbrMetric OBJECT-TYPE
	SYNTAX  Integer32
	MAX-ACCESS  read-create
	STATUS  current
	DESCRIPTION
		"index to the path ext qos metric table"
	::= { pathExtEntry 4 }

pathExtUbrMetric OBJECT-TYPE
	SYNTAX  Integer32
	MAX-ACCESS  read-create
	STATUS  current
	DESCRIPTION
		"index to the path ext qos metric table"
	::= { pathExtEntry 5 }

pathExtEntryStatus OBJECT-TYPE
	SYNTAX  EntryStatus
	MAX-ACCESS  read-create
	STATUS  current
	DESCRIPTION
	    ""
	::= { pathExtEntry 6 }

------------------------------------------------------------------------

-- Orig Path extension table

outputPathExtTable OBJECT-TYPE
	SYNTAX  SEQUENCE OF OutputPathExtEntry
	MAX-ACCESS  not-accessible
	STATUS  current
	DESCRIPTION
		""
	::= { pathExtGroup 3 }

outputPathExtEntry OBJECT-TYPE
	SYNTAX  OutputPathExtEntry
	MAX-ACCESS  not-accessible
	STATUS  current
	DESCRIPTION
		""
	INDEX   { opathPort, opathVPI }
	::= { outputPathExtTable 1 }

OutputPathExtEntry ::=
	SEQUENCE {
	opathExtCbrMetric	Integer32,
	opathExtRtVbrMetric	Integer32,
	opathExtNrtVbrMetric	Integer32,
	opathExtAbrMetric	Integer32,
	opathExtUbrMetric	Integer32,
	opathExtEntryStatus     EntryStatus
	}

opathExtCbrMetric OBJECT-TYPE
	SYNTAX  Integer32
	MAX-ACCESS  read-create
	STATUS  current
	DESCRIPTION
		"index to the path ext qos metric table"
	::= { outputPathExtEntry 1 }

opathExtRtVbrMetric OBJECT-TYPE
	SYNTAX  Integer32
	MAX-ACCESS  read-create
	STATUS  current
	DESCRIPTION
		"index to the path ext qos metric table"
	::= { outputPathExtEntry 2 }

opathExtNrtVbrMetric OBJECT-TYPE
	SYNTAX  Integer32
	MAX-ACCESS  read-create
	STATUS  current
	DESCRIPTION
		"index to the path ext qos metric table"
	::= { outputPathExtEntry 3 }

opathExtAbrMetric OBJECT-TYPE
	SYNTAX  Integer32
	MAX-ACCESS  read-create
	STATUS  current
	DESCRIPTION
		"index to the path ext qos metric table"
	::= { outputPathExtEntry 4 }

opathExtUbrMetric OBJECT-TYPE
	SYNTAX  Integer32
	MAX-ACCESS  read-create
	STATUS  current
	DESCRIPTION
		"index to the path ext qos metric table"
	::= { outputPathExtEntry 5 }

opathExtEntryStatus OBJECT-TYPE
	SYNTAX  EntryStatus
	MAX-ACCESS  read-create
	STATUS  current
	DESCRIPTION
		""
	::= { outputPathExtEntry 6 }

------------------------------------------------------------------------

-- VP group

vpGroupTable OBJECT-TYPE
	SYNTAX  SEQUENCE OF VpGroupEntry
	MAX-ACCESS  not-accessible
	STATUS  current
	DESCRIPTION
		""
	::= { pathExtGroup 4 }

vpGroupEntry OBJECT-TYPE
	SYNTAX  VpGroupEntry
	MAX-ACCESS  not-accessible
	STATUS  current
	DESCRIPTION
		""
	INDEX   { vpGroupIndex, vpGroupPort, vpGroupVPI }
	::= { vpGroupTable 1 }

VpGroupEntry ::=
	SEQUENCE {
	vpGroupIndex       Integer32,
	vpGroupPort        Integer32,
	vpGroupVPI         Integer32,
	vpGroupVPCI        Integer32,
	vpGroupEntryStatus EntryStatus
	}

vpGroupIndex OBJECT-TYPE
	SYNTAX	Integer32
	MAX-ACCESS	read-only
	STATUS	current
	DESCRIPTION
		"Zero mean not belong to any vpgroup group"
	::= { vpGroupEntry 1 }

vpGroupPort OBJECT-TYPE
	SYNTAX	Integer32
	MAX-ACCESS	read-only
	STATUS	current
	DESCRIPTION
		""
	::= { vpGroupEntry 2 }

vpGroupVPI OBJECT-TYPE
	SYNTAX	Integer32
	MAX-ACCESS	read-only
	STATUS	current
	DESCRIPTION
		""
	::= { vpGroupEntry 3 }

vpGroupVPCI OBJECT-TYPE
	SYNTAX	Integer32
	MAX-ACCESS	read-create
	STATUS	current
	DESCRIPTION
		""
	::= { vpGroupEntry 4 }

vpGroupEntryStatus OBJECT-TYPE
	SYNTAX  EntryStatus
	MAX-ACCESS  read-create
	STATUS  current
	DESCRIPTION
		""
	::= { vpGroupEntry 5 }
------------------------------------------------------------------------
-- The Pool Configuration Group.
--
-- This group has the pool configuration information.
-- The two parameters needed for pool configuration are:
-- # of Point-to-Point calls and # of PMP calls.

poolConfPPCalls OBJECT-TYPE
	SYNTAX  Integer32
	MAX-ACCESS  read-write
	STATUS  current
	DESCRIPTION
		"Specifies the number of point to point calls that the
		switch should handle through pools. The switch comes up
		with enough resources in the pools to handle so many point
		to point calls. The new value will take effect at the next
		reboot."
	::= { poolConfGroup 1 }


poolConfPMPCalls OBJECT-TYPE
	SYNTAX  Integer32
	MAX-ACCESS  read-write
	STATUS  current
	DESCRIPTION
		"Specifies the number of point to multipoint calls that the
		switch should handle through pools. The switch comes up
		with enough resources in the pools to handle so many point
		to multipoint calls. The new value will take effect at the next
		reboot."
	::= { poolConfGroup 2 }

poolConfMaxPercentage OBJECT-TYPE
	SYNTAX  Integer32
	MAX-ACCESS  read-write
	STATUS  current
	DESCRIPTION
		"Limits the max percentage of the main heap that can be taken
		for pool configuration purposes."
	::= { poolConfGroup 5 }

------------------------------------------------------------------------

-- The Switch Board Group

swBoardTable OBJECT-TYPE
	SYNTAX	SEQUENCE OF SwBoardEntry
	MAX-ACCESS	not-accessible
	STATUS	current
	DESCRIPTION
		"A table of ATM switch cluster configuration information."
	::= { swBoardGroup 1 }

swBoardEntry OBJECT-TYPE
	SYNTAX	SwBoardEntry
	MAX-ACCESS	not-accessible
	STATUS	current
	DESCRIPTION
		"A table entry containing ATM switch cluster information,
		index by the switch board."
	INDEX	{ swBoardIndex }
	::= { swBoardTable 1 }

SwBoardEntry ::=
	SEQUENCE {
		swBoardIndex		Integer32,
		swBoardMaxPaths		Integer32,
		swBoardMaxChannels	Integer32,
		swBoardAtmAddress	SpansAddress,
		swBoardUptime		TimeTicks,
		swBoardCDV		Integer32,
		swBoardPolicingAction	INTEGER,
		swBoardNsapPrefix	NsapPrefix,
		swBoardClockScalingFactor  Integer32,
		swBoardDebugMode        INTEGER,
		swBoardMulticastMode	INTEGER,
		swBoardFingerMode       INTEGER,
		swBoardATMLayerOAM	INTEGER
	}

swBoardIndex OBJECT-TYPE
	SYNTAX	Integer32
	MAX-ACCESS	read-only
	STATUS	current
	DESCRIPTION
		"The index of this switch board within the ATM switch cluster."
	::= { swBoardEntry 1 }

swBoardMaxPaths OBJECT-TYPE
	SYNTAX	Integer32
	MAX-ACCESS	read-only
	STATUS	current
	DESCRIPTION
		"The maximum number of input VPIs (Virtual Path Identifier)
		on this switch board."
	::= { swBoardEntry 2 }

swBoardMaxChannels OBJECT-TYPE
	SYNTAX	Integer32
	MAX-ACCESS	read-only
	STATUS	current
	DESCRIPTION
		"The maximum number of input VCIs (Virtual Channel Identifiers)
		on this switch board."
	::= { swBoardEntry 3 }

swBoardAtmAddress OBJECT-TYPE
	SYNTAX	SpansAddress
	MAX-ACCESS	read-only
	STATUS	current
	DESCRIPTION
		"The address of this ATM switch board."
	::= { swBoardEntry 4 }

swBoardUptime OBJECT-TYPE
	SYNTAX	TimeTicks
	MAX-ACCESS	read-only
	STATUS	current
	DESCRIPTION
		"The length of time this ATM switch board has been up,
		in hundredths of a second."
	::= { swBoardEntry 5 }

swBoardCDV OBJECT-TYPE
	SYNTAX	Integer32
	MAX-ACCESS	read-write
	STATUS	deprecated
	DESCRIPTION
		"The switch board Cell Delay Variation (CDV) specified
		in microseconds, indicates the time window in which
		a cell may be received on a connection and be accepted.
		A cell that is received on a connection outside the
		CDV window will be tagged or dropped as indicated by the
		swBoardPolicingAction object. The boardCDV is the default
		CDV for all the connection on this switch board. Individual
		connections can be set to explicitly override this value."
	::= { swBoardEntry 6 }

swBoardPolicingAction OBJECT-TYPE
	SYNTAX	INTEGER {
			tag(1),
			drop(2)
		}
	MAX-ACCESS	read-write
	STATUS	deprecated
	DESCRIPTION
		"This object indicates the action the switch board will take
		in case of bandwidth violation. The swBoardPolicingAction is
		the default policing action for all the connections on this
		switch board. Individual connections can be set to explicitly
		override this default action."
	::= { swBoardEntry 7 }

swBoardNsapPrefix OBJECT-TYPE
	SYNTAX	NsapPrefix
	MAX-ACCESS	read-write
	STATUS	current
	DESCRIPTION
		"The default NSAP (Network Service Access Point) prefix for
		this ATM switch board. The NSAP prefix will be used in the
		ILMI address registration message as well as the 'hello-indication'
		SPANS-NNI message."
	::= { swBoardEntry 8 }

swBoardClockScalingFactor OBJECT-TYPE
	SYNTAX	Integer32
	MAX-ACCESS	read-write
	STATUS	current
	DESCRIPTION
		"This specifies the value written into the switch boards
		Time Scaling Factor register.  See Sec. 3.2.1 for more info.
		The Time Scaling Factor is an 8-bit register that determines
		the number of 25ns clock cycles that occur between
		increments of the Time and Interrupt Timer Reigsters.
		Increasing the Time Scale Factor increases the burst
		tolerance that can be represented by the policer (in multiples
		of .838 seconds) while reducing the precision of the policer
		by a similar factor. The possible values for this variable
		are 1 through 255."
	::= { swBoardEntry 9 }

swBoardDebugMode OBJECT-TYPE
	SYNTAX  INTEGER {
			off(1),
			on(2)
		}
	MAX-ACCESS  read-write
	STATUS  current
	DESCRIPTION
		"This object indicates whether or not debugging services are
		available for this switch."
	::= { swBoardEntry 10 }

swBoardMulticastMode OBJECT-TYPE
	SYNTAX	INTEGER {
			non-extended(1),
			extended(2)
		}
	MAX-ACCESS	read-only
	STATUS	current
	DESCRIPTION
		"This object identifies the mode in which this ATM
		switch board is operating.  Extended-mode provides
		greater flexibility when selecting VCI for point to
		multipoint connections.  Non-extended (mixed) mode
		is more restrictive.  If any series A or B netmods
		are present, the switch board should operate in
		non-extended mode."
	::= { swBoardEntry 11 }

swBoardFingerMode OBJECT-TYPE
	SYNTAX  INTEGER {
			disabled(1),
			enabled(2)
		}
	MAX-ACCESS  read-write
	STATUS  current
	DESCRIPTION
		"This object indicates whether or not finger services are
		available for this switch."
	::= { swBoardEntry 12 }

swBoardATMLayerOAM OBJECT-TYPE
	SYNTAX  INTEGER {
			enabled(1),
			disabled(2)
		}
	MAX-ACCESS  read-write
	STATUS  deprecated
	DESCRIPTION
		"This object specifies whether the processing of ATM layer
		OAM cells by this switch board is enabled or disabled."
	DEFVAL  { disabled }
	::= { swBoardEntry 13 }


------------------------------------------------------------------------
-- The Switch Board Topology Group

swBoardTopoTable OBJECT-TYPE
	SYNTAX	SEQUENCE OF SwBoardTopoEntry
	MAX-ACCESS	not-accessible
	STATUS	current
	DESCRIPTION
		"A table of switch board topology general information."
	::= { swBoardTopologyGroup 1 }

swBoardTopoEntry OBJECT-TYPE
	SYNTAX	SwBoardTopoEntry
	MAX-ACCESS	not-accessible
	STATUS	current
	DESCRIPTION
		"A table entry containing switch board topology information."
	INDEX	{ swBoardTopoIndex }
	::= { swBoardTopoTable 1 }

SwBoardTopoEntry ::=
	SEQUENCE {
		swBoardTopoIndex		Integer32,
		swBoardTopoNumberOfLinks	Integer32
	}

swBoardTopoIndex OBJECT-TYPE
	SYNTAX	Integer32
	MAX-ACCESS	read-only
	STATUS	current
	DESCRIPTION
		"The index of this switch board within the ATM switch cluster.
		This object should be the same as the swBoardIndex."
	::= { swBoardTopoEntry 1 }

swBoardTopoNumberOfLinks OBJECT-TYPE
	SYNTAX	Integer32
	MAX-ACCESS	read-only
	STATUS	current
	DESCRIPTION
		"Current number of inter-switch links known by
		this switch board."
	::= { swBoardTopoEntry 2 }


------------------------------------------------------------------------

swBoardLinkTable OBJECT-TYPE
	SYNTAX	SEQUENCE OF SwBoardLinkEntry
	MAX-ACCESS	not-accessible
	STATUS	current
	DESCRIPTION
		"A table of ATM links that are known to a given
		switch board in the switch cluster. If all boards in
		the switch cluster are interconnected, all
		swBoardLinkEntries will be identical."
	::= { swBoardTopologyGroup 2 }

swBoardLinkEntry OBJECT-TYPE
	SYNTAX	SwBoardLinkEntry
	MAX-ACCESS	not-accessible
	STATUS	current
	DESCRIPTION
		"A table entry containing link information
		known to a given switch board."
	INDEX	{ swBoardLinkIndex, swBoardLinkSrc, swBoardLinkDest }
	::= { swBoardLinkTable 1 }

SwBoardLinkEntry ::=
	SEQUENCE {
		swBoardLinkIndex	Integer32,
		swBoardLinkSrc		SpansAddress,
		swBoardLinkDest		SpansAddress,
		swBoardLinkCapacity	Integer32,
		swBoardLinkAge		Integer32
	}

swBoardLinkIndex OBJECT-TYPE
	SYNTAX	Integer32
	MAX-ACCESS	read-only
	STATUS	current
	DESCRIPTION
		"The index of this switch board within the ATM switch cluster.
		This object should be the same as the swBoardIndex."
	::= { swBoardLinkEntry 1 }

swBoardLinkSrc OBJECT-TYPE
	SYNTAX	SpansAddress
	MAX-ACCESS	read-only
	STATUS	current
	DESCRIPTION
		"The ATM address of the source switch of this link."
	::= { swBoardLinkEntry 2 }

swBoardLinkDest OBJECT-TYPE
	SYNTAX	SpansAddress
	MAX-ACCESS	read-only
	STATUS	current
	DESCRIPTION
		"The ATM address of the destination switch of this link."
	::= { swBoardLinkEntry 3 }

swBoardLinkCapacity OBJECT-TYPE
	SYNTAX	Integer32
	MAX-ACCESS	read-only
	STATUS	current
	DESCRIPTION
		"The free capacity of this link in kilobits per second."
	::= { swBoardLinkEntry 4 }

swBoardLinkAge OBJECT-TYPE
	SYNTAX	Integer32
	MAX-ACCESS	read-only
	STATUS	current
	DESCRIPTION
		"The freshness of the information about this link. The
		actual value has no units associated with it. It should be
		used for comparison."
	::= { swBoardLinkEntry 5 }


------------------------------------------------------------------------
-- The OAM Group

oamGeneratingChannelTable OBJECT-TYPE
	SYNTAX	SEQUENCE OF OamGeneratingChannelEntry
	MAX-ACCESS	not-accessible
	STATUS	current
	DESCRIPTION
		"When an AIS cell is generated on a particular channel
		it gets added to this table.  If a channel is deleted the
		corresponding entry is removed from this table."
	::= { oamGroup 1 }

oamGeneratingChannelEntry OBJECT-TYPE
	SYNTAX	OamGeneratingChannelEntry
	MAX-ACCESS	not-accessible
	STATUS	current
	DESCRIPTION
		"A table entry containing a channel which has
		generated AIS cells."
	INDEX	{ chanPort, chanVPI, chanVCI }
	::= { oamGeneratingChannelTable 1 }

OamGeneratingChannelEntry ::=
	SEQUENCE {
		oamGeneratingChannelCells		Counter32
	}

oamGeneratingChannelCells OBJECT-TYPE
	SYNTAX	Counter32
	MAX-ACCESS	read-only
	STATUS	current
	DESCRIPTION
		"The number of AIS OAM cells generated on this channel."
	::= { oamGeneratingChannelEntry 1 }

oamGeneratingOpathTable OBJECT-TYPE
	SYNTAX	SEQUENCE OF OamGeneratingOpathEntry
	MAX-ACCESS	not-accessible
	STATUS	current
	DESCRIPTION
		"When an RDI cell is generated on a particular
		outgoing path it gets added to this table.  If an
		outgoing path is deleted the corresponding entry
		is removed from this table."
	::= { oamGroup 2 }

oamGeneratingOpathEntry OBJECT-TYPE
	SYNTAX	OamGeneratingOpathEntry
	MAX-ACCESS	not-accessible
	STATUS	current
	DESCRIPTION
		"A table entry containing an outgoing path which
		has generated RDI cells."
	INDEX	{ opathPort, opathVPI }
	::= { oamGeneratingOpathTable 1 }

OamGeneratingOpathEntry ::=
	SEQUENCE {
		oamGeneratingOpathCells		Counter32
	}

oamGeneratingOpathCells OBJECT-TYPE
	SYNTAX	Counter32
	MAX-ACCESS	read-only
	STATUS	current
	DESCRIPTION
		"The number of RDI OAM cells generated on this path."
	::= { oamGeneratingOpathEntry 1 }

oamGeneratingPathrTable OBJECT-TYPE
	SYNTAX	SEQUENCE OF OamGeneratingPathrEntry
	MAX-ACCESS	not-accessible
	STATUS	current
	DESCRIPTION
		"When an AIS cell is generated on a particular
		through path it gets added to this table.  If a
		through path is deleted the corresponding entry
		is removed from this table."
	::= { oamGroup 3 }

oamGeneratingPathrEntry OBJECT-TYPE
	SYNTAX	OamGeneratingPathrEntry
	MAX-ACCESS	not-accessible
	STATUS	current
	DESCRIPTION
		"A table entry containing a through path which
		has generated AIS cells."
	INDEX	{ pathrInputPort, pathrInputVPI, pathrOutputPort, pathrOutputVPI }
	::= { oamGeneratingPathrTable 1 }

OamGeneratingPathrEntry ::=
	SEQUENCE {
		oamGeneratingPathrCells		Counter32
	}

oamGeneratingPathrCells OBJECT-TYPE
	SYNTAX	Counter32
	MAX-ACCESS	read-only
	STATUS	current
	DESCRIPTION
		"The number of AIS OAM cells generated on this path."
	::= { oamGeneratingPathrEntry 1 }

oamReceivedPathTable OBJECT-TYPE
	SYNTAX	SEQUENCE OF OamReceivedPathEntry
	MAX-ACCESS	not-accessible
	STATUS	current
	DESCRIPTION
		"When an OAM cell is received on a particular
		terminating path it gets added to this table.  If a
		terminating path is deleted the corresponding entry
		is removed from this table."
	::= { oamGroup 4 }

oamReceivedPathEntry OBJECT-TYPE
	SYNTAX	OamReceivedPathEntry
	MAX-ACCESS	not-accessible
	STATUS	current
	DESCRIPTION
		"A table entry containing a terminating path which
		has received OAM cells."
	INDEX	{ pathPort, pathVPI }
	::= { oamReceivedPathTable 1 }

OamReceivedPathEntry ::=
	SEQUENCE {
		oamReceivedPathAISCells		Counter32,
		oamReceivedPathRDICells		Counter32
	}

oamReceivedPathAISCells OBJECT-TYPE
	SYNTAX	Counter32
	MAX-ACCESS	read-only
	STATUS	current
	DESCRIPTION
		"The number of AIS OAM cells received on this path."
	::= { oamReceivedPathEntry 1 }

oamReceivedPathRDICells OBJECT-TYPE
	SYNTAX	Counter32
	MAX-ACCESS	read-only
	STATUS	current
	DESCRIPTION
		"The number of RDI OAM cells received on this path."
	::= { oamReceivedPathEntry 2 }

------------------------------------------------------------------------
-- The OAM Group

guardTable OBJECT-TYPE
	SYNTAX	SEQUENCE OF GuardEntry
	MAX-ACCESS	not-accessible
	STATUS	current
	DESCRIPTION
		"The OAM guards for each board in a switch."
	::= { guardGroup 1 }

guardEntry OBJECT-TYPE
	SYNTAX	GuardEntry
	MAX-ACCESS	not-accessible
	STATUS	current
	DESCRIPTION
		"A table entry containing the guards for a board."
	INDEX	{ boardIndex }
	::= { guardTable 1 }

GuardEntry ::=
	SEQUENCE {
		oamGuard		TimeStamp
	}

oamGuard OBJECT-TYPE
	SYNTAX	TimeStamp
	MAX-ACCESS	read-only
	STATUS	current
	DESCRIPTION
		"The value of sysUpTime the last time an OAM cell was
		generated/received on this board."
	::= { guardEntry 1 }

------------------------------------------------------------------------
-- The Traps Configuration Group

trapNumberOfDest OBJECT-TYPE
	SYNTAX	Integer32
	MAX-ACCESS	read-only
	STATUS	deprecated
	DESCRIPTION
		"The current number of configured trap destinations.
		All traps are sent to all destinations."
	::= { trapConfGroup 1 }

trapDestTable OBJECT-TYPE
	SYNTAX	SEQUENCE OF TrapDestEntry
	MAX-ACCESS	not-accessible
	STATUS	deprecated
	DESCRIPTION
		"A table of destinations to which the agent sends traps."
	::= { trapConfGroup 2 }

trapDestEntry OBJECT-TYPE
	SYNTAX	TrapDestEntry
	MAX-ACCESS	not-accessible
	STATUS	deprecated
	DESCRIPTION
		"A table entry containing address of a management station,
		to which the agent sends traps."
	INDEX	{ trapDest }
	::= { trapDestTable 1 }

TrapDestEntry ::=
	SEQUENCE {
		trapDest	IpAddress,
		trapDestStatus	EntryStatus
	}

trapDest OBJECT-TYPE
	SYNTAX	IpAddress
	MAX-ACCESS	read-only
	STATUS	deprecated
	DESCRIPTION
		"Address to which the agent sends traps. Usually a network
		management station sets this address to itself."
	::= { trapDestEntry 1 }

trapDestStatus OBJECT-TYPE
	SYNTAX	EntryStatus
	MAX-ACCESS	read-create
	STATUS	deprecated
	DESCRIPTION
		"The status of this trap destination entry."
	::= { trapDestEntry 2 }

------------------------------------------------------------------------
-- The SNMP Configuration Databse Group

snmpReconfigure OBJECT-TYPE
	SYNTAX	INTEGER {
		disable (1),
		enable (2)
	}
	MAX-ACCESS	read-write
	STATUS	deprecated
	DESCRIPTION
		"The SNMP agent will reset itself and reconfigure its
		database from the default database when this variable
		is set to enable(2). After reconfiguring is done, the
		value of this object is disable(1).
		Note that enabling snmpReconfigure will end up with
		a loss of the entire ATM configuration."
	::= { snmpConfGroup 1 }

snmpReadCommunity OBJECT-TYPE
	SYNTAX	OCTET STRING
	MAX-ACCESS	read-write
	STATUS	deprecated
	DESCRIPTION
		"The community string used for SNMP (v1) read operations,
		i.e. get and getnext requests.  This has been deprecated,
		since it's now possible to have more than one read
		community string.  Setting this variable will result in
		all current read community strings being deleted, and this
		one added.

		Note this object is write-only and reading it will
		result in implementation-specific results."
	::= { snmpConfGroup 2 }

snmpWriteCommunity OBJECT-TYPE
	SYNTAX	OCTET STRING
	MAX-ACCESS	read-write
	STATUS	deprecated
	DESCRIPTION
		"The community string used for SNMP (v1) write operations,
		i.e. set requests.  This has been deprecated, since it's now
		possible to have more than one write community string.
		Setting this variable will result in all current write
		community strings being deleted, and this one added.

		Note this object is write-only and reading it will
		result in implementation-specific results."
	::= { snmpConfGroup 3 }

snmpWarmStart OBJECT-TYPE
	SYNTAX	INTEGER {
		disable (1),
		enable (2)
	}
	MAX-ACCESS	read-write
	STATUS	current
	DESCRIPTION
		"The SNMP agent will reset the switch, and restart the
		switch control software using the existing configuration
		database when this variable is set to enable(2). After the
		warm start, the	value of this object is disable(1). A
		warmStart trap is sent after the switch control software
		restarts."
	::= { snmpConfGroup 4 }

snmpColdStart OBJECT-TYPE
	SYNTAX	INTEGER {
		disable (1),
		enableResetATMconf (2),
		enableResetAllConf (3)
	}
	MAX-ACCESS	read-write
	STATUS	current
	DESCRIPTION
		"The SNMP agent will reset the configuration database for
		all ATM related configuration objects, and reboot the switch,
		when this variable is set to enableResetAtmConf(2). When the
		value of this variable is set to enableResetAllConf(3), all
		configuration objects, including ATM and IP objects will be
		removed, and the switch will be rebooted. A coldStart trap
		is sent just before the trap destination table is removed.
		After the cold start, the value of this object is disable(1)."
	::= { snmpConfGroup 5 }

snmpRemoteSetsStatus OBJECT-TYPE
	SYNTAX  INTEGER {
		enabled (1),
		disabled (2)
	}
	MAX-ACCESS  read-only
	STATUS  deprecated
	DESCRIPTION
		"The value of this object controls SNMP set operations
		from remote management stations. The default value is
		enabled(1). If it is set to disabled(2), set requests from
		remote management stations will not be processed and
		an authorization error is returned.
		This value can be set only by the manager running on
		this device."
	::= { snmpConfGroup 6 }
------------------------------------------------------------------------
-- The SNMP agent address group.
--
-- This group provides addressing information to SNMP managers, to allow
-- those managers to discover related SNMP agents within the same enclosure.

snmpThisAgentBoardNumber OBJECT-TYPE
	SYNTAX INTEGER (1..4)
	MAX-ACCESS	read-only
	STATUS	current
	DESCRIPTION
		"The instance of this agent type within the
		 enclosure; typically a board number."
	::= { snmpAgentAddressGroup 1 }

snmpAgentTable OBJECT-TYPE
	SYNTAX	SEQUENCE OF SnmpAgentEntry
	MAX-ACCESS	not-accessible
	STATUS	current
	DESCRIPTION
		"A table of SNMP agent IP addresses. Each entry
		 in this table represents an IP address which may
		 be used to reach the associated SNMP agent,
		 assuming appropriate network connectivity."
	::= { snmpAgentAddressGroup 2 }

snmpAgentEntry OBJECT-TYPE
	SYNTAX	SnmpAgentEntry
	MAX-ACCESS	not-accessible
	STATUS	current
	DESCRIPTION
		"A table entry containing the identity and address of
		 an SNMP agent."
	INDEX	{ snmpAgentBoardNumber, snmpAgentInterface }
	::= { snmpAgentTable 1 }

SnmpAgentEntry ::=
	SEQUENCE {
		snmpAgentBoardNumber	Integer32,
		snmpAgentInterface	Integer32,
		snmpAgentAddress	IpAddress
	}

snmpAgentBoardNumber OBJECT-TYPE
	SYNTAX  Integer32
	MAX-ACCESS	read-only
	STATUS	current
	DESCRIPTION
		"The number of the SNMP agent within this
		 enclosure. This generally corresponds to a
		 board number."
	::= { snmpAgentEntry 1 }

snmpAgentInterface OBJECT-TYPE
	SYNTAX  Integer32
	MAX-ACCESS	read-only
	STATUS	current
	DESCRIPTION
		"An interface number associated with the
		 agent IP address. This number is for tabulation
		 purposes only, and has no other significance."
	::= { snmpAgentEntry 2 }

snmpAgentAddress OBJECT-TYPE
	SYNTAX	IpAddress
	MAX-ACCESS	read-only
	STATUS	current
	DESCRIPTION
		"The IP address of the identified SNMP agent."
	::= { snmpAgentEntry 3 }

------------------------------------------------------------------------
-- The Switch Traps

-- The enterprise specific traps that are supported by the ATM switch
-- in addition to the generic traps.

asxSwLinkDown NOTIFICATION-TYPE
	OBJECTS { portNumber, portName, trapLogIndex }
	STATUS      current
	DESCRIPTION
		"An asxSwLinkDown trap signifies that the sending protocol
		entity recognizes a failure in one of the ATM Switch links
		that is connected to another switch."
	::= { atmSwitch 0 0 }

asxSwLinkUp NOTIFICATION-TYPE
	OBJECTS { portNumber, portName, trapLogIndex }
	STATUS      current
	DESCRIPTION
		"An asxSwLinkUp trap signifies that the sending protocol
		entity recognizes that one of the ATM Switch links that
		is connected to another switch has come up."
	::= { atmSwitch 0 1 }

asxHostLinkDown NOTIFICATION-TYPE
	OBJECTS { portNumber, portName, trapLogIndex }
	STATUS      current
	DESCRIPTION
		"An asxHostLinkDown trap signifies that the sending protocol
		entity recognizes a failure in one of the ATM Switch links
		that is connected to a host."
	::= { atmSwitch 0 2 }

asxHostLinkUp NOTIFICATION-TYPE
	OBJECTS { portNumber, portName, trapLogIndex }
	STATUS      current
	DESCRIPTION
		"An asxHostLinkUp trap signifies that the sending protocol
		entity recognizes that one of the ATM Switch links that is
		connected to a host has come up."
	::= { atmSwitch 0 3 }

asxNetModuleDown NOTIFICATION-TYPE
	OBJECTS { moduleBoard, moduleNumber, trapLogIndex }
	STATUS      current
	DESCRIPTION
		"An asxNetModuleDown trap signifies that the sending protocol
		entity recognizes a failure in one of the ATM Switch network
		modules, that is identified by the board and the module numbers.
		This is probably caused by a hot-swap of a network module."
	::= { atmSwitch 0 4 }

asxNetModuleUp NOTIFICATION-TYPE
	OBJECTS { moduleBoard, moduleNumber, trapLogIndex }
	STATUS      current
	DESCRIPTION
		"An asxNetModuleUp trap signifies that the sending protocol
		entity recognizes a new operational ATM Switch network module,
		that is identified by the board and the module numbers. This is
		probably caused by a hot-swap of a network module."
	::= { atmSwitch 0 5 }

asxPsInputDown NOTIFICATION-TYPE
	OBJECTS { envPowerSupplyIndex, trapLogIndex }
	STATUS      current
	DESCRIPTION
		"This trap alerts that one ATM switch power supply failed
		due to failure in the input voltage. The power supply that
		failed is identified by the power supply index. Note that
		an input voltage may be out of spec and may not cause a power
		supply failure if high loads are not applied."
	::= { atmSwitch 0 6 }

asxPsInputUp NOTIFICATION-TYPE
	OBJECTS { envPowerSupplyIndex, trapLogIndex }
	STATUS      current
	DESCRIPTION
		"This trap alerts that one ATM switch power supply that had
		an input failure is up. The power supply that is back up
		is identified by the power supply index."
	::= { atmSwitch 0 7 }

-- trap asxAllPsInputUp { atmSwitch 8 } was deprecated

asxPsOutputDown NOTIFICATION-TYPE
	OBJECTS { envPowerSupplyIndex, trapLogIndex }
	STATUS      current
	DESCRIPTION
		"This trap alerts that one ATM switch power supply output
		failed, or the power supply was physically removed. The power
		supply that failed is identified by the power supply
		index."
	::= { atmSwitch 0 9 }

asxPsOutputUp NOTIFICATION-TYPE
	OBJECTS { envPowerSupplyIndex, trapLogIndex }
	STATUS      current
	DESCRIPTION
		"This trap alerts that one ATM switch power supply that had
		an output failure or was removed is now up. The power supply
		that is back up is identified by the power supply index."
	::= { atmSwitch 0 10 }

-- traps { atmSwitch 11 - 17 } for different power supplies outputs failures
-- and recovery were deprecated.
-- traps { atmSwitch 18 - 21 } for PS over temperature and regular temperature
-- were deprecated.

asxFanBankDown NOTIFICATION-TYPE
	OBJECTS { envFanBankIndex, trapLogIndex }
	STATUS      current
	DESCRIPTION
		"This trap alerts that one ATM switch fan bank failed. The
		fan bank that failed is identified by the fan bank index."
	::= { atmSwitch 0 22 }

asxFanBankUp NOTIFICATION-TYPE
	OBJECTS { envFanBankIndex, trapLogIndex }
	STATUS      current
	DESCRIPTION
		"This trap alerts that one ATM switch fan bank is up. The
		fan bank that is back up is identified by the fan bank index."
	::= { atmSwitch 0 23 }

-- traps { atm Switch 24 - 25 } for fans were deprecated.
-- traps { atmSwitch 26 - 27 } for enclosure temperature were deprecated.

asxLinkDown NOTIFICATION-TYPE
	OBJECTS {  portNumber, portName, trapLogIndex }
	STATUS      current
	DESCRIPTION
		"This trap alerts that the link that is identified by
		portName was configured up, but its underlying physical
		layer has lost its carrier (or the framing bit) and
		is currently down."
	::= { atmSwitch 0 28 }

asxLinkUp NOTIFICATION-TYPE
	OBJECTS {  portNumber, portName, trapLogIndex }
	STATUS      current
	DESCRIPTION
		"This trap alerts that the link that is identified by
		portName is back up."
	::= { atmSwitch 0 29 }

asxSpansDown NOTIFICATION-TYPE
	OBJECTS { portName, sigPathPort, sigPathVPI, trapLogIndex }
	STATUS      current
	DESCRIPTION
		"This trap alerts that the SPANS signalling on the link
		that is identified by the sigPathPort and sigPathVPI failed."
	::= { atmSwitch 0 30 }

asxSpansUp NOTIFICATION-TYPE
	OBJECTS { portName, sigPathPort, sigPathVPI, trapLogIndex }
	STATUS      current
	DESCRIPTION
		"This trap alerts that the SPANS signalling on the link
		that is identified by the sigPathPort and sigPathVPI is up."
	::= { atmSwitch 0 31 }

asxTempSensorOverTemp NOTIFICATION-TYPE
	OBJECTS { envTempSensorIndex, trapLogIndex }
	STATUS      current
	DESCRIPTION
		"This trap alerts that one of the temperature sensors indicates
		over temperature. The temperature sensor is identified by the
		temperature sensor index."
	::= { atmSwitch 0 32 }

asxTempSensorRegularTemp NOTIFICATION-TYPE
	OBJECTS { envTempSensorIndex, trapLogIndex }
	STATUS      current
	DESCRIPTION
		"This trap alerts that one of the temperature sensors indicates
		regular temperature. The temperature sensor is identified by the
		temperature sensor index."
	::= { atmSwitch 0 33 }

asxFabricTemperatureOverTemp NOTIFICATION-TYPE
	OBJECTS { envFabricIndex, trapLogIndex }
	STATUS      current
	DESCRIPTION
		"This trap alerts that one of the temperature sensors indicates
		over temperature. The temperature sensor is identified by the
		temperature sensor index."
	::= { atmSwitch 0 34 }

asxFabricTemperatureRegularTemp NOTIFICATION-TYPE
	OBJECTS { envFabricIndex, trapLogIndex }
	STATUS      current
	DESCRIPTION
		"This trap alerts that one of the temperature sensors indicates
		regular temperature. The temperature sensor is identified by the
		temperature sensor index."
	::= { atmSwitch 0 35 }

-- ------------------------------------------------------------------------- --
-- begin of netmod trap region
-- ------------------------------------------------------------------------- --

asxSonetLOSDetected NOTIFICATION-TYPE
	OBJECTS { hwPortName, hwPortBoard, hwPortModule, hwPortNumber,
		trapLogIndex }
	STATUS      current
	DESCRIPTION
		"This trap indicates that the specified SONET port is
		experiencing Loss Of Signal. Bellcore Document
		TA-NWT-000253 Section 6.3.1.1.1 states that... A SONET
		NE shall declare a LOS failure when the LOS defect
		persists for 2.5 (+- .5) seconds, or when a LOS defect
		is present and the criteria for LOF failure
		declaration have been met."
	::= { atmSwitch 0 36 }

asxSonetLOSCleared NOTIFICATION-TYPE
	OBJECTS { hwPortName, hwPortBoard, hwPortModule, hwPortNumber,
		trapLogIndex }
	STATUS      current
	DESCRIPTION
		"This trap indicates that the LOS condition identified
		by trap asxSonetLOSDetected has been cleared."
	::= { atmSwitch 0 37 }

asxSonetPathLabelDetected NOTIFICATION-TYPE
	OBJECTS { hwPortName, hwPortBoard, hwPortModule, hwPortNumber,
		trapLogIndex }
	STATUS      current
	DESCRIPTION
		"This trap indicates that the specified SONET port is
		receiving and errored C2 Path Label byte. Reference
		Bellcore Document TA-NWT-000253 Section 3.3.2.3 and
		6.3.1.1.8 the Path Label (C2) byte should have the
		value 0x13 or 0x01."
	::= { atmSwitch 0 38 }

asxSonetPathLabelCleared NOTIFICATION-TYPE
	OBJECTS { hwPortName, hwPortBoard, hwPortModule, hwPortNumber,
		trapLogIndex }
	STATUS      current
	DESCRIPTION
		"This trap indicates that the Errored Path Label (C2)
		byte error condition signaled by the
		asxSonetPathLabelDetected trap has been cleared."
	::= { atmSwitch 0 39 }

asxSonetLineAISDetected NOTIFICATION-TYPE
	OBJECTS { hwPortName, hwPortBoard, hwPortModule, hwPortNumber,
		trapLogIndex }
	STATUS      current
	DESCRIPTION
		"This trap indicates that the specified SONET port is
		receiving a Line level Alarm Indication Signal from the
		far-end equipment."
	::= { atmSwitch 0 40 }

asxSonetLineAISCleared NOTIFICATION-TYPE
	OBJECTS { hwPortName, hwPortBoard, hwPortModule, hwPortNumber,
		trapLogIndex }
	STATUS      current
	DESCRIPTION
		"This trap indicates that the Line AIS error condition
		signaled by the asxSonetLineAISDetected trap has been
		cleared."
	::= { atmSwitch 0 41 }

-- ------------------------------------------------------------------------- --

asxDS3PLCPYellowDetected NOTIFICATION-TYPE
	OBJECTS { hwPortName, hwPortBoard, hwPortModule, hwPortNumber,
		trapLogIndex }
	STATUS      current
	DESCRIPTION
		"This trap indicates that the specified DS3 port has
		detected incoming PLCP Yellow Alarm."
	::= { atmSwitch 0 46 }

asxDS3PLCPYellowCleared NOTIFICATION-TYPE
	OBJECTS { hwPortName, hwPortBoard, hwPortModule, hwPortNumber,
		trapLogIndex }
	STATUS      current
	DESCRIPTION
		"This trap indicates that the specified DS3 port has
		detected clearance of incoming PLCP Yellow Alarm."
	::= { atmSwitch 0 47 }

asxDS3PLCPLOFDetected NOTIFICATION-TYPE
	OBJECTS { hwPortName, hwPortBoard, hwPortModule, hwPortNumber,
		trapLogIndex }
	STATUS      current
	DESCRIPTION
		"This trap indicates that the specified DS3 port has
		detected incoming PLCP LOF Alarm."
	::= { atmSwitch 0 48 }

asxDS3PLCPLOFCleared NOTIFICATION-TYPE
	OBJECTS { hwPortName, hwPortBoard, hwPortModule, hwPortNumber,
		trapLogIndex }
	STATUS      current
	DESCRIPTION
		"This trap indicates that the specified DS3 port has
		detected clearance of incoming PLCP LOF Alarm."
	::= { atmSwitch 0 49 }

asxDS3LOFDetected NOTIFICATION-TYPE
	OBJECTS { hwPortName, hwPortBoard, hwPortModule, hwPortNumber,
		trapLogIndex }
	STATUS      current
	DESCRIPTION
		"This trap indicates that Loss Of Frame(LOF) is detected on
		the incoming signal."
	::= { atmSwitch 0 50 }

asxDS3LOFCleared NOTIFICATION-TYPE
	OBJECTS { hwPortName, hwPortBoard, hwPortModule, hwPortNumber,
		trapLogIndex }
	STATUS      current
	DESCRIPTION
		"This trap indicates that Loss Of Frame is cleared on
		the incoming signal."
	::= { atmSwitch 0 51 }

asxDS3AISDetected NOTIFICATION-TYPE
	OBJECTS { hwPortName, hwPortBoard, hwPortModule, hwPortNumber,
		trapLogIndex }
	STATUS      current
	DESCRIPTION
		"This trap indicates that AIS Alarm is detected on
		the incoming signal."
	::= { atmSwitch 0 52 }

asxDS3AISCleared NOTIFICATION-TYPE
	OBJECTS { hwPortName, hwPortBoard, hwPortModule, hwPortNumber,
		trapLogIndex }
	STATUS      current
	DESCRIPTION
		"This trap indicates that AIS Alarm is cleared on
		the incoming signal."
	::= { atmSwitch 0 53 }

-- ------------------------------------------------------------------------- --

asxDS1PLCPYellowDetected NOTIFICATION-TYPE
	OBJECTS { hwPortName, hwPortBoard, hwPortModule, hwPortNumber,
		trapLogIndex }
	STATUS      current
	DESCRIPTION
		"This trap indicates that the specified DS1 port has
		detected incoming PLCP Yellow Alarm."
	::= { atmSwitch 0 60 }

asxDS1PLCPYellowCleared NOTIFICATION-TYPE
	OBJECTS { hwPortName, hwPortBoard, hwPortModule, hwPortNumber,
		trapLogIndex }
	STATUS      current
	DESCRIPTION
		"This trap indicates that the specified DS1 port has
		detected clearance of incoming PLCP Yellow Alarm."
	::= { atmSwitch 0 61 }

asxDS1PLCPLOFDetected NOTIFICATION-TYPE
	OBJECTS { hwPortName, hwPortBoard, hwPortModule, hwPortNumber,
		trapLogIndex }
	STATUS      current
	DESCRIPTION
		"This trap indicates that the specified DS1 port has
		detected incoming PLCP LOF Alarm."
	::= { atmSwitch 0 62 }

asxDS1PLCPLOFCleared NOTIFICATION-TYPE
	OBJECTS { hwPortName, hwPortBoard, hwPortModule, hwPortNumber,
		trapLogIndex }
	STATUS      current
	DESCRIPTION
		"This trap indicates that the specified DS1 port has
		detected clearance of incoming PLCP LOF Alarm."
	::= { atmSwitch 0 63 }

asxDS1YellowDetected NOTIFICATION-TYPE
	OBJECTS { hwPortName, hwPortBoard, hwPortModule, hwPortNumber,
		trapLogIndex }
	STATUS      current
	DESCRIPTION
		"This trap indicates that Yellow Alarm is detected on
		the incoming signal."
	::= { atmSwitch 0 64 }

asxDS1YellowCleared NOTIFICATION-TYPE
	OBJECTS { hwPortName, hwPortBoard, hwPortModule, hwPortNumber,
		trapLogIndex }
	STATUS      current
	DESCRIPTION
		"This trap indicates that Yellow Alarm is cleared on
		the incoming signal."
	::= { atmSwitch 0 65 }

asxDS1AISDetected NOTIFICATION-TYPE
	OBJECTS { hwPortName, hwPortBoard, hwPortModule, hwPortNumber,
		trapLogIndex }
	STATUS      current
	DESCRIPTION
		"This trap indicates that AIS Alarm is detected on
		the incoming signal."
	::= { atmSwitch 0 66 }

asxDS1AISCleared NOTIFICATION-TYPE
	OBJECTS { hwPortName, hwPortBoard, hwPortModule, hwPortNumber,
		    trapLogIndex }
	STATUS      current
	DESCRIPTION
		"This trap indicates that AIS Alarm is cleared on
		the incoming signal."
	::= { atmSwitch 0 67 }

asxDS1LOSDetected NOTIFICATION-TYPE
	OBJECTS { hwPortName, hwPortBoard, hwPortModule, hwPortNumber,
		trapLogIndex }
	STATUS      current
	DESCRIPTION
		"This trap indicates that LOS Alarm is detected on
		the incoming signal."
	::= { atmSwitch 0 68 }

asxDS1LOSCleared NOTIFICATION-TYPE
	OBJECTS { hwPortName, hwPortBoard, hwPortModule, hwPortNumber,
		trapLogIndex }
	STATUS      current
	DESCRIPTION
		"This trap indicates that LOS Alarm is cleared on
		the incoming signal."
	::= { atmSwitch 0 69 }

asxDS1LOFDetected NOTIFICATION-TYPE
	OBJECTS { hwPortName, hwPortBoard, hwPortModule, hwPortNumber,
		trapLogIndex }
	STATUS      current
	DESCRIPTION
		"This trap indicates that LOF Alarm is detected on
		the incoming signal."
	::= { atmSwitch 0 70 }

asxDS1LOFCleared NOTIFICATION-TYPE
	OBJECTS { hwPortName, hwPortBoard, hwPortModule, hwPortNumber,
		trapLogIndex }
	STATUS      current
	DESCRIPTION
		"This trap indicates that LOF Alarm is cleared on
		the incoming signal."
	::= { atmSwitch 0 71 }

-- ------------------------------------------------------------------------- --

asxDS3FERFDetected NOTIFICATION-TYPE
	OBJECTS { hwPortName, hwPortBoard, hwPortModule, hwPortNumber,
		trapLogIndex }
	STATUS      current
	DESCRIPTION
		"This trap indicates that FERF Alarm or DS3 Yellow Alarm
		is detected on the incoming signal."
	::= { atmSwitch 0 74 }

asxDS3FERFCleared NOTIFICATION-TYPE
	OBJECTS { hwPortName, hwPortBoard, hwPortModule, hwPortNumber,
		trapLogIndex }
	STATUS      current
	DESCRIPTION
		"This trap indicates that FERF Alarm or DS3 Yellow Alarm
		is cleared on the incoming signal."
	::= { atmSwitch 0 75 }

-- ------------------------------------------------------------------------- --

asxE3YellowDetected NOTIFICATION-TYPE
	OBJECTS { hwPortName, hwPortBoard, hwPortModule, hwPortNumber,
		trapLogIndex }
	STATUS      current
	DESCRIPTION
		"This trap indicates that the Yellow Alarm is being detected
		on the incoming signal."
	::= { atmSwitch 0 78 }

asxE3YellowCleared NOTIFICATION-TYPE
	OBJECTS { hwPortName, hwPortBoard, hwPortModule, hwPortNumber,
		trapLogIndex }
	STATUS      current
	DESCRIPTION
		"This trap indicates that Yellow alarm has cleared on
		the incoming signal."
	::= { atmSwitch 0 79 }

asxE3OOFDetected NOTIFICATION-TYPE
	OBJECTS { hwPortName, hwPortBoard, hwPortModule, hwPortNumber,
		trapLogIndex }
	STATUS      current
	DESCRIPTION
		"This trap indicates that Out Of Frame (OOF) is detected on
		the incoming signal."
	::= { atmSwitch 0 80 }

asxE3OOFCleared NOTIFICATION-TYPE
	OBJECTS { hwPortName, hwPortBoard, hwPortModule, hwPortNumber,
		trapLogIndex }
	STATUS      current
	DESCRIPTION
		"This trap indicates that Loss Of Frame is cleared on
		the incoming signal."
	::= { atmSwitch 0 81 }

asxE3AtmLCDDetected NOTIFICATION-TYPE
	OBJECTS { hwPortName, hwPortBoard, hwPortModule, hwPortNumber,
		trapLogIndex }
	STATUS      current
	DESCRIPTION
		"This trap indicates that the specified E3 port is
		experiencing Loss of Cell Deliniation (LCD). A LCD
		failure is declared when the LCD defect persists for a
		period of 2.5 +/- 0.5 seconds."
	::= { atmSwitch 0 82 }

asxE3AtmLCDCleared NOTIFICATION-TYPE
	OBJECTS { hwPortName, hwPortBoard, hwPortModule, hwPortNumber,
		trapLogIndex }
	STATUS      current
	DESCRIPTION
		"This trap indicates that the LCD failure identified
		by trap asxE3AtmLCDDetected has been cleared. A LCD
		failure is cleared when the LCD defect is absent for
		10 +/- 0.5 seconds."
	::= { atmSwitch 0 83 }

asxE3PLCPYellowDetected NOTIFICATION-TYPE
	OBJECTS { hwPortName, hwPortBoard, hwPortModule, hwPortNumber,
		trapLogIndex }
	STATUS      current
	DESCRIPTION
		"This trap indicates that the specified E3 port has
		detected incoming PLCP Yellow Alarm."
	::= { atmSwitch 0 86 }

asxE3PLCPYellowCleared NOTIFICATION-TYPE
	OBJECTS { hwPortName, hwPortBoard, hwPortModule, hwPortNumber,
		trapLogIndex }
	STATUS      current
	DESCRIPTION
		"This trap indicates that the specified E3 port has
		detected clearance of incoming PLCP Yellow Alarm."
	::= { atmSwitch 0 87 }

-- ------------------------------------------------------------------------- --

asxE1YellowDetected NOTIFICATION-TYPE
	OBJECTS { hwPortName, hwPortBoard, hwPortModule, hwPortNumber,
		trapLogIndex }
	STATUS      current
	DESCRIPTION
		"This trap indicates that the Yellow Alarm is being detected
		on the incoming signal."
	::= { atmSwitch 0 90 }

asxE1YellowCleared NOTIFICATION-TYPE
	OBJECTS { hwPortName, hwPortBoard, hwPortModule, hwPortNumber,
		trapLogIndex }
	STATUS      current
	DESCRIPTION
		"This trap indicates that Yellow alarm has cleared on
		the incoming signal."
	::= { atmSwitch 0 91 }

asxE1LOFDetected NOTIFICATION-TYPE
	OBJECTS { hwPortName, hwPortBoard, hwPortModule, hwPortNumber,
		trapLogIndex }
	STATUS      current
	DESCRIPTION
		"This trap indicates that LOF is being detected on
		the incoming signal."
	::= { atmSwitch 0 92 }

asxE1LOFCleared NOTIFICATION-TYPE
	OBJECTS { hwPortName, hwPortBoard, hwPortModule, hwPortNumber,
		trapLogIndex }
	STATUS      current
	DESCRIPTION
		"This trap indicates that LOF is cleared on
		the incoming signal."
	::= { atmSwitch 0 93 }

asxE1PLCPYellowDetected NOTIFICATION-TYPE
	OBJECTS { hwPortName, hwPortBoard, hwPortModule, hwPortNumber,
		trapLogIndex }
	STATUS      current
	DESCRIPTION
		"This trap indicates that the specified E1 port has
		detected incoming PLCP Yellow Alarm."
	::= { atmSwitch 0 96 }

asxE1PLCPYellowCleared NOTIFICATION-TYPE
	OBJECTS { hwPortName, hwPortBoard, hwPortModule, hwPortNumber,
		trapLogIndex }
	STATUS      current
	DESCRIPTION
		"This trap indicates that the specified E1 port has
		detected clearance of incoming PLCP Yellow Alarm."
	::= { atmSwitch 0 97 }

asxE1PLCPLOFDetected NOTIFICATION-TYPE
	OBJECTS { hwPortName, hwPortBoard, hwPortModule, hwPortNumber,
		trapLogIndex }
	STATUS      current
	DESCRIPTION
		"This trap indicates that the specified E1 port has
		detected incoming PLCP LOF Alarm."
	::= { atmSwitch 0 98 }

asxE1PLCPLOFCleared NOTIFICATION-TYPE
	OBJECTS { hwPortName, hwPortBoard, hwPortModule, hwPortNumber,
		trapLogIndex }
	STATUS      current
	DESCRIPTION
		"This trap indicates that incoming PLCP LOF alarm has been
		cleared on the specified E1 port."
	::= { atmSwitch 0 99 }

asxE1LOSDetected NOTIFICATION-TYPE
	OBJECTS { hwPortName, hwPortBoard, hwPortModule, hwPortNumber,
		trapLogIndex }
	STATUS      current
	DESCRIPTION
		"This trap indicates that the specified E1 port has
		detected incoming LOS Alarm."
	::= { atmSwitch 0 100 }

asxE1LOSCleared NOTIFICATION-TYPE
	OBJECTS { hwPortName, hwPortBoard, hwPortModule, hwPortNumber,
		trapLogIndex }
	STATUS      current
	DESCRIPTION
		"This trap indicates that incoming LOS alarm has been
		cleared on the specified E1 port."
	::= { atmSwitch 0 101 }

asxE1AISDetected NOTIFICATION-TYPE
	OBJECTS { hwPortName, hwPortBoard, hwPortModule, hwPortNumber,
		trapLogIndex }
	STATUS      current
	DESCRIPTION
		"This trap indicates that the specified E1 port has
		detected incoming AIS Alarm."
	::= { atmSwitch 0 102 }

asxE1AISCleared NOTIFICATION-TYPE
	OBJECTS { hwPortName, hwPortBoard, hwPortModule, hwPortNumber,
		trapLogIndex }
	STATUS      current
	DESCRIPTION
		"This trap indicates that incoming AIS alarm has been
		cleared on the specified E1 port."
	::= { atmSwitch 0 103 }

-- ------------------------------------------------------------------------- --

asxE3AISDetected NOTIFICATION-TYPE
	OBJECTS { hwPortName, hwPortBoard, hwPortModule, hwPortNumber,
		trapLogIndex }
	STATUS      current
	DESCRIPTION
		"This trap indicates that the specified E3 port has
		detected incoming AIS Alarm."
	::= { atmSwitch 0 104 }

asxE3AISCleared NOTIFICATION-TYPE
	OBJECTS { hwPortName, hwPortBoard, hwPortModule, hwPortNumber,
		trapLogIndex }
	STATUS      current
	DESCRIPTION
		"This trap indicates that incoming AIS alarm has been
		cleared on the specified E3 port."
	::= { atmSwitch 0 105 }

asxE3LOSDetected NOTIFICATION-TYPE
	OBJECTS { hwPortName, hwPortBoard, hwPortModule, hwPortNumber,
		trapLogIndex }
	STATUS      current
	DESCRIPTION
		"This trap indicates that the specified E3 port has
		detected incoming LOS Alarm."
	::= { atmSwitch 0 106 }

asxE3LOSCleared NOTIFICATION-TYPE
	OBJECTS { hwPortName, hwPortBoard, hwPortModule, hwPortNumber,
		trapLogIndex }
	STATUS      current
	DESCRIPTION
		"This trap indicates that incoming LOS alarm has been
		cleared on the specified E3 port."
	::= { atmSwitch 0 107 }

asxE3PLCPLOFDetected NOTIFICATION-TYPE
	OBJECTS { hwPortName, hwPortBoard, hwPortModule, hwPortNumber,
		trapLogIndex }
	STATUS      current
	DESCRIPTION
		"This trap indicates that the specified E3 port has
		detected incoming PLCP LOF Alarm."
	::= { atmSwitch 0 108 }

asxE3PLCPLOFCleared NOTIFICATION-TYPE
	OBJECTS { hwPortName, hwPortBoard, hwPortModule, hwPortNumber,
		trapLogIndex }
	STATUS      current
	DESCRIPTION
		"This trap indicates that incoming PLCP LOF alarm has been
		cleared on the specified E3 port."
	::= { atmSwitch 0 109 }

-- ------------------------------------------------------------------------- --

asxJ2YellowDetected NOTIFICATION-TYPE
	OBJECTS { hwPortName, hwPortBoard, hwPortModule, hwPortNumber,
		trapLogIndex }
	STATUS      current
	DESCRIPTION
		"This trap indicates that Yellow Alarm is detected on
		the incoming signal."
	::= { atmSwitch 0 112 }

asxJ2YellowCleared NOTIFICATION-TYPE
	OBJECTS { hwPortName, hwPortBoard, hwPortModule, hwPortNumber,
		trapLogIndex }
	STATUS      current
	DESCRIPTION
		"This trap indicates that Yellow Alarm is cleared on
		the incoming signal."
	::= { atmSwitch 0 113 }

asxJ2AISDetected NOTIFICATION-TYPE
	OBJECTS { hwPortName, hwPortBoard, hwPortModule, hwPortNumber,
		trapLogIndex }
	STATUS      current
	DESCRIPTION
		"This trap indicates that AIS Alarm is detected on
		the incoming signal."
	::= { atmSwitch 0 114 }

asxJ2AISCleared NOTIFICATION-TYPE
	OBJECTS { hwPortName, hwPortBoard, hwPortModule, hwPortNumber,
		trapLogIndex }
	STATUS      current
	DESCRIPTION
		"This trap indicates that AIS Alarm is cleared on
		the incoming signal."
	::= { atmSwitch 0 115 }

asxJ2LOSDetected NOTIFICATION-TYPE
	OBJECTS { hwPortName, hwPortBoard, hwPortModule, hwPortNumber,
		trapLogIndex }
	STATUS      current
	DESCRIPTION
		"This trap indicates that LOS Alarm is detected on
		the incoming signal."
	::= { atmSwitch 0 116 }

asxJ2LOSCleared NOTIFICATION-TYPE
	OBJECTS { hwPortName, hwPortBoard, hwPortModule, hwPortNumber,
		trapLogIndex }
	STATUS      current
	DESCRIPTION
		"This trap indicates that LOS Alarm is cleared on
		the incoming signal."
	::= { atmSwitch 0 117 }

asxJ2LOFDetected NOTIFICATION-TYPE
	OBJECTS { hwPortName, hwPortBoard, hwPortModule, hwPortNumber,
		trapLogIndex }
	STATUS      current
	DESCRIPTION
		"This trap indicates that LOF Alarm is detected on
		the incoming signal."
	::= { atmSwitch 0 118 }

asxJ2LOFCleared NOTIFICATION-TYPE
	OBJECTS { hwPortName, hwPortBoard, hwPortModule, hwPortNumber,
		trapLogIndex }
	STATUS      current
	DESCRIPTION
		"This trap indicates that LOF Alarm is cleared on
		the incoming signal."
	::= { atmSwitch 0 119 }

-- ------------------------------------------------------------------------- --

asxDS3LOSDetected NOTIFICATION-TYPE
	OBJECTS { hwPortName, hwPortBoard, hwPortModule, hwPortNumber,
		trapLogIndex }
	STATUS      current
	DESCRIPTION
		"This trap indicates that the specified DS3 port has
		detected incoming LOS Alarm."
	::= { atmSwitch 0 120 }

asxDS3LOSCleared NOTIFICATION-TYPE
	OBJECTS { hwPortName, hwPortBoard, hwPortModule, hwPortNumber,
		trapLogIndex }
	STATUS      current
	DESCRIPTION
		"This trap indicates that the incoming LOS Alarm has been
		cleared on the specified DS3 port."
	::= { atmSwitch 0 121 }

-- ------------------------------------------------------------------------- --

asxSonetLOFDetected NOTIFICATION-TYPE
	OBJECTS { hwPortName, hwPortBoard, hwPortModule, hwPortNumber,
		trapLogIndex }
	STATUS      current
	DESCRIPTION
		"This trap indicates that the specified SONET port is
		experiencing Loss Of Frame (LOF) failure. An LOF
		failure is declared when the LOF defect persists fore
		a period of 2.5 +/- 0.5 seconds, except when an LOS
		defect or failure is present."
	::= { atmSwitch 0 130 }

asxSonetLOFCleared NOTIFICATION-TYPE
	OBJECTS { hwPortName, hwPortBoard, hwPortModule, hwPortNumber,
		trapLogIndex }
	STATUS      current
	DESCRIPTION
		"This trap indicates that the LOF failure identified
		by trap asxSonetLOFDetected has been cleared. The LOF
		failure is cleared when the LOS failure is declared,
		or when the LOF defect is absent for 10 +/- 0.5
		seconds."
	::= { atmSwitch 0 131 }

asxSonetLineRDIDetected NOTIFICATION-TYPE
	OBJECTS { hwPortName, hwPortBoard, hwPortModule, hwPortNumber,
		trapLogIndex }
	STATUS      current
	DESCRIPTION
		"This trap indicates that the specified SONET port is
		experiencing Line Remote Defect Indication (LRDI). A
		Line RDI failure is declared when the incoming Line
		RDI defects lasts for 2.5 +/- 0.5 seconds."
	::= { atmSwitch 0 132 }

asxSonetLineRDICleared NOTIFICATION-TYPE
	OBJECTS { hwPortName, hwPortBoard, hwPortModule, hwPortNumber,
		trapLogIndex }
	STATUS      current
	DESCRIPTION
		"This trap indicates that the Line RDI failure
		identified by trap asxSonetLineRDIDetected has been
		cleared.  The Line RDI failure is cleared when no Line
		RDI defects are detected for 10 +/- 0.5 seconds."
	::= { atmSwitch 0 133 }

asxSonetPathAISDetected NOTIFICATION-TYPE
	OBJECTS { hwPortName, hwPortBoard, hwPortModule, hwPortNumber,
		trapLogIndex }
	STATUS      current
	DESCRIPTION
		"This trap indicates that the specified SONET port is
		experiencing Path Alarm Inidication Signal (PAIS). A Path
		AIS failure is declared when the Path AIS defect
		persists for 2.5 +/- 0.5 seconds."
	::= { atmSwitch 0 134 }

asxSonetPathAISCleared NOTIFICATION-TYPE
	OBJECTS { hwPortName, hwPortBoard, hwPortModule, hwPortNumber,
		trapLogIndex }
	STATUS      current
	DESCRIPTION
		"This trap indicates that the PathAIS failure
		identified by trap asxSonetPathAISDetected has been
		cleared.  A PAIS failure is cleared when the PAIS
		defect is absent for 10 +/- 0.5 seconds."
	::= { atmSwitch 0 135 }

asxSonetPathLOPDetected NOTIFICATION-TYPE
	OBJECTS { hwPortName, hwPortBoard, hwPortModule, hwPortNumber,
		trapLogIndex }
	STATUS      current
	DESCRIPTION
		"This trap indicates that the specified SONET port is
		experiencing Loss Of Pointer (LOP). A LOP failure is
		declared when the LOP defect persists for a period of
		2.5 +/- 0.5 seconds."
	::= { atmSwitch 0 136 }

asxSonetPathLOPCleared NOTIFICATION-TYPE
	OBJECTS { hwPortName, hwPortBoard, hwPortModule, hwPortNumber,
		trapLogIndex }
	STATUS      current
	DESCRIPTION
		"This trap indicates that the LOP failure identified
		by trap asxSonetLOPDetected has been cleared. A LOP
		failure is cleared when the LOP defect is absent for
		10 +/- 0.5 seconds."
	::= { atmSwitch 0 137 }

asxSonetPathUNEQDetected NOTIFICATION-TYPE
	OBJECTS { hwPortName, hwPortBoard, hwPortModule, hwPortNumber,
		trapLogIndex }
	STATUS      current
	DESCRIPTION
		"This trap indicates that the specified SONET port is
		experiencing unequiped (UNEQ). A UNEQ failure is
		declared when the UNEQ defect persists for a period of
		2.5 +/- 0.5 seconds."
	::= { atmSwitch 0 138 }

asxSonetPathUNEQCleared NOTIFICATION-TYPE
	OBJECTS { hwPortName, hwPortBoard, hwPortModule, hwPortNumber,
		trapLogIndex }
	STATUS      current
	DESCRIPTION
		"This trap indicates that the UNEQ failure identified
		by trap asxSonetUNEQDetected has been cleared. A UNEQ
		failure is cleared when the UNEQ defect is absent for
		10 +/- 0.5 seconds."
	::= { atmSwitch 0 139 }

asxSonetPathRDIDetected NOTIFICATION-TYPE
	OBJECTS { hwPortName, hwPortBoard, hwPortModule, hwPortNumber,
		trapLogIndex }
	STATUS      current
	DESCRIPTION
		"This trap indicates that the specified SONET port is
		experiencing Path Remote Defect Indication (PRDI). A
		Path RDI failure is declared when the incoming Path
		RDI defects lasts for 2.5 +/- 0.5 seconds."
	::= { atmSwitch 0 140 }

asxSonetPathRDICleared NOTIFICATION-TYPE
	OBJECTS { hwPortName, hwPortBoard, hwPortModule, hwPortNumber ,
		trapLogIndex }
	STATUS      current
	DESCRIPTION
		"This trap indicates that the Path RDI failure
		identified by trap asxSonetPathRDIDetected has been
		cleared.  The Path RDI failure is cleared when no Path
		RDI defects are detected for 10 +/- 0.5 seconds."
	::= { atmSwitch 0 141 }

asxSonetAtmLCDDetected NOTIFICATION-TYPE
	OBJECTS { hwPortName, hwPortBoard, hwPortModule, hwPortNumber,
		trapLogIndex }
	STATUS      current
	DESCRIPTION
		"This trap indicates that the specified SONET port is
		experiencing Loss of Cell Deliniation (LCD). A LCD
		failure is declared when the LCD defect persists for a
		period of 2.5 +/- 0.5 seconds."
	::= { atmSwitch 0 142 }

asxSonetAtmLCDCleared NOTIFICATION-TYPE
	OBJECTS { hwPortName, hwPortBoard, hwPortModule, hwPortNumber,
		trapLogIndex }
	STATUS      current
	DESCRIPTION
		"This trap indicates that the LCD failure identified
		by trap asxSonetAtmLCDDetected has been cleared. A LCD
		failure is cleared when the LCD defect is absent for
		10 +/- 0.5 seconds."
	::= { atmSwitch 0 143 }

asxSonetAtmLineBIPDetected NOTIFICATION-TYPE
	OBJECTS { hwPortName, hwPortBoard, hwPortModule, hwPortNumber,
		trapLogIndex }
	STATUS      current
	DESCRIPTION
		"This trap indicates that the specified SONET port is
		 experiencing Bit Interleaved Parity (BIP) errors. A
		 Line BIP failure is declared when the Line BIP defect
		 persists for a period of 2.5 +/- 0.5 seconds."
	::= { atmSwitch 0 144 }

asxSonetAtmLineBIPCleared NOTIFICATION-TYPE
	OBJECTS { hwPortName, hwPortBoard, hwPortModule, hwPortNumber,
		trapLogIndex }
	STATUS      current
	DESCRIPTION
		"This trap indicates that the Line BIP failure identified
		 by trap asxSonetAtmLineBIPDetected has been cleared. A Line
		 BIP failure is cleared when the Line BIP defect is absent
		 for 10 +/- 0.5 seconds."
	::= { atmSwitch 0 145 }

-- ------------------------------------------------------------------------- --

asxDS3IdleDetected NOTIFICATION-TYPE
	OBJECTS { hwPortName, hwPortBoard, hwPortModule, hwPortNumber,
		trapLogIndex }
	STATUS      current
	DESCRIPTION
		"This trap indicates that an Idle Maintenance Signal
		(IDLE) is detected on the incoming signal."
	::= { atmSwitch 0 160 }

asxDS3IdleCleared NOTIFICATION-TYPE
	OBJECTS { hwPortName, hwPortBoard, hwPortModule, hwPortNumber,
		trapLogIndex }
	STATUS      current
	DESCRIPTION
		"This trap indicates that an Idle Maintenance Signal
		(IDLE) is cleared on the incoming signal."
	::= { atmSwitch 0 161 }

asxDS3AtmLCDDetected NOTIFICATION-TYPE
	OBJECTS { hwPortName, hwPortBoard, hwPortModule, hwPortNumber,
		trapLogIndex }
	STATUS      current
	DESCRIPTION
		"This trap indicates that the specified DS3 port is
		experiencing Loss of Cell Deliniation (LCD). A LCD
		failure is declared when the LCD defect persists for a
		period of 2.5 +/- 0.5 seconds."
	::= { atmSwitch 0 162 }

asxDS3AtmLCDCleared NOTIFICATION-TYPE
	OBJECTS { hwPortName, hwPortBoard, hwPortModule, hwPortNumber,
		trapLogIndex }
	STATUS      current
	DESCRIPTION
		"This trap indicates that the LCD failure identified
		by trap asxDS3AtmLCDDetected has been cleared. A LCD
		failure is cleared when the LCD defect is absent for
		10 +/- 0.5 seconds."
	::= { atmSwitch 0 163 }

asxDS3PbitPerrDetected NOTIFICATION-TYPE
	OBJECTS { hwPortName, hwPortBoard, hwPortModule, hwPortNumber,
		trapLogIndex }
	STATUS      current
	DESCRIPTION
		"This trap indicates that the specified DS3 port is
		 experiencing P-bit Parity errors. A P-bit Parity Error
		 failure is declared when the P-bit Parity Error
		 persists for a period of 2.5 +/- 0.5 seconds."
	::= { atmSwitch 0 164 }

asxDS3PbitPerrCleared NOTIFICATION-TYPE
	OBJECTS { hwPortName, hwPortBoard, hwPortModule, hwPortNumber,
		trapLogIndex }
	STATUS      current
	DESCRIPTION
		"This trap indicates that the P-bit Parity Error failure
		 identified by trap asxDS3PbitPerrDetected has been cleared.
		 A P-bit Parity Error failure is cleared when the P-bit Parity
		 Error defect is absent for 10 +/- 0.5 seconds."
	::= { atmSwitch 0 165 }

-- ------------------------------------------------------------------------- --

asxDS1PRBSDetected NOTIFICATION-TYPE
	OBJECTS { hwPortName, hwPortBoard, hwPortModule, hwPortNumber,
		trapLogIndex }
	STATUS      current
	DESCRIPTION
		"This trap indicates that PRBS pattern is detected on
		the incoming signal."
	::= { atmSwitch 0 176 }

asxDS1PRBSCleared NOTIFICATION-TYPE
	OBJECTS { hwPortName, hwPortBoard, hwPortModule, hwPortNumber,
		trapLogIndex }
	STATUS      current
	DESCRIPTION
		"This trap indicates that PRBS pattern is cleared on
		the incoming signal."
	::= { atmSwitch 0 177 }

asxDS1AtmLCDDetected NOTIFICATION-TYPE
	OBJECTS { hwPortName, hwPortBoard, hwPortModule, hwPortNumber,
		trapLogIndex }
	STATUS      current
	DESCRIPTION
		"This trap indicates that the specified DS1 port is
		experiencing Loss of Cell Deliniation (LCD). A LCD
		failure is declared when the LCD defect persists for a
		period of 2.5 +/- 0.5 seconds."
	::= { atmSwitch 0 178 }

asxDS1AtmLCDCleared NOTIFICATION-TYPE
	OBJECTS { hwPortName, hwPortBoard, hwPortModule, hwPortNumber,
		trapLogIndex }
	STATUS      current
	DESCRIPTION
		"This trap indicates that the LCD failure identified
		by trap asxDS1AtmLCDDetected has been cleared. A LCD
		failure is cleared when the LCD defect is absent for
		10 +/- 0.5 seconds."
	::= { atmSwitch 0 179 }

asxDS1CRCErrDetected NOTIFICATION-TYPE
	OBJECTS { hwPortName, hwPortBoard, hwPortModule, hwPortNumber,
		trapLogIndex }
	STATUS      current
	DESCRIPTION
		"This trap indicates that the specified DS1 port is
		 experiencing excessive CRC-6 errors. A CRC-6 Error
		 failure is declared when the CRC-6 Error
		 persists for a period of 2.5 +/- 0.5 seconds."
	::= { atmSwitch 0 180 }

asxDS1CRCErrCleared NOTIFICATION-TYPE
	OBJECTS { hwPortName, hwPortBoard, hwPortModule, hwPortNumber,
		trapLogIndex }
	STATUS      current
	DESCRIPTION
		"This trap indicates that the excessive CRC-6 Error failure
		 identified by trap asxDS1CRCErrDetected has been cleared.
		 A CRC-6 Parity Error failure is cleared when the CRC-6
		 Error defect is absent for 10 +/- 0.5 seconds."
	::= { atmSwitch 0 181 }

-- ------------------------------------------------------------------------- --

asxE3TrailChangeDetected NOTIFICATION-TYPE
	OBJECTS { hwPortName, hwPortBoard, hwPortModule, hwPortNumber,
		trapLogIndex }
	STATUS      current
	DESCRIPTION
		"This trap indicates that a change in the trail trace
		 message was detected on the incoming signal."
	::= { atmSwitch 0 192 }

-- ------------------------------------------------------------------------- --

asxE1AtmLCDDetected NOTIFICATION-TYPE
	OBJECTS { hwPortName, hwPortBoard, hwPortModule, hwPortNumber,
		trapLogIndex }
	STATUS      current
	DESCRIPTION
		"This trap indicates that the specified E1 port is
		experiencing Loss of Cell Deliniation (LCD). A LCD
		failure is declared when the LCD defect persists for a
		period of 2.5 +/- 0.5 seconds."
	::= { atmSwitch 0 208 }

asxE1AtmLCDCleared NOTIFICATION-TYPE
	OBJECTS { hwPortName, hwPortBoard, hwPortModule, hwPortNumber,
		trapLogIndex }
	STATUS      current
	DESCRIPTION
		"This trap indicates that the LCD failure identified
		by trap asxE1AtmLCDDetected has been cleared. A LCD
		failure is cleared when the LCD defect is absent for
		10 +/- 0.5 seconds."
	::= { atmSwitch 0 209 }

-- ------------------------------------------------------------------------- --

asxJ2RLOCDetected NOTIFICATION-TYPE
	OBJECTS { hwPortName, hwPortBoard, hwPortModule, hwPortNumber,
		trapLogIndex }
	STATUS      current
	DESCRIPTION
		"This trap indicates that Receive Loss of Clock (RLOC)
		is detected on the incoming signal."
	::= { atmSwitch 0 224 }

asxJ2RLOCCleared NOTIFICATION-TYPE
	OBJECTS { hwPortName, hwPortBoard, hwPortModule, hwPortNumber,
		trapLogIndex }
	STATUS      current
	DESCRIPTION
		"This trap indicates that Receive Loss of Clock (RLOC)
		is cleared on the incoming signal."
	::= { atmSwitch 0 225 }

asxJ2HBERDetected NOTIFICATION-TYPE
	OBJECTS { hwPortName, hwPortBoard, hwPortModule, hwPortNumber,
		trapLogIndex }
	STATUS      current
	DESCRIPTION
		"This trap indicates that High Bit Error Rate (HBER)
		is detected on the incoming signal."
	::= { atmSwitch 0 226 }

asxJ2HBERCleared NOTIFICATION-TYPE
	OBJECTS { hwPortName, hwPortBoard, hwPortModule, hwPortNumber,
		trapLogIndex }
	STATUS      current
	DESCRIPTION
		"This trap indicates that High Bit Error Rate (HBER)
		is cleared on the incoming signal."
	::= { atmSwitch 0 227 }

asxJ2PAISDetected NOTIFICATION-TYPE
	OBJECTS { hwPortName, hwPortBoard, hwPortModule, hwPortNumber,
		trapLogIndex }
	STATUS      current
	DESCRIPTION
		"This trap indicates that Payload Alarm Indication
		Signal (PAIS) is detected on the incoming signal."
	::= { atmSwitch 0 228 }

asxJ2PAISCleared NOTIFICATION-TYPE
	OBJECTS { hwPortName, hwPortBoard, hwPortModule, hwPortNumber,
		trapLogIndex }
	STATUS      current
	DESCRIPTION
		"This trap indicates that Payload Alarm Indication
		SIgnal (PAIS) is cleared on the incoming signal."
	::= { atmSwitch 0 229 }

asxJ2AtmLCDDetected NOTIFICATION-TYPE
	OBJECTS { hwPortName, hwPortBoard, hwPortModule, hwPortNumber,
		trapLogIndex }
	STATUS      current
	DESCRIPTION
		"This trap indicates that the specified J2 port is
		experiencing Loss of Cell Deliniation (LCD). A LCD
		failure is declared when the LCD defect persists for a
		period of 2.5 +/- 0.5 seconds."
	::= { atmSwitch 0 230 }

asxJ2AtmLCDCleared NOTIFICATION-TYPE
	OBJECTS { hwPortName, hwPortBoard, hwPortModule, hwPortNumber,
		trapLogIndex }
	STATUS      current
	DESCRIPTION
		"This trap indicates that the LCD failure identified
		by trap asxJ2AtmLCDDetected has been cleared. A LCD
		failure is cleared when the LCD defect is absent for
		10 +/- 0.5 seconds."
	::= { atmSwitch 0 231 }

asxJ2TLOCDetected NOTIFICATION-TYPE
	OBJECTS { hwPortName, hwPortBoard, hwPortModule, hwPortNumber,
		trapLogIndex }
	STATUS      current
	DESCRIPTION
		"This trap indicates that Transmit Loss of Clock
		(TLOC) is detected."
	::= { atmSwitch 0 232 }

asxJ2TLOCCleared NOTIFICATION-TYPE
	OBJECTS { hwPortName, hwPortBoard, hwPortModule, hwPortNumber,
		trapLogIndex }
	STATUS      current
	DESCRIPTION
		"This trap indicates that Transmit Loss of Clock
		(TLOC) is cleared."
	::= { atmSwitch 0 233 }

-------------------------------------------------------------------
-- TP25 netmod traps
-------------------------------------------------------------------

asxTP25LOSDetected NOTIFICATION-TYPE
	OBJECTS { hwPortName, hwPortBoard, hwPortModule, hwPortNumber,
		trapLogIndex }
	STATUS      current
	DESCRIPTION
		"This trap indicates that LOS Alarm is detected on
		the incoming signal."
	::= { atmSwitch 0 250 }

asxTP25LOSCleared NOTIFICATION-TYPE
	OBJECTS { hwPortName, hwPortBoard, hwPortModule, hwPortNumber,
		trapLogIndex }
	STATUS      current
	DESCRIPTION
		"This trap indicates that LOS Alarm is cleared on
		the incoming signal."
	::= { atmSwitch 0 251 }


-- ------------------------------------------------------------------------- --
-- end of netmod trap region
-- ------------------------------------------------------------------------- --

-- begin asxd trap region 1024 ->

asxOutputQueueCongested NOTIFICATION-TYPE
	OBJECTS { portName, pshmemPriority, trapLogIndex }
	STATUS      current
	DESCRIPTION
		"This trap indicates that the output queue for the
		given priority has exceeded its dedicated length,
		and has begun overflowing into the shared buffer
		space on the netmod."
	::= { atmSwitch 0 1024 }

asxOutputQueueCellLoss NOTIFICATION-TYPE
	OBJECTS { portName, pshmemPriority, trapLogIndex }
	STATUS      current
	DESCRIPTION
		"This trap indicates that the output queue for the
		given priority has overflowed and cells have been
		dropped."
	::= { atmSwitch 0 1025 }

asxExtendedModeViolation NOTIFICATION-TYPE
	OBJECTS { moduleBoard, moduleNumber, trapLogIndex }
	STATUS      current
	DESCRIPTION
		"This trap indicates that a series A or B network
		module was inserted into a switch board running
		in extended mode.  Multicast will not work on the
		series B module without removing all series D modules
		and rebooting the rebooted."
	::= { atmSwitch 0 1026 }

asxNonextendedModeWarning NOTIFICATION-TYPE
	OBJECTS { moduleBoard, moduleNumber, trapLogIndex }
	STATUS      current
	DESCRIPTION
		"This trap indicates that a series C or greater network
		module was inserted into a switch board running
		in non-extended mode."
	::= { atmSwitch 0 1027 }

--q2931AVRejectTrap TRAP-TYPE
--	ENTERPRISE atmSwitch
--	VARIABLES {
--		hwPortName, q2931AVStatsPort, q2931AVStatsVPI,
--		q2931AVCurrentRejectUnknownCount, trapLogIndex
--		}
--	DESCRIPTION
--		"This trap is generated whenever any UNI3.x with
--		AddressValidation enabled rejects a Setup Request
--		call more than q2931AVRejectTrapThreshold times in any
--		given q2931AVRejectTrapPeriod."
--	::= 1028

crConfMemoryOflow NOTIFICATION-TYPE
	OBJECTS { crMemoryAllocated, trapLogIndex }
	STATUS      current
	DESCRIPTION
		" This trap is generated when the allocated callrecord
		memory(as indicated by crMemoryAllocated) is exceeded."
	::= { atmSwitch 0 1029 }

crXfrPrimaryXfrFailed NOTIFICATION-TYPE
	OBJECTS { crXfrIndex, crXfrPrimaryTrapStatus, trapLogIndex }
	STATUS      current
	DESCRIPTION
		" This trap is generated when the call record transfer
		to the primary host(as indicated by crXfrPrimaryUrl)
		fails."
	::= { atmSwitch 0 1030 }

crXfrSecondaryXfrFailed NOTIFICATION-TYPE
	OBJECTS { crXfrIndex, crXfrSecondaryTrapStatus, trapLogIndex }
	STATUS      current
	DESCRIPTION
		" This trap is generated when the call record transfer
		to the secondary host(as indicated by
		crXfrSecondaryUrl) fails."
	::= { atmSwitch 0 1031 }

crConfMemAllocFail NOTIFICATION-TYPE
	OBJECTS { crMemoryAllocated, trapLogIndex }
	STATUS      current
	DESCRIPTION
		" This trap is generated when Callrecord functionality
		is unable to allocate memory as specified by
		crMemoryAllocated. This can happen when the
		crConfAdminStatus changes state from `off' or when
		the switch reboots when Callrecords is configured `on'."
	::= { atmSwitch 0 1032 }

crGeneralFailure NOTIFICATION-TYPE
	OBJECTS { crXfrIndex, trapLogIndex }
	STATUS      current
	DESCRIPTION
		" This trap is generated when any of the callrecord
		related functionality fails for any reason. One example
		would be when the Callrecord Module fails to schedule
		an interval timer."
	::= { atmSwitch 0 1033 }

asxDualScpSyncFailure NOTIFICATION-TYPE
	OBJECTS { boardIndex, dualScpSyncState, trapLogIndex }
	STATUS      current
	DESCRIPTION
		"This trap indicates that automatic CDB synchronization
		is disabled due to failures."
	::= { atmSwitch 0 1034 }

asxDualScpSwitchOver NOTIFICATION-TYPE
	OBJECTS { boardIndex, dualScpSlot, dualScpSwitchOverTime,
		trapLogIndex }
	STATUS      current
	DESCRIPTION
		"This trap indicates that the backup SCP has taken
		control of the switch."
	::= { atmSwitch 0 1035 }

asxDualScpHotSwap NOTIFICATION-TYPE
	OBJECTS { boardIndex, dualScpSlot, dualScpState, trapLogIndex }
	STATUS      current
	DESCRIPTION
		"This trap indicates that an SCP hotswap insertion
		or removal has occurred."
	::= { atmSwitch 0 1036 }

asxVPAISDetected NOTIFICATION-TYPE
	OBJECTS { portName, pathPort, pathVPI, trapLogIndex }
	STATUS      current
	DESCRIPTION
		"This trap indicates that the Alarm Indication Signal (AIS)
		is detected on the incoming (terminating) virtual path.  This
		trap is generated once when the virtual path is declared to
		be in the active AIS state."
	::= { atmSwitch 0 1037 }

asxVPAISCleared NOTIFICATION-TYPE
	OBJECTS { portName, pathPort, pathVPI, trapLogIndex }
	STATUS      current
	DESCRIPTION
		"This trap indicates that the Alarm Indication Signal (AIS)
		has been removed from the incoming (terminating) virtual path.
		This trap is generated once when the virtual path is declared
		to be in the inactive AIS state."
	::= { atmSwitch 0 1038 }

asxVPRDIDetected NOTIFICATION-TYPE
	OBJECTS { portName, pathPort, pathVPI, trapLogIndex }
	STATUS      current
	DESCRIPTION
		"This trap indicates that the Remote Defect Indication (RDI)
		is detected on the incoming (terminating) virtual path.  This
		trap is generated once when the virtual path is declared to be
		in the active RDI state."
	::= { atmSwitch 0 1039 }

asxVPRDICleared NOTIFICATION-TYPE
	OBJECTS { portName, pathPort, pathVPI, trapLogIndex }
	STATUS      current
	DESCRIPTION
		"This trap indicates that the Remote Defect Indication (RDI)
		has been removed from the incoming (terminating) virtual path.
		This trap is generated once when the virtual path is declared
		to be in the inactive RDI state."
	::= { atmSwitch 0 1040 }

asxNonextendedModeViolation NOTIFICATION-TYPE
	OBJECTS { moduleBoard, moduleNumber, trapLogIndex }
	STATUS      current
	DESCRIPTION
		"This trap indicates that a series D network
		module was inserted into a switch board running
		in non-extended mode.  Multicast will not work
		on the series D module without removing all
		series B modules and rebooting the switch."
	::= { atmSwitch 0 1041 }

asxUnsupportedNetworkModule NOTIFICATION-TYPE
	OBJECTS { moduleBoard, moduleNumber, trapLogIndex }
	STATUS      current
	DESCRIPTION
		"This trap indicates that a unsupported network
		module was inserted into a switch."
	::= { atmSwitch 0 1042 }

asxDualScpRedundancy NOTIFICATION-TYPE
	OBJECTS { boardIndex, dualScpSlot, dualScpRedundancyState,
		    trapLogIndex }
	STATUS      current
	DESCRIPTION
		"This trap indicates that there is a change in
		 the state of dual SCP Redundancy."
	::= { atmSwitch 0 1043 }

asxIpFilterViolation NOTIFICATION-TYPE
	OBJECTS {
		ipFilterStatsVPI,
		ipFilterStatsVCI,
		ipFilterStatsIfName
		}
	STATUS      current
	DESCRIPTION
		"An asxIpFilterViolation trap occurs when an incoming IP
		packet is unauthorized to enter the switch control port
		and has been dropped."
	::= { atmSwitch 0 1049 }

q2931AFRejectKnown NOTIFICATION-TYPE
	OBJECTS {
		portName,		-- for incoming port
		pathPort,
		pathVPI,
		portName,		-- for outgoing port
		opathPort,
		opathVPI,
		trapLogIndex
		}
	STATUS      current
	DESCRIPTION
		"This trap is generated whenever any q2931 UNI with
		Address Filtering enabled rejects a Setup request
		because the request matched a template with the
		action 'reject'.
		The variables sent in the trap identify the
		source and destination UNI for the call."
	::= { atmSwitch 0 1053 }

q2931AFRejectUnknown NOTIFICATION-TYPE
	OBJECTS {
		portName,		-- for incoming port
		pathPort,
		pathVPI,
		portName,		-- for outgoing port
		opathPort,
		opathVPI,
		trapLogIndex
		}
	STATUS      current
	DESCRIPTION
		"This trap is generated whenever any q2931 UNI with
		Address Filtering enabled rejects a Setup request
		because the address matched no template.
		The variables sent in the trap identify the
		source and destination UNI for the call."
	::= { atmSwitch 0 1054 }

q2931CreationFailure NOTIFICATION-TYPE
	OBJECTS { portName, q2931AdminPort, q2931AdminVPI, trapLogIndex }
	STATUS      current
	DESCRIPTION
		"This trap is generated whenever a switch fails to
		create a UNI.  This is most likely due to a
		resource limitation on the switch."
	::= { atmSwitch 0 1061 }

asxPsCurrentDown NOTIFICATION-TYPE
	OBJECTS { envPowerSupplyIndex, trapLogIndex }
	STATUS      current
	DESCRIPTION
		"This trap alerts that one ATM switch power supply had a
		curent failure. The power supply that failed is identified
		by the power supply index."
	::= { atmSwitch 0 1068 }

asxPsCurrentUp NOTIFICATION-TYPE
	OBJECTS { envPowerSupplyIndex, trapLogIndex }
	STATUS      current
	DESCRIPTION
		"This trap alerts that one ATM switch power supply that had
		a curent failure is now up. The power supply that is back up
		is identified by the power supply index."
	::= { atmSwitch 0 1069 }

asxPs5VoltDown NOTIFICATION-TYPE
	OBJECTS { envPowerSupplyIndex, trapLogIndex }
	STATUS      current
	DESCRIPTION
		"This trap alerts that one ATM switch power supply had a
		+5V failure. The power supply that failed is identified
		by the power supply index."
	::= { atmSwitch 0 1070 }

asxPs5VoltUp NOTIFICATION-TYPE
	OBJECTS { envPowerSupplyIndex, trapLogIndex }
	STATUS      current
	DESCRIPTION
		"This trap alerts that one ATM switch power supply that had
		a +5V failure is now up. The power supply that is back up
		is identified by the power supply index."
	::= { atmSwitch 0 1071 }

asxSwitchLoginDetected NOTIFICATION-TYPE
	OBJECTS { switchCurrentUserid, switchCurrentLoginFrom, trapLogIndex}
	STATUS      current
	DESCRIPTION
		"An asxSwitchLoginDetected trap signifies that a
		user logged in on the switch."
	::= { atmSwitch 0 1072 }

asxSwitchLoginFailed NOTIFICATION-TYPE
	OBJECTS { switchCurrentUserid, switchCurrentLoginFrom, trapLogIndex}
	STATUS      current
	DESCRIPTION
		"An asxSwitchLoginFailed trap signifies that a
		user's attempt to log in on the switch failed."
	::= { atmSwitch 0 1073 }

-- begin PNNI trap region 1074

pnniTdbGuardbandResrvFail NOTIFICATION-TYPE
	OBJECTS { pnniNodeId, hrSystemDate, numBytesFree, numBlocksFree, numBlocksAlloc, maxBlockSizeFree, trapLogIndex }
	STATUS      current
	DESCRIPTION
		" This trap is generated when guardband memory reserve for
		  any of the PNNI TDB(Topology Database) related functionalites
		  like creation,modification and deletion on objects like node,
		  ptse,flags,interal prefixes,external prefixes and etc fails.
		  The switch is low on memory."
	::= { atmSwitch 0 1074 }

pnniTdbInconsistentState NOTIFICATION-TYPE
	OBJECTS { pnniNodeId, hrSystemDate, numBytesFree, numBlocksFree, numBlocksAlloc, maxBlockSizeFree, trapLogIndex }
	STATUS      current
	DESCRIPTION
		"This trap is generated when PNNI TDB(Topology Database) is in
		 an unrecoverable error condition due to MALLOC and other TDB
		 related faliures. When this happenes the associated logical
		 node is shutdown and this trap is sent.The switch has to be
		 rebooted to bring this PNNI logical node up again."
	::= { atmSwitch 0 1075 }

asxShmem2OutputQueueCongested NOTIFICATION-TYPE
	OBJECTS { portName, pShmem2Priority, trapLogIndex }
	STATUS      current
	DESCRIPTION
		"This trap indicates that the output queue for the
		given priority has exceeded its dedicated length,
		and has begun overflowing into the shared buffer
		space on the netmod."
	::= { atmSwitch 0 1077 }

asxShmem2OutputQueueCellLoss NOTIFICATION-TYPE
	OBJECTS { portName, pShmem2Priority, trapLogIndex }
	STATUS      current
	DESCRIPTION
		"This trap indicates that the output queue for the
		given priority has overflowed and cells have been
		dropped."
	::= { atmSwitch 0 1078 }

fabricLvl3Lookup              NOTIFICATION-TYPE
	OBJECTS { boardIndex }
	STATUS      current
	DESCRIPTION
		"This trap is generated when a fabric detects
		 excessive level 3 lookup errors. The level 3
		 lookup count is read every second. If the
		 lookup count is non-null for 5 consecutive
		 seconds, then this trap is generated.
		 If the errors continue, this trap will be generated
		 continuously every 5 seconds.
		 This trap can be caused by: a misconfigured
		 PVC; bad hardware."
	::= { atmSwitch 0 1080 }

fabricCorrectedLookup              NOTIFICATION-TYPE
	OBJECTS { boardIndex }
	STATUS      current
	DESCRIPTION
		"This trap is generated when the SCP detects
		 inconsistant information in the HDCOMP lookup.
		 The switch has corrected the bad information
		 in the HDCOMP lookup ASIC's data structures."
	::= { atmSwitch 0 1081 }

spvcRerouteInitiated              NOTIFICATION-TYPE
	OBJECTS { boardIndex, spvcSrcInPort, spvcSrcInVPI, spvcSrcInVCI }
	STATUS      current
	DESCRIPTION
		"This trap is sent when a SPVC is being re-routed due to
		a better path being found."
	::= { atmSwitch 0 1090 }

asxQ2931Down NOTIFICATION-TYPE
	OBJECTS { portName, q2931AdminPort, q2931AdminVPI, trapLogIndex }
	STATUS      current
	DESCRIPTION
		"This trap is generated whenever UNI signalling goes down."
	::= { atmSwitch 0 1091 }

asxQ2931Up NOTIFICATION-TYPE
	OBJECTS { portName, q2931AdminPort, q2931AdminVPI, trapLogIndex }
	STATUS      current
	DESCRIPTION
		"This trap is generated whenever UNI signalling goes up."
	::= { atmSwitch 0 1092 }

asxFabricDown NOTIFICATION-TYPE
	OBJECTS { boardIndex, trapLogIndex }
	STATUS      current
	DESCRIPTION
		"An asxFabricDown trap signifies that the sending protocol
		entity recognizes a failure in one of the ATM Switch fabric,
		that is identified by the board number.  This is probably
		caused by a hot-swap of a fabric module."
	::= { atmSwitch 0 1093 }

asxFabricUp NOTIFICATION-TYPE
	OBJECTS { boardIndex, trapLogIndex }
	STATUS      current
	DESCRIPTION
		"An asxFabricUp trap signifies that the sending protocol
		entity recognizes a new operational ATM Switch fabric,
		that is identified by the board number.  This is
		probably caused by a hot-swap of a fabric module."
	::= { atmSwitch 0 1094 }

asxQ2931CallClearing NOTIFICATION-TYPE
	OBJECTS { portName, q2931AdminPort, q2931AdminVPI, trapLogIndex }
	STATUS      current
	DESCRIPTION
		"This trap is generated whenever calls are cleared in a
		 signalling interface for the following reasons.
		 * Carrier loss
		 * SONET alarms in case of SONE
		 * VP failure "
	::= { atmSwitch 0 1095 }


----------------------------------------------------------------------------
--               Inteligent Network TRAPS starts here
----------------------------------------------------------------------------

-- Definition of the TRAP generated by the FR/ATM interworking function

-- The followings are the linkUp and linkDown traps defined in RFC1573
-- that are generated to reflect changes in ifAdminStatus and ifOperStatus,
-- instrumenting transitions into/out of the down state which generate
-- traps.

--*
--* These traps are no longer used. The new rfc2233 now implements them.
--*
--ifLinkDown   TRAP-TYPE
--             ENTERPRISE atmSwitch
--             VARIABLES  { ifIndex,
--                          ifAdminStatus,
--                          ifOperStatus,
--                          trapLogIndex }
--             DESCRIPTION
--             "This trap alerts that the SNMP agent has detected that
--             the ifOperStatus of this interface is about to transition
--             into the down state."
--             ::= 2001
--
--
--ifLinkUp     TRAP-TYPE
--             ENTERPRISE atmSwitch
--             VARIABLES  { ifIndex,
--                          ifAdminStatus,
--                          ifOperStatus,
--                          trapLogIndex }
--             DESCRIPTION
--             "This trap alerts that the SNMP agent has detected that
--             the ifOperStatus of this interface has transitioned
--             out of the down state."
--             ::= 2002

-- framNakMsg   TRAP-TYPE
--              ENTERPRISE atmSwitch
--              VARIABLES  { messageType,
--                           errorCode,
--                           board,
--                           netmod,
--                           port,
--                           channel,
--                           dlci,
--                           funivpi,
--                           funivci }
--              DESCRIPTION
--	     "This trap is sent when a message from the SCP to the
--	     FRAM netmod does not succeed."
--	     ::= 2003

pnniSpvccDown              NOTIFICATION-TYPE
	OBJECTS {     boardIndex,
			pnniSpvcSrcCallingPort,
			pnniSpvcSrcCallingVPI,
			pnniSpvcSrcCallingVCI,
			pnniSpvcSrcDownReason,
			pnniSpvcSrcName,
			pnniSpvcSrcLastFailCause,
			pnniSpvcSrcLastLocation}
	STATUS      current
	DESCRIPTION
		"This trap is sent when a SPVC call is cleared or deleted.
		The pnniSpvcSrcDownReason indicates if the call was cleared due
		to a better route being found or a network failure. It also
		may indicate SPVC deletion.
		This trap is only sent if pnniSpvcTrapMode is all."
	::= { atmSwitch 0 2004 }

pnniSpvccUp             NOTIFICATION-TYPE
	OBJECTS {     boardIndex,
			pnniSpvcSrcCallingPort,
			pnniSpvcSrcCallingVPI,
			pnniSpvcSrcCallingVCI,
			pnniSpvcSrcOldRouteCost,
			pnniSpvcSrcName,
			pnniSpvcSrcRouteCost}
	STATUS      current
	DESCRIPTION
		"This trap is send when a SPVC call is established.
		It identifies the SPVC and the old and new cost.
		If the call has not been up before, the pnniSpvcSrcOldRouteCost
		will be -1.
		This trap is only sent if pnniSpvcTrapMode is failure or all."
	::= { atmSwitch 0 2005 }

pnniSpvccFail              NOTIFICATION-TYPE
	OBJECTS {     boardIndex,
			pnniSpvcSrcCallingPort,
			pnniSpvcSrcCallingVPI,
			pnniSpvcSrcCallingVCI,
			pnniSpvcSrcDownReason,
			pnniSpvcSrcName,
			pnniSpvcSrcLastFailCause,
			pnniSpvcSrcLastLocation}
	STATUS      current
	DESCRIPTION
		"This trap is sent when a SPVC call that is down
		fails to get connected on 16 consecutive attempts.
		This trap is only sent if pnniSpvcTrapMode is failure or all."
	::= { atmSwitch 0 2006 }

pnniSpvpcDown             NOTIFICATION-TYPE
	OBJECTS {     boardIndex,
			pnniSpvpcSrcCallingPort,
			pnniSpvpcSrcCallingVPI,
			pnniSpvpcSrcDownReason,
			pnniSpvpcSrcName,
			pnniSpvpcSrcLastFailCause,
			pnniSpvpcSrcLastLocation}
	STATUS      current
	DESCRIPTION
		 "This trap is sent when a SPVP call is cleared.
		The pnniSpvcSrcDownReason indicates if the call was cleared due
		to a better route being found or a network failure.  It also
		may indicate SPVPC deletion.
		This trap is only sent if pnniSpvpcTrapMode is all."
	::= { atmSwitch 0 2007 }

pnniSpvpcUp            NOTIFICATION-TYPE
	OBJECTS {     boardIndex,
			pnniSpvpcSrcCallingPort,
			pnniSpvpcSrcCallingVPI,
			pnniSpvpcSrcOldRouteCost,
			pnniSpvpcSrcName,
			pnniSpvpcSrcRouteCost}
	STATUS      current
	DESCRIPTION
		"This trap is send when a SPVP call is established.
		It identifies the SPVP and the old and new cost.
		If the call has not been up before, the pnniSpvcSrcOldRouteCost
		will be -1.
		This trap is only sent if pnniSpvpcTrapMode is all or failure."
	::= { atmSwitch 0 2008 }

pnniSpvpcFail             NOTIFICATION-TYPE
	OBJECTS {     boardIndex,
			pnniSpvpcSrcCallingPort,
			pnniSpvpcSrcCallingVPI,
			pnniSpvpcSrcDownReason,
			pnniSpvpcSrcName,
			pnniSpvpcSrcLastFailCause,
			pnniSpvpcSrcLastLocation}
	STATUS      current
	DESCRIPTION
		"This trap is sent when a SPVP call that is down
		fails to get connected on 16 consecutive attempts.
		This trap is only sent if pnniSpvpcTrapMode is all or failure."
	::= { atmSwitch 0 2009 }

-- PortCard Traps

asxPortCardDown NOTIFICATION-TYPE
	OBJECTS { portCardName, trapLogIndex }
	STATUS      current
	DESCRIPTION
		"An asxPortCardDown trap signifies that the sending protocol
		entity recognizes a failure in one of the ATM Switch portcards,
		that is identified by the portcard name. This is probably
		caused by a hot-swap of the port card."
	::= { atmSwitch 0 2010 }

asxPortCardUp NOTIFICATION-TYPE
	OBJECTS { portCardName, trapLogIndex }
	STATUS      current
	DESCRIPTION
		"An asxPortCardUp trap signifies that the sending protocol
		entity recognizes a new operational ATM Switch port card,
		that is identified by the portcard name. This is
		probably caused by a hot-swap of the port card."
	::= { atmSwitch 0 2011 }

------------------------------------------------------------------------------
-- Service category based Shmem Traps for congestion and loss
--

asxServiceCategoryOutputQueueCongested NOTIFICATION-TYPE
	OBJECTS { portName, serviceCategoryName, trapLogIndex }
	STATUS      current
	DESCRIPTION
		"This trap indicates that the output queue for the
		service category has exceeded its dedicated length,
		and has begun overflowing into the shared buffer
		space on the netmod."
	::= { atmSwitch 0 2013 }

asxServiceCategoryOutputQueueCellLoss NOTIFICATION-TYPE
	OBJECTS { portName, serviceCategoryName, trapLogIndex }
	STATUS      current
	DESCRIPTION
		"This trap indicates that the output queue for the
		given service category has overflowed and cells have been
		dropped."
	::= { atmSwitch 0 2014 }

pnniNormalToOverloadTransition NOTIFICATION-TYPE
	OBJECTS { pnniNodeId, hrSystemDate, numBytesFree, numBlocksFree, numBlocksAlloc, maxBlockSizeFree, trapLogIndex }
	STATUS      current
	DESCRIPTION
		"This trap is generated on transition from the normal state to
		 the overload state."
	::= { atmSwitch 0 2015 }

pnniOverloadToNormalTransition NOTIFICATION-TYPE
	OBJECTS { pnniNodeId, hrSystemDate, numBytesFree, numBlocksFree, numBlocksAlloc, maxBlockSizeFree, trapLogIndex }
	STATUS      current
	DESCRIPTION
		"This trap is generated on transition from the overload to
		the normal state."
	::= { atmSwitch 0 2016 }

--------------------------------------------------------
--
--   Syslog related
--------------------------------------------------------

syslogFacility OBJECT-TYPE
    SYNTAX INTEGER {
        daemon(0),
        local0(1),
        local1(2),
        local2(3),
        local3(4),
        local4(5),
        local5(6),
        local6(7),
        local7(8)
    }
    MAX-ACCESS read-write
    STATUS current
    DESCRIPTION
        "The syslog facility string, possible values are
         daemon, local[0-7]."
    ::= { syslogGroup 1 }

syslogConsoleState OBJECT-TYPE
    SYNTAX INTEGER {
        on(1),
        off(2)
    }
    MAX-ACCESS read-write
    STATUS current
    DESCRIPTION
        "The syslog console state, ON means syslog messages are sent
        to console."
    ::= { syslogGroup 2 }

syslogDestinationTable OBJECT-TYPE
    SYNTAX   SEQUENCE OF SyslogDestinationEntry
    MAX-ACCESS not-accessible
    STATUS current
    DESCRIPTION
        "This table lists all the syslog destinations"
    ::= { syslogGroup 3 }

syslogDestinationEntry OBJECT-TYPE
    SYNTAX SyslogDestinationEntry
    MAX-ACCESS not-accessible
    STATUS current
    DESCRIPTION
        "A structure containing the parameters for a syslog destination"
    INDEX { syslogDestinationHost }
    ::= { syslogDestinationTable 1 }

SyslogDestinationEntry ::= SEQUENCE {
    syslogDestinationHost IpAddress,
    syslogDestinationStatus RowStatus
}

syslogDestinationHost OBJECT-TYPE
    SYNTAX   IpAddress
    MAX-ACCESS not-accessible
    STATUS current
    DESCRIPTION
        "The host IP address of the syslog destination"
    ::= { syslogDestinationEntry 1 }

syslogDestinationStatus OBJECT-TYPE 
    SYNTAX  RowStatus 
    MAX-ACCESS  read-write 
    STATUS  current 
    DESCRIPTION 
        "Administrative status of this entry" 
    ::= { syslogDestinationEntry 2 } 

--------------------------------------------------------
--
--   Traps related to PMP calls
--------------------------------------------------------
pnniPmpRerouteInitiated	NOTIFICATION-TYPE
	OBJECTS  { 
			pnniPmpSpvccSrcRootPort,
			pnniPmpSpvccSrcRootVPI,
			pnniPmpSpvccSrcRootVCI
		  }
	STATUS      current
	DESCRIPTION
		"This trap is sent when a party is being re-routed due to
		a better path being found or if a reroute is requested using a AMI command."
	::= { atmSwitch 0 2020 }


pnniPmpSpvcUp             NOTIFICATION-TYPE
	OBJECTS  {   
			pnniPmpSpvccSrcRootPort,
			pnniPmpSpvccSrcRootVPI,
			pnniPmpSpvccSrcRootVCI,
			pnniPmpSpvccSrcPartyName,
			pnniPmpSpvccSrcPartyRouteCost
		  }
	STATUS      current
	DESCRIPTION
		"This trap is send when a pmp SPVC call is established.
		This trap is only sent if pnniSpvcTrapMode is failure or all."
	::= { atmSwitch 0 2021 }

pnniPmpSpvcDown             NOTIFICATION-TYPE
	OBJECTS  {  
			pnniPmpSpvccSrcRootPort,
			pnniPmpSpvccSrcRootVPI,
			pnniPmpSpvccSrcRootVCI,
			pnniPmpSpvccSrcPartyDownReason,
			pnniPmpSpvccSrcPartyName,
			pnniPmpSpvccSrcPartyLastFailCause,
			pnniPmpSpvccSrcPartyLastLocation
		   }
	STATUS      current
	DESCRIPTION
		 "This trap is sent when a pmp SPVC call is cleared.
		The pnniSpvcSrcDownReason indicates if the call was cleared due
		to a better route being found or a network failure.
		This trap is only sent if pnniSpvpcTrapMode is all."
	::= { atmSwitch 0 2022 }

pnniPmpSpvcFail              NOTIFICATION-TYPE
	OBJECTS  { 	
			pnniPmpSpvccSrcRootPort,
			pnniPmpSpvccSrcRootVPI,
			pnniPmpSpvccSrcRootVCI,
			pnniPmpSpvccSrcPartyDownReason,
			pnniPmpSpvccSrcPartyName,
			pnniPmpSpvccSrcPartyLastFailCause,
			pnniPmpSpvccSrcPartyLastLocation
		  }
	STATUS      current
	DESCRIPTION
		"This trap is sent when a SPVC call that is down
		fails to get connected on 16 consecutive attempts.
		This trap is only sent if pnniSpvcTrapMode is failure or all."
	::= { atmSwitch 0 2023 }

pnniSpvxRGroupSwover   NOTIFICATION-TYPE
	OBJECTS  {
	            pnniSpvxcRGroupSwitchoverCmd, 
                    pnniSpvxcRGroupActivePort, 
	            trapLogIndex }
	STATUS      current
	DESCRIPTION
		"This trap is sent when a automatic switch over 
                 occurs in a SPVC Redundancy group that has 
                 automatic PVC switch over enabled."
	::= { atmSwitch 0 2024 }

--------------------------------------------------------
--
--   Traps related to SVx/SPVx Preservation.
--------------------------------------------------------
asxSVXCPStateTransferFailed	NOTIFICATION-TYPE
	OBJECTS { 	dualScpSlot, trapLogIndex }
	STATUS      current
	DESCRIPTION
		"This trap is sent when the SVx/SPVx Preservation module
		 is unable to transfer call and interface state information
		 to the Standby SCP, due either to temporary unavailablility
		 of system resources or to a permanent system error 
		 requiring a system reboot."
	::= { atmSwitch 0 2025 }

asxSVXCPStateTransferRestarted	NOTIFICATION-TYPE
	OBJECTS { 	dualScpSlot, trapLogIndex }
	STATUS      current
	DESCRIPTION
		"This trap is sent when the SVx/SPVx Preservation module
		 has restarted its transfer of call and interface state 
		 information to the Standby SCP, which transfer was 
		 halted due to unavailablility of system resources."
	::= {atmSwitch 0 2026 }

asxSVXCPStateDroppedCall	NOTIFICATION-TYPE
	OBJECTS { 	trapLogIndex }
	STATUS      current
	DESCRIPTION
		"This trap is sent when the SVx/SPVx Preservation module 
		 has insufficient memory to store one or more calls during 
		 its transfer of call and interface state information to 
		 the Standby SCP.
		 Such calls therefore will be lost (not preserved on
		 switchover).  This trap is sent only once, no matter how
		 many calls suffer this fate.  Recovering any lost calls is
		 possible only by disabling and then re-enabling 
		 SVx/SPVx Preservation, in order to provoke a complete 
		 retrial of the transfer process."
	::= {atmSwitch 0 2027 }

END
