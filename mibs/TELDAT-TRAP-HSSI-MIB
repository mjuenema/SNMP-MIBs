-- file automatically created


TELDAT-TRAP-HSSI-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


hssiTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the HSSI event subsystem."
    REVISION "201401200930Z"
    DESCRIPTION "Initial implementation"
        ::= { telEventTraps 177 }


hssiEventsGroup	OBJECT IDENTIFIER	::= { hssiTrapsMIB 1 }

hssiNotifications	OBJECT IDENTIFIER	::= { hssiTrapsMIB 2 }
hssiNotificationsPrefix	OBJECT IDENTIFIER	::= { hssiNotifications 0 }

hssiEventObjects1 OBJECT-IDENTITY
    STATUS current
    DESCRIPTION
        "Event HSSI.1
        A packet buffer was not available when the interface self-test
        needed one. "
    ::= { hssiEventsGroup 1 }

hssi1_interface OBJECT-TYPE
    SYNTAX DisplayString
    MAX-ACCESS accessible-for-notify
    STATUS current
    DESCRIPTION
        "Parameter 'interface' in event HSSI.1"
    ::= { hssiEventObjects1 1 }

hssiEventObjects2 OBJECT-IDENTITY
    STATUS current
    DESCRIPTION
        "Event HSSI.2
        Self-test is being started on the high speed serial interface."
    ::= { hssiEventsGroup 2 }

hssi2_interface OBJECT-TYPE
    SYNTAX DisplayString
    MAX-ACCESS accessible-for-notify
    STATUS current
    DESCRIPTION
        "Parameter 'interface' in event HSSI.2"
    ::= { hssiEventObjects2 1 }

hssiEventObjects3 OBJECT-IDENTITY
    STATUS current
    DESCRIPTION
        "Event HSSI.3
        The interface failed self test because at least one of the
        required signals was off."
    ::= { hssiEventsGroup 3 }

hssi3_ta OBJECT-TYPE
    SYNTAX DisplayString
    MAX-ACCESS accessible-for-notify
    STATUS current
    DESCRIPTION
        "Parameter 'ta' in event HSSI.3"
    ::= { hssiEventObjects3 1 }

hssi3_ca OBJECT-TYPE
    SYNTAX DisplayString
    MAX-ACCESS accessible-for-notify
    STATUS current
    DESCRIPTION
        "Parameter 'ca' in event HSSI.3"
    ::= { hssiEventObjects3 2 }

hssi3_interface OBJECT-TYPE
    SYNTAX DisplayString
    MAX-ACCESS accessible-for-notify
    STATUS current
    DESCRIPTION
        "Parameter 'interface' in event HSSI.3"
    ::= { hssiEventObjects3 3 }

hssiEventObjects4 OBJECT-IDENTITY
    STATUS current
    DESCRIPTION
        "Event HSSI.4
        A signal status change has occurred. The present state is described."
    ::= { hssiEventsGroup 4 }

hssi4_ta OBJECT-TYPE
    SYNTAX DisplayString
    MAX-ACCESS accessible-for-notify
    STATUS current
    DESCRIPTION
        "Parameter 'ta' in event HSSI.4"
    ::= { hssiEventObjects4 1 }

hssi4_ca OBJECT-TYPE
    SYNTAX DisplayString
    MAX-ACCESS accessible-for-notify
    STATUS current
    DESCRIPTION
        "Parameter 'ca' in event HSSI.4"
    ::= { hssiEventObjects4 2 }

hssi4_la OBJECT-TYPE
    SYNTAX DisplayString
    MAX-ACCESS accessible-for-notify
    STATUS current
    DESCRIPTION
        "Parameter 'la' in event HSSI.4"
    ::= { hssiEventObjects4 3 }

hssi4_lb OBJECT-TYPE
    SYNTAX DisplayString
    MAX-ACCESS accessible-for-notify
    STATUS current
    DESCRIPTION
        "Parameter 'lb' in event HSSI.4"
    ::= { hssiEventObjects4 4 }

hssi4_lc OBJECT-TYPE
    SYNTAX DisplayString
    MAX-ACCESS accessible-for-notify
    STATUS current
    DESCRIPTION
        "Parameter 'lc' in event HSSI.4"
    ::= { hssiEventObjects4 5 }

hssi4_interface OBJECT-TYPE
    SYNTAX DisplayString
    MAX-ACCESS accessible-for-notify
    STATUS current
    DESCRIPTION
        "Parameter 'interface' in event HSSI.4"
    ::= { hssiEventObjects4 6 }

hssiEventObjects5 OBJECT-IDENTITY
    STATUS current
    DESCRIPTION
        "Event HSSI.5
        The interface was brought down because one of the signals was off."
    ::= { hssiEventsGroup 5 }

hssi5_ta OBJECT-TYPE
    SYNTAX DisplayString
    MAX-ACCESS accessible-for-notify
    STATUS current
    DESCRIPTION
        "Parameter 'ta' in event HSSI.5"
    ::= { hssiEventObjects5 1 }

hssi5_ca OBJECT-TYPE
    SYNTAX DisplayString
    MAX-ACCESS accessible-for-notify
    STATUS current
    DESCRIPTION
        "Parameter 'ca' in event HSSI.5"
    ::= { hssiEventObjects5 2 }

hssi5_interface OBJECT-TYPE
    SYNTAX DisplayString
    MAX-ACCESS accessible-for-notify
    STATUS current
    DESCRIPTION
        "Parameter 'interface' in event HSSI.5"
    ::= { hssiEventObjects5 3 }


hssiNotification1 NOTIFICATION-TYPE
    OBJECTS { 
              hssi1_interface 
            }
    STATUS current
    DESCRIPTION
        "Notification of Event HSSI.1

        Message: 'no buffer available for selftest interface $1'

        Parameters list:
              $1: hssi1_interface

        A packet buffer was not available when the interface self-test
        needed one. "
    ::= { hssiNotificationsPrefix 1 }

hssiNotification2 NOTIFICATION-TYPE
    OBJECTS { 
              hssi2_interface 
            }
    STATUS current
    DESCRIPTION
        "Notification of Event HSSI.2

        Message: 'start selftest interface $1'

        Parameters list:
              $1: hssi2_interface

        Self-test is being started on the high speed serial interface."
    ::= { hssiNotificationsPrefix 2 }

hssiNotification3 NOTIFICATION-TYPE
    OBJECTS { 
              hssi3_ta, 
              hssi3_ca,
              hssi3_interface 
            }
    STATUS current
    DESCRIPTION
        "Notification of Event HSSI.3

        Message: 'Self test failed, TA = $1, CA = $2, int $3'

        Parameters list:
              $1: hssi3_ta
              $2: hssi3_ca
              $3: hssi3_interface

        The interface failed self test because at least one of the
        required signals was off."
    ::= { hssiNotificationsPrefix 3 }

hssiNotification4 NOTIFICATION-TYPE
    OBJECTS { 
              hssi4_ta, 
              hssi4_ca,
              hssi4_la,
              hssi4_lb,
              hssi4_lc,
              hssi4_interface 
            }
    STATUS current
    DESCRIPTION
        "Notification of Event HSSI.4

        Message: 'Signal change TA = $1, CA = $2, LA = $3, LB = $4, LC = $5, on interface $6'

        Parameters list:
              $1: hssi4_ta
              $2: hssi4_ca
              $3: hssi4_la
              $4: hssi4_lb
              $5: hssi4_lc
              $6: hssi4_interface

        A signal status change has occurred. The present state is described."
    ::= { hssiNotificationsPrefix 4 }

hssiNotification5 NOTIFICATION-TYPE
    OBJECTS { 
              hssi5_ta, 
              hssi5_ca,
              hssi5_interface 
            }
    STATUS current
    DESCRIPTION
        "Notification of Event HSSI.5

        Message: 'Interface down because of signal status, TA = $1, CA = $2, int $3'

        Parameters list:
              $1: hssi5_ta
              $2: hssi5_ca
              $3: hssi5_interface

        The interface was brought down because one of the signals was off."
    ::= { hssiNotificationsPrefix 5 }


END
