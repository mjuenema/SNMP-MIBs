-- =========================================================================
-- Copyright (C) 2008 by H3C Technologies. All rights reserved.
--
-- Description:This file describes various common MIB objects implemented by both
--             Routers and Switches for use.
-- Reference:
-- Version: V2.1
-- History:
-- V1.0 26th Nov 2003
--      Separated from a3Comm8040.mib
-- V1.1 9th Dec 2003
--      a3comoemrouter.mib added
-- V1.2 23rd Jan 2004
--      merged in common node defns from a3Comoemrouter.mib
-- V1.3 24th Feb 2004
--      module imported from A3COM-HUAWEI-OID-MIB which is the root MIB MODULE for huawei-3com.
--      delete MODULE-IDENTITY import declaration
-- V1.4 16th Aug 2004
--      Add a trap node 'hwRebootSendTrap' into hwSystemNotification
-- V2.0 2004-10-12 updated by gaolong
--      Import from SNMPv2-SMI and SNMPv2-TC instead from RFC1212 and RFC1155-SMI
--      Change ACCESS clauses to MAX-ACCESS
--      Change STATUS clauses from mandatory to current
-- V2.1 2008-11-11 add node hwSysBootType by lifengguang
-- =========================================================================
A3COM-HUAWEI-COMMON-MIB DEFINITIONS ::= BEGIN

	IMPORTS
		OBJECT-TYPE, NOTIFICATION-TYPE
			FROM SNMPv2-SMI
		DisplayString
			FROM SNMPv2-TC
		hwSystem
			FROM A3COM-HUAWEI-OID-MIB;

-- ==============================
-- Begin define of hwmHostName
-- ==============================

	hwWriteConfig OBJECT-TYPE
		SYNTAX INTEGER{
					   save(1)
					  }
		MAX-ACCESS read-write
		STATUS current
		DESCRIPTION
			"Write config to router."
		::= { hwSystem 5 }

	hwStartFtpServer OBJECT-TYPE
		SYNTAX INTEGER{
					   enable(1),
					   disable(2)
					   }
		MAX-ACCESS read-write
		STATUS current
		DESCRIPTION
			"Decide whether start ftp-server.enable(1) indicates to start ftp-server;
			disable(2) indicates to stop ftp-server."
		::= { hwSystem 6 }

	hwReboot OBJECT-TYPE
		SYNTAX INTEGER{
					   reboot(1)
					   }
		MAX-ACCESS read-write
		STATUS current
		DESCRIPTION
			"Reboot router."
		::= { hwSystem 7 }

	hwSystemNotification OBJECT IDENTIFIER ::= { hwSystem 8 }

	hwWriteSuccessTrap NOTIFICATION-TYPE
		STATUS current
		DESCRIPTION
			"This trap is sent for writing success."
		::= { hwSystemNotification 1 }

	hwWriteFailureTrap NOTIFICATION-TYPE
		STATUS current
		DESCRIPTION
			"This trap is sent for writing failure."
		::= { hwSystemNotification 2 }

	hwRebootSendTrap NOTIFICATION-TYPE
		STATUS current
		DESCRIPTION
			"When users restart the device with command 'reboot', this trap will be sent two seconds before the device reboots."
		::= { hwSystemNotification 3 }

	hwSoftwareVersion OBJECT-TYPE
		SYNTAX DisplayString
		MAX-ACCESS read-only
		STATUS current
		DESCRIPTION
			"Software version."
		::= { hwSystem 9 }

	hwSysBootType OBJECT-TYPE
		SYNTAX INTEGER
		{
			coldStart(1),           -- Cold start
			warmStart(2)            -- Warm start
		}
		MAX-ACCESS read-only
		STATUS current
		DESCRIPTION
			"The boot type of the system whether the last device reboot was by
			CLI (warm start) or power off (cold start)."
		::= { hwSystem 10 }

END
