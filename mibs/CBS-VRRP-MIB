CBS-VRRP-MIB DEFINITIONS ::= BEGIN

IMPORTS
   MODULE-IDENTITY, OBJECT-TYPE, 
   NOTIFICATION-TYPE, Integer32             FROM SNMPv2-SMI
 
   TEXTUAL-CONVENTION,
   DisplayString, TruthValue                FROM SNMPv2-TC

   ProductID, KBytes                        FROM HOST-RESOURCES-MIB

   InetAddressType, InetAddress             FROM INET-ADDRESS-MIB

   cbsMIBs, cbsMgmt, cbsTraps               FROM CROSSBEAM-SYSTEMS-MIB

   cbsVgVapGroupID, cbsVgVapGroupName       FROM CBS-VAPGROUP-MIB

   cbsHwModuleID, ModuleState               FROM CBS-HARDWARE-MIB;


cbsVrrpMIB MODULE-IDENTITY
   LAST-UPDATED "200508300000Z"     -- 30 August 2005
   ORGANIZATION "Crossbeam Systems, Inc."
   CONTACT-INFO "Email:  mib-admin@crossbeamsys.com
                 Postal: 80 Central Street
                         Boxborough, MA  01719"
   DESCRIPTION  "This MIB module defines the objects related to
                 Crossbeam VRRP Traps."

::= { cbsMIBs 5 }

cbsVrrp   OBJECT IDENTIFIER ::= { cbsMgmt 5 }
cbsVrrpTraps   OBJECT IDENTIFIER ::= { cbsTraps 4 }

cbsVrrpOperations  OBJECT IDENTIFIER ::= { cbsVrrp 1 }

-- The trap variables

cbsVrrpTrapNewMasterReason OBJECT-TYPE
   SYNTAX      INTEGER {
       priority  (0),
       preempted (1),
       masterNoResponse (2)
   }
   MAX-ACCESS   accessible-for-notify
   STATUS       current
   DESCRIPTION
              "This indicates the reason for NewMaster trap.
               Used by cbsVrrpTrapNewMaster trap."
   ::= { cbsVrrpOperations 1 }

cbsVrrpTrapNewMasterFailGrName OBJECT-TYPE
   SYNTAX       DisplayString
   MAX-ACCESS   accessible-for-notify
   STATUS       current
   DESCRIPTION
              "This object contains the VRRP Failover Group 
               name. Used by cbsVrrpTrapNewMaster trap."
   ::= { cbsVrrpOperations 2 }

cbsVrrpTrapNewMasterVrId OBJECT-TYPE
   SYNTAX       Integer32 
   MAX-ACCESS   accessible-for-notify
   STATUS       current
   DESCRIPTION
              "This object contains the Virtual Router Identifier (VRID).
               Used by cbsVrrpTrapNewMaster trap."
   ::= { cbsVrrpOperations 3 }

cbsVrrpTrapNewMasterCirId OBJECT-TYPE
   SYNTAX       Integer32
   MAX-ACCESS   accessible-for-notify
   STATUS       current
   DESCRIPTION
              "This object contains the circuit ID.
               Used by cbsVrrpTrapNewMaster trap."
   ::= { cbsVrrpOperations 4 }

cbsVrrpTrapNewMasterCirName OBJECT-TYPE
   SYNTAX       DisplayString
   MAX-ACCESS   accessible-for-notify
   STATUS       current
   DESCRIPTION
              "This object contains the circuit name.
               Used by cbsVrrpTrapNewMaster trap."
   ::= { cbsVrrpOperations 5 }

cbsVrrpTrapProtoErrReason OBJECT-TYPE
   SYNTAX  INTEGER {
        hopLimitError (0),
        versionError  (1),
        checksumError (2),
        vridError(3)
   }
   MAX-ACCESS   accessible-for-notify
   STATUS       current
   DESCRIPTION
               "This indicates the reason for protocol error trap.
                Used by cbsVrrpTrapProtoError trap."
   ::= { cbsVrrpOperations 6 }


-- The traps

cbsVrrpTrapNewMaster NOTIFICATION-TYPE
   OBJECTS      { cbsVrrpTrapNewMasterFailGrName,
                  cbsVrrpTrapNewMasterVrId,
                  cbsVrrpTrapNewMasterCirId,
                  cbsVrrpTrapNewMasterCirName,
                  cbsVrrpTrapNewMasterReason
                        }
   STATUS       current
   DESCRIPTION
               "The newMaster trap indicates that the sending agent
                transitioned to 'Master' state."
   ::= { cbsVrrpTraps 1 }

cbsVrrpTrapProtoError NOTIFICATION-TYPE
   OBJECTS      { cbsVrrpTrapProtoErrReason
                }
   STATUS       current
   DESCRIPTION
               "The error trap indicates that the sending agent
                encountered the protocol error indicated by
                vrrpTrapProtoErrorReason."
   ::= { cbsVrrpTraps 2 }

END
