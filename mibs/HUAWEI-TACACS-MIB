-- =================================================================
-- Copyright (C) 2003 by  HUAWEI TECHNOLOGIES. All rights reserved
--
-- Description:HUAWEI-HWTACACS-MIB
-- Reference:
-- =================================================================
HUAWEI-TACACS-MIB    DEFINITIONS ::= BEGIN

IMPORTS
    IpAddress, Counter32, Gauge32, Integer32,Unsigned32,NOTIFICATION-TYPE
            FROM SNMPv2-SMI
    OBJECT-TYPE
            FROM RFC-1212
    TRAP-TYPE
            FROM RFC-1215
    RowStatus
        FROM SNMPv2-TC
    DisplayString
        FROM  RFC1213-MIB
    huawei,huaweiMgmt,huaweiDatacomm
    FROM HUAWEI-3COM-OID-MIB;

--	HUAWEI products
hwTACACS        OBJECT IDENTIFIER ::= { huaweiDatacomm 20 }

-- Following is for Node:hwTACACSServerConfig
 hwTACACSServerConfig        OBJECT IDENTIFIER ::= { hwTACACS 1 }
-- TABLE: hwTACACSServerGroupTable
  hwTACACSServerGroupTable OBJECT-TYPE
    SYNTAX      SEQUENCE OF HWTACACSServerGroupTableEntry
    MAX-ACCESS  not-accessible
    STATUS      current
    DESCRIPTION
      "Group table"
    ::= { hwTACACSServerConfig 1 }

  hwTACACSServerGroupTableEntry OBJECT-TYPE
    SYNTAX      HWTACACSServerGroupTableEntry
    MAX-ACCESS  not-accessible
    STATUS      current
    DESCRIPTION
      "Group table entry"
    INDEX {
              hwTACACSServerGroupName
             }
    ::= { hwTACACSServerGroupTable 1 }

  HWTACACSServerGroupTableEntry ::=
    SEQUENCE
    {
      hwTACACSServerGroupName	OCTET STRING,
      hwTACACSServerGroupSourceIP	IpAddress,
      hwTACACSServerGroupKey	OCTET STRING,
      hwTACACSServerGroupTimer	Integer32,
      hwTACACSServerGroupDomain	INTEGER,
      hwTACACSServerGroupPriAuthen	IpAddress,
      hwTACACSServerGroupPriAuthor	IpAddress,
      hwTACACSServerGroupPriAccout	IpAddress,
      hwTACACSServerGroupCurAuthen	IpAddress,
      hwTACACSServerGroupCurAuthor	IpAddress,
      hwTACACSServerGroupCurAccout	IpAddress,
      hwTACACSServerGroupRowStatus	RowStatus
    }

  hwTACACSServerGroupName OBJECT-TYPE
    SYNTAX      OCTET STRING(SIZE(1..20))
    MAX-ACCESS  read-only
    STATUS      current
    DESCRIPTION
        "Hwtacac server template name"
    ::={ hwTACACSServerGroupTableEntry 1 }

  hwTACACSServerGroupSourceIP OBJECT-TYPE
    SYNTAX      IpAddress
    MAX-ACCESS  read-create
    STATUS      current
    DESCRIPTION
        "Specify hwtacacs source-ip"
    ::={ hwTACACSServerGroupTableEntry 2 }

  hwTACACSServerGroupKey OBJECT-TYPE
    SYNTAX      OCTET STRING(SIZE(0..64))
    MAX-ACCESS  read-create
    STATUS      current
    DESCRIPTION
        "Specify group encryption shared-key"
    DEFVAL      { 5 }
    ::={ hwTACACSServerGroupTableEntry 3 }

  hwTACACSServerGroupTimer OBJECT-TYPE
    SYNTAX      Integer32(1..255)
    MAX-ACCESS  read-create
    STATUS      current
    DESCRIPTION
        "Set time interval before retry the down-server"
    DEFVAL {1}
    ::={ hwTACACSServerGroupTableEntry 4 }

  hwTACACSServerGroupDomain OBJECT-TYPE
    SYNTAX      INTEGER{
                       open(1),
                       close(2)
                }
    MAX-ACCESS  read-create
    STATUS      current
    DESCRIPTION
        "Domain switch:1,open;2,close"
    DEFVAL {1}
    ::={ hwTACACSServerGroupTableEntry 5 }

  hwTACACSServerGroupPriAuthen OBJECT-TYPE
    SYNTAX      IpAddress
    MAX-ACCESS  read-only
    STATUS      current
    DESCRIPTION
        "Primary authen server"
    ::={ hwTACACSServerGroupTableEntry 6 }

  hwTACACSServerGroupPriAuthor OBJECT-TYPE
    SYNTAX      IpAddress
    MAX-ACCESS  read-only
    STATUS      current
    DESCRIPTION
        "Primary author server"
    ::={ hwTACACSServerGroupTableEntry 7 }

  hwTACACSServerGroupPriAccout OBJECT-TYPE
    SYNTAX      IpAddress
    MAX-ACCESS  read-only
    STATUS      current
    DESCRIPTION
        "Primary accounting server"
    ::={ hwTACACSServerGroupTableEntry 8 }

  hwTACACSServerGroupCurAuthen OBJECT-TYPE
    SYNTAX      IpAddress
    MAX-ACCESS  read-only
    STATUS      current
    DESCRIPTION
        "Current authen server"
    ::={ hwTACACSServerGroupTableEntry 9 }

  hwTACACSServerGroupCurAuthor OBJECT-TYPE
    SYNTAX      IpAddress
    MAX-ACCESS  read-only
    STATUS      current
    DESCRIPTION
        "Current author server"
    ::={ hwTACACSServerGroupTableEntry 10 }

  hwTACACSServerGroupCurAccout OBJECT-TYPE
    SYNTAX      IpAddress
    MAX-ACCESS  read-only
    STATUS      current
    DESCRIPTION
        "Current account server"
    ::={ hwTACACSServerGroupTableEntry 11 }

  hwTACACSServerGroupRowStatus OBJECT-TYPE
    SYNTAX      RowStatus
    MAX-ACCESS  read-create
    STATUS      current
    DESCRIPTION
        "RowStatus"
    ::={ hwTACACSServerGroupTableEntry 12 }

-- TABLE: hwTACACSServerTable
  hwTACACSServerTable OBJECT-TYPE
    SYNTAX      SEQUENCE OF HWTACACSServerTableEntry
    MAX-ACCESS  not-accessible
    STATUS      current
    DESCRIPTION
      "Server table"
    ::= { hwTACACSServerConfig 2 }

  hwTACACSServerTableEntry OBJECT-TYPE
    SYNTAX      HWTACACSServerTableEntry
    MAX-ACCESS  not-accessible
    STATUS      current
    DESCRIPTION
      "Server table entry"
    INDEX {
              hwTACACSGroupName,hwTACACSServerAddr
             }
    ::= { hwTACACSServerTable 1 }

  HWTACACSServerTableEntry ::=
   SEQUENCE
   {
      hwTACACSGroupName	OCTET STRING,
      hwTACACSServerAddr	IpAddress,
      hwTACACSServerPort	Integer32,
      hwTACACSTimeout	Integer32,
      hwTACACSServerKey	OCTET STRING,
      hwTACACSServerPriAuthen	INTEGER,
      hwTACACSServerPriAuthor	INTEGER,
      hwTACACSServerPriAcct	INTEGER,
      hwTACACSAuthenClientRoundTripTime	Integer32,
      hwTACACSAuthenClientAccessReqPacket	Counter32,
      hwTACACSAuthenClientAccessReqLogin	Counter32,
      hwTACACSAuthenClientAccessReqChaPass	Counter32,
      hwTACACSAuthenClientAccessReqSendPass	Counter32,
      hwTACACSAuthenClientAccessReqSendAuth	Counter32,
      hwTACACSAuthenClientAccessResPack	Counter32,
      hwTACACSAuthenClientAccessResPass	Counter32,
      hwTACACSAuthenClientAccessResFail	Counter32,
      hwTACACSAuthenClientAccessResGetData	Counter32,
      hwTACACSAuthenClientAccessResGetUser	Counter32,
      hwTACACSAuthenClientAccessResGetPass	Counter32,
      hwTACACSAuthenClientAccessResRestart	Counter32,
      hwTACACSAuthenClientAccessResError	Counter32,
      hwTACACSAuthenClientAccessResFollow	Counter32,
      hwTACACSAuthenClientMalformedAccessResponses	Counter32,
      hwTACACSAuthenClientAccessConPack	Counter32,
      hwTACACSAuthenClientAccessConAbort	Counter32,
      hwTACACSAuthenClientPendingRequests	Counter32,
      hwTACACSAuthenClientTimeouts	Counter32,
      hwTACACSAuthenClientUnknownTypes	Counter32,
      hwTACACSAuthenClientPacketsDropped	Counter32,
      hwTACACSAuthorClientRoundTripTime	Integer32,
      hwTACACSAuthorClientReqPacket	Counter32,
      hwTACACSAuthorClientReqEXEC	Counter32,
      hwTACACSAuthorClientReqLCP	Counter32,
      hwTACACSAuthorClientReqIPCP	Counter32,
      hwTACACSAuthorClientReqVPDN	Counter32,
      hwTACACSAuthorClientReqCommandLevel	Counter32,
      hwTACACSAuthorClientResPack	Counter32,
      hwTACACSAuthorClientResEXEC	Counter32,
      hwTACACSAuthorClientResLCP	Counter32,
      hwTACACSAuthorClientResIPCP	Counter32,
      hwTACACSAuthorClientResVPDN	Counter32,
      hwTACACSAuthorClientResCommandLevel	Counter32,
      hwTACACSAuthorClientResError	Counter32,
      hwTACACSAuthorClientReqPending	Counter32,
      hwTACACSAuthorClientTimeouts	Counter32,
      hwTACACSAuthorClientUnknownTypes	Counter32,
      hwTACACSAuthorClientPacketsDropped	Counter32,
      hwTACACSAccClientRoundTripTime	Integer32,
      hwTACACSAccClientReqPacket	Counter32,
      hwTACACSAccClientReqNetwork	Counter32,
      hwTACACSAccClientReqConnection	Counter32,
      hwTACACSAccClientReqEXEC	Counter32,
      hwTACACSAccClientReqSysEvent	Counter32,
      hwTACACSAccClientReqCommandLevel	Counter32,
      hwTACACSAccClientReqUpdate	Counter32,
      hwTACACSAccClientResPacket	Counter32,
      hwTACACSAccClientResError	Counter32,
      hwTACACSAccClientReqPending	Counter32,
      hwTACACSAccClientTimeouts	Counter32,
      hwTACACSAccClientUnknownTypes	Counter32,
      hwTACACSAccClientPacketsDropped	Counter32,
      hwTACACSServerRowStatus	RowStatus
    }

  hwTACACSGroupName OBJECT-TYPE
    SYNTAX      OCTET STRING(SIZE(1..20))
    MAX-ACCESS  read-only
    STATUS      current
    DESCRIPTION
        "Hwtacac server template name"
    ::={ hwTACACSServerTableEntry 1 }

  hwTACACSServerAddr OBJECT-TYPE
    SYNTAX      IpAddress
    MAX-ACCESS  read-only
    STATUS      current
    DESCRIPTION
        "Specify server ip address"
    ::={ hwTACACSServerTableEntry 2 }

  hwTACACSServerPort OBJECT-TYPE
    SYNTAX      Integer32(1..65535)
    MAX-ACCESS  read-create
    STATUS      current
    DESCRIPTION
        "Specify server port"
    DEFVAL      { 49 }
    ::={ hwTACACSServerTableEntry 3 }

  hwTACACSTimeout OBJECT-TYPE
    SYNTAX      Integer32(1..1000)
    MAX-ACCESS  read-create
    STATUS      current
    DESCRIPTION
        "Specify server response timeout"
    DEFVAL      { 5 }
    ::={ hwTACACSServerTableEntry 4 }

  hwTACACSServerKey OBJECT-TYPE
    SYNTAX      OCTET STRING(SIZE(0..64))
    MAX-ACCESS  read-create
    STATUS      current
    DESCRIPTION
        "Specify server encryption shared-key"
    ::={ hwTACACSServerTableEntry 5 }

  hwTACACSServerPriAuthen OBJECT-TYPE
    SYNTAX      INTEGER{
                       no(1),
                       yes(2)
                       }
    MAX-ACCESS  read-create
    STATUS      current
    DESCRIPTION
        "Primary authen server:1:no,2:yes"
    DEFVAL      { no }
    ::={ hwTACACSServerTableEntry 6 }

  hwTACACSServerPriAuthor OBJECT-TYPE
    SYNTAX      INTEGER{
                       no(1),
                       yes(2)
                       }
    MAX-ACCESS  read-create
    STATUS      current
    DESCRIPTION
        "Primary author server:1:no,2:yes"
    DEFVAL      { no }
    ::={ hwTACACSServerTableEntry 7 }

  hwTACACSServerPriAcct OBJECT-TYPE
    SYNTAX      INTEGER{
                       no(1),
                       yes(2)
                       }
    MAX-ACCESS  read-create
    STATUS      current
    DESCRIPTION
        "Primary account server:1:no,2:yes"
    DEFVAL      { no }
    ::={ hwTACACSServerTableEntry 8 }

  hwTACACSAuthenClientRoundTripTime OBJECT-TYPE
    SYNTAX      Integer32
    MAX-ACCESS  read-only
    STATUS      current
    DESCRIPTION
        "Round trip time about authen server"
    ::={ hwTACACSServerTableEntry 9 }

  hwTACACSAuthenClientAccessReqPacket OBJECT-TYPE
    SYNTAX      Counter32
    MAX-ACCESS  read-only
    STATUS      current
    DESCRIPTION
        "Request packets about authen server"
    ::={ hwTACACSServerTableEntry 10 }

  hwTACACSAuthenClientAccessReqLogin OBJECT-TYPE
    SYNTAX      Counter32
    MAX-ACCESS  read-only
    STATUS      current
    DESCRIPTION
        "Request login packets about authen server"
    ::={ hwTACACSServerTableEntry 11 }

  hwTACACSAuthenClientAccessReqChaPass OBJECT-TYPE
    SYNTAX      Counter32
    MAX-ACCESS  read-only
    STATUS      current
    DESCRIPTION
        "Request change password packets about authen server"
    ::={ hwTACACSServerTableEntry 12 }

  hwTACACSAuthenClientAccessReqSendPass OBJECT-TYPE
    SYNTAX      Counter32
    MAX-ACCESS  read-only
    STATUS      current
    DESCRIPTION
        "Request send password packets about authen server"
    ::={ hwTACACSServerTableEntry 13 }

  hwTACACSAuthenClientAccessReqSendAuth OBJECT-TYPE
    SYNTAX      Counter32
    MAX-ACCESS  read-only
    STATUS      current
    DESCRIPTION
        "Request send authen packets about authen server"
    ::={ hwTACACSServerTableEntry 14 }

  hwTACACSAuthenClientAccessResPack OBJECT-TYPE
    SYNTAX      Counter32
    MAX-ACCESS  read-only
    STATUS      current
    DESCRIPTION
        "Response packets about authen server"
    ::={ hwTACACSServerTableEntry 15 }

  hwTACACSAuthenClientAccessResPass OBJECT-TYPE
    SYNTAX      Counter32
    MAX-ACCESS  read-only
    STATUS      current
    DESCRIPTION
        "Response pass packets about authen server"
    ::={ hwTACACSServerTableEntry 16 }

  hwTACACSAuthenClientAccessResFail OBJECT-TYPE
    SYNTAX      Counter32
    MAX-ACCESS  read-only
    STATUS      current
    DESCRIPTION
        "Response fail packets about authen server"
    ::={ hwTACACSServerTableEntry 17 }

  hwTACACSAuthenClientAccessResGetData OBJECT-TYPE
    SYNTAX      Counter32
    MAX-ACCESS  read-only
    STATUS      current
    DESCRIPTION
        "Get data packets about authen server"
    ::={ hwTACACSServerTableEntry 18 }

  hwTACACSAuthenClientAccessResGetUser OBJECT-TYPE
    SYNTAX      Counter32
    MAX-ACCESS  read-only
    STATUS      current
    DESCRIPTION
        "Get user packets about authen server"
    ::={ hwTACACSServerTableEntry 19 }

  hwTACACSAuthenClientAccessResGetPass OBJECT-TYPE
    SYNTAX      Counter32
    MAX-ACCESS  read-only
    STATUS      current
    DESCRIPTION
        "Get password packets about authen server"
    ::={ hwTACACSServerTableEntry 20 }

  hwTACACSAuthenClientAccessResRestart OBJECT-TYPE
    SYNTAX      Counter32
    MAX-ACCESS  read-only
    STATUS      current
    DESCRIPTION
        "Restart packets about authen server"
    ::={ hwTACACSServerTableEntry 21 }

  hwTACACSAuthenClientAccessResError OBJECT-TYPE
    SYNTAX      Counter32
    MAX-ACCESS  read-only
    STATUS      current
    DESCRIPTION
        "Response error packets about authen server"
    ::={ hwTACACSServerTableEntry 22 }

  hwTACACSAuthenClientAccessResFollow OBJECT-TYPE
    SYNTAX      Counter32
    MAX-ACCESS  read-only
    STATUS      current
    DESCRIPTION
        "Follow packets about authen server"
    ::={ hwTACACSServerTableEntry 23 }

  hwTACACSAuthenClientMalformedAccessResponses OBJECT-TYPE
    SYNTAX      Counter32
    MAX-ACCESS  read-only
    STATUS      current
    DESCRIPTION
        "Response packets about authen server"
    ::={ hwTACACSServerTableEntry 24 }

  hwTACACSAuthenClientAccessConPack OBJECT-TYPE
    SYNTAX      Counter32
    MAX-ACCESS  read-only
    STATUS      current
    DESCRIPTION
        "Connection packets about authen server"
    ::={ hwTACACSServerTableEntry 25 }

  hwTACACSAuthenClientAccessConAbort OBJECT-TYPE
    SYNTAX      Counter32
    MAX-ACCESS  read-only
    STATUS      current
    DESCRIPTION
        "Connection abort packets about authen server"
    ::={ hwTACACSServerTableEntry 26 }

  hwTACACSAuthenClientPendingRequests OBJECT-TYPE
    SYNTAX      Counter32
    MAX-ACCESS  read-only
    STATUS      current
    DESCRIPTION
        "Request pending packets about authen server"
    ::={ hwTACACSServerTableEntry 27 }

  hwTACACSAuthenClientTimeouts OBJECT-TYPE
    SYNTAX      Counter32
    MAX-ACCESS  read-only
    STATUS      current
    DESCRIPTION
        "Time out packets about authen server"
    ::={ hwTACACSServerTableEntry 28 }

  hwTACACSAuthenClientUnknownTypes OBJECT-TYPE
    SYNTAX      Counter32
    MAX-ACCESS  read-only
    STATUS      current
    DESCRIPTION
        "Unknown type packets about authen server"
    ::={ hwTACACSServerTableEntry 29 }

  hwTACACSAuthenClientPacketsDropped OBJECT-TYPE
    SYNTAX      Counter32
    MAX-ACCESS  read-only
    STATUS      current
    DESCRIPTION
        "Drop packets about authen server"
    ::={ hwTACACSServerTableEntry 30 }

  hwTACACSAuthorClientRoundTripTime OBJECT-TYPE
    SYNTAX      Integer32
    MAX-ACCESS  read-only
    STATUS      current
    DESCRIPTION
        "Round trip time about author server"
    ::={ hwTACACSServerTableEntry 31 }

  hwTACACSAuthorClientReqPacket OBJECT-TYPE
    SYNTAX      Counter32
    MAX-ACCESS  read-only
    STATUS      current
    DESCRIPTION
        "Request packets about author server"
    ::={ hwTACACSServerTableEntry 32 }

  hwTACACSAuthorClientReqEXEC OBJECT-TYPE
    SYNTAX      Counter32
    MAX-ACCESS  read-only
    STATUS      current
    DESCRIPTION
        "Request exec packets about author server"
    ::={ hwTACACSServerTableEntry 33 }

  hwTACACSAuthorClientReqLCP OBJECT-TYPE
    SYNTAX      Counter32
    MAX-ACCESS  read-only
    STATUS      current
    DESCRIPTION
        "Request lcp packets about author server"
    ::={ hwTACACSServerTableEntry 34 }

  hwTACACSAuthorClientReqIPCP OBJECT-TYPE
    SYNTAX      Counter32
    MAX-ACCESS  read-only
    STATUS      current
    DESCRIPTION
        "Request ipcp packets about author server"
    ::={ hwTACACSServerTableEntry 35 }

  hwTACACSAuthorClientReqVPDN OBJECT-TYPE
    SYNTAX      Counter32
    MAX-ACCESS  read-only
    STATUS      current
    DESCRIPTION
        "Request vpdn packets about author server"
    ::={ hwTACACSServerTableEntry 36 }

  hwTACACSAuthorClientReqCommandLevel OBJECT-TYPE
    SYNTAX      Counter32
    MAX-ACCESS  read-only
    STATUS      current
    DESCRIPTION
        "Request command level packets about author server"
    ::={ hwTACACSServerTableEntry 37 }

  hwTACACSAuthorClientResPack OBJECT-TYPE
    SYNTAX      Counter32
    MAX-ACCESS  read-only
    STATUS      current
    DESCRIPTION
        "Response packets about author server"
    ::={ hwTACACSServerTableEntry 38 }

  hwTACACSAuthorClientResEXEC OBJECT-TYPE
    SYNTAX      Counter32
    MAX-ACCESS  read-only
    STATUS      current
    DESCRIPTION
        "Response exec packet about author server"
    ::={ hwTACACSServerTableEntry 39 }

  hwTACACSAuthorClientResLCP OBJECT-TYPE
    SYNTAX      Counter32
    MAX-ACCESS  read-only
    STATUS      current
    DESCRIPTION
        "Response lcp packets about author server"
    ::={ hwTACACSServerTableEntry 40 }

  hwTACACSAuthorClientResIPCP OBJECT-TYPE
    SYNTAX      Counter32
    MAX-ACCESS  read-only
    STATUS      current
    DESCRIPTION
        "Response ipcp packets about author server"
    ::={ hwTACACSServerTableEntry 41 }

  hwTACACSAuthorClientResVPDN OBJECT-TYPE
    SYNTAX      Counter32
    MAX-ACCESS  read-only
    STATUS      current
    DESCRIPTION
        "Response vpdn packets about author server"
    ::={ hwTACACSServerTableEntry 42 }

  hwTACACSAuthorClientResCommandLevel OBJECT-TYPE
    SYNTAX      Counter32
    MAX-ACCESS  read-only
    STATUS      current
    DESCRIPTION
        "Response command level packets about author server"
    ::={ hwTACACSServerTableEntry 43 }

  hwTACACSAuthorClientResError OBJECT-TYPE
    SYNTAX      Counter32
    MAX-ACCESS  read-only
    STATUS      current
    DESCRIPTION
        "Response error packets about author server"
    ::={ hwTACACSServerTableEntry 44 }

  hwTACACSAuthorClientReqPending OBJECT-TYPE
    SYNTAX      Counter32
    MAX-ACCESS  read-only
    STATUS      current
    DESCRIPTION
        "Request pending packets about author server"
    ::={ hwTACACSServerTableEntry 45 }

  hwTACACSAuthorClientTimeouts OBJECT-TYPE
    SYNTAX      Counter32
    MAX-ACCESS  read-only
    STATUS      current
    DESCRIPTION
        "Time out packets about author server"
    ::={ hwTACACSServerTableEntry 46 }

  hwTACACSAuthorClientUnknownTypes OBJECT-TYPE
    SYNTAX      Counter32
    MAX-ACCESS  read-only
    STATUS      current
    DESCRIPTION
        "Unknown type packets about author server"
    ::={ hwTACACSServerTableEntry 47 }

  hwTACACSAuthorClientPacketsDropped OBJECT-TYPE
    SYNTAX      Counter32
    MAX-ACCESS  read-only
    STATUS      current
    DESCRIPTION
        "Drop packets about author server"
    ::={ hwTACACSServerTableEntry 48 }

  hwTACACSAccClientRoundTripTime OBJECT-TYPE
    SYNTAX      Integer32
    MAX-ACCESS  read-only
    STATUS      current
    DESCRIPTION
        "Round trip time about accounting server"
    ::={ hwTACACSServerTableEntry 49 }

  hwTACACSAccClientReqPacket OBJECT-TYPE
    SYNTAX      Counter32
    MAX-ACCESS  read-only
    STATUS      current
    DESCRIPTION
        "Request packets about accounting server"
    ::={ hwTACACSServerTableEntry 50 }

  hwTACACSAccClientReqNetwork OBJECT-TYPE
    SYNTAX      Counter32
    MAX-ACCESS  read-only
    STATUS      current
    DESCRIPTION
        "Request network packets about accounting server"
    ::={ hwTACACSServerTableEntry 51 }

  hwTACACSAccClientReqConnection OBJECT-TYPE
    SYNTAX      Counter32
    MAX-ACCESS  read-only
    STATUS      current
    DESCRIPTION
        "Request connection packets about accounting server"
    ::={ hwTACACSServerTableEntry 52 }

  hwTACACSAccClientReqEXEC OBJECT-TYPE
    SYNTAX      Counter32
    MAX-ACCESS  read-only
    STATUS      current
    DESCRIPTION
        "Request exec packets about accounting server"
    ::={ hwTACACSServerTableEntry 53 }

  hwTACACSAccClientReqSysEvent OBJECT-TYPE
    SYNTAX      Counter32
    MAX-ACCESS  read-only
    STATUS      current
    DESCRIPTION
        "Request system event packets about accounting server"
    ::={ hwTACACSServerTableEntry 54 }

  hwTACACSAccClientReqCommandLevel OBJECT-TYPE
    SYNTAX      Counter32
    MAX-ACCESS  read-only
    STATUS      current
    DESCRIPTION
        "Request command level packets about accounting server"
    ::={ hwTACACSServerTableEntry 55 }

  hwTACACSAccClientReqUpdate OBJECT-TYPE
    SYNTAX      Counter32
    MAX-ACCESS  read-only
    STATUS      current
    DESCRIPTION
        "Request update packets about accounting server"
    ::={ hwTACACSServerTableEntry 56 }

  hwTACACSAccClientResPacket OBJECT-TYPE
    SYNTAX      Counter32
    MAX-ACCESS  read-only
    STATUS      current
    DESCRIPTION
        "Response packets about accounting server"
    ::={ hwTACACSServerTableEntry 57 }

  hwTACACSAccClientResError OBJECT-TYPE
    SYNTAX      Counter32
    MAX-ACCESS  read-only
    STATUS      current
    DESCRIPTION
        "Response error packets about accounting server"
    ::={ hwTACACSServerTableEntry 58 }

  hwTACACSAccClientReqPending OBJECT-TYPE
    SYNTAX      Counter32
    MAX-ACCESS  read-only
    STATUS      current
    DESCRIPTION
        "Request pending packets about accounting server"
    ::={ hwTACACSServerTableEntry 59 }

  hwTACACSAccClientTimeouts OBJECT-TYPE
    SYNTAX      Counter32
    MAX-ACCESS  read-only
    STATUS      current
    DESCRIPTION
        "Time out packets about accounting server"
    ::={ hwTACACSServerTableEntry 60 }

  hwTACACSAccClientUnknownTypes OBJECT-TYPE
    SYNTAX      Counter32
    MAX-ACCESS  read-only
    STATUS      current
    DESCRIPTION
        "Unknown types packets about accounting server"
    ::={ hwTACACSServerTableEntry 61 }

  hwTACACSAccClientPacketsDropped OBJECT-TYPE
    SYNTAX      Counter32
    MAX-ACCESS  read-only
    STATUS      current
    DESCRIPTION
        "Drop packets about accounting server"
    ::={ hwTACACSServerTableEntry 62 }

hwTACACSServerRowStatus OBJECT-TYPE
    SYNTAX      RowStatus
    MAX-ACCESS  read-create
    STATUS      current
    DESCRIPTION
        "RowStatus"
    ::={ hwTACACSServerTableEntry 63 }

END
