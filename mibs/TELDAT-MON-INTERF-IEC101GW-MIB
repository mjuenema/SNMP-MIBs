-- Teldat, S.A.

                -- Parque Tecnolgico de Madrid

                -- 28760, Tres Cantos (Madrid)

                -- Tlf: +34-918076565

                -- Fax: +34-918076521

                -- e-mail: id@teldat.com


            -- MIB privada de Teldat

            -- Monitorizacin del interfaz IEC-101-GW


    -- Historial:
    --      07/02/14    M.A. Pastor     XH 3523. Errors with HP Openview 9.20
    -- 1.2  11-01-13    E. Amorena      XH 2610. MIBs compilation.
    -- 1.1  03/01/13  F. Hernandez     XH 2610. Compilation error
    -- 1.0  08-05-07    Benjam�n G.     Implementacin inicial
--------------------------------------------------------------------------------

TELDAT-MON-INTERF-IEC101GW-MIB DEFINITIONS ::= BEGIN

IMPORTS
    OBJECT-TYPE
        FROM RFC-1212
    telProdNpMonInterfRouter
        FROM TELDAT-SW-STRUCTURE-MIB;


-- Monitorizacin privada del interfaz IEC101GW

telProdNpMonInterfIec101gw OBJECT IDENTIFIER ::= { telProdNpMonInterfRouter 23 }


--  = = = = = = = = = = = = = = = = = = = = = = = = = = = = = = = = = = = = = =
--  Global Info IEC101GW monitoring variables
--  = = = = = = = = = = = = = = = = = = = = = = = = = = = = = = = = = = = = = =

teldatIec101gwInfoInterfaceTable OBJECT-TYPE
    SYNTAX  SEQUENCE OF TeldatIec101gwInfoInterfaceEntry
    ACCESS  not-accessible
    STATUS  mandatory
    DESCRIPTION
        "Table of information available for IEC101 GW interfaces.
        Each row represents an interface"
    ::= { telProdNpMonInterfIec101gw 1 }

teldatIec101gwInfoInterfaceEntry OBJECT-TYPE
    SYNTAX  TeldatIec101gwInfoInterfaceEntry
    ACCESS  not-accessible
    STATUS  mandatory
    DESCRIPTION
        "A base list of objects that are information about a Iec101gw interface.
        The inex is the number of the interface"
    INDEX   { teldatIec101gwInfoInterfaceIndex }
    ::= { teldatIec101gwInfoInterfaceTable 1 }

TeldatIec101gwInfoInterfaceEntry ::= SEQUENCE
{
    teldatIec101gwInfoInterfaceIndex                INTEGER,
    teldatIec101gwInfoInterfaceSpeed                INTEGER,
    teldatIec101gwInfoInterfaceMultilink            INTEGER
}

teldatIec101gwInfoInterfaceIndex OBJECT-TYPE
    SYNTAX  INTEGER
    ACCESS  read-only
    STATUS  mandatory
    DESCRIPTION
        "IEC101-GW interface index."
    ::= { teldatIec101gwInfoInterfaceEntry 1 }

teldatIec101gwInfoInterfaceSpeed OBJECT-TYPE
    SYNTAX  INTEGER
    ACCESS  read-only
    STATUS  mandatory
    DESCRIPTION
        "Value of interface Speed option"
    ::={ teldatIec101gwInfoInterfaceEntry 2 }

teldatIec101gwInfoInterfaceMultilink OBJECT-TYPE
    SYNTAX  INTEGER {
        disable(0),
        enable(1)
    }
    ACCESS  read-only
    STATUS  mandatory
    DESCRIPTION
        "Value of Multilink option"
    ::={ teldatIec101gwInfoInterfaceEntry 3 }


--  = = = = = = = = = = = = = = = = = = = = = = = = = = = = = = = = = = = = = =
--  Iec101gw RTU's monitoring state variables
--  = = = = = = = = = = = = = = = = = = = = = = = = = = = = = = = = = = = = = =

teldatIec101gwRtuStatObject    OBJECT IDENTIFIER ::= { telProdNpMonInterfIec101gw 2 }

--  - - - - - - - - - - - - - - - - - - - - - - - - - - - - - - - - - - - - - -
--   Iec101gw State Table, interface variables
--  - - - - - - - - - - - - - - - - - - - - - - - - - - - - - - - - - - - - - -

teldatIec101gwRtuStateTable OBJECT-TYPE
    SYNTAX  SEQUENCE OF TeldatIec101gwRtuStateEntry
    ACCESS  not-accessible
    STATUS  mandatory
    DESCRIPTION
        "Table of RTU's monitoring information for IEC101-GW interfaces."
    ::= { teldatIec101gwRtuStatObject 1 }

teldatIec101gwRtuStateEntry OBJECT-TYPE
    SYNTAX  TeldatIec101gwRtuStateEntry
    ACCESS  not-accessible
    STATUS  mandatory
    DESCRIPTION
        "Each entry contains RTU's info for IEC101-GW interface, which value is
        the first table index, and it contains all possible RTU's info for that
        interface. The second table index indicates the order number of that
        RTU's inside that interface."
    INDEX   { teldatIec101gwRtuStateIfcIndex, teldatIec101gwRtuStateRtuIndex}
    ::= { teldatIec101gwRtuStateTable 1 }

TeldatIec101gwRtuStateEntry ::= SEQUENCE
{
    teldatIec101gwRtuStateIfcIndex              INTEGER,
    teldatIec101gwRtuStateRtuIndex              INTEGER,
    teldatIec101gwRtuStateAddress               INTEGER,
    teldatIec101gwRtuStateStatus                INTEGER,
    teldatIec101gwRtuStateMaster                INTEGER,
    teldatIec101gwRtuStateSlave                 INTEGER
}

teldatIec101gwRtuStateIfcIndex OBJECT-TYPE
    SYNTAX  INTEGER
    ACCESS  read-only
    STATUS  mandatory
    DESCRIPTION
        "First table index: interface number that owns that entry RTU."
    ::={ teldatIec101gwRtuStateEntry 1 }

teldatIec101gwRtuStateRtuIndex OBJECT-TYPE
    SYNTAX  INTEGER
    ACCESS  read-only
    STATUS  mandatory
    DESCRIPTION
        "Second table index: order number of the RTU inside the list of
        configured for current interface."
    ::={ teldatIec101gwRtuStateEntry 2 }

teldatIec101gwRtuStateAddress OBJECT-TYPE
    SYNTAX  INTEGER
    ACCESS  read-only
    STATUS  mandatory
    DESCRIPTION
        "RTU link address."
    ::={ teldatIec101gwRtuStateEntry 3 }

teldatIec101gwRtuStateStatus OBJECT-TYPE
    SYNTAX  INTEGER{
        deactive(0),
        active(1)
    }
    ACCESS  read-only
    STATUS  mandatory
    DESCRIPTION
        "RTU link status."
    ::={ teldatIec101gwRtuStateEntry 4 }

teldatIec101gwRtuStateMaster OBJECT-TYPE
    SYNTAX  INTEGER{
        unknown(0),
        linkreset(1),
        exreqlink(2),
        exresetlink(3),
        masterlinkavail(4),
        sendcon(5),
        slavebusy(6)
    }
    ACCESS  read-only
    STATUS  mandatory
    DESCRIPTION
        "State of Master link way to RTU."
    ::={ teldatIec101gwRtuStateEntry 5 }

teldatIec101gwRtuStateSlave OBJECT-TYPE
    SYNTAX  INTEGER{
        unknown(0),
        linkunreset(1),
        slavebusy(2),
        exresetlink(3),
        slavelinkavail(4),
        sendcon(5),
        sendnoreply(6)
    }
    ACCESS  read-only
    STATUS  mandatory
    DESCRIPTION
        "State of Slave link way to RTU."
    ::={ teldatIec101gwRtuStateEntry 6 }



--  - - - - - - - - - - - - - - - - - - - - - - - - - - - - - - - - - - - - - -
--   Iec101gw Statistics Table, Mobile variables
--  - - - - - - - - - - - - - - - - - - - - - - - - - - - - - - - - - - - - - -

teldatIec101gwStatisticsObject   OBJECT IDENTIFIER ::= { telProdNpMonInterfIec101gw 3 }

--  - - - - - - - - - - - - - - - - - - - - - - - - - - - - - - - - - - - - - -
--   Iec101gw State Table, interface variables
--  - - - - - - - - - - - - - - - - - - - - - - - - - - - - - - - - - - - - - -

teldatIec101gwStatisticsTable OBJECT-TYPE
    SYNTAX  SEQUENCE OF TeldatIec101gwStatisticsEntry
    ACCESS  not-accessible
    STATUS  mandatory
    DESCRIPTION
        "Table of IEC101-GW statistics information."
    ::= { teldatIec101gwStatisticsObject 1 }

teldatIec101gwStatisticsEntry OBJECT-TYPE
    SYNTAX  TeldatIec101gwStatisticsEntry
    ACCESS  not-accessible
    STATUS  mandatory
    DESCRIPTION
        "A base list of objects that are IEC101-GW statistics information."
    INDEX   { teldatIec101gwStatisticsIndex }
    ::= { teldatIec101gwStatisticsTable 1 }

TeldatIec101gwStatisticsEntry ::= SEQUENCE
{
    teldatIec101gwStatisticsIndex                      INTEGER,
    teldatIec101gwStatisticsQueueToRtu                 INTEGER,
    teldatIec101gwStatisticsRxBytes                    INTEGER,
    teldatIec101gwStatisticsRxPackets                  INTEGER,
    teldatIec101gwStatisticsRxCrcError                 INTEGER,
    teldatIec101gwStatisticsTxBytes                    INTEGER,
    teldatIec101gwStatisticsTxPackets                  INTEGER,
    teldatIec101gwStatisticsTxCongestion               INTEGER

}

teldatIec101gwStatisticsIndex OBJECT-TYPE
    SYNTAX  INTEGER
    ACCESS  read-only
    STATUS  mandatory
    DESCRIPTION
        "IEC101-GW interface index."
    ::={ teldatIec101gwStatisticsEntry 1 }

teldatIec101gwStatisticsQueueToRtu OBJECT-TYPE
    SYNTAX  INTEGER
    ACCESS  read-only
    STATUS  mandatory
    DESCRIPTION
        "Queue messages lenght, pending to send to RTU"
    ::={ teldatIec101gwStatisticsEntry  2 }

teldatIec101gwStatisticsRxBytes OBJECT-TYPE
    SYNTAX  INTEGER
    ACCESS  read-only
    STATUS  mandatory
    DESCRIPTION
        "Number of data bytes received from RTU"
    ::={ teldatIec101gwStatisticsEntry  3 }

teldatIec101gwStatisticsRxPackets OBJECT-TYPE
    SYNTAX  INTEGER
    ACCESS  read-only
    STATUS  mandatory
    DESCRIPTION
        "Number of IEC-101 packets received from RTU"
    ::={ teldatIec101gwStatisticsEntry  4 }

teldatIec101gwStatisticsRxCrcError  OBJECT-TYPE
    SYNTAX  INTEGER
    ACCESS  read-only
    STATUS  mandatory
    DESCRIPTION
        "Number of IEC-101 packets received from RTU with CRC error"
    ::={ teldatIec101gwStatisticsEntry  5 }

teldatIec101gwStatisticsTxBytes OBJECT-TYPE
    SYNTAX  INTEGER
    ACCESS  read-only
    STATUS  mandatory
    DESCRIPTION
        "Number of data bytes sent to RTU"
    ::={ teldatIec101gwStatisticsEntry  6 }

teldatIec101gwStatisticsTxPackets OBJECT-TYPE
    SYNTAX  INTEGER
    ACCESS  read-only
    STATUS  mandatory
    DESCRIPTION
        "Number of IEC-101 packets sent to RTU"
    ::={ teldatIec101gwStatisticsEntry  7 }

teldatIec101gwStatisticsTxCongestion OBJECT-TYPE
    SYNTAX  INTEGER
    ACCESS  read-only
    STATUS  mandatory
    DESCRIPTION
        "Number of packets discarded due to transmission congestion to RTU"
    ::={ teldatIec101gwStatisticsEntry  8 }


END
