OMNI-gx2Rx200BX4-MIB DEFINITIONS ::= BEGIN

    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Rx200BX4
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"1" Oct 3, 2007
		   --REVISION	"2" May 5, 2009
		   --DESCRIPTION
		   --			Initial revision derived from RX200BX2

		--    OMNISTAR Quad (High Density) Return Path Receiver Module  MIB MODULE

	-- This MIB module defines information for management of HFC networks
		-- 
		-- The MIB module assumes that all generic (static) network element
		-- information is defined in a different module such as the HFC module
		-- The MIB consists of two groups:
		-- the device type descriptor subgroup and 
		-- gx2Rx200BX4 Network Elements subgroup.
		-- The device type descriptor subgroup is used to define 
		-- parameters specific to gx2Rx200BX4 device type.
		-- These parameters are common across all network elements
		-- from gx2Rx200BX4 device type.
		--
		-- The gx2Rx200BX4 Network Elements subgroup is
		-- a list of gx2Rx200BX4 type elements in the
		-- current network topology with nominal
		-- and current parameter values for the
		-- individual network elements; the individual
		-- network elements are identified by  
		-- index from hfcCommonTable.
		-- That implies what hfcCommonTableIndex and
		-- gx2Rx200BX4TableIndex are equal for each individual
		-- network element.
		-- This table is an extension of the hfcCommonTable
		-- for all elements of gx2Rx200BX4 type.
		--
		-- Both groups are mandatory for management of gx2Rx200BX4 devices.

-- ****************************************************************************
		--
		-- All floating point numbers will be represented by an IEEE 32 Bit number.
		-- Conversion of this number must be done on the user interface to view the 
		-- actual floating point number. 
		--

		Float ::= Counter  -- UNSIGNED (32 BITS) 
		U32Data ::= Counter -- UNSIGNED (32 BITS) 

-- ****************************************************************************

		-- gx2Rx200BX4 Device Descriptor subgroup.

		-- The device type descriptor subgroup is used to define 
		-- parameters specific to gx2Rx200BX4 device type.
		-- These parameters are common across all network elements
		-- from gx2Rx200BX4 device type.


		gx2Rx200BX4Descriptor OBJECT IDENTIFIER ::= {gx2Rx200BX4 1}



--*****************************************************************************
		--              gx2Rx200BX4 Table
		
		-- Contains a list of all gx2Rx200BX4 type devices in
		-- the network. Each device is characterized with
		-- current network topology information, with nominal
		-- and current parameter values for the
		-- individual network elements;
		--
		-- The individual network elements indentified by  
		-- index from hfcCommonTable.
		-- That implies what hfcCommonTableIndex and
		-- gx2Rx200BX4TableIndex are equal for each individual
		-- nettwork element.
		-- This table should be used as an extension of the hfcCommonTable
		-- for all elements of gx2Rx200BX4 type.


	       gx2Rx200BX4AnalogTable                    OBJECT-TYPE
			 SYNTAX             SEQUENCE OF Gx2Rx200BX4AnalogEntry
			 ACCESS             not-accessible
			 STATUS             mandatory
			 DESCRIPTION
			 "This table contains gx2Rx200BX4 specific parameters with
			  nominal and current values."
			 ::= { gx2Rx200BX4 2 }


	       gx2Rx200BX4AnalogEntry               OBJECT-TYPE
			 SYNTAX             Gx2Rx200BX4AnalogEntry
			 ACCESS             not-accessible
			 STATUS             mandatory
			 DESCRIPTION
			 "This list contains digital product class and the
			  associated RF channel parameters and descriptions."
			 INDEX { gx2Rx200BX4AnalogTableIndex }
			 ::= { gx2Rx200BX4AnalogTable  1}

--***********************************************************************
	       gx2Rx200BX4DigitalTable                    OBJECT-TYPE
			 SYNTAX             SEQUENCE OF Gx2Rx200BX4DigitalEntry
			 ACCESS             not-accessible
			 STATUS             mandatory
			 DESCRIPTION
			 "This table contains gx2Rx200BX4 specific parameters with
			  nominal and current values."
			 ::= { gx2Rx200BX4 3 }

	       gx2Rx200BX4DigitalEntry               OBJECT-TYPE
			 SYNTAX             Gx2Rx200BX4DigitalEntry
			 ACCESS             not-accessible
			 STATUS             mandatory
			 DESCRIPTION
			 "This list contains digital product class and the
			  associated RF channel parameters and descriptions."
			 INDEX { gx2Rx200BX4DigitalTableIndex }
			 ::= { gx2Rx200BX4DigitalTable  2}

--***********************************************************************
	       gx2Rx200BX4StatusTable                    OBJECT-TYPE
			 SYNTAX             SEQUENCE OF Gx2Rx200BX4StatusEntry
			 ACCESS             not-accessible
			 STATUS             mandatory
			 DESCRIPTION
			 "This table contains gx2Rx200BX4 specific parameters with
			  nominal and current values."
			 ::= { gx2Rx200BX4 4 }

	       gx2Rx200BX4StatusEntry               OBJECT-TYPE
			 SYNTAX             Gx2Rx200BX4StatusEntry
			 ACCESS             not-accessible
			 STATUS             mandatory
			 DESCRIPTION
			 "This list contains digital product class and the
			  associated RF channel parameters and descriptions."
			 INDEX { gx2Rx200BX4StatusTableIndex }
			 ::= { gx2Rx200BX4StatusTable  3}

--***********************************************************************
	       gx2Rx200BX4FactoryTable                    OBJECT-TYPE
			 SYNTAX             SEQUENCE OF Gx2Rx200BX4FactoryEntry
			 ACCESS             not-accessible
			 STATUS             mandatory
			 DESCRIPTION
			 "This table contains gx2Rx200BX4 specific parameters with
			  nominal and current values."
			 ::= { gx2Rx200BX4 5 }

	       gx2Rx200BX4FactoryEntry               OBJECT-TYPE
			 SYNTAX             Gx2Rx200BX4FactoryEntry
			 ACCESS             not-accessible
			 STATUS             mandatory
			 DESCRIPTION
			 "This list contains digital product class and the
			  associated RF channel parameters and descriptions."
			 INDEX { gx2Rx200BX4FactoryTableIndex }
			 ::= { gx2Rx200BX4FactoryTable  4}

--***********************************************************************


--MM          Rx200BX4AnalogTableIndex
	      Gx2Rx200BX4AnalogEntry    ::= SEQUENCE  
	       {
		gx2Rx200BX4AnalogTableIndex         INTEGER,   
		
		--           Analog Parameters

		rx4labelOptPowerOne			DisplayString (SIZE (0..80)),
		rx4uomOptPowerOne			DisplayString (SIZE (0..80)),
		rx4majorHighOptPowerOne		Float, 
		rx4majorLowOptPowerOne		Float, 
		rx4minorHighOptPowerOne		Float,
		rx4minorLowOptPowerOne		Float, 
		rx4currentValueOptPowerOne	Float, 
		rx4stateFlagOptPowerOne		INTEGER,
		rx4minValueOptPowerOne		Float,
		rx4maxValueOptPowerOne 		Float,
		rx4alarmStateOptPowerOne		INTEGER,

		rx4labelOptPowerTwo			DisplayString (SIZE (0..80)),
		rx4uomOptPowerTwo			DisplayString (SIZE (0..80)),
		rx4majorHighOptPowerTwo		Float, 
		rx4majorLowOptPowerTwo		Float, 
		rx4minorHighOptPowerTwo		Float,
		rx4minorLowOptPowerTwo		Float, 
		rx4currentValueOptPowerTwo	Float, 
		rx4stateFlagOptPowerTwo		INTEGER,
		rx4minValueOptPowerTwo		Float,
		rx4maxValueOptPowerTwo 		Float,
		rx4alarmStateOptPowerTwo		INTEGER,

		rx4labelOptPowerThree			DisplayString (SIZE (0..80)),
		rx4uomOptPowerThree			DisplayString (SIZE (0..80)),
		rx4majorHighOptPowerThree		Float, 
		rx4majorLowOptPowerThree		Float, 
		rx4minorHighOptPowerThree		Float,
		rx4minorLowOptPowerThree		Float, 
		rx4currentValueOptPowerThree	Float, 
		rx4stateFlagOptPowerThree		INTEGER,
		rx4minValueOptPowerThree		Float,
		rx4maxValueOptPowerThree 		Float,
		rx4alarmStateOptPowerThree		INTEGER,

		rx4labelOptPowerFour			DisplayString (SIZE (0..80)),
		rx4uomOptPowerFour			DisplayString (SIZE (0..80)),
		rx4majorHighOptPowerFour		Float, 
		rx4majorLowOptPowerFour		Float, 
		rx4minorHighOptPowerFour		Float,
		rx4minorLowOptPowerFour		Float, 
		rx4currentValueOptPowerFour	Float, 
		rx4stateFlagOptPowerFour		INTEGER,
		rx4minValueOptPowerFour		Float,
		rx4maxValueOptPowerFour 		Float,
		rx4alarmStateOptPowerFour		INTEGER,

		rx4labelModTemp			DisplayString (SIZE (0..80)),
		rx4uomModTemp				DisplayString (SIZE (0..80)),
		rx4majorHighModTemp			Float, 
		rx4majorLowModTemp			Float, 
		rx4minorHighModTemp			Float,
		rx4minorLowModTemp			Float, 
		rx4currentValueModTemp		Float, 
		rx4stateFlagModTemp			INTEGER,
		rx4minValueModTemp			Float,
		rx4maxValueModTemp			Float,
		rx4alarmStateModTemp			INTEGER,

		rx4labelFanCurrent			DisplayString (SIZE (0..80)),
		rx4uomFanCurrent			DisplayString (SIZE (0..80)),
		rx4majorHighFanCurrent		Float, 
		rx4majorLowFanCurrent		Float, 
		rx4minorHighFanCurrent		Float,
		rx4minorLowFanCurrent		Float, 
		rx4currentValueFanCurrent		Float, 
		rx4stateFlagFanCurrent		INTEGER,
		rx4minValueFanCurrent		Float,
		rx4maxValueFanCurrent 		Float,
		rx4alarmStateFanCurrent		INTEGER,

		rx4label12Volt				DisplayString (SIZE (0..80)),
		rx4uom12Volt				DisplayString (SIZE (0..80)),
		rx4majorHigh12Volt			Float, 
		rx4majorLow12Volt			Float, 
		rx4minorHigh12Volt			Float,
		rx4minorLow12Volt			Float, 
		rx4currentValue12Volt		Float, 
		rx4stateFlag12Volt			INTEGER,
		rx4minValue12Volt			Float,
		rx4maxValue12Volt			Float,
		rx4alarmState12Volt			INTEGER

		}

		-- ****************  Digital Parameters ***********************
	      Gx2Rx200BX4DigitalEntry    ::= SEQUENCE  
	       {
		gx2Rx200BX4DigitalTableIndex         INTEGER,   

		rx4labelModeOne	 			DisplayString (SIZE (0..80)),
		rx4valueModeOne				INTEGER,
		rx4enumModeOne				DisplayString (SIZE (0..80)),
		rx4stateFlagModeOne     	    	INTEGER,

		rx4labelWavelengthOne	 		DisplayString (SIZE (0..80)),
		rx4valueWavelengthOne			INTEGER,
		rx4enumWavelengthOne			DisplayString (SIZE (0..80)),
		rx4stateFlagWavelengthOne         	INTEGER,

		rx4labelAttnSettingOne	 		DisplayString (SIZE (0..80)),
		rx4valueAttnSettingOne			INTEGER,
		rx4enumAttnSettingOne			DisplayString (SIZE (0..80)),
		rx4stateFlagAttnSettingOne        	INTEGER,

		rx4labelSwModeSettingOne		DisplayString (SIZE (0..80)),
		rx4valueSwModeSettingOne		INTEGER,
		rx4enumSwModeSettingOne			DisplayString (SIZE (0..80)),
		rx4stateFlagSwModeSettingOne     	INTEGER,

		rx4labelSwModeThresholdOne	 	DisplayString (SIZE (0..80)),
		rx4valueSwModeThresholdOne		INTEGER,
		rx4enumSwModeThresholdOne		DisplayString (SIZE (0..80)),
		rx4stateFlagSwModeThresholdOne     	INTEGER,

		rx4labelModeTwo	 			DisplayString (SIZE (0..80)),
		rx4valueModeTwo				INTEGER,
		rx4enumModeTwo				DisplayString (SIZE (0..80)),
		rx4stateFlagModeTwo     	    	INTEGER,

		rx4labelWavelengthTwo	 		DisplayString (SIZE (0..80)),
		rx4valueWavelengthTwo			INTEGER,
		rx4enumWavelengthTwo			DisplayString (SIZE (0..80)),
		rx4stateFlagWavelengthTwo         	INTEGER,

		rx4labelAttnSettingTwo	 		DisplayString (SIZE (0..80)),
		rx4valueAttnSettingTwo			INTEGER,
		rx4enumAttnSettingTwo			DisplayString (SIZE (0..80)),
		rx4stateFlagAttnSettingTwo        	INTEGER,

		rx4labelSwModeSettingTwo		DisplayString (SIZE (0..80)),
		rx4valueSwModeSettingTwo		INTEGER,
		rx4enumSwModeSettingTwo			DisplayString (SIZE (0..80)),
		rx4stateFlagSwModeSettingTwo     	INTEGER,

		rx4labelSwModeThresholdTwo	 	DisplayString (SIZE (0..80)),
		rx4valueSwModeThresholdTwo		INTEGER,
		rx4enumSwModeThresholdTwo		DisplayString (SIZE (0..80)),
		rx4stateFlagSwModeThresholdTwo     	INTEGER,

		rx4labelModeThree	 			DisplayString (SIZE (0..80)),
		rx4valueModeThree				INTEGER,
		rx4enumModeThree				DisplayString (SIZE (0..80)),
		rx4stateFlagModeThree     	    	INTEGER,

		rx4labelWavelengthThree	 		DisplayString (SIZE (0..80)),
		rx4valueWavelengthThree			INTEGER,
		rx4enumWavelengthThree			DisplayString (SIZE (0..80)),
		rx4stateFlagWavelengthThree         	INTEGER,

		rx4labelAttnSettingThree	 		DisplayString (SIZE (0..80)),
		rx4valueAttnSettingThree			INTEGER,
		rx4enumAttnSettingThree			DisplayString (SIZE (0..80)),
		rx4stateFlagAttnSettingThree        	INTEGER,

		rx4labelSwModeSettingThree		DisplayString (SIZE (0..80)),
		rx4valueSwModeSettingThree		INTEGER,
		rx4enumSwModeSettingThree			DisplayString (SIZE (0..80)),
		rx4stateFlagSwModeSettingThree     	INTEGER,

		rx4labelSwModeThresholdThree	 	DisplayString (SIZE (0..80)),
		rx4valueSwModeThresholdThree		INTEGER,
		rx4enumSwModeThresholdThree		DisplayString (SIZE (0..80)),
		rx4stateFlagSwModeThresholdThree     	INTEGER,

		rx4labelModeFour	 			DisplayString (SIZE (0..80)),
		rx4valueModeFour				INTEGER,
		rx4enumModeFour				DisplayString (SIZE (0..80)),
		rx4stateFlagModeFour     	    	INTEGER,

		rx4labelWavelengthFour	 		DisplayString (SIZE (0..80)),
		rx4valueWavelengthFour			INTEGER,
		rx4enumWavelengthFour			DisplayString (SIZE (0..80)),
		rx4stateFlagWavelengthFour         	INTEGER,

		rx4labelAttnSettingFour	 		DisplayString (SIZE (0..80)),
		rx4valueAttnSettingFour			INTEGER,
		rx4enumAttnSettingFour			DisplayString (SIZE (0..80)),
		rx4stateFlagAttnSettingFour        	INTEGER,

		rx4labelSwModeSettingFour		DisplayString (SIZE (0..80)),
		rx4valueSwModeSettingFour		INTEGER,
		rx4enumSwModeSettingFour			DisplayString (SIZE (0..80)),
		rx4stateFlagSwModeSettingFour     	INTEGER,

		rx4labelSwModeThresholdFour	 	DisplayString (SIZE (0..80)),
		rx4valueSwModeThresholdFour		INTEGER,
		rx4enumSwModeThresholdFour		DisplayString (SIZE (0..80)),
		rx4stateFlagSwModeThresholdFour     	INTEGER,

		rx4labelModuleConfig		DisplayString (SIZE (0..80)),
		rx4valueModuleConfig		INTEGER,
		rx4enumModuleConfig		DisplayString (SIZE (0..80)),
		rx4stateFlagModuleConfig   	INTEGER,

		rx4labelRevertTime		DisplayString (SIZE (0..80)),
		rx4valueRevertTime		INTEGER,
		rx4enumRevertTime		DisplayString (SIZE (0..80)),
		rx4stateFlagRevertTime   	INTEGER,

		rx4labelTestPointSelect	DisplayString (SIZE (0..80)),
		rx4valueTestPointSelect		INTEGER,
		rx4enumTestPointSelect		DisplayString (SIZE (0..80)),
		rx4stateFlagTestPointSelect   	INTEGER,

		rx4labelFactoryDefault		DisplayString (SIZE (0..80)),
		rx4valueFactoryDefault		INTEGER,
		rx4enumFactoryDefault		DisplayString (SIZE (0..80)),
		rx4stateFlagFactoryDefault   	INTEGER

		}
		-- ****************  Status Parameters ************************************
	      Gx2Rx200BX4StatusEntry    ::= SEQUENCE  
	       {

		gx2Rx200BX4StatusTableIndex         INTEGER,   
		rx4labelBoot				DisplayString (SIZE (0..80)),
		rx4valueBoot				INTEGER,
		rx4stateflagBoot			INTEGER,
		
		rx4labelFlash				DisplayString (SIZE (0..80)),
		rx4valueFlash				INTEGER,
		rx4stateflagFlash			INTEGER,

		rx4labelFactoryDataCRC 		DisplayString (SIZE (0..80)),
		rx4valueFactoryDataCRC		INTEGER,
		rx4stateflagFactoryDataCRC		INTEGER,

		rx4labelAlarmDataCRC 		DisplayString (SIZE (0..80)),
		rx4valueAlarmDataCRC			INTEGER,
		rx4stateflagAlarmDataCRC		INTEGER,

		rx4labelCalibrationDataCRC		DisplayString (SIZE (0..80)),
		rx4valueCalibrationDataCRC		INTEGER,
		rx4stateflagCalibrationDataCRC	INTEGER,

		rx4labelHW					DisplayString (SIZE (0..80)),
		rx4valueHW					INTEGER,
		rx4stateflagHW				INTEGER,

		rx4labelOptSigOne			DisplayString (SIZE (0..80)),
		rx4valueOptSigOne			INTEGER,
		rx4stateflagOptSigOne		INTEGER,

		rx4labelOptSigTwo			DisplayString (SIZE (0..80)),
		rx4valueOptSigTwo			INTEGER,
		rx4stateflagOptSigTwo		INTEGER,

		rx4labelOptSigThree			DisplayString (SIZE (0..80)),
		rx4valueOptSigThree			INTEGER,
		rx4stateflagOptSigThree		INTEGER,

		rx4labelOptSigFour			DisplayString (SIZE (0..80)),
		rx4valueOptSigFour			INTEGER,
		rx4stateflagOptSigFour		INTEGER,

		rx4labelBackupCable			DisplayString (SIZE (0..80)),
		rx4valueBackupCable			INTEGER,
		rx4stateflagBackupCable		INTEGER


}
		

		-- ****************  Factory Parameters *************************************
	      Gx2Rx200BX4FactoryEntry    ::= SEQUENCE  
	       {
		gx2Rx200BX4FactoryTableIndex         INTEGER,   
		rx4bootControlByte  			INTEGER,
		rx4bootStatusByte   			INTEGER,
		rx4bank0CRC    			INTEGER,
		rx4bank1CRC    			INTEGER,
		rx4prgEEPROMByte    			INTEGER,
		rx4factoryCRC    			INTEGER,
		rx4calculateCRC    			INTEGER,
		rx4hourMeter    			INTEGER,
		rx4flashPrgCntA    			INTEGER,
		rx4flashPrgCntB    			INTEGER,
		rx4fwRev0	    			DisplayString (SIZE (0..80)),
		rx4fwRev1	    			DisplayString (SIZE (0..80))
		}


		-- ****************  Hold Time Parameters *************************************
--	    Gx2Rx200BX4HoldTimeEntry    ::= SEQUENCE  
--	    {
--		gx2Rx200BX4HoldTimeTableIndex        INTEGER,
--		gx2Rx200BX4HoldTimeSpecIndex         INTEGER,   
--		gx2Rx200BX4HoldTimeData  			INTEGER
--		}
--

        -- ************** Analog Parameters ****************************
		gx2Rx200BX4AnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx200BX4AnalogEntry 1}

-- New Parameter

		rx4labelOptPowerOne             OBJECT-TYPE
			   SYNTAX           DisplayString (SIZE (0..80))
			   ACCESS           read-only
			   STATUS           optional
			   DESCRIPTION
			   "The value of this object provides the label of the
			    Optical Power Analog parameter."
			   ::= { gx2Rx200BX4AnalogEntry 2}

		rx4uomOptPowerOne               OBJECT-TYPE
			   SYNTAX           DisplayString (SIZE (0..80))
			   ACCESS           read-only
			   STATUS           optional
			   DESCRIPTION
			   "The value of this object provides the Unit of Measure of the
			    Optical Power Analog parameter."
			   ::= { gx2Rx200BX4AnalogEntry 3}

		rx4majorHighOptPowerOne         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx200BX4AnalogEntry 4}


		rx4majorLowOptPowerOne          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx200BX4AnalogEntry 5}

		rx4minorHighOptPowerOne         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx200BX4AnalogEntry 6}

		rx4minorLowOptPowerOne          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx200BX4AnalogEntry 7}

		rx4currentValueOptPowerOne      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx200BX4AnalogEntry 8}

		rx4stateFlagOptPowerOne         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx200BX4AnalogEntry 9}

		rx4minValueOptPowerOne          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx200BX4AnalogEntry 10}

		rx4maxValueOptPowerOne          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx200BX4AnalogEntry 11}

		rx4alarmStateOptPowerOne        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx200BX4AnalogEntry 12}

-- New Parameter

		rx4labelOptPowerTwo             OBJECT-TYPE
			   SYNTAX           DisplayString (SIZE (0..80))
			   ACCESS           read-only
			   STATUS           optional
			   DESCRIPTION
			   "The value of this object provides the label of the
			    Optical Power Analog parameter."
			   ::= { gx2Rx200BX4AnalogEntry 13}

		rx4uomOptPowerTwo               OBJECT-TYPE
			   SYNTAX           DisplayString (SIZE (0..80))
			   ACCESS           read-only
			   STATUS           optional
			   DESCRIPTION
			   "The value of this object provides the Unit of Measure of the
			    Optical Power Analog parameter."
			   ::= { gx2Rx200BX4AnalogEntry 14}

		rx4majorHighOptPowerTwo         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx200BX4AnalogEntry 15}


		rx4majorLowOptPowerTwo          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx200BX4AnalogEntry 16}

		rx4minorHighOptPowerTwo         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx200BX4AnalogEntry 17}

		rx4minorLowOptPowerTwo          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx200BX4AnalogEntry 18}

		rx4currentValueOptPowerTwo      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx200BX4AnalogEntry 19}

		rx4stateFlagOptPowerTwo         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx200BX4AnalogEntry 20}

		rx4minValueOptPowerTwo          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx200BX4AnalogEntry 21}

		rx4maxValueOptPowerTwo          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx200BX4AnalogEntry 22}

		rx4alarmStateOptPowerTwo        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx200BX4AnalogEntry 23}

-- New Parameter

		rx4labelOptPowerThree             OBJECT-TYPE
			   SYNTAX           DisplayString (SIZE (0..80))
			   ACCESS           read-only
			   STATUS           optional
			   DESCRIPTION
			   "The value of this object provides the label of the
			    Optical Power Analog parameter."
			   ::= { gx2Rx200BX4AnalogEntry 24}

		rx4uomOptPowerThree               OBJECT-TYPE
			   SYNTAX           DisplayString (SIZE (0..80))
			   ACCESS           read-only
			   STATUS           optional
			   DESCRIPTION
			   "The value of this object provides the Unit of Measure of the
			    Optical Power Analog parameter."
			   ::= { gx2Rx200BX4AnalogEntry 25}

		rx4majorHighOptPowerThree         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx200BX4AnalogEntry 26}


		rx4majorLowOptPowerThree          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx200BX4AnalogEntry 27}

		rx4minorHighOptPowerThree         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx200BX4AnalogEntry 28}

		rx4minorLowOptPowerThree          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx200BX4AnalogEntry 29}

		rx4currentValueOptPowerThree      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx200BX4AnalogEntry 30}

		rx4stateFlagOptPowerThree         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx200BX4AnalogEntry 31}

		rx4minValueOptPowerThree          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx200BX4AnalogEntry 32}

		rx4maxValueOptPowerThree          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx200BX4AnalogEntry 33}

		rx4alarmStateOptPowerThree        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx200BX4AnalogEntry 34}

-- New Parameter

		rx4labelOptPowerFour             OBJECT-TYPE
			   SYNTAX           DisplayString (SIZE (0..80))
			   ACCESS           read-only
			   STATUS           optional
			   DESCRIPTION
			   "The value of this object provides the label of the
			    Optical Power Analog parameter."
			   ::= { gx2Rx200BX4AnalogEntry 35}

		rx4uomOptPowerFour               OBJECT-TYPE
			   SYNTAX           DisplayString (SIZE (0..80))
			   ACCESS           read-only
			   STATUS           optional
			   DESCRIPTION
			   "The value of this object provides the Unit of Measure of the
			    Optical Power Analog parameter."
			   ::= { gx2Rx200BX4AnalogEntry 36}

		rx4majorHighOptPowerFour         OBJECT-TYPE
			   SYNTAX           Float 
			   ACCESS           read-only
			   STATUS           mandatory
			   DESCRIPTION
			   "The value of this object provides the Major High alarm value
			          of the Optical Power Analog parameter. This value is a floating 
			    point number that is represented as an IEEE 32 bit number."
			   ::= { gx2Rx200BX4AnalogEntry 37}


		rx4majorLowOptPowerFour          OBJECT-TYPE
			   SYNTAX           Float 
			   ACCESS           read-only
			   STATUS           mandatory
			   DESCRIPTION
			   "The value of this object provides the Major Low alarm value
			          of the Optical Power Analog parameter. This value is a floating 
			    point number that is represented as an IEEE 32 bit number."
			   ::= { gx2Rx200BX4AnalogEntry 38}

		rx4minorHighOptPowerFour         OBJECT-TYPE
			   SYNTAX           Float
			   ACCESS           read-only
			   STATUS           mandatory
			   DESCRIPTION
			   "The value of this object provides the Minor High alarm value
			          of the Optical Power Analog parameter. This value is a floating 
			    point number that is represented as an IEEE 32 bit number."
			   ::= { gx2Rx200BX4AnalogEntry 39}

		rx4minorLowOptPowerFour          OBJECT-TYPE
			   SYNTAX           Float 
			   ACCESS           read-only
			   STATUS           mandatory
			   DESCRIPTION
			   "The value of this object provides the Minor Low alarm value
			          of the Optical Power Analog parameter. This value is a floating 
			    point number that is represented as an IEEE 32 bit number."
			   ::= { gx2Rx200BX4AnalogEntry 40}

		rx4currentValueOptPowerFour      OBJECT-TYPE
			   SYNTAX           Float 
			   ACCESS           read-only
			   STATUS           mandatory
			   DESCRIPTION
			   "The value of this object provides the Current value
			          of the Optical Power Analog parameter. This value is a floating 
			    point number that is represented as an IEEE 32 bit number."
			   ::= { gx2Rx200BX4AnalogEntry 41}

		rx4stateFlagOptPowerFour         OBJECT-TYPE
			   SYNTAX           INTEGER
								{
								hidden(1),
								read-only(2),
								updateable(3)
								}
			   ACCESS           read-only
			   STATUS           mandatory
			   DESCRIPTION
			   "The value of this object provides the state
			    of the Optical Power Analog parameter. (0-Hidden	
			          1-Read-Only, 2-Updateable)."
			   ::= { gx2Rx200BX4AnalogEntry 42}

		rx4minValueOptPowerFour          OBJECT-TYPE
			   SYNTAX           Float
			   ACCESS           read-only
			   STATUS           mandatory
			   DESCRIPTION
			   "The value of this object provides the minimum value
			          of the Optical Power Analog parameter. This value is a floating 
			    point number that is represented as an IEEE 32 bit number."
			   ::= { gx2Rx200BX4AnalogEntry 43}

		rx4maxValueOptPowerFour          OBJECT-TYPE
			   SYNTAX           Float
			   ACCESS           read-only
			   STATUS           mandatory
			   DESCRIPTION
			   "The value of this object provides the maximum value
			          of the Optical Power Analog parameter. This value is a floating 
			    point number that is represented as an IEEE 32 bit number."
			   ::= { gx2Rx200BX4AnalogEntry 44}

		rx4alarmStateOptPowerFour        OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Analog parameter."
			   ::= { gx2Rx200BX4AnalogEntry 45}

-- New Parameter

		rx4labelModTemp              OBJECT-TYPE
			   SYNTAX           DisplayString (SIZE (0..80))
			   ACCESS           read-only
			   STATUS           optional
			   DESCRIPTION
			   "The value of this object provides the label of the
			    Module Temperature Analog parameter."
			   ::= { gx2Rx200BX4AnalogEntry 46}

		rx4uomModTemp                OBJECT-TYPE
			   SYNTAX           DisplayString (SIZE (0..80))
			   ACCESS           read-only
			   STATUS           optional
			   DESCRIPTION
			   "The value of this object provides the Unit of Measure of the
			    Module Temperature Analog parameter."
			   ::= { gx2Rx200BX4AnalogEntry 47}

		rx4majorHighModTemp          OBJECT-TYPE
			   SYNTAX           Float 
			   ACCESS           read-only
			   STATUS           mandatory
			   DESCRIPTION
			   "The value of this object provides the Major High alarm value
			          of the Module Temperature Analog parameter. This value is a floating 
			    point number that is represented as an IEEE 32 bit number."
			   ::= { gx2Rx200BX4AnalogEntry 48}


		rx4majorLowModTemp           OBJECT-TYPE
			   SYNTAX           Float 
			   ACCESS           read-only
			   STATUS           mandatory
			   DESCRIPTION
			   "The value of this object provides the Major Low alarm value
			          of the Module Temperature Analog parameter. This value is a floating 
			    point number that is represented as an IEEE 32 bit number."
			   ::= { gx2Rx200BX4AnalogEntry 49}

		rx4minorHighModTemp          OBJECT-TYPE
			   SYNTAX           Float
			   ACCESS           read-only
			   STATUS           mandatory
			   DESCRIPTION
			   "The value of this object provides the Minor High alarm value
			          of the Module Temperature Analog parameter. This value is a floating 
			    point number that is represented as an IEEE 32 bit number."
			   ::= { gx2Rx200BX4AnalogEntry 50}

		rx4minorLowModTemp           OBJECT-TYPE
			   SYNTAX           Float 
			   ACCESS           read-only
			   STATUS           mandatory
			   DESCRIPTION
			   "The value of this object provides the Minor Low alarm value
			          of the Module Temperature Analog parameter. This value is a floating 
			    point number that is represented as an IEEE 32 bit number."
			   ::= { gx2Rx200BX4AnalogEntry 51}

		rx4currentValueModTemp       OBJECT-TYPE
			   SYNTAX           Float 
			   ACCESS           read-only
			   STATUS           mandatory
			   DESCRIPTION
			   "The value of this object provides the Current value
			          of the Module Temperature Analog parameter. This value is a floating 
			    point number that is represented as an IEEE 32 bit number."
			   ::= { gx2Rx200BX4AnalogEntry 52}

		rx4stateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2Rx200BX4AnalogEntry 53}

		rx4minValueModTemp           OBJECT-TYPE
			   SYNTAX           Float
			   ACCESS           read-only
			   STATUS           mandatory
			   DESCRIPTION
			   "The value of this object provides the minimum value
			          of the Module Temperature Analog parameter. This value is a floating 
			    point number that is represented as an IEEE 32 bit number."
			   ::= { gx2Rx200BX4AnalogEntry 54}

		rx4maxValueModTemp           OBJECT-TYPE
			   SYNTAX           Float
			   ACCESS           read-only
			   STATUS           mandatory
			   DESCRIPTION
			   "The value of this object provides the maximum value
			          of the Module Temperature Analog parameter. This value is a floating 
			    point number that is represented as an IEEE 32 bit number."
			   ::= { gx2Rx200BX4AnalogEntry 55}

		rx4alarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2Rx200BX4AnalogEntry 56}
-- New Parameter

		rx4labelFanCurrent           OBJECT-TYPE
			   SYNTAX           DisplayString (SIZE (0..80))
			   ACCESS           read-only
			   STATUS           optional
			   DESCRIPTION
			   "The value of this object provides the label of the
			    Fan Current Analog parameter."
			   ::= { gx2Rx200BX4AnalogEntry 57}

		rx4uomFanCurrent             OBJECT-TYPE
			   SYNTAX           DisplayString (SIZE (0..80))
			   ACCESS           read-only
			   STATUS           optional
			   DESCRIPTION
			   "The value of this object provides the Unit of Measure of the
			    Fan Current Analog parameter."
			   ::= { gx2Rx200BX4AnalogEntry 58}

		rx4majorHighFanCurrent       OBJECT-TYPE
			   SYNTAX           Float 
			   ACCESS           read-only
			   STATUS           mandatory
			   DESCRIPTION
			   "The value of this object provides the Major High alarm value
			          of the Fan Current Analog parameter. This value is a floating 
			    point number that is represented as an IEEE 32 bit number."
			   ::= { gx2Rx200BX4AnalogEntry 59}


		rx4majorLowFanCurrent        OBJECT-TYPE
			   SYNTAX           Float 
			   ACCESS           read-only
			   STATUS           mandatory
			   DESCRIPTION
			   "The value of this object provides the Major Low alarm value
			          of the Fan Current Analog parameter. This value is a floating 
			    point number that is represented as an IEEE 32 bit number."
			   ::= { gx2Rx200BX4AnalogEntry 60}

		rx4minorHighFanCurrent       OBJECT-TYPE
			   SYNTAX           Float
			   ACCESS           read-only
			   STATUS           mandatory
			   DESCRIPTION
			   "The value of this object provides the Minor High alarm value
			          of the Fan Current Analog parameter. This value is a floating 
			    point number that is represented as an IEEE 32 bit number."
			   ::= { gx2Rx200BX4AnalogEntry 61}

		rx4minorLowFanCurrent        OBJECT-TYPE
			   SYNTAX           Float 
			   ACCESS           read-only
			   STATUS           mandatory
			   DESCRIPTION
			   "The value of this object provides the Minor Low alarm value
			          of the Fan Current Analog parameter. This value is a floating 
			    point number that is represented as an IEEE 32 bit number."
			   ::= { gx2Rx200BX4AnalogEntry 62}

		rx4currentValueFanCurrent    OBJECT-TYPE
			   SYNTAX           Float 
			   ACCESS           read-only
			   STATUS           mandatory
			   DESCRIPTION
			   "The value of this object provides the Current value
			          of the Fan Current Analog parameter. This value is a floating 
			    point number that is represented as an IEEE 32 bit number."
			   ::= { gx2Rx200BX4AnalogEntry 63}

		rx4stateFlagFanCurrent       OBJECT-TYPE
			   SYNTAX           INTEGER
								{
								hidden(1),
								read-only(2),
								updateable(3)
								}

			   ACCESS           read-only
			   STATUS           mandatory
			   DESCRIPTION
			   "The value of this object provides the state
			    of the Fan Current Analog parameter. (0-Hidden	
			          1-Read-Only, 2-Updateable)."
			   ::= { gx2Rx200BX4AnalogEntry 64}

		rx4minValueFanCurrent        OBJECT-TYPE
			   SYNTAX           Float
			   ACCESS           read-only
			   STATUS           mandatory
			   DESCRIPTION
			   "The value of this object provides the minimum value
			          of the Fan Current Analog parameter. This value is a floating 
			    point number that is represented as an IEEE 32 bit number."
			   ::= { gx2Rx200BX4AnalogEntry 65}

		rx4maxValueFanCurrent        OBJECT-TYPE
			   SYNTAX           Float
			   ACCESS           read-only
			   STATUS           mandatory
			   DESCRIPTION
			   "The value of this object provides the maximum value
			          of the Fan Current Analog parameter. This value is a floating 
			    point number that is represented as an IEEE 32 bit number."
			   ::= { gx2Rx200BX4AnalogEntry 66}

		rx4alarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2Rx200BX4AnalogEntry 67}
-- New Parameter

		rx4label12Volt               OBJECT-TYPE
			   SYNTAX           DisplayString (SIZE (0..80))
			   ACCESS           read-only
			   STATUS           optional
			   DESCRIPTION
			   "The value of this object provides the label of the
			    12v Current Analog parameter."
			   ::= { gx2Rx200BX4AnalogEntry 68}

		rx4uom12Volt                 OBJECT-TYPE
			   SYNTAX           DisplayString (SIZE (0..80))
			   ACCESS           read-only
			   STATUS           optional
			   DESCRIPTION
			   "The value of this object provides the Unit of Measure of the
			    12v Current Analog parameter."
			   ::= { gx2Rx200BX4AnalogEntry 69}

		rx4majorHigh12Volt           OBJECT-TYPE
			   SYNTAX           Float 
			   ACCESS           read-only
			   STATUS           mandatory
			   DESCRIPTION
			   "The value of this object provides the Major High alarm value
			          of the 12 Volt Current Analog parameter. This value is a floating 
			    point number that is represented as an IEEE 32 bit number."
			   ::= { gx2Rx200BX4AnalogEntry 70}


		rx4majorLow12Volt            OBJECT-TYPE
			   SYNTAX           Float 
			   ACCESS           read-only
			   STATUS           mandatory
			   DESCRIPTION
			   "The value of this object provides the Major Low alarm value
			          of the 12 Volt Current Analog parameter. This value is a floating 
			    point number that is represented as an IEEE 32 bit number."
			   ::= { gx2Rx200BX4AnalogEntry 71}

		rx4minorHigh12Volt           OBJECT-TYPE
			   SYNTAX           Float
			   ACCESS           read-only
			   STATUS           mandatory
			   DESCRIPTION
			   "The value of this object provides the Minor High alarm value
			          of the 12 Volt Current Analog parameter. This value is a floating 
			    point number that is represented as an IEEE 32 bit number."
			   ::= { gx2Rx200BX4AnalogEntry 72}

		rx4minorLow12Volt            OBJECT-TYPE
			   SYNTAX           Float 
			   ACCESS           read-only
			   STATUS           mandatory
			   DESCRIPTION
			   "The value of this object provides the Minor Low alarm value
			          of the 12 Volt Current Analog parameter. This value is a floating 
			    point number that is represented as an IEEE 32 bit number."
			   ::= { gx2Rx200BX4AnalogEntry 73}

		rx4currentValue12Volt        OBJECT-TYPE
			   SYNTAX           Float 
			   ACCESS           read-only
			   STATUS           mandatory
			   DESCRIPTION
			   "The value of this object provides the Current value
			          of the 12 Volt Current Analog parameter. This value is a floating 
			    point number that is represented as an IEEE 32 bit number."
			   ::= { gx2Rx200BX4AnalogEntry 74}

		rx4stateFlag12Volt           OBJECT-TYPE
			   SYNTAX           INTEGER
								{
								hidden(1),
								read-only(2),
								updateable(3)
								}
			   ACCESS           read-only
			   STATUS           mandatory
			   DESCRIPTION
			   "The value of this object provides the state
			    of the 12v Current Analog parameter. (0-Hidden	
			          1-Read-Only, 2-Updateable)."
			   ::= { gx2Rx200BX4AnalogEntry 75}

		rx4minValue12Volt            OBJECT-TYPE
			   SYNTAX           Float
			   ACCESS           read-only
			   STATUS           mandatory
			   DESCRIPTION
			   "The value of this object provides the minimum value
			          of the 12 Volt Current Analog parameter. This value is a floating 
			    point number that is represented as an IEEE 32 bit number."
			   ::= { gx2Rx200BX4AnalogEntry 76}

		rx4maxValue12Volt            OBJECT-TYPE
			   SYNTAX           Float
			   ACCESS           read-only
			   STATUS           mandatory
			   DESCRIPTION
			   "The value of this object provides the maximum value
			          of the 12 Volt Current Analog parameter. This value is a floating 
			    point number that is represented as an IEEE 32 bit number."
			   ::= { gx2Rx200BX4AnalogEntry 77}

		rx4alarmState12Volt          OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v Current Analog parameter."
			   ::= { gx2Rx200BX4AnalogEntry 78}

-- ************************ Digital parameters **********************************
		gx2Rx200BX4DigitalTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx200BX4DigitalEntry 1}

-- New parameter
		rx4labelModeOne	             	OBJECT-TYPE
			   SYNTAX         	DisplayString (SIZE (0..80))         
			   ACCESS           	read-only
			   STATUS           	optional
			   DESCRIPTION
			   "The value of this object provides the label of the
			    Rx200BX4's Mode  Digital parameter."
			   ::= { gx2Rx200BX4DigitalEntry 2}

		rx4enumModeOne	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 3}

		rx4valueModeOne	                OBJECT-TYPE
			   SYNTAX       		INTEGER
					    		{
							off(1),
							manual(2),
							agc(3)
					    		}
			   ACCESS           	read-write
			   STATUS           	mandatory
			   DESCRIPTION
			   "The value of this object is the current value of the parameter."
			   ::= { gx2Rx200BX4DigitalEntry 4}

		rx4stateFlagModeOne	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 5}
-- New parameter
		rx4labelWavelengthOne             	OBJECT-TYPE
			   SYNTAX         	DisplayString (SIZE (0..80))         
			   ACCESS           	read-only
			   STATUS           	optional
			   DESCRIPTION
			   "The value of this object provides the label of the
			    Rx200BX4's Wavelength  Digital parameter."
			   ::= { gx2Rx200BX4DigitalEntry 6}

		rx4enumWavelengthOne               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 7}

		rx4valueWavelengthOne               OBJECT-TYPE
			   SYNTAX       		INTEGER
					    		{
							nM1270(1),
							nM1290(2),
							nM1310(3),
							nM1330(4),
							nM1350(5),
							nM1370(6),
							nM1390(7),
							nM1410(8),
							nM1430(9),
							nM1450(10),
							nM1470(11),
							nM1490(12),
							nM1510(13),
							nM1530(14),
							nM1550(15),
							nM1570(16),
							nM1590(17),
							nM1610(18)
								}
			   ACCESS           	read-write
			   STATUS           	mandatory
			   DESCRIPTION
			   "The value of this object is the current value of the parameter."
			   ::= { gx2Rx200BX4DigitalEntry 8}

		rx4stateFlagWavelengthOne	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 9}
-- New parameter
		rx4labelAttnSettingOne	          	OBJECT-TYPE
			   SYNTAX         	DisplayString (SIZE (0..80))         
			   ACCESS           	read-only
			   STATUS           	optional
			   DESCRIPTION
			   "The value of this object provides the label of the
			    Rx200BX4's AttnSetting  Digital parameter."
			   ::= { gx2Rx200BX4DigitalEntry 10}

		rx4enumAttnSettingOne	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 11}

		rx4valueAttnSettingOne	            OBJECT-TYPE
			   SYNTAX       		INTEGER

			   ACCESS           	read-write
			   STATUS           	mandatory
			   DESCRIPTION
			   "The value of this object is the current value of the parameter. It is an integer 
                      value from 0 to 40. Each increment represents 1/2 dB of attenuation from 0 to 20 dB. 
			    Where 0 = 0db and 40 = 20db"
			   ::= { gx2Rx200BX4DigitalEntry 12}

		rx4stateFlagAttnSettingOne	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 13}
-- New parameter
		rx4labelSwModeSettingOne	     	OBJECT-TYPE
			   SYNTAX         	DisplayString (SIZE (0..80))         
			   ACCESS           	read-only
			   STATUS           	optional
			   DESCRIPTION
			   "The value of this object provides the label of the
			    Rx200BX4's Switch Mode Setting  Digital parameter."
			   ::= { gx2Rx200BX4DigitalEntry 14}

		rx4enumSwModeSettingOne	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx200BX4DigitalEntry 15}

		rx4valueSwModeSettingOne	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx200BX4DigitalEntry 16}

		rx4stateFlagSwModeSettingOne	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 17}
-- New parameter
		rx4labelSwModeThresholdOne	      OBJECT-TYPE
			   SYNTAX         	DisplayString (SIZE (0..80))         
			   ACCESS           	read-only
			   STATUS           	optional
			   DESCRIPTION
			   "The value of this object provides the label of the
			    Rx200BX4's Switch Mode Threshold  Digital parameter."
			   ::= { gx2Rx200BX4DigitalEntry 18}

		rx4enumSwModeThresholdOne		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 19}

		rx4valueSwModeThresholdOne	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx200BX4DigitalEntry 20}

		rx4stateFlagSwModeThresholdOne	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 21}

-- New parameter
		rx4labelModeTwo	             	OBJECT-TYPE
			   SYNTAX         	DisplayString (SIZE (0..80))         
			   ACCESS           	read-only
			   STATUS           	optional
			   DESCRIPTION
			   "The value of this object provides the label of the
			    Rx200BX4's Mode  Digital parameter."
			   ::= { gx2Rx200BX4DigitalEntry 22}

		rx4enumModeTwo	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 23}

		rx4valueModeTwo	                OBJECT-TYPE
			   SYNTAX       		INTEGER
					    		{
							off(1),
							manual(2),
							agc(3)
					    		}
			   ACCESS           	read-write
			   STATUS           	mandatory
			   DESCRIPTION
			   "The value of this object is the current value of the parameter."
			   ::= { gx2Rx200BX4DigitalEntry 24}

		rx4stateFlagModeTwo	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 25}
-- New parameter
		rx4labelWavelengthTwo             	OBJECT-TYPE
			   SYNTAX         	DisplayString (SIZE (0..80))         
			   ACCESS           	read-only
			   STATUS           	optional
			   DESCRIPTION
			   "The value of this object provides the label of the
			    Rx200BX4's Wavelength  Digital parameter."
			   ::= { gx2Rx200BX4DigitalEntry 26}

		rx4enumWavelengthTwo               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 27}

		rx4valueWavelengthTwo               OBJECT-TYPE
			   SYNTAX       		INTEGER
					    		{
							nM1270(1),
							nM1290(2),
							nM1310(3),
							nM1330(4),
							nM1350(5),
							nM1370(6),
							nM1390(7),
							nM1410(8),
							nM1430(9),
							nM1450(10),
							nM1470(11),
							nM1490(12),
							nM1510(13),
							nM1530(14),
							nM1550(15),
							nM1570(16),
							nM1590(17),
							nM1610(18)
					    		}
			   ACCESS           	read-write
			   STATUS           	mandatory
			   DESCRIPTION
			   "The value of this object is the current value of the parameter."
			   ::= { gx2Rx200BX4DigitalEntry 28}

		rx4stateFlagWavelengthTwo	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 29}
-- New parameter
		rx4labelAttnSettingTwo	          	OBJECT-TYPE
			   SYNTAX         	DisplayString (SIZE (0..80))         
			   ACCESS           	read-only
			   STATUS           	optional
			   DESCRIPTION
			   "The value of this object provides the label of the
			    Rx200BX4's AttnSetting  Digital parameter."
			   ::= { gx2Rx200BX4DigitalEntry 30}

		rx4enumAttnSettingTwo	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 31}

		rx4valueAttnSettingTwo	            OBJECT-TYPE
			   SYNTAX       		INTEGER

			   ACCESS           	read-write
			   STATUS           	mandatory
			   DESCRIPTION
			   "The value of this object is the current value of the parameter. It is an integer 
                      value from 0 to 40. Each increment represents 1/2 dB of attenuation from 0 to 20 dB. 
			    Where 0 = 0db and 40 = 20db"
			   ::= { gx2Rx200BX4DigitalEntry 32}

		rx4stateFlagAttnSettingTwo	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 33}
-- New parameter
		rx4labelSwModeSettingTwo	     	OBJECT-TYPE
			   SYNTAX         	DisplayString (SIZE (0..80))         
			   ACCESS           	read-only
			   STATUS           	optional
			   DESCRIPTION
			   "The value of this object provides the label of the
			    Rx200BX4's Switch Mode Setting  Digital parameter."
			   ::= { gx2Rx200BX4DigitalEntry 34}

		rx4enumSwModeSettingTwo	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx200BX4DigitalEntry 35}

		rx4valueSwModeSettingTwo	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx200BX4DigitalEntry 36}

		rx4stateFlagSwModeSettingTwo	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 37}
-- New parameter
		rx4labelSwModeThresholdTwo	      OBJECT-TYPE
			   SYNTAX         	DisplayString (SIZE (0..80))         
			   ACCESS           	read-only
			   STATUS           	optional
			   DESCRIPTION
			   "The value of this object provides the label of the
			    Rx200BX4's Switch Mode Threshold  Digital parameter."
			   ::= { gx2Rx200BX4DigitalEntry 38}

		rx4enumSwModeThresholdTwo		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 39}

		rx4valueSwModeThresholdTwo	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx200BX4DigitalEntry 40}

		rx4stateFlagSwModeThresholdTwo	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 41}


-- New parameter
		rx4labelModeThree	             	OBJECT-TYPE
			   SYNTAX         	DisplayString (SIZE (0..80))         
			   ACCESS           	read-only
			   STATUS           	optional
			   DESCRIPTION
			   "The value of this object provides the label of the
			    Rx200BX4's Mode  Digital parameter."
			   ::= { gx2Rx200BX4DigitalEntry 42}

		rx4enumModeThree	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 43}

		rx4valueModeThree	                OBJECT-TYPE
			   SYNTAX       		INTEGER
					    		{
							off(1),
							manual(2),
							agc(3)
					    		}
			   ACCESS           	read-write
			   STATUS           	mandatory
			   DESCRIPTION
			   "The value of this object is the current value of the parameter."
			   ::= { gx2Rx200BX4DigitalEntry 44}

		rx4stateFlagModeThree	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 45}
-- New parameter
		rx4labelWavelengthThree             	OBJECT-TYPE
			   SYNTAX         	DisplayString (SIZE (0..80))         
			   ACCESS           	read-only
			   STATUS           	optional
			   DESCRIPTION
			   "The value of this object provides the label of the
			    Rx200BX4's Wavelength  Digital parameter."
			   ::= { gx2Rx200BX4DigitalEntry 46}

		rx4enumWavelengthThree               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 47}

		rx4valueWavelengthThree               OBJECT-TYPE
			   SYNTAX       		INTEGER
					    		{
							nM1270(1),
							nM1290(2),
							nM1310(3),
							nM1330(4),
							nM1350(5),
							nM1370(6),
							nM1390(7),
							nM1410(8),
							nM1430(9),
							nM1450(10),
							nM1470(11),
							nM1490(12),
							nM1510(13),
							nM1530(14),
							nM1550(15),
							nM1570(16),
							nM1590(17),
							nM1610(18)
					    		}
			   ACCESS           	read-write
			   STATUS           	mandatory
			   DESCRIPTION
			   "The value of this object is the current value of the parameter."
			   ::= { gx2Rx200BX4DigitalEntry 48}

		rx4stateFlagWavelengthThree	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 49}
-- New parameter
		rx4labelAttnSettingThree	          	OBJECT-TYPE
			   SYNTAX         	DisplayString (SIZE (0..80))         
			   ACCESS           	read-only
			   STATUS           	optional
			   DESCRIPTION
			   "The value of this object provides the label of the
			    Rx200BX4's AttnSetting  Digital parameter."
			   ::= { gx2Rx200BX4DigitalEntry 50}

		rx4enumAttnSettingThree	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 51}

		rx4valueAttnSettingThree	            OBJECT-TYPE
			   SYNTAX       		INTEGER

			   ACCESS           	read-write
			   STATUS           	mandatory
			   DESCRIPTION
			   "The value of this object is the current value of the parameter. It is an integer 
                      value from 0 to 40. Each increment represents 1/2 dB of attenuation from 0 to 20 dB. 
			    Where 0 = 0db and 40 = 20db"
			   ::= { gx2Rx200BX4DigitalEntry 52}

		rx4stateFlagAttnSettingThree	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 53}
-- New parameter
		rx4labelSwModeSettingThree	     	OBJECT-TYPE
			   SYNTAX         	DisplayString (SIZE (0..80))         
			   ACCESS           	read-only
			   STATUS           	optional
			   DESCRIPTION
			   "The value of this object provides the label of the
			    Rx200BX4's Switch Mode Setting  Digital parameter."
			   ::= { gx2Rx200BX4DigitalEntry 54}

		rx4enumSwModeSettingThree	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx200BX4DigitalEntry 55}

		rx4valueSwModeSettingThree	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx200BX4DigitalEntry 56}

		rx4stateFlagSwModeSettingThree	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 57}
-- New parameter
		rx4labelSwModeThresholdThree	      OBJECT-TYPE
			   SYNTAX         	DisplayString (SIZE (0..80))         
			   ACCESS           	read-only
			   STATUS           	optional
			   DESCRIPTION
			   "The value of this object provides the label of the
			    Rx200BX4's Switch Mode Threshold  Digital parameter."
			   ::= { gx2Rx200BX4DigitalEntry 58}

		rx4enumSwModeThresholdThree		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 59}

		rx4valueSwModeThresholdThree	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx200BX4DigitalEntry 60}

		rx4stateFlagSwModeThresholdThree	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 61}


-- New parameter
		rx4labelModeFour	             	OBJECT-TYPE
			   SYNTAX         	DisplayString (SIZE (0..80))         
			   ACCESS           	read-only
			   STATUS           	optional
			   DESCRIPTION
			   "The value of this object provides the label of the
			    Rx200BX4's Mode  Digital parameter."
			   ::= { gx2Rx200BX4DigitalEntry 62}

		rx4enumModeFour	               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 63}

		rx4valueModeFour	                OBJECT-TYPE
			   SYNTAX       		INTEGER
					    		{
							off(1),
							manual(2),
							agc(3)
					    		}
			   ACCESS           	read-write
			   STATUS           	mandatory
			   DESCRIPTION
			   "The value of this object is the current value of the parameter."
			   ::= { gx2Rx200BX4DigitalEntry 64}

		rx4stateFlagModeFour	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 65}
-- New parameter
		rx4labelWavelengthFour             	OBJECT-TYPE
			   SYNTAX         	DisplayString (SIZE (0..80))         
			   ACCESS           	read-only
			   STATUS           	optional
			   DESCRIPTION
			   "The value of this object provides the label of the
			    Rx200BX4's Wavelength  Digital parameter."
			   ::= { gx2Rx200BX4DigitalEntry 66}

		rx4enumWavelengthFour               	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 67}

		rx4valueWavelengthFour               OBJECT-TYPE
			   SYNTAX       		INTEGER
					    		{
							nM1270(1),
							nM1290(2),
							nM1310(3),
							nM1330(4),
							nM1350(5),
							nM1370(6),
							nM1390(7),
							nM1410(8),
							nM1430(9),
							nM1450(10),
							nM1470(11),
							nM1490(12),
							nM1510(13),
							nM1530(14),
							nM1550(15),
							nM1570(16),
							nM1590(17),
							nM1610(18)
					    		}
			   ACCESS           	read-write
			   STATUS           	mandatory
			   DESCRIPTION
			   "The value of this object is the current value of the parameter."
			   ::= { gx2Rx200BX4DigitalEntry 68}

		rx4stateFlagWavelengthFour	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 69}
-- New parameter
		rx4labelAttnSettingFour	          	OBJECT-TYPE
			   SYNTAX         	DisplayString (SIZE (0..80))         
			   ACCESS           	read-only
			   STATUS           	optional
			   DESCRIPTION
			   "The value of this object provides the label of the
			    Rx200BX4's AttnSetting  Digital parameter."
			   ::= { gx2Rx200BX4DigitalEntry 70}

		rx4enumAttnSettingFour	          	OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 71}

		rx4valueAttnSettingFour	            OBJECT-TYPE
			   SYNTAX       		INTEGER

			   ACCESS           	read-write
			   STATUS           	mandatory
			   DESCRIPTION
			   "The value of this object is the current value of the parameter. It is an integer 
                      value from 0 to 40. Each increment represents 1/2 dB of attenuation from 0 to 20 dB. 
			    Where 0 = 0db and 40 = 20db"
			   ::= { gx2Rx200BX4DigitalEntry 72}

		rx4stateFlagAttnSettingFour	    	OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 73}
-- New parameter
		rx4labelSwModeSettingFour	     	OBJECT-TYPE
			   SYNTAX         	DisplayString (SIZE (0..80))         
			   ACCESS           	read-only
			   STATUS           	optional
			   DESCRIPTION
			   "The value of this object provides the label of the
			    Rx200BX4's Switch Mode Setting  Digital parameter."
			   ::= { gx2Rx200BX4DigitalEntry 74}

		rx4enumSwModeSettingFour	           	OBJECT-TYPE
			   SYNTAX         	DisplayString (SIZE (0..80))         
			   ACCESS           	read-only
			   STATUS           	optional
			   DESCRIPTION
			   "The value of this object represents the Enumeration values
			    possible for the Digital parameter. Each Enumerated values          is
			    separated by a common. The first value has a enumerated value of 1."
			   ::= { gx2Rx200BX4DigitalEntry 75}

		rx4valueSwModeSettingFour	      OBJECT-TYPE
			   SYNTAX       		INTEGER
					    		{
							off(1),
							alarm-only(2),
							alarm-and-switch(3)
					    		}
			   ACCESS           	read-write
			   STATUS           	mandatory
			   DESCRIPTION
			   "The value of this object is the current value of the parameter."
			   ::= { gx2Rx200BX4DigitalEntry 76}

		rx4stateFlagSwModeSettingFour	      OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 77}
-- New parameter
		rx4labelSwModeThresholdFour	      OBJECT-TYPE
			   SYNTAX         	DisplayString (SIZE (0..80))         
			   ACCESS           	read-only
			   STATUS           	optional
			   DESCRIPTION
			   "The value of this object provides the label of the
			    Rx200BX4's Switch Mode Threshold  Digital parameter."
			   ::= { gx2Rx200BX4DigitalEntry 78}

		rx4enumSwModeThresholdFour		OBJECT-TYPE
			   SYNTAX         	DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 79}

		rx4valueSwModeThresholdFour	      OBJECT-TYPE
			   SYNTAX       		INTEGER
			   ACCESS           	read-write
			   STATUS           	mandatory
			   DESCRIPTION
			   "The value of this object reflects the setting of the threshold at 
			    which the Optical Input Failed signal is sent. It is in 1 dB increments 
                      ranging from -2 to -17 dB. The user can enter a number from 0 to 15,
			    where 0 = -2db and 15= -17db"
			   ::= { gx2Rx200BX4DigitalEntry 80}

		rx4stateFlagSwModeThresholdFour	            OBJECT-TYPE
			   SYNTAX         	INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 81}

-- New parameter
		rx4labelModuleConfig           OBJECT-TYPE
			   SYNTAX       		DisplayString (SIZE (0..80))         
			   ACCESS           	read-only
			   STATUS           	optional
			   DESCRIPTION
			   "The value of this object provides the label of the
			    Factory Default Reset  Digital parameter."
			   ::= { gx2Rx200BX4DigitalEntry 82}

		rx4enumModuleConfig          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 83}

		rx4valueModuleConfig         	OBJECT-TYPE
			   SYNTAX       		INTEGER
					    		{
							slave(1),
							master(2),
							burst(3)
					    		}
			   ACCESS           	read-write
			   STATUS           	mandatory
			   DESCRIPTION
			   "The value of this object is the current value of the parameter."
			   ::= { gx2Rx200BX4DigitalEntry 84}

		rx4stateFlagModuleConfig     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 85}


-- New parameter
		rx4labelRevertTime           OBJECT-TYPE
			   SYNTAX       		DisplayString (SIZE (0..80))         
			   ACCESS           	read-only
			   STATUS           	optional
			   DESCRIPTION
			   "The value of this object provides the label of the
			    Factory Default Reset  Digital parameter."
			   ::= { gx2Rx200BX4DigitalEntry 86}

		rx4enumRevertTime          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 87}

		rx4valueRevertTime         	OBJECT-TYPE
			   SYNTAX       		INTEGER
					    		{
							one-sec(1),
							ten-sec(2),
							sixty-sec(3),
					    	six-hundred-sec(4)
					    		}
			   ACCESS           	read-write
			   STATUS           	mandatory
			   DESCRIPTION
			   "The value of this object is the current value of the parameter."
			   ::= { gx2Rx200BX4DigitalEntry 88}

		rx4stateFlagRevertTime     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 89}


-- New parameter
		rx4labelTestPointSelect           OBJECT-TYPE
			   SYNTAX       		DisplayString (SIZE (0..80))         
			   ACCESS           	read-only
			   STATUS           	optional
			   DESCRIPTION
			   "The value of this object provides the label of the
			    Test point Select Digital parameter."
			   ::= { gx2Rx200BX4DigitalEntry 90}

		rx4enumTestPointSelect          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 91}

		rx4valueTestPointSelect         	OBJECT-TYPE
			   SYNTAX       		INTEGER
					    	{
							one(1),
							two(2),
							three(3),
							four(4)
					    	}
			   ACCESS           	read-write
			   STATUS           	mandatory
			   DESCRIPTION
			   "The value of this object is the current value of the parameter."
			   ::= { gx2Rx200BX4DigitalEntry 92}

		rx4stateFlagTestPointSelect     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 93}


-- New parameter
		rx4labelFactoryDefault           OBJECT-TYPE
			   SYNTAX       		DisplayString (SIZE (0..80))         
			   ACCESS           	read-only
			   STATUS           	optional
			   DESCRIPTION
			   "The value of this object provides the label of the
			    Factory Default Reset  Digital parameter."
			   ::= { gx2Rx200BX4DigitalEntry 94}

		rx4enumFactoryDefault          	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2Rx200BX4DigitalEntry 95}

		rx4valueFactoryDefault         	OBJECT-TYPE
			   SYNTAX       		INTEGER
					    		{
							off(1),
							on(2)
					    		}
			   ACCESS           	read-write
			   STATUS           	mandatory
			   DESCRIPTION
			   "The value of this object is the current value of the parameter."
			   ::= { gx2Rx200BX4DigitalEntry 96}

		rx4stateFlagFactoryDefault     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4DigitalEntry 97}



		--*********** STATUS *****************
		gx2Rx200BX4StatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx200BX4StatusEntry 1}

--New Parameter
		rx4labelBoot               	OBJECT-TYPE
			   SYNTAX       		DisplayString (SIZE (0..80))         
			   ACCESS           	read-only
			   STATUS           	optional
			   DESCRIPTION
			   "The value of this object provides the label of the
			    Boot Status  Status parameter."
			   ::= { gx2Rx200BX4StatusEntry 2}

		rx4valueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 3}

		rx4stateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry  4}


--New Parameter
		rx4labelFlash               	OBJECT-TYPE
			   SYNTAX       		DisplayString (SIZE (0..80))         
			   ACCESS           	read-only
			   STATUS           	optional
			   DESCRIPTION
			   "The value of this object provides the label of the
			    Flash Status  Status parameter."
			   ::= { gx2Rx200BX4StatusEntry 5}

		rx4valueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 6}

		rx4stateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 7}


--New Parameter
		rx4labelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2Rx200BX4StatusEntry 8}

		rx4valueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 9}

		rx4stateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 10}


--New Parameter
		rx4labelAlarmDataCRC             OBJECT-TYPE
			   SYNTAX       		DisplayString (SIZE (0..80))         
			   ACCESS           	read-only
			   STATUS           	optional
			   DESCRIPTION
			   "The value of this object provides the label of the
			    Alarm Data CRC Status parameter."
			   ::= { gx2Rx200BX4StatusEntry 11}

		rx4valueAlarmDataCRC           	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 12}

		rx4stateflagAlarmDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 13}


--New Parameter
		rx4labelCalibrationDataCRC       OBJECT-TYPE
			   SYNTAX       		DisplayString (SIZE (0..80))         
			   ACCESS           	read-only
			   STATUS           	optional
			   DESCRIPTION
			   "The value of this object provides the label of the
			    Calibration Data CRC Status parameter."
			   ::= { gx2Rx200BX4StatusEntry 14}

		rx4valueCalibrationDataCRC      	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 15}

		rx4stateflagCalibrationDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 16}


--New Parameter
		rx4labelHW               	      OBJECT-TYPE
			   SYNTAX       		DisplayString (SIZE (0..80))         
			   ACCESS           	read-only
			   STATUS           	optional
			   DESCRIPTION
			   "The value of this object provides the label of the
			    Hardware Status parameter."
			   ::= { gx2Rx200BX4StatusEntry 17}

		rx4valueHW              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 18}

		rx4stateflagHW     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 19}


--New Parameter
		rx4labelOptSigOne		    OBJECT-TYPE
			   SYNTAX       		DisplayString (SIZE (0..80))         
			   ACCESS           	read-only
			   STATUS           	optional
			   DESCRIPTION
			   "The value of this object provides the label of the
			    Optical Signal Status parameter."
			   ::= { gx2Rx200BX4StatusEntry 20}

		rx4valueOptSigOne       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 21}

		rx4stateflagOptSigOne     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 22}

--New Parameter
		rx4labelOptSigTwo		    OBJECT-TYPE
			   SYNTAX       		DisplayString (SIZE (0..80))         
			   ACCESS           	read-only
			   STATUS           	optional
			   DESCRIPTION
			   "The value of this object provides the label of the
			    Optical Signal Status parameter."
			   ::= { gx2Rx200BX4StatusEntry 23}

		rx4valueOptSigTwo       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 24}

		rx4stateflagOptSigTwo     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 25}

--New Parameter
		rx4labelOptSigThree		    OBJECT-TYPE
			   SYNTAX       		DisplayString (SIZE (0..80))         
			   ACCESS           	read-only
			   STATUS           	optional
			   DESCRIPTION
			   "The value of this object provides the label of the
			    Optical Signal Status parameter."
			   ::= { gx2Rx200BX4StatusEntry 26}

		rx4valueOptSigThree       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 27}

		rx4stateflagOptSigThree     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 28}

--New Parameter
		rx4labelOptSigFour		    OBJECT-TYPE
			   SYNTAX       		DisplayString (SIZE (0..80))         
			   ACCESS           	read-only
			   STATUS           	optional
			   DESCRIPTION
			   "The value of this object provides the label of the
			    Optical Signal Status parameter."
			   ::= { gx2Rx200BX4StatusEntry 29}

		rx4valueOptSigFour       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 30}

		rx4stateflagOptSigFour     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 31}

--New Parameter
		rx4labelBackupCable		    OBJECT-TYPE
			   SYNTAX       		DisplayString (SIZE (0..80))         
			   ACCESS           	read-only
			   STATUS           	optional
			   DESCRIPTION
			   "The value of this object provides the label of the
			    Backup Cable Status parameter."
			   ::= { gx2Rx200BX4StatusEntry 32}

		rx4valueBackupCable       	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2Rx200BX4StatusEntry 33}

		rx4stateflagBackupCable     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2Rx200BX4StatusEntry 34}

            -- ************ FACTORY DATA ****************
		gx2Rx200BX4FactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2Rx200BX4FactoryEntry 1}

		rx4bootControlByte          	OBJECT-TYPE
			   SYNTAX       		INTEGER
			   ACCESS           	read-only
			   STATUS           	mandatory
			   DESCRIPTION
			   "The value of this object indicates which bank the firmware
			    is currently being boot from."
			   ::= { gx2Rx200BX4FactoryEntry 2}

		rx4bootStatusByte          	OBJECT-TYPE
			   SYNTAX       		INTEGER
			   ACCESS           	read-only
			   STATUS           	mandatory
			   DESCRIPTION
			   "This object indicates the status of the last boot"
			   ::= { gx2Rx200BX4FactoryEntry 3}

		rx4bank0CRC          		OBJECT-TYPE
			   SYNTAX       		INTEGER
			   ACCESS           	read-only
			   STATUS           	mandatory
			   DESCRIPTION
			   "This object provides the CRC code of bank 0."
			   ::= { gx2Rx200BX4FactoryEntry 4}

		rx4bank1CRC          		OBJECT-TYPE
			   SYNTAX       		INTEGER
			   ACCESS           	read-only
			   STATUS           	mandatory
			   DESCRIPTION
			   "This object provides the CRC code of bank 1."
			   ::= { gx2Rx200BX4FactoryEntry 5}

		rx4prgEEPROMByte          		OBJECT-TYPE
			   SYNTAX       		INTEGER
			   ACCESS           	read-only
			   STATUS           	mandatory
			   DESCRIPTION
			   "This object indicates if the EEPROM has been programmed"
			   ::= { gx2Rx200BX4FactoryEntry 6}

		rx4factoryCRC          		OBJECT-TYPE
			   SYNTAX       		INTEGER
			   ACCESS           	read-only
			   STATUS           	mandatory
			   DESCRIPTION
			   "This object provides the CRC code for the Factory data."
			   ::= { gx2Rx200BX4FactoryEntry 7}

		rx4calculateCRC          		OBJECT-TYPE
			   SYNTAX       		INTEGER
					    		{
							factory(1),
							calibration(2),
							alarm(3),
							tempComp(4)
					    		}
			   ACCESS           	read-only
			   STATUS           	mandatory
			   DESCRIPTION
			   "This object indicates which of the Emnums will have the CRC calculated."
			   ::= { gx2Rx200BX4FactoryEntry 8}

		rx4hourMeter          		OBJECT-TYPE
			   SYNTAX       		INTEGER
			   ACCESS           	read-only
			   STATUS           	mandatory
			   DESCRIPTION
			   "This object provides the hour meter reading of the module."
			   ::= { gx2Rx200BX4FactoryEntry 9}

		rx4flashPrgCntA          		OBJECT-TYPE
			   SYNTAX       		INTEGER
			   ACCESS           	read-only
			   STATUS           	mandatory
			   DESCRIPTION
			   "This object provides the number of times the flash has been 
                      programmed on side A."
			   ::= { gx2Rx200BX4FactoryEntry 10}

		rx4flashPrgCntB          		OBJECT-TYPE
			   SYNTAX       		INTEGER
			   ACCESS           	read-only
			   STATUS           	mandatory
			   DESCRIPTION
			   "This object provides the number of times the flash has been 
                      programmed on side B."
			   ::= { gx2Rx200BX4FactoryEntry 11}

		rx4fwRev0     		     		OBJECT-TYPE
			   SYNTAX       		DisplayString (SIZE (0..80))
			   ACCESS           	read-only
			   STATUS           	mandatory
			   DESCRIPTION
			   "This object provides the Revision of the firmware stores in bank 0."
			   ::= { gx2Rx200BX4FactoryEntry 12}

		rx4fwRev1     		     		OBJECT-TYPE
			   SYNTAX       		DisplayString (SIZE (0..80))
			   ACCESS           	read-only
			   STATUS           	mandatory
			   DESCRIPTION
			   "This object provides the Revision of the firmware stores in bank 1."
			   ::= { gx2Rx200BX4FactoryEntry 13}


-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************
-- **************************************************************************
--                              Rx200BX4 Module traps
-- **************************************************************************
   trapRx200BX4ConfigChangeInteger TRAP-TYPE
       ENTERPRISE gx2Rx200BX4
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapRx200BX4ConfigChangeDisplayString TRAP-TYPE
       ENTERPRISE gx2Rx200BX4
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
  
  trapRx200BX4OpticalPower1Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Receiver's channel 1 Optical Power parameter 
	 goes out of range.
	 trapAdditionalInfoInteger variable contains current reading of 
	 the this parameter."
  ::= 3

  trapRx200BX4OpticalPower2Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Receiver's channel 2  Optical Power parameter 
	 goes out of range.
	 trapAdditionalInfoInteger variable contains current reading of 
	 the this parameter."
  ::= 4

  trapRx200BX4OpticalPower3Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Receiver's channel 3 Optical Power parameter 
	 goes out of range.
	 trapAdditionalInfoInteger variable contains current reading of 
	 the this parameter."
  ::= 5

  trapRx200BX4OpticalPower4Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Receiver's channel 4 Optical Power parameter 
	 goes out of range.
	 trapAdditionalInfoInteger variable contains current reading of 
	 the this parameter."
  ::= 6

  trapRx200BX4ModuleTemperatureAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx200BX4 Modules Temperature goes out of range.
	 trapAdditionalInfoInteger variable contains current reading of 
	 the this parameter."
  ::= 7

  trapRx200BX4FanCurrentAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx200BX4 Modules Fan Currrent parameter 
	 goes out of range. trapAdditionalInfoInteger variable contains current reading of 
	 the this parameter."
  ::= 8

  trapRx200BX4Plus12CurrentAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx200BX4 Modules positive 12 volt current parameter 
	 goes out of range. trapAdditionalInfoInteger variable contains current reading of 
	 the this parameter."
  ::= 9

  trapRx200BX4Boot0Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx200BX4 Modules Bank 0 Boot sequence has detected an error.
       trapAdditionalInfoInteger variable contains current reading of 
	 the this parameter."
  ::= 10

  trapRx200BX4Boot1Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx200BX4 Modules Bank 1 Boot sequence has detected an error.
       trapAdditionalInfoInteger variable contains current reading of 
	 the this parameter."
  ::= 11

  trapRx200BX4FlashAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Rx200BX4 Modules boot or flash programming sequence has 
       detected a Flash error. trapAdditionalInfoInteger variable contains current reading of 
	 the this parameter."
  ::= 12

  trapRx200BX4AlarmDataCRCAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Module detects an error calculating the alarm limit CRC.
       trapAdditionalInfoInteger variable contains current reading of the this parameter."
  ::= 13

  trapRx200BX4FactoryDataCRCAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Module detects an error calculating the Factory data CRC.
       trapAdditionalInfoInteger variable contains current reading of the this parameter."
  ::= 14

  trapRx200BX4CalDataCRCAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Module detects an error calculating the Calibration data CRC.
       trapAdditionalInfoInteger variable contains current reading of the this parameter."
  ::= 15

  trapRx200BX4DefaultAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Module is reset to it's factory default state.
       trapAdditionalInfoInteger variable contains current reading of the this parameter."
  ::= 16

  trapRx200BX4Mode1Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Modules receiver 1 mode is changed from manual or AGC to off and back.
       trapAdditionalInfoInteger variable contains current reading of the this parameter."
  ::= 17

  trapRx200BX4Mode2Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Modules receiver 1 mode is changed from manual or AGC to off and back.
       trapAdditionalInfoInteger variable contains current reading of the this parameter."
  ::= 18

  trapRx200BX4Mode3Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Modules receiver 1 mode is changed from manual or AGC to off and back.
       trapAdditionalInfoInteger variable contains current reading of the this parameter."
  ::= 19

  trapRx200BX4Mode4Alarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Modules receiver 1 mode is changed from manual or AGC to off and back.
       trapAdditionalInfoInteger variable contains current reading of the this parameter."
  ::= 20

  trapRx200BX4Output1SwitchedAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Module's receiver 1 output to the RF Switch Module changes state 
       from good to bad or bad to good. trapAdditionalInfoInteger variable contains current reading 
       of the this parameter."
  ::= 21

  trapRx200BX4Output2SwitchedAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Module's receiver 2 output to the RF Switch Module changes state 
       from good to bad or bad to good. trapAdditionalInfoInteger variable contains current reading 
       of the this parameter."
  ::= 22

  trapRx200BX4Output3SwitchedAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Module's receiver 3 output to the RF Switch Module changes state 
       from good to bad or bad to good. trapAdditionalInfoInteger variable contains current reading 
       of the this parameter."
  ::= 23

  trapRx200BX4Output4SwitchedAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the Rx200BX4 Module's receiver 4 output to the RF Switch Module changes state 
       from good to bad or bad to good. trapAdditionalInfoInteger variable contains current reading 
       of the this parameter."
  ::= 24

  trapRx200BX4RX1StatusAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when receiver 1 of the Rx200BX4 Module output is turned on or off."
  ::= 25

  trapRx200BX4RX2StatusAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when receiver 2 of the Rx200BX4 Module output is turned on or off."
  ::= 26

  trapRx200BX4RX3StatusAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when receiver 3 of the Rx200BX4 Module output is turned on or off."
  ::= 27

  trapRx200BX4RX4StatusAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when receiver 4 of the Rx200BX4 Module output is turned on or off."
  ::= 28

  trapRx200BX4BackupCableAlarm TRAP-TYPE
	ENTERPRISE gx2Rx200BX4
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
      DESCRIPTION
      "This trap is issued when the slave receiver loses connection to the master receiver."
  ::= 29

  END
