-- file automatically created


TELDAT-TRAP-ACL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


aclTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ACL event subsystem."
    REVISION "201401200930Z"
    DESCRIPTION "Initial implementation"
        ::= { telEventTraps 240 }


aclEventsGroup	OBJECT IDENTIFIER	::= { aclTrapsMIB 1 }

aclNotifications	OBJECT IDENTIFIER	::= { aclTrapsMIB 2 }
aclNotificationsPrefix	OBJECT IDENTIFIER	::= { aclNotifications 0 }

aclEventObjects1 OBJECT-IDENTITY
    STATUS current
    DESCRIPTION
        "Event ACL.1
        Per packet trace (free format)."
    ::= { aclEventsGroup 1 }

acl1_cache OBJECT-TYPE
    SYNTAX DisplayString
    MAX-ACCESS accessible-for-notify
    STATUS current
    DESCRIPTION
        "Parameter 'cache' in event ACL.1"
    ::= { aclEventObjects1 1 }

acl1_trace OBJECT-TYPE
    SYNTAX DisplayString
    MAX-ACCESS accessible-for-notify
    STATUS current
    DESCRIPTION
        "Parameter 'trace' in event ACL.1"
    ::= { aclEventObjects1 2 }

aclEventObjects2 OBJECT-IDENTITY
    STATUS current
    DESCRIPTION
        "Event ACL.2
        Usual operation trace (free format)."
    ::= { aclEventsGroup 2 }

acl2_cache OBJECT-TYPE
    SYNTAX DisplayString
    MAX-ACCESS accessible-for-notify
    STATUS current
    DESCRIPTION
        "Parameter 'cache' in event ACL.2"
    ::= { aclEventObjects2 1 }

acl2_trace OBJECT-TYPE
    SYNTAX DisplayString
    MAX-ACCESS accessible-for-notify
    STATUS current
    DESCRIPTION
        "Parameter 'trace' in event ACL.2"
    ::= { aclEventObjects2 2 }

aclEventObjects3 OBJECT-IDENTITY
    STATUS current
    DESCRIPTION
        "Event ACL.3
        Error (free format)."
    ::= { aclEventsGroup 3 }

acl3_cache OBJECT-TYPE
    SYNTAX DisplayString
    MAX-ACCESS accessible-for-notify
    STATUS current
    DESCRIPTION
        "Parameter 'cache' in event ACL.3"
    ::= { aclEventObjects3 1 }

acl3_error OBJECT-TYPE
    SYNTAX DisplayString
    MAX-ACCESS accessible-for-notify
    STATUS current
    DESCRIPTION
        "Parameter 'error' in event ACL.3"
    ::= { aclEventObjects3 2 }


aclNotification1 NOTIFICATION-TYPE
    OBJECTS { 
              acl1_cache, 
              acl1_trace 
            }
    STATUS current
    DESCRIPTION
        "Notification of Event ACL.1

        Message: 'Cache $1 - $2'

        Parameters list:
              $1: acl1_cache
              $2: acl1_trace

        Per packet trace (free format)."
    ::= { aclNotificationsPrefix 1 }

aclNotification2 NOTIFICATION-TYPE
    OBJECTS { 
              acl2_cache, 
              acl2_trace 
            }
    STATUS current
    DESCRIPTION
        "Notification of Event ACL.2

        Message: 'Cache $1 - $2'

        Parameters list:
              $1: acl2_cache
              $2: acl2_trace

        Usual operation trace (free format)."
    ::= { aclNotificationsPrefix 2 }

aclNotification3 NOTIFICATION-TYPE
    OBJECTS { 
              acl3_cache, 
              acl3_error 
            }
    STATUS current
    DESCRIPTION
        "Notification of Event ACL.3

        Message: 'Cache $1 Error - $2'

        Parameters list:
              $1: acl3_cache
              $2: acl3_error

        Error (free format)."
    ::= { aclNotificationsPrefix 3 }


END
