-- =============================================================================
-- Copyright (C) 2009 by HUAWEI TECHNOLOGIES. All rights reserved.
--    
-- Description: The MIB is designed to get IPSec tunnels' statistic information. 
-- Reference: Huawei Enterprise MIB
-- Version: 1.0
-- History: 
--          V1.0 The initial version created by LiShengbai 90004270. 
-- =============================================================================

HUAWEI-SECURITY-TRUNK-MIB DEFINITIONS ::= BEGIN
 
	IMPORTS    
	        Integer32, OBJECT-TYPE            
            FROM SNMPv2-SMI
    		enterprises			
		            FROM RFC1155-SMI; 

    hwTrunk MODULE-IDENTITY 
		        LAST-UPDATED "200912160900Z"        -- December 16, 2009 at 09:00 GMT
		        ORGANIZATION 
		            "Huawei Symantec Technologies Co., Ltd."
		        CONTACT-INFO 
		            "3rd Floor,Section D, Keshi Building, No.28, Xinxi Rd., Shangdi,
		         	 Hai-Dian District Beijing P.R. China
			         Zip:100085
			         Http://www.huaweisymantec.com
                     "
		        DESCRIPTION 
		            "V1.00
			         The Trunk mib is for Eudemon and USG product series."

		        ::= { hwSecurity 33 }
           
		
-- ===============================================
-- Node definitions
-- ===============================================
	    
	    	-- 1.3.6.1.4.1.2011
		huawei OBJECT IDENTIFIER ::= { enterprises 2011 }
	        
		-- 1.3.6.1.4.1.2011.6
		huaweiUtility OBJECT IDENTIFIER ::= { huawei 6 }
	        
		-- 1.3.6.1.4.1.2011.6.122
		hwSecurity OBJECT IDENTIFIER ::= { huaweiUtility 122 }     
		       
		  
		hwTrunkNotification OBJECT IDENTIFIER ::= { hwTrunk 0 }  
		hwTrunkTrapObject OBJECT IDENTIFIER ::= { hwTrunkNotification 1 }   
		hwTrunkTraps OBJECT IDENTIFIER ::= { hwTrunkNotification 2 }


-- ===============================================
-- TrapObject.
-- ===============================================
 	        	        		
 		    trunkIfIndex  OBJECT-TYPE
	        	SYNTAX Integer32 
	        	MAX-ACCESS accessible-for-notify
	        	STATUS current
	        	DESCRIPTION
	            		"The index of the trunk interface."
	        	::= { hwTrunkTrapObject 1 }     
	        
	    	mainIfIndex OBJECT-TYPE
	        	SYNTAX Integer32 
	        	MAX-ACCESS accessible-for-notify
	       	 	STATUS current
	        	DESCRIPTION
	            		"The index of the main interface."
	        	::= { hwTrunkTrapObject 2 }  
	        
	        standbyIfIndex OBJECT-TYPE
	        	SYNTAX Integer32 
	        	MAX-ACCESS accessible-for-notify
	       	 	STATUS current
	        	DESCRIPTION
	            		"The index of the standby interface."
	        	::= { hwTrunkTrapObject 3 }
	        	
	    	trunkIfName OBJECT-TYPE
	        	SYNTAX OCTET STRING (SIZE (0..255))
	        	MAX-ACCESS accessible-for-notify
	        	STATUS current
	        	DESCRIPTION
	            		"The name of the trunk interface."
	        	::= { hwTrunkTrapObject 4 }   
	        	    	
	        mainIfName OBJECT-TYPE
	        	SYNTAX OCTET STRING (SIZE (0..255))
	        	MAX-ACCESS accessible-for-notify
	        	STATUS current
	        	DESCRIPTION
	            		"The name of the main interface."
	        	::= { hwTrunkTrapObject 5 }   
	        
	        standbyIfName OBJECT-TYPE
	        	SYNTAX OCTET STRING (SIZE (0..255))
	        	MAX-ACCESS accessible-for-notify
	        	STATUS current
	        	DESCRIPTION
	            		"The name of the standby interface."
	        	::= { hwTrunkTrapObject 6 } 
	        
            
             mainIfAdminStatus OBJECT-TYPE
	        	SYNTAX  INTEGER {
                up(1),
                down(2),
                testing(3)
                } 
	        	MAX-ACCESS accessible-for-notify
	       	 	STATUS current
	        	DESCRIPTION
	            		"The current administrant state of the main interface."
	        	::= { hwTrunkTrapObject 7 }   
	        	
	         mainIfOperStatus OBJECT-TYPE
	        	SYNTAX  INTEGER {
                up(1), 
			 	down(2), 
			 	testing(3),
			 	unknown(4), 
			 	dormant(5), 
			 	notPresent(6), 
			 	lowerLayerDown(7)                
 	            } 
	        	MAX-ACCESS accessible-for-notify
	       	 	STATUS current
	        	DESCRIPTION
	            		"The current operational state of the main interface."
	        	::= { hwTrunkTrapObject 8 }
	        
-- ===============================================
-- definition of traps.      
-- ===============================================                        
	         hwTrunkPortSwitch NOTIFICATION-TYPE
			OBJECTS { 
				trunkIfIndex,
				mainIfIndex,
				standbyIfIndex,
				trunkIfName,
				mainIfName,
				standbyIfName,
				mainIfAdminStatus,
				mainIfOperStatus  
			        }
			STATUS     current
			DESCRIPTION
			    "Physical ports of Trunk switch over."
			::= { hwTrunkTraps 1}
			
	                   			
	END
