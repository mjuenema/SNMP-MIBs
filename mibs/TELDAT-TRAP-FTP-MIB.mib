-- file automatically created


TELDAT-TRAP-FTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ftpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the FTP event subsystem."
    REVISION "201401200930Z"
    DESCRIPTION "Initial implementation"
        ::= { telEventTraps 80 }


ftpEventsGroup	OBJECT IDENTIFIER	::= { ftpTrapsMIB 1 }

ftpNotifications	OBJECT IDENTIFIER	::= { ftpTrapsMIB 2 }
ftpNotificationsPrefix	OBJECT IDENTIFIER	::= { ftpNotifications 0 }

ftpEventObjects3 OBJECT-IDENTITY
    STATUS current
    DESCRIPTION
        "Event FTP.3
        FTP has received an FTP command."
    ::= { ftpEventsGroup 3 }

ftp3_ftp_command_string OBJECT-TYPE
    SYNTAX DisplayString
    MAX-ACCESS accessible-for-notify
    STATUS current
    DESCRIPTION
        "Parameter 'ftp_command_string' in event FTP.3"
    ::= { ftpEventObjects3 1 }

ftpEventObjects4 OBJECT-IDENTITY
    STATUS current
    DESCRIPTION
        "Event FTP.4
        FTP return a result code for a command."
    ::= { ftpEventsGroup 4 }

ftp4_ftp_reply_code OBJECT-TYPE
    SYNTAX Integer32
    MAX-ACCESS accessible-for-notify
    STATUS current
    DESCRIPTION
        "Parameter 'ftp_reply_code' in event FTP.4"
    ::= { ftpEventObjects4 1 }

ftp4_ftp_reply_string OBJECT-TYPE
    SYNTAX DisplayString
    MAX-ACCESS accessible-for-notify
    STATUS current
    DESCRIPTION
        "Parameter 'ftp_reply_string' in event FTP.4"
    ::= { ftpEventObjects4 2 }


ftpNotification1 NOTIFICATION-TYPE
    STATUS current
    DESCRIPTION
        "Notification of Event FTP.1

        Message: 'received connection request'

        FTP has recevied a connection request from a remote client."
    ::= { ftpNotificationsPrefix 1 }

ftpNotification2 NOTIFICATION-TYPE
    STATUS current
    DESCRIPTION
        "Notification of Event FTP.2

        Message: 'received disconnect indication'

        FTP has received a disconnection indication from a remote client."
    ::= { ftpNotificationsPrefix 2 }

ftpNotification3 NOTIFICATION-TYPE
    OBJECTS { 
              ftp3_ftp_command_string 
            }
    STATUS current
    DESCRIPTION
        "Notification of Event FTP.3

        Message: 'received command $1'

        Parameters list:
              $1: ftp3_ftp_command_string

        FTP has received an FTP command."
    ::= { ftpNotificationsPrefix 3 }

ftpNotification4 NOTIFICATION-TYPE
    OBJECTS { 
              ftp4_ftp_reply_code, 
              ftp4_ftp_reply_string 
            }
    STATUS current
    DESCRIPTION
        "Notification of Event FTP.4

        Message: 'reply code = $1  text = $2'

        Parameters list:
              $1: ftp4_ftp_reply_code
              $2: ftp4_ftp_reply_string

        FTP return a result code for a command."
    ::= { ftpNotificationsPrefix 4 }


END
