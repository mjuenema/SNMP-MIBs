-- file automatically created


TELDAT-TRAP-STUN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


stunTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the STUN event subsystem."
    REVISION "201401200930Z"
    DESCRIPTION "Initial implementation"
        ::= { telEventTraps 187 }


stunEventsGroup	OBJECT IDENTIFIER	::= { stunTrapsMIB 1 }

stunNotifications	OBJECT IDENTIFIER	::= { stunTrapsMIB 2 }
stunNotificationsPrefix	OBJECT IDENTIFIER	::= { stunNotifications 0 }

stunEventObjects1 OBJECT-IDENTITY
    STATUS current
    DESCRIPTION
        "Event STUN.1
        client state changed"
    ::= { stunEventsGroup 1 }

stun1_state OBJECT-TYPE
    SYNTAX DisplayString
    MAX-ACCESS accessible-for-notify
    STATUS current
    DESCRIPTION
        "Parameter 'state' in event STUN.1"
    ::= { stunEventObjects1 1 }

stunEventObjects2 OBJECT-IDENTITY
    STATUS current
    DESCRIPTION
        "Event STUN.2
        stun request sent"
    ::= { stunEventsGroup 2 }

stun2_ip OBJECT-TYPE
    SYNTAX IpAddress
    MAX-ACCESS accessible-for-notify
    STATUS current
    DESCRIPTION
        "Parameter 'ip' in event STUN.2"
    ::= { stunEventObjects2 1 }

stun2_port OBJECT-TYPE
    SYNTAX Integer32
    MAX-ACCESS accessible-for-notify
    STATUS current
    DESCRIPTION
        "Parameter 'port' in event STUN.2"
    ::= { stunEventObjects2 2 }

stun2_id OBJECT-TYPE
    SYNTAX DisplayString
    MAX-ACCESS accessible-for-notify
    STATUS current
    DESCRIPTION
        "Parameter 'id' in event STUN.2"
    ::= { stunEventObjects2 3 }

stunEventObjects3 OBJECT-IDENTITY
    STATUS current
    DESCRIPTION
        "Event STUN.3
        stun message received"
    ::= { stunEventsGroup 3 }

stun3_type OBJECT-TYPE
    SYNTAX DisplayString
    MAX-ACCESS accessible-for-notify
    STATUS current
    DESCRIPTION
        "Parameter 'type' in event STUN.3"
    ::= { stunEventObjects3 1 }

stun3_id OBJECT-TYPE
    SYNTAX DisplayString
    MAX-ACCESS accessible-for-notify
    STATUS current
    DESCRIPTION
        "Parameter 'id' in event STUN.3"
    ::= { stunEventObjects3 2 }

stun3_ip OBJECT-TYPE
    SYNTAX IpAddress
    MAX-ACCESS accessible-for-notify
    STATUS current
    DESCRIPTION
        "Parameter 'ip' in event STUN.3"
    ::= { stunEventObjects3 3 }

stun3_port OBJECT-TYPE
    SYNTAX Integer32
    MAX-ACCESS accessible-for-notify
    STATUS current
    DESCRIPTION
        "Parameter 'port' in event STUN.3"
    ::= { stunEventObjects3 4 }


stunNotification1 NOTIFICATION-TYPE
    OBJECTS { 
              stun1_state 
            }
    STATUS current
    DESCRIPTION
        "Notification of Event STUN.1

        Message: 'Client $1'

        Parameters list:
              $1: stun1_state

        client state changed"
    ::= { stunNotificationsPrefix 1 }

stunNotification2 NOTIFICATION-TYPE
    OBJECTS { 
              stun2_ip, 
              stun2_port,
              stun2_id 
            }
    STATUS current
    DESCRIPTION
        "Notification of Event STUN.2

        Message: 'Request sent to $1:$2 id $3'

        Parameters list:
              $1: stun2_ip
              $2: stun2_port
              $3: stun2_id

        stun request sent"
    ::= { stunNotificationsPrefix 2 }

stunNotification3 NOTIFICATION-TYPE
    OBJECTS { 
              stun3_type, 
              stun3_id,
              stun3_ip,
              stun3_port 
            }
    STATUS current
    DESCRIPTION
        "Notification of Event STUN.3

        Message: 'Msg $1 rcvd, id $2 from $3:$4'

        Parameters list:
              $1: stun3_type
              $2: stun3_id
              $3: stun3_ip
              $4: stun3_port

        stun message received"
    ::= { stunNotificationsPrefix 3 }


END
