-- file automatically created


TELDAT-TRAP-SYNC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


syncTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SYNC event subsystem."
    REVISION "201401200930Z"
    DESCRIPTION "Initial implementation"
        ::= { telEventTraps 151 }


syncEventsGroup	OBJECT IDENTIFIER	::= { syncTrapsMIB 1 }

syncNotifications	OBJECT IDENTIFIER	::= { syncTrapsMIB 2 }
syncNotificationsPrefix	OBJECT IDENTIFIER	::= { syncNotifications 0 }

syncEventObjects1 OBJECT-IDENTITY
    STATUS current
    DESCRIPTION
        "Event SYNC.1
        Selftest completed succesfully."
    ::= { syncEventsGroup 1 }

sync1_interface OBJECT-TYPE
    SYNTAX DisplayString
    MAX-ACCESS accessible-for-notify
    STATUS current
    DESCRIPTION
        "Parameter 'interface' in event SYNC.1"
    ::= { syncEventObjects1 1 }

syncEventObjects2 OBJECT-IDENTITY
    STATUS current
    DESCRIPTION
        "Event SYNC.2
        Maintenance failure."
    ::= { syncEventsGroup 2 }

sync2_interface OBJECT-TYPE
    SYNTAX DisplayString
    MAX-ACCESS accessible-for-notify
    STATUS current
    DESCRIPTION
        "Parameter 'interface' in event SYNC.2"
    ::= { syncEventObjects2 1 }

syncEventObjects3 OBJECT-IDENTITY
    STATUS current
    DESCRIPTION
        "Event SYNC.3
        When configured in totally transparent mode, if automatic resynchronization
        is enabled, this notices that the interface is not synchronized and is
        going down to resynchronize."
    ::= { syncEventsGroup 3 }

sync3_interface OBJECT-TYPE
    SYNTAX DisplayString
    MAX-ACCESS accessible-for-notify
    STATUS current
    DESCRIPTION
        "Parameter 'interface' in event SYNC.3"
    ::= { syncEventObjects3 1 }


syncNotification1 NOTIFICATION-TYPE
    OBJECTS { 
              sync1_interface 
            }
    STATUS current
    DESCRIPTION
        "Notification of Event SYNC.1

        Message: 'Serial Port came up sucessfully on interface $1'

        Parameters list:
              $1: sync1_interface

        Selftest completed succesfully."
    ::= { syncNotificationsPrefix 1 }

syncNotification2 NOTIFICATION-TYPE
    OBJECTS { 
              sync2_interface 
            }
    STATUS current
    DESCRIPTION
        "Notification of Event SYNC.2

        Message: 'Maintenance failure on interface $1'

        Parameters list:
              $1: sync2_interface

        Maintenance failure."
    ::= { syncNotificationsPrefix 2 }

syncNotification3 NOTIFICATION-TYPE
    OBJECTS { 
              sync3_interface 
            }
    STATUS current
    DESCRIPTION
        "Notification of Event SYNC.3

        Message: 'Resynchronizing interface $1'

        Parameters list:
              $1: sync3_interface

        When configured in totally transparent mode, if automatic resynchronization
        is enabled, this notices that the interface is not synchronized and is
        going down to resynchronize."
    ::= { syncNotificationsPrefix 3 }


END
