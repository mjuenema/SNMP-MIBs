--
-- EXTREME-SUMMIT-WM-BRANCH-OFFICE-MIB.my
-- MIB generated by MG-SOFT Visual MIB Builder Version 4.0 Build 349
-- Friday, September 02, 2005 at 17:14:32
--

	EXTREME-SUMMIT-WM-BRANCH-OFFICE-MIB DEFINITIONS ::= BEGIN
 
		IMPORTS
			altitudeIndex			
				FROM EXTREME-SUMMIT-WM-MIB			
			summitWMMgmt, summitWMModules			
				FROM EXTREME-SUMMIT-WM-SMI			
			OBJECT-GROUP, MODULE-COMPLIANCE			
				FROM SNMPv2-CONF			
			IpAddress, Integer32, OBJECT-TYPE, MODULE-IDENTITY			
				FROM SNMPv2-SMI			
			RowStatus			
				FROM SNMPv2-TC;
	
	
--  September 01, 2005 at 02:37 GMT
		-- 1.3.6.1.4.1.1916.5.5.4
		summitWMBranchOfficeMIB MODULE-IDENTITY 
			LAST-UPDATED "200509010237Z"		-- September 01, 2005 at 02:37 GMT
			ORGANIZATION 
				"Extreme Networks, Inc."
			CONTACT-INFO 
				"www.extremenetworks.com"
			DESCRIPTION 
				"Branch office configuration MIB for the Summit WM switch"
			REVISION  "200509010237Z"		-- September 01, 2005 at 02:37 GMT
                     DESCRIPTION
                                "Initial version."
			::= { summitWMModules 4 }

		
	
	
--
-- Node definitions
--
	
		-- 1.3.6.1.4.1.1916.5.3.22
		summitWMBranchOfficeMib OBJECT IDENTIFIER ::= { summitWMMgmt 22 }

		
		-- 1.3.6.1.4.1.1916.5.3.22.1
		branchOfficeObjects OBJECT IDENTIFIER ::= { summitWMBranchOfficeMib 1 }

		
		-- 1.3.6.1.4.1.1916.5.3.22.1.1
		branchOfficeTable OBJECT-TYPE
			SYNTAX SEQUENCE OF BranchOfficeEntry
			MAX-ACCESS not-accessible
			STATUS current
			DESCRIPTION
				"Table of branch office configuration values for the access points."
			::= { branchOfficeObjects 1 }

		
		-- 1.3.6.1.4.1.1916.5.3.22.1.1.1
		branchOfficeEntry OBJECT-TYPE
			SYNTAX BranchOfficeEntry
			MAX-ACCESS not-accessible
			STATUS current
			DESCRIPTION
				"Branch office configuration values for a specific access point."
			INDEX { altitudeIndex }
			::= { branchOfficeTable 1 }

		
		BranchOfficeEntry ::=
			SEQUENCE { 
				boConnectMode
					INTEGER,
				boIpAllocation
					INTEGER,
				boStaticIpAddress
					IpAddress,
				boStaticNetmask
					IpAddress,
				boStaticGateway
					IpAddress,
				boRebootOnPollFailure
					Integer32
			 }

		-- 1.3.6.1.4.1.1916.5.3.22.1.1.1.1
		boConnectMode OBJECT-TYPE
			SYNTAX INTEGER
				{
				autoDiscovery(1),
				staticConnect(2)
				}
			MAX-ACCESS read-write
			STATUS current
			DESCRIPTION
				"Access point connection mode - use a static definition or service discovery."
			::= { branchOfficeEntry 1 }

		
		-- 1.3.6.1.4.1.1916.5.3.22.1.1.1.2
		boIpAllocation OBJECT-TYPE
			SYNTAX INTEGER
				{
				dhcp(1),
				static(2)
				}
			MAX-ACCESS read-write
			STATUS current
			DESCRIPTION
				"Indicates if access point is to use DHCP to acquire an IP address or has a statically configured IP address."
			::= { branchOfficeEntry 2 }

		
		-- 1.3.6.1.4.1.1916.5.3.22.1.1.1.3
		boStaticIpAddress OBJECT-TYPE
			SYNTAX IpAddress
			MAX-ACCESS read-write
			STATUS current
			DESCRIPTION
				"If access point is statically configured, contains the IP addres."
			::= { branchOfficeEntry 3 }

		
		-- 1.3.6.1.4.1.1916.5.3.22.1.1.1.4
		boStaticNetmask OBJECT-TYPE
			SYNTAX IpAddress
			MAX-ACCESS read-write
			STATUS current
			DESCRIPTION
				"Netmask for the access point if statically configured."
			::= { branchOfficeEntry 4 }

		
		-- 1.3.6.1.4.1.1916.5.3.22.1.1.1.5
		boStaticGateway OBJECT-TYPE
			SYNTAX IpAddress
			MAX-ACCESS read-write
			STATUS current
			DESCRIPTION
				"Default gateway for the access point if statically configured."
			::= { branchOfficeEntry 5 }

		
		-- 1.3.6.1.4.1.1916.5.3.22.1.1.1.6
		boRebootOnPollFailure OBJECT-TYPE
			SYNTAX Integer32
			MAX-ACCESS read-write
			STATUS current
			DESCRIPTION
				"Indicates if access point should reboot on a poll failure (disabling wireless access) or continue to provide limited local wireless service."
			::= { branchOfficeEntry 6 }

		
		-- 1.3.6.1.4.1.1916.5.3.22.1.2
		branchOfficeWMTable OBJECT-TYPE
			SYNTAX SEQUENCE OF BranchOfficeWMEntry
			MAX-ACCESS not-accessible
			STATUS current
			DESCRIPTION
				"Contains the list of access controller IP addressIf an access point has a static."
			::= { branchOfficeObjects 2 }

		
		-- 1.3.6.1.4.1.1916.5.3.22.1.2.1
		branchOfficeWMEntry OBJECT-TYPE
			SYNTAX BranchOfficeWMEntry
			MAX-ACCESS not-accessible
			STATUS current
			DESCRIPTION
				"The access controller search list for an access point."
			INDEX { altitudeIndex }
			::= { branchOfficeWMTable 1 }

		
		BranchOfficeWMEntry ::=
			SEQUENCE { 
				boWMConnectOrder
					Integer32,
				boWMIpAddress
					IpAddress,
				boWMRowStatus
					RowStatus
			 }

		-- 1.3.6.1.4.1.1916.5.3.22.1.2.1.1
		boWMConnectOrder OBJECT-TYPE
			SYNTAX Integer32
			MAX-ACCESS read-write
			STATUS current
			DESCRIPTION
				"The position of the access controller in the search list."
			::= { branchOfficeWMEntry 1 }

		
		-- 1.3.6.1.4.1.1916.5.3.22.1.2.1.2
		boWMIpAddress OBJECT-TYPE
			SYNTAX IpAddress
			MAX-ACCESS read-write
			STATUS current
			DESCRIPTION
				"IP address of the access controller."
			::= { branchOfficeWMEntry 2 }

		
		-- 1.3.6.1.4.1.1916.5.3.22.1.2.1.3
		boWMRowStatus OBJECT-TYPE
			SYNTAX RowStatus
			MAX-ACCESS read-write
			STATUS current
			DESCRIPTION
				"RowStatus attribute to control modification of branchOfficeWMTable."
			::= { branchOfficeWMEntry 3 }

		
		-- 1.3.6.1.4.1.1916.5.3.22.2
		summitWMBranchOfficeConformance OBJECT IDENTIFIER ::= { summitWMBranchOfficeMib 2 }

		
		-- 1.3.6.1.4.1.1916.5.3.22.2.1
		summitWMBranchOfficeGroup OBJECT-GROUP
			OBJECTS { boConnectMode, boIpAllocation, boStaticIpAddress, boStaticNetmask, boStaticGateway, 
				boWMConnectOrder, boWMIpAddress, boWMRowStatus, boRebootOnPollFailure }
			STATUS current
			DESCRIPTION 
				"Conformance group definitions for the branch office MIB."
			::= { summitWMBranchOfficeConformance 1 }

		
--  this module
		-- 1.3.6.1.4.1.1916.5.3.22.2.2
		summitWMBOConformance MODULE-COMPLIANCE
			STATUS current
			DESCRIPTION 
				"Compliance group definitions for the branch office MIB."
			MODULE -- this module
				MANDATORY-GROUPS { summitWMBranchOfficeGroup }
			::= { summitWMBranchOfficeConformance 2 }

		
	
	END
