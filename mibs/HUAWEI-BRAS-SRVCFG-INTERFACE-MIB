--  =================================================================
-- Copyright (C) 2003 by  HUAWEI TECHNOLOGIES. All rights reserved.
-- 
-- Description:HUAWEI-BRAS-SRVCFGINTERFACE-MIB
-- Reference:
-- Version: V1.0
-- History:
--         v1.1
--         modified by huangjun 2009-12-08
      
-- =================================================================

	HUAWEI-BRAS-SRVCFGINTERFACE-MIB DEFINITIONS ::= BEGIN
 
		IMPORTS
		   hwBRASMib                     
                                FROM HUAWEI-MIB  
                        InterfaceIndex			
				                        FROM IF-MIB	 
                        EnabledStatus			
				                        FROM P-BRIDGE-MIB				                
                        MODULE-IDENTITY,MODULE-COMPLIANCE,OBJECT-GROUP,
                        IpAddress, Integer32, OBJECT-TYPE,Unsigned32                  
                                FROM SNMPv2-SMI                 
                        RowStatus, MacAddress, TruthValue, DisplayString                        
                                FROM SNMPv2-TC;
				
						
		hwBRASSrvcfgInterface MODULE-IDENTITY 
			LAST-UPDATED "200403041608Z"		-- March 04, 2004 at 16:08 GMT
			ORGANIZATION 
				"
				Huawei Technologies Co., Ltd.
				"
			CONTACT-INFO 
				"
				NanJing Institute,Huawei Technologies Co.,Ltd.
				HuiHong Mansion,No.91 BaiXia Rd.
				NanJing, P.R. of China
				Zipcode:210001
				 
				Http://www.huawei.com                                       
				E-mail:support@huawei.com 
				"
			DESCRIPTION 
				"The MIB contains objects of module SRVCFG INTERFACE."
			::= { hwBRASMib 1 }
		
	
	
--
-- Node definitions
--
		hwSrvcfgInterfaceMibObjects OBJECT IDENTIFIER ::= { hwBRASSrvcfgInterface 1 }
		
		hwBRASIfCfgTable OBJECT-TYPE
			SYNTAX SEQUENCE OF HwBRASIfCfgEntry
			MAX-ACCESS not-accessible
			STATUS current
			DESCRIPTION
				"BRAS interface configure table
				"
			::= { hwSrvcfgInterfaceMibObjects 1 }
		
		hwBRASIfCfgEntry OBJECT-TYPE
			SYNTAX HwBRASIfCfgEntry
			MAX-ACCESS not-accessible
			STATUS current
			DESCRIPTION
				"
				BRAS interface entry.
				"
			INDEX { hwBRASIfCfgIfIndex }
			::= { hwBRASIfCfgTable 1 }
		
		HwBRASIfCfgEntry ::=
			SEQUENCE { 
				hwBRASIfCfgIfIndex
					InterfaceIndex,
				hwBRASIfCfgAccessType
					INTEGER,
				hwBRASIfCfgBRASIfName
					DisplayString,
				hwBRASIfCfgPreAuthDomain
					DisplayString,
				hwBRASIfCfgAuthDomain
					DisplayString,
				hwBRASIfCfgForceAuthDomain
					INTEGER,
				hwBRASIfCfgAcctCpyRdSvr
					DisplayString,
				hwBRASIfCfgAuthMethod
					Integer32,
				hwBRASIfCfgNasPortType
					Integer32,
				hwBRASIfCfgLeaseName
					DisplayString,
				hwBRASIfCfgLeasePwd
					DisplayString,
				hwBRASIfCfgArpInterval
					Integer32,
				hwBRASIfCfgArpFailTimes
					Integer32,
				hwBRASIfCfgArpProxy
					TruthValue,
				hwBRASIfCfgRoamIsp
					TruthValue,
				hwBRASIfCfgDhcpBroadCast
					TruthValue,
				hwBRASIfCfgHostCar
					Integer32,
				hwBRASIfCfgRowStatus
					RowStatus,
				hwBRASIfCfgEapTrigger
					TruthValue,
				hwBRASIfCfgWlanSwitch
					Integer32,
				hwBRASIfCfgWlanAuthorization
					TruthValue,
				hwBRASIfCfgDhcpShortLease
					Integer32,
				hwBRASIfCfgRoamDomain
					DisplayString,
				hwBRASIfVsiName
					DisplayString,
				hwBRASIfCfgOption82
					TruthValue,
				hwBRASIfVpnInstance
					DisplayString,
				hwBRASIfCopyMulticasePerUser
					TruthValue,
				hwBRASIfCfgNDProxy
					TruthValue,
				hwBRASIfCfgVBasMAC
					MacAddress,
				hwBRASIfCfgVBasAuthMode
					INTEGER,
				hwBRASIfCfgPermitDomain1
					DisplayString,
				hwBRASIfCfgPermitDomain2
					DisplayString,
				hwBRASIfCfgPermitDomain3
					DisplayString,
				hwBRASIfCfgPermitDomain4
					DisplayString,
				hwBRASIfCfgAccessDelayType
					INTEGER,
				hwBRASIfCfgTermlessDelayTime
					Integer32,
				hwBRASIfCfgOddMacDelayTime
					Integer32,
				hwBRASIfCfgEvenMacDelayTime
					Integer32,
				hwBRASIfCfgAccessNodeIdentify
					DisplayString,
				hwBRASIfCfgAniDelayTime
					Integer32,
				hwBRASIfCfgRemoteBackupProfile
					DisplayString,
				hwBRASIfCfgOption60
					TruthValue,
				hwBRASIfCfgIpTrigger
					TruthValue,
				hwBRASIfCfgArpTrigger
					TruthValue,
				hwBRASIfCfgWlanSSID
					TruthValue
			 }

		hwBRASIfCfgIfIndex OBJECT-TYPE
			SYNTAX InterfaceIndex
			MAX-ACCESS read-only
			STATUS current
			DESCRIPTION
				"
				This object indicates the index of a BRAS interface.
				"
			::= { hwBRASIfCfgEntry 1 }
		
		hwBRASIfCfgAccessType OBJECT-TYPE
			SYNTAX INTEGER
				{
				interface(0),
				l2subscriber(1),
				l2leasedline(2),
				l3leasedline(3),
				l2vpnleasedline(4),
				l3subscriber(6)
				}
			MAX-ACCESS read-write
			STATUS current
			DESCRIPTION
				"
				This object indicates the access-type of users on a BRAS interface.
				"
			::= { hwBRASIfCfgEntry 2 }
		
		hwBRASIfCfgBRASIfName OBJECT-TYPE
			SYNTAX DisplayString (SIZE (1..32))
			MAX-ACCESS read-write
			STATUS current
			DESCRIPTION
				"
				This object indicates the name of a BRAS interface.
				"
			::= { hwBRASIfCfgEntry 3 }
		
		hwBRASIfCfgPreAuthDomain OBJECT-TYPE
			SYNTAX DisplayString (SIZE (1..64))
			MAX-ACCESS read-write
			STATUS current
			DESCRIPTION
				"
				This object indicates the pre-authentication domain. 
				If the value is set to '--', it indicates that the default value is restored.
				"
			::= { hwBRASIfCfgEntry 4 }
		
		hwBRASIfCfgAuthDomain OBJECT-TYPE
			SYNTAX DisplayString (SIZE (1..64))
			MAX-ACCESS read-write
			STATUS current
			DESCRIPTION
				"
				This object indicates the authentication domain. 
				If the value is set to '--', it indicates that the default value is restored.
				"
			::= { hwBRASIfCfgEntry 5 }
		
		hwBRASIfCfgForceAuthDomain OBJECT-TYPE
			SYNTAX INTEGER
				{
				none(0),
				force(1),
				replace(2)
				}
			MAX-ACCESS read-write
			STATUS current
			DESCRIPTION
				"
				This object indicates the mode of replacing the authentication domain.
				"
			DEFVAL { 0 }
			::= { hwBRASIfCfgEntry 6 }
		
		hwBRASIfCfgAcctCpyRdSvr OBJECT-TYPE
			SYNTAX DisplayString (SIZE (1..32))
			MAX-ACCESS read-write
			STATUS current
			DESCRIPTION
				"
				This object indicates the accounting copy RADIUS server group.
				"
			::= { hwBRASIfCfgEntry 7 }
		
		hwBRASIfCfgAuthMethod OBJECT-TYPE
			SYNTAX Integer32 (1..16)
			MAX-ACCESS read-write
			STATUS current
			DESCRIPTION
				"
				authentication method:
				ppp(1)
				dot1x(2)
				web(4)
				fast(8)
				bind(16)
				"
			DEFVAL { 1 }
			::= { hwBRASIfCfgEntry 8 }
		
		hwBRASIfCfgNasPortType OBJECT-TYPE
			SYNTAX Integer32 (0..20)
			MAX-ACCESS read-write
			STATUS current
			DESCRIPTION
				"
				This object indicates the type of the access port.
				"
			::= { hwBRASIfCfgEntry 9 }
		
		hwBRASIfCfgLeaseName OBJECT-TYPE
			SYNTAX DisplayString (SIZE (1..129))
			MAX-ACCESS read-write
			STATUS current
			DESCRIPTION
				"
				This object indicates the name of the leased-line user.
				"
			::= { hwBRASIfCfgEntry 10 }
		
		hwBRASIfCfgLeasePwd OBJECT-TYPE
			SYNTAX DisplayString (SIZE (1..128))
			MAX-ACCESS read-write
			STATUS current
			DESCRIPTION
				"
				This object indicates the password of the leased-line user.
				"
			::= { hwBRASIfCfgEntry 11 }
		
		hwBRASIfCfgArpInterval OBJECT-TYPE
			SYNTAX Integer32 (0..121)
			MAX-ACCESS read-write
			STATUS current
			DESCRIPTION
				"
				This object indicates the ARP detection interval. 
				If the value is set to 121, it indicates that the default value is restored.
				"
			DEFVAL { 30 }
			::= { hwBRASIfCfgEntry 12 }
		
		hwBRASIfCfgArpFailTimes OBJECT-TYPE
			SYNTAX Integer32 (2..11)
			MAX-ACCESS read-write
			STATUS current
			DESCRIPTION
				"
				This object indicates the allowed number of continuous ARP detection failures. 
				If the value is set to 11, it indicates that the default value is restored.
				"
			DEFVAL { 5 }
			::= { hwBRASIfCfgEntry 13 }
		
		hwBRASIfCfgArpProxy OBJECT-TYPE
			SYNTAX TruthValue
			MAX-ACCESS read-write
			STATUS current
			DESCRIPTION
				"
				This object indicates whether proxy ARP is enabled.
				"
			DEFVAL { false }
			::= { hwBRASIfCfgEntry 14 }
		
		hwBRASIfCfgRoamIsp OBJECT-TYPE
			SYNTAX TruthValue
			MAX-ACCESS read-write
			STATUS current
			DESCRIPTION
				"
				This object indicates whether the roaming domain is enabled.
				"
			DEFVAL { false }
			::= { hwBRASIfCfgEntry 15 }
		
		hwBRASIfCfgDhcpBroadCast OBJECT-TYPE
			SYNTAX TruthValue
			MAX-ACCESS read-write
			STATUS current
			DESCRIPTION
				"
				This object indicates whether DHCP packets are transmitted in broadcast mode.
				"
			DEFVAL { false }
			::= { hwBRASIfCfgEntry 16 }
		
		hwBRASIfCfgHostCar OBJECT-TYPE
			SYNTAX Integer32 (0..16)
			MAX-ACCESS read-write
			STATUS current
			DESCRIPTION
				"
				"
			DEFVAL { 0 }
			::= { hwBRASIfCfgEntry 17 }
		
		hwBRASIfCfgRowStatus OBJECT-TYPE
			SYNTAX RowStatus
			MAX-ACCESS read-write
			STATUS current
			DESCRIPTION
				"
				This object indicates the row status.
				"
			::= { hwBRASIfCfgEntry 18 }
		
		hwBRASIfCfgEapTrigger OBJECT-TYPE
			SYNTAX TruthValue
			MAX-ACCESS read-write
			STATUS current
			DESCRIPTION
				"
				This object indicates whether to initiate an EAP authentication.
				"
			DEFVAL { false }
			::= { hwBRASIfCfgEntry 19 }
		
		hwBRASIfCfgWlanSwitch OBJECT-TYPE
			SYNTAX Integer32 (0..1)
			MAX-ACCESS read-write
			STATUS current
			DESCRIPTION
				"
				WLAN switch
				"
			DEFVAL { 0 }
			::= { hwBRASIfCfgEntry 20 }
		
		hwBRASIfCfgWlanAuthorization OBJECT-TYPE
			SYNTAX TruthValue
			MAX-ACCESS read-write
			STATUS current
			DESCRIPTION
				"
				This object indicates whether to perform AS authorization on WLAN users.
				"
			DEFVAL { false }
			::= { hwBRASIfCfgEntry 21 }
		
		hwBRASIfCfgDhcpShortLease OBJECT-TYPE
			SYNTAX Integer32 (9..240)
			MAX-ACCESS read-write
			STATUS current
			DESCRIPTION
				"
				"
			DEFVAL { 9 }
			::= { hwBRASIfCfgEntry 22 }
		
		hwBRASIfCfgRoamDomain OBJECT-TYPE
			SYNTAX DisplayString (SIZE (1..64))
			MAX-ACCESS read-write
			STATUS current
			DESCRIPTION
				"
				This object indicates the roaming domain for authentication.
				"
			::= { hwBRASIfCfgEntry 23 }
		
		hwBRASIfVsiName OBJECT-TYPE
			SYNTAX DisplayString (SIZE (1..20))
			MAX-ACCESS read-write
			STATUS current
			DESCRIPTION
				"
				VSI Name
				"
			::= { hwBRASIfCfgEntry 24 }
		
		hwBRASIfCfgOption82 OBJECT-TYPE
			SYNTAX TruthValue
			MAX-ACCESS read-write
			STATUS current
			DESCRIPTION
				"
				option82 switch
				"
			DEFVAL { false }
			::= { hwBRASIfCfgEntry 25 }
		
		hwBRASIfVpnInstance OBJECT-TYPE
			SYNTAX DisplayString (SIZE (1..31))
			MAX-ACCESS read-write
			STATUS current
			DESCRIPTION
				"
				VPN-instance name
				"
			::= { hwBRASIfCfgEntry 26 }
		
		hwBRASIfCopyMulticasePerUser OBJECT-TYPE
			SYNTAX TruthValue
			MAX-ACCESS read-write
			STATUS current
			DESCRIPTION
				"
				This object indicates whether to perform user-based multicast replication.
				"
			DEFVAL { false }
			::= { hwBRASIfCfgEntry 27 }
		
		hwBRASIfCfgNDProxy OBJECT-TYPE
			SYNTAX TruthValue
			MAX-ACCESS read-write
			STATUS current
			DESCRIPTION
				"
				This object indicates whether proxy ND is enabled.
				"
			DEFVAL { false }
			::= { hwBRASIfCfgEntry 28 }
		
		hwBRASIfCfgVBasMAC OBJECT-TYPE
			SYNTAX MacAddress
			MAX-ACCESS read-write
			STATUS current
			DESCRIPTION
				"
				This object indicates the MAC address of the VBAS.
				"
			::= { hwBRASIfCfgEntry 29 }
		
		hwBRASIfCfgVBasAuthMode OBJECT-TYPE
			SYNTAX INTEGER
				{
				ignore(0),
				reject(1)
				}
			MAX-ACCESS read-write
			STATUS current
			DESCRIPTION
				"
				This object indicates the authentication mode of the VBAS.
				"
			DEFVAL { 1 }
			::= { hwBRASIfCfgEntry 30 }
		
		hwBRASIfCfgPermitDomain1 OBJECT-TYPE
			SYNTAX DisplayString (SIZE (1..64))
			MAX-ACCESS read-write
			STATUS current
			DESCRIPTION
				"
				This object indicates domain 1 for user access on a BAS interface.
				"
			::= { hwBRASIfCfgEntry 31 }
		
		hwBRASIfCfgPermitDomain2 OBJECT-TYPE
			SYNTAX DisplayString (SIZE (1..64))
			MAX-ACCESS read-write
			STATUS current
			DESCRIPTION
				"
				This object indicates domain 2 for user access on a BAS interface.
				"
			::= { hwBRASIfCfgEntry 32 }
		
		hwBRASIfCfgPermitDomain3 OBJECT-TYPE
			SYNTAX DisplayString (SIZE (1..64))
			MAX-ACCESS read-write
			STATUS current
			DESCRIPTION
				"
				This object indicates domain 3 for user access on a BAS interface.
				"
			::= { hwBRASIfCfgEntry 33 }
		
		hwBRASIfCfgPermitDomain4 OBJECT-TYPE
			SYNTAX DisplayString (SIZE (1..64))
			MAX-ACCESS read-write
			STATUS current
			DESCRIPTION
				"
				This object indicates domain 4 for user access on a BAS interface.
				"
			::= { hwBRASIfCfgEntry 34 }
		
		hwBRASIfCfgAccessDelayType OBJECT-TYPE
			SYNTAX INTEGER
				{   
				none(0),
				termless(1),
				userinfomation(2),
				macaddress(3)
				}
			MAX-ACCESS read-write
			STATUS current
			DESCRIPTION
				"
				This object indicates the response delay type.
				"
			::= { hwBRASIfCfgEntry 35 }
		
		hwBRASIfCfgTermlessDelayTime OBJECT-TYPE
			SYNTAX Integer32 (0..255)
			MAX-ACCESS read-write
			STATUS current
			DESCRIPTION
				"
				This object indicates the response delay time without restrictions.
				"
			DEFVAL { 0 }
			::= { hwBRASIfCfgEntry 36 }
		
		hwBRASIfCfgOddMacDelayTime OBJECT-TYPE
			SYNTAX Integer32 (0..255)
			MAX-ACCESS read-write
			STATUS current
			DESCRIPTION
				"
				This object indicates the response delay based on the odd MAC.
				"
			DEFVAL { 0 }
			::= { hwBRASIfCfgEntry 37 }
		
		hwBRASIfCfgEvenMacDelayTime OBJECT-TYPE
			SYNTAX Integer32 (0..255)
			MAX-ACCESS read-write
			STATUS current
			DESCRIPTION
				"
				This object indicates the response delay based on the even MAC.
				"
			DEFVAL { 0 }
			::= { hwBRASIfCfgEntry 38 }
		
		hwBRASIfCfgAccessNodeIdentify OBJECT-TYPE
			SYNTAX DisplayString (SIZE (1..32))
			MAX-ACCESS read-write
			STATUS current
			DESCRIPTION
				"
				This object indicates the identifier of the access node.
				"
			::= { hwBRASIfCfgEntry 39 }
		
		hwBRASIfCfgAniDelayTime OBJECT-TYPE
			SYNTAX Integer32 (0..255)
			MAX-ACCESS read-write
			STATUS current
			DESCRIPTION
				"
				This object indicates the response delay based on the identifier of the access node.
				"
			DEFVAL { 0 }
			::= { hwBRASIfCfgEntry 40 }
		
		hwBRASIfCfgRemoteBackupProfile OBJECT-TYPE
			SYNTAX DisplayString (SIZE (1..32))
			MAX-ACCESS read-write
			STATUS current
			DESCRIPTION
				"
				remote-backup-profile
				"
			::= { hwBRASIfCfgEntry 42 }
		
		hwBRASIfCfgOption60 OBJECT-TYPE
			SYNTAX TruthValue
			MAX-ACCESS read-write
			STATUS current
			DESCRIPTION
				"
				option60 switch
				"
			DEFVAL { false }
			::= { hwBRASIfCfgEntry 43 }
		
		hwBRASIfCfgIpTrigger OBJECT-TYPE
			SYNTAX TruthValue
			MAX-ACCESS read-write
			STATUS current
			DESCRIPTION
				"
				set ip-trigger flag
				"
			DEFVAL { false }
			::= { hwBRASIfCfgEntry 44 }
		
		hwBRASIfCfgArpTrigger OBJECT-TYPE
			SYNTAX TruthValue
			MAX-ACCESS read-write
			STATUS current
			DESCRIPTION
				"
				set arp-trigger flag
				"
			DEFVAL { false }
			::= { hwBRASIfCfgEntry 45 }
		
		hwBRASIfCfgWlanSSID OBJECT-TYPE
			SYNTAX TruthValue
			MAX-ACCESS read-write
			STATUS current
			DESCRIPTION
				"
				set WLAN-ssid flag
				"
			DEFVAL { false }
			::= { hwBRASIfCfgEntry 46 }
		
		hwBRASIfVlanTable OBJECT-TYPE
			SYNTAX SEQUENCE OF HwBRASIfVlanEntry
			MAX-ACCESS not-accessible
			STATUS current
			DESCRIPTION
				"
				"
			::= { hwSrvcfgInterfaceMibObjects 2 }
		
		hwBRASIfVlanEntry OBJECT-TYPE
			SYNTAX HwBRASIfVlanEntry
			MAX-ACCESS not-accessible
			STATUS current
			DESCRIPTION
				"
				Description.
				"
			INDEX { hwBRASIfVlanIfIndex, hwBRASIfVlanVlanId, hwBRASIfQinQVlanID }
			::= { hwBRASIfVlanTable 1 }
		
		HwBRASIfVlanEntry ::=
			SEQUENCE { 
				hwBRASIfVlanIfIndex
					InterfaceIndex,
				hwBRASIfVlanVlanId
					Integer32,
				hwBRASIfVlanVlanNumber
					Integer32,
				hwBRASIfVlanAccessLimit
					Integer32,
				hwBRASIfVlanAccessNumber
					Integer32,
				hwBRASIfVlanBlock
					TruthValue,
				hwBRASIfVlanDevAccessNumber
					Integer32,
				hwBRASIfVlanSchedulerVcName
					DisplayString,
				hwBRASIfVlanSchedulerVcGroupName
					DisplayString,
				hwBRASIfVlanSchedulerVpGroupName
					DisplayString,
				hwBRASIfQinQVlanID
					Integer32
			 }

		hwBRASIfVlanIfIndex OBJECT-TYPE
			SYNTAX InterfaceIndex
			MAX-ACCESS read-only
			STATUS current
			DESCRIPTION
				"
				This object indicates the index of a BRAS interface.
				"
			::= { hwBRASIfVlanEntry 1 }
		
		hwBRASIfVlanVlanId OBJECT-TYPE
			SYNTAX Integer32 (1..4094)
			MAX-ACCESS read-only
			STATUS current
			DESCRIPTION
				"
				This object indicates the VLAN ID. 
				Note that only the primary interface can be assigned to VLAN 0.
				"
			::= { hwBRASIfVlanEntry 2 }
		
		hwBRASIfVlanVlanNumber OBJECT-TYPE
			SYNTAX Integer32 (0..4094)
			MAX-ACCESS read-write
			STATUS current
			DESCRIPTION
				"
				This object indicates the number of consecutive VLANs.
				"
			::= { hwBRASIfVlanEntry 3 }
		
		hwBRASIfVlanAccessLimit OBJECT-TYPE
			SYNTAX Integer32 (0..49153)
			MAX-ACCESS read-write
			STATUS current
			DESCRIPTION
				"
				This object indicates the upper limit of access users. 
				If the value is set to 49153, it indicates that the default value is restored.
				"
			DEFVAL { 49152 }
			::= { hwBRASIfVlanEntry 4 }
		
		hwBRASIfVlanAccessNumber OBJECT-TYPE
			SYNTAX Integer32 (0..49152)
			MAX-ACCESS read-only
			STATUS current
			DESCRIPTION
				"
				The VLAN access number, default is 49152. 
				"
			::= { hwBRASIfVlanEntry 5 }
		
		hwBRASIfVlanBlock OBJECT-TYPE
			SYNTAX TruthValue
			MAX-ACCESS read-write
			STATUS current
			DESCRIPTION
				"
				This object indicates whether the VLAN of the BRAS interface is blocked.
				"
			DEFVAL { false }
			::= { hwBRASIfVlanEntry 6 }
		
		hwBRASIfVlanDevAccessNumber OBJECT-TYPE
			SYNTAX Integer32 (0..4096)
			MAX-ACCESS read-only
			STATUS current
			DESCRIPTION
				"
				"
			::= { hwBRASIfVlanEntry 7 }
		
		hwBRASIfVlanSchedulerVcName OBJECT-TYPE
			SYNTAX DisplayString (SIZE (0..32))
			MAX-ACCESS read-write
			STATUS current
			DESCRIPTION
				"
				scheduler VC name
				"
			::= { hwBRASIfVlanEntry 8 }
		
		hwBRASIfVlanSchedulerVcGroupName OBJECT-TYPE
			SYNTAX DisplayString (SIZE (0..32))
			MAX-ACCESS read-write
			STATUS current
			DESCRIPTION
				"
				scheduler VC-group name
				"
			::= { hwBRASIfVlanEntry 9 }
		
		hwBRASIfVlanSchedulerVpGroupName OBJECT-TYPE
			SYNTAX DisplayString (SIZE (0..32))
			MAX-ACCESS read-write
			STATUS current
			DESCRIPTION
				"
				scheduler VP-group name
				"
			::= { hwBRASIfVlanEntry 10 }
		
		hwBRASIfQinQVlanID OBJECT-TYPE
			SYNTAX Integer32 (1..4094)
			MAX-ACCESS read-only
			STATUS current
			DESCRIPTION
				"
				QinQ VLAN
				"
			::= { hwBRASIfVlanEntry 11 }
		
		hwBRASIfPvcTable OBJECT-TYPE
			SYNTAX SEQUENCE OF HwBRASIfPvcEntry
			MAX-ACCESS not-accessible
			STATUS current
			DESCRIPTION
				"
				This object indicates the PVC table of the BAS interface.
				"
			::= { hwSrvcfgInterfaceMibObjects 3 }
		
		hwBRASIfPvcEntry OBJECT-TYPE
			SYNTAX HwBRASIfPvcEntry
			MAX-ACCESS not-accessible
			STATUS current
			DESCRIPTION
				"
				Description.
				"
			INDEX { hwBRASIfPvcIfIndex, hwBRASIfPvcVpi, hwBRASIfPvcVci }
			::= { hwBRASIfPvcTable 1 }
		
		HwBRASIfPvcEntry ::=
			SEQUENCE { 
				hwBRASIfPvcIfIndex
					InterfaceIndex,
				hwBRASIfPvcVpi
					Unsigned32,
				hwBRASIfPvcVci
					Unsigned32,
				hwBRASIfPvcPvcNumber
					Integer32,
				hwBRASIfPvcAccessLimit
					Integer32,
				hwBRASIfPvcAccessNumber
					Integer32,
				hwBRASIfPvcBlock
					TruthValue,
				hwBRASIfPvcDevAccessNumber
					Integer32,
				hwBRASIfPvcSchedulerVcGroupName
					DisplayString,
				hwBRASIfPvcSchedulerVpGroupName
					DisplayString
			 }

		hwBRASIfPvcIfIndex OBJECT-TYPE
			SYNTAX InterfaceIndex
			MAX-ACCESS read-only
			STATUS current
			DESCRIPTION
				"
				"
			::= { hwBRASIfPvcEntry 1 }
		
		hwBRASIfPvcVpi OBJECT-TYPE
			SYNTAX Unsigned32 (0..255)
			MAX-ACCESS read-only
			STATUS current
			DESCRIPTION
				"
				This object indicates the VPI number of the PVC. 
				Note that the VPI and VCI cannot be 0s at the same time.
				"
			::= { hwBRASIfPvcEntry 2 }
		
		hwBRASIfPvcVci OBJECT-TYPE
			SYNTAX Unsigned32 (0..65534)
			MAX-ACCESS read-only
			STATUS current
			DESCRIPTION
				"
				This object indicates the VCI number of the PVC. 
				Note that the VPI and VCI cannot be 0s at the same time.
				"
			::= { hwBRASIfPvcEntry 3 }
		
		hwBRASIfPvcPvcNumber OBJECT-TYPE
			SYNTAX Integer32 (0..4094)
			MAX-ACCESS read-write
			STATUS current
			DESCRIPTION
				"
				This object indicates the number of consecutive PVCs.
				"
			::= { hwBRASIfPvcEntry 4 }
		
		hwBRASIfPvcAccessLimit OBJECT-TYPE
			SYNTAX Integer32 (0..49153)
			MAX-ACCESS read-write
			STATUS current
			DESCRIPTION
				"
				This object indicates the upper limit of access users. 
				If the value is set to 49153, it indicates that the default value is restored.
				"
			DEFVAL { 49152 }
			::= { hwBRASIfPvcEntry 5 }
		
		hwBRASIfPvcAccessNumber OBJECT-TYPE
			SYNTAX Integer32 (0..49152)
			MAX-ACCESS read-only
			STATUS current
			DESCRIPTION
				" 
				PVC access number,default is 49152.
				"
			::= { hwBRASIfPvcEntry 6 }
		
		hwBRASIfPvcBlock OBJECT-TYPE
			SYNTAX TruthValue
			MAX-ACCESS read-write
			STATUS current
			DESCRIPTION
				"
				"
			DEFVAL { false }
			::= { hwBRASIfPvcEntry 7 }
		
		hwBRASIfPvcDevAccessNumber OBJECT-TYPE
			SYNTAX Integer32 (0..4096)
			MAX-ACCESS read-only
			STATUS current
			DESCRIPTION
				"
				"
			::= { hwBRASIfPvcEntry 8 }
		
		hwBRASIfPvcSchedulerVcGroupName OBJECT-TYPE
			SYNTAX DisplayString (SIZE (1..31))
			MAX-ACCESS read-write
			STATUS current
			DESCRIPTION
				"
				scheduler vc-group name
				"
			::= { hwBRASIfPvcEntry 9 }
		
		hwBRASIfPvcSchedulerVpGroupName OBJECT-TYPE
			SYNTAX DisplayString (SIZE (1..31))
			MAX-ACCESS read-write
			STATUS current
			DESCRIPTION
				"
				scheduler vp-group name
				"
			::= { hwBRASIfPvcEntry 10 }
		
		hwSTPRelayTable OBJECT-TYPE
			SYNTAX SEQUENCE OF HwSTPRelayEntry
			MAX-ACCESS not-accessible
			STATUS current
			DESCRIPTION
				"
				This object indicates the table of the STP relay leased-line users.
				"
			::= { hwSrvcfgInterfaceMibObjects 4 }
		
		hwSTPRelayEntry OBJECT-TYPE
			SYNTAX HwSTPRelayEntry
			MAX-ACCESS not-accessible
			STATUS current
			DESCRIPTION
				"
				Description.
				"
			INDEX { hwSTPRelayIndex }
			::= { hwSTPRelayTable 1 }
		
		HwSTPRelayEntry ::=
			SEQUENCE { 
				hwSTPRelayIndex
					Unsigned32,
				hwSTPRelayInIfIndex
					InterfaceIndex,
				hwSTPRelayOutIfIndex
					InterfaceIndex,
				hwSTPRelayRowStatus
					RowStatus,
				hwSTPRelayInIfName
					DisplayString,
				hwSTPRelayOutIfName
					DisplayString,
				hwSTPRelayInMac
					MacAddress,
				hwSTPRelayOutMac
					MacAddress
			 }

		hwSTPRelayIndex OBJECT-TYPE
			SYNTAX Unsigned32 (0..127)
			MAX-ACCESS read-only
			STATUS current
			DESCRIPTION
				"
				This object indicates the index of the STP-relay-leased-line.
				"
			::= { hwSTPRelayEntry 1 }
		
		hwSTPRelayInIfIndex OBJECT-TYPE
			SYNTAX InterfaceIndex
			MAX-ACCESS read-create
			STATUS current
			DESCRIPTION
				"
				This object indicates the index of an inbound interface.
				"
			::= { hwSTPRelayEntry 2 }
		
		hwSTPRelayOutIfIndex OBJECT-TYPE
			SYNTAX InterfaceIndex
			MAX-ACCESS read-create
			STATUS current
			DESCRIPTION
				"
				This object indicates the index of an outbound interface.
				"
			::= { hwSTPRelayEntry 3 }
		
		hwSTPRelayRowStatus OBJECT-TYPE
			SYNTAX RowStatus
			MAX-ACCESS read-create
			STATUS current
			DESCRIPTION
				"
				This object indicates the row status.
				"
			::= { hwSTPRelayEntry 4 }
		
		hwSTPRelayInIfName OBJECT-TYPE
			SYNTAX DisplayString (SIZE (1..47))
			MAX-ACCESS read-create
			STATUS current
			DESCRIPTION
				"
				This object indicates the name of an inbound interface.
				"
			::= { hwSTPRelayEntry 5 }
		
		hwSTPRelayOutIfName OBJECT-TYPE
			SYNTAX DisplayString (SIZE (1..47))
			MAX-ACCESS read-create
			STATUS current
			DESCRIPTION
				"
				This object indicates the name of an outbound interface.
				"
			::= { hwSTPRelayEntry 6 }
		
		hwSTPRelayInMac OBJECT-TYPE
			SYNTAX MacAddress
			MAX-ACCESS read-create
			STATUS current
			DESCRIPTION
				"
				stp-relay-line mac-address of in side
				"
			::= { hwSTPRelayEntry 7 }
		
		hwSTPRelayOutMac OBJECT-TYPE
			SYNTAX MacAddress
			MAX-ACCESS read-create
			STATUS current
			DESCRIPTION
				"
				stp-relay-line mac-address of out side
				"
			::= { hwSTPRelayEntry 8 }
		
		hwPortAccessLimitTable OBJECT-TYPE
			SYNTAX SEQUENCE OF HwPortAccessLimitEntry
			MAX-ACCESS not-accessible
			STATUS current
			DESCRIPTION
				"
				"
			::= { hwSrvcfgInterfaceMibObjects 5 }
		
		hwPortAccessLimitEntry OBJECT-TYPE
			SYNTAX HwPortAccessLimitEntry
			MAX-ACCESS not-accessible
			STATUS current
			DESCRIPTION
				"
				Description.
				"
			INDEX { hwPortAccessLimitIfIndex }
			::= { hwPortAccessLimitTable 1 }
		
		HwPortAccessLimitEntry ::=
			SEQUENCE { 
				hwPortAccessLimitIfIndex
					InterfaceIndex,
				hwPortAccessLimitLimit
					Integer32,
				hwPortAccessLimitNumber
					Integer32,
				hwPortAccessLimitDevNumber
					Integer32
			 }

		hwPortAccessLimitIfIndex OBJECT-TYPE
			SYNTAX InterfaceIndex
			MAX-ACCESS read-only
			STATUS current
			DESCRIPTION
				"
				Port index
				"
			::= { hwPortAccessLimitEntry 1 }
		
		hwPortAccessLimitLimit OBJECT-TYPE
			SYNTAX Integer32 (0..49153)
			MAX-ACCESS read-write
			STATUS current
			DESCRIPTION
				"
				This object indicates the access number limit of the port.
				"
			::= { hwPortAccessLimitEntry 2 }
		
		hwPortAccessLimitNumber OBJECT-TYPE
			SYNTAX Integer32 (0..49152)
			MAX-ACCESS read-only
			STATUS current
			DESCRIPTION
				"
				This object indicates the number of users that already access the port.
				"
			::= { hwPortAccessLimitEntry 3 }
		
		hwPortAccessLimitDevNumber OBJECT-TYPE
			SYNTAX Integer32 (0..4096)
			MAX-ACCESS read-only
			STATUS current
			DESCRIPTION
				"
				This object indicates the number of device users that already access the port.
				"
			::= { hwPortAccessLimitEntry 4 }
		
		hwL3SubscriberIspTable OBJECT-TYPE
			SYNTAX SEQUENCE OF HwL3SubscriberIspEntry
			MAX-ACCESS not-accessible
			STATUS current
			DESCRIPTION
				"
				The object indicates the configuration of the layer3-subscriber user.
				"
			::= { hwSrvcfgInterfaceMibObjects 6 }
		
		hwL3SubscriberIspEntry OBJECT-TYPE
			SYNTAX HwL3SubscriberIspEntry
			MAX-ACCESS not-accessible
			STATUS current
			DESCRIPTION
				"
				Description.
				"
			INDEX { hwL3SubscriberIspStartIp, hwL3SubscriberIspVpnId }
			::= { hwL3SubscriberIspTable 1 }
		
		HwL3SubscriberIspEntry ::=
			SEQUENCE { 
				hwL3SubscriberIspStartIp
					IpAddress,
				hwL3SubscriberIspVpnId
					DisplayString,
				hwL3SubscriberIspEndIp
					IpAddress,
				hwL3SubscriberIspDomainName
					DisplayString,
				hwL3SubscriberIspRowStatus
					RowStatus
			 }

		hwL3SubscriberIspStartIp OBJECT-TYPE
			SYNTAX IpAddress
			MAX-ACCESS read-only
			STATUS current
			DESCRIPTION
				"
				This object indicates the start IP address of the network segment for Layer-3 users.
				"
			::= { hwL3SubscriberIspEntry 1 }
		
		hwL3SubscriberIspVpnId OBJECT-TYPE
			SYNTAX DisplayString (SIZE (1..19))
			MAX-ACCESS read-only
			STATUS current
			DESCRIPTION
				"
				This object indicates the name of the VPN instance bound to the network segment for Layer-3 users.
				"
			::= { hwL3SubscriberIspEntry 2 }
		
		hwL3SubscriberIspEndIp OBJECT-TYPE
			SYNTAX IpAddress
			MAX-ACCESS read-create
			STATUS current
			DESCRIPTION
				"
				This object indicates the end IP address of the network segment for Layer-3 users.
				"
			::= { hwL3SubscriberIspEntry 3 }
		
		hwL3SubscriberIspDomainName OBJECT-TYPE
			SYNTAX DisplayString (SIZE (1..64))
			MAX-ACCESS read-create
			STATUS current
			DESCRIPTION
				"
				This object indicates the pre-authentication domain of the network segment for Layer-3 users.
				"
			::= { hwL3SubscriberIspEntry 4 }
		
		hwL3SubscriberIspRowStatus OBJECT-TYPE
			SYNTAX RowStatus
			MAX-ACCESS read-create
			STATUS current
			DESCRIPTION
				"
				This object indicates the row status.
				"
			::= { hwL3SubscriberIspEntry 5 }
		
		srvcfgScalar OBJECT IDENTIFIER ::= { hwSrvcfgInterfaceMibObjects 8 }
		
--        The SrvCfg Scalar configuration
-- 
-- This group of objects describe the global configuration of SrvCfg.
		hwDhcpOption60DomainInclude OBJECT-TYPE
			SYNTAX TruthValue
			MAX-ACCESS read-write
			STATUS current
			DESCRIPTION
				"				
				"
			::= { srvcfgScalar 1 }
		
		hwDhcpOption60PartialMatch OBJECT-TYPE
			SYNTAX TruthValue
			MAX-ACCESS read-write
			STATUS current
			DESCRIPTION
				"
				"
			::= { srvcfgScalar 2 }
		
		hwConnTimeOutTable OBJECT IDENTIFIER ::= { hwSrvcfgInterfaceMibObjects 9 }
		
		hwConnTimeOutTcp OBJECT-TYPE
			SYNTAX Integer32 (1..255)
			MAX-ACCESS read-write
			STATUS current
			DESCRIPTION
				" 
				The TCP connect time out,default is 5.
				"
			::= { hwConnTimeOutTable 1 }
		
		hwConnTimeOutUdp OBJECT-TYPE
			SYNTAX Integer32 (1..255)
			MAX-ACCESS read-write
			STATUS current
			DESCRIPTION
				"
				The UDP connect time out,default is 5.
				"
			::= { hwConnTimeOutTable 2 }
		
		hwBRASIfVlanNumTable OBJECT-TYPE
			SYNTAX SEQUENCE OF HwBRASIfVlanNumEntry
			MAX-ACCESS not-accessible
			STATUS current
			DESCRIPTION
				"
				This object indicates the VLAN statistics table of a board.
				"
			::= { hwSrvcfgInterfaceMibObjects 10 }
		
		hwBRASIfVlanNumEntry OBJECT-TYPE
			SYNTAX HwBRASIfVlanNumEntry
			MAX-ACCESS not-accessible
			STATUS current
			DESCRIPTION
				"
				Description.
				"
			INDEX { hwBRASIfSlot }
			::= { hwBRASIfVlanNumTable 1 }
		
		HwBRASIfVlanNumEntry ::=
			SEQUENCE { 
				hwBRASIfSlot
					Unsigned32,
				hwBRASSlotVlanNum
					Integer32,
				hwBRASSLotStaticVlanNum
					Integer32
			 }

		hwBRASIfSlot OBJECT-TYPE
			SYNTAX Unsigned32 (0..16)
			MAX-ACCESS read-only
			STATUS current
			DESCRIPTION
				"
				This object indicates the slot number of a board. Slot 0 is for trunk.
				"
			::= { hwBRASIfVlanNumEntry 1 }
		
		hwBRASSlotVlanNum OBJECT-TYPE
			SYNTAX Integer32 (0..65536)
			MAX-ACCESS read-only
			STATUS current
			DESCRIPTION
				"
				This object indicates the VLAN statistics on a board.
				"
			::= { hwBRASIfVlanNumEntry 2 }
		
		hwBRASSLotStaticVlanNum OBJECT-TYPE
			SYNTAX Integer32 (0..16384)
			MAX-ACCESS read-only
			STATUS current
			DESCRIPTION
				"
				This object indicates the static VLAN statistics on a board.
				"
			::= { hwBRASIfVlanNumEntry 3 }
		
		hwServiceIfCfgTable OBJECT-TYPE
			SYNTAX SEQUENCE OF HwServiceIfCfgEntry
			MAX-ACCESS not-accessible
			STATUS current
			DESCRIPTION
				"
				This table indicates the service configurations of a service interface.
				"
			::= { hwSrvcfgInterfaceMibObjects 11 }
		
		hwServiceIfCfgEntry OBJECT-TYPE
			SYNTAX HwServiceIfCfgEntry
			MAX-ACCESS not-accessible
			STATUS current
			DESCRIPTION
				"
				An entry of hwServiceIfCfgTable.
				"
			INDEX { hwServiceIfCfgIfIndex }
			::= { hwServiceIfCfgTable 1 }
		
		HwServiceIfCfgEntry ::=
			SEQUENCE { 
				hwServiceIfCfgIfIndex
					InterfaceIndex,
				hwServiceIfCfgIdentificationMode
					INTEGER,
				hwServiceIfCfgDomain
					DisplayString,
				hwServiceIfCfgUserName
					DisplayString,
				hwServiceIfCfgPassword
					DisplayString,
				hwServiceIfCfgDetectNum
					Integer32,
				hwServiceIfCfgDetectInterval
					Integer32,
				hwServiceIfCfgOption82
					TruthValue,
				hwServiceIfCfgAccessLimit
					Integer32,
				hwServiceIfCfgOption60
					TruthValue,
				hwServiceIfCfgIpTriggerEnable
					EnabledStatus,
				hwServiceIfCfgArpTriggerEnable
					EnabledStatus,
				hwServiceIfCfgIfBlock
					TruthValue,
				hwServiceIfCfgQosProfile
					DisplayString,
				hwServiceIfCfgBindingUserPasswordMode
					INTEGER,
				hwServiceIfCfgBindingUserNameFormat
					Integer32,
				hwServiceIfCfgBindingUserPassword
					DisplayString,
				hwServiceIfCfgRowStatus
					RowStatus
			 }

		hwServiceIfCfgIfIndex OBJECT-TYPE
			SYNTAX InterfaceIndex
			MAX-ACCESS not-accessible
			STATUS current
			DESCRIPTION
				"
				The value of this object identifies the index of the service interface. 				 
				"
			::= { hwServiceIfCfgEntry 1 }
		
		hwServiceIfCfgIdentificationMode OBJECT-TYPE
			SYNTAX INTEGER
				{
				host(1),
				location(2),
				ceVlan(3)
				}
			MAX-ACCESS read-create
			STATUS current
			DESCRIPTION
				" This value of this object identifies the user identification mode.
                  The QoS resources are allocated and charged according to which user identification mode 
                  is configured for the user of the interface.
 	              host (1): identifies a user according to the IP address and MAC address.
 	              location (2): identifies a user according to the Option 82 information.
 	              ceVlan (3): identifies a user according to the CE-VLAN information. In other words, 
 	              when a group of users of the same inner VLAN tag access multiple interfaces, these 
 	              users are considered as the same user. 
                  The default value is host (1).
                  The latest modification cannot override the previous configurations. You need to change 
                  the value to host before choosing another mode.

				"
			::= { hwServiceIfCfgEntry 2 }
		
		hwServiceIfCfgDomain OBJECT-TYPE
			SYNTAX DisplayString (SIZE (1..20))
			MAX-ACCESS read-create
			STATUS current
			DESCRIPTION
				"
				 This object indicates the domain to which the user belongs.
                 --: default value.
                 --: deletes the configuration.
                 If the domain has users, you cannot delete the setting of this object.

				"
			::= { hwServiceIfCfgEntry 3 }
		
		hwServiceIfCfgUserName OBJECT-TYPE
			SYNTAX DisplayString (SIZE (1..31))
			MAX-ACCESS read-create
			STATUS current
			DESCRIPTION
				"  
				Not supported.
				"
			::= { hwServiceIfCfgEntry 4 }
		
		hwServiceIfCfgPassword OBJECT-TYPE
			SYNTAX DisplayString (SIZE (1..31))
			MAX-ACCESS read-create
			STATUS current
			DESCRIPTION
				"  
				Not supported.
				"
			::= { hwServiceIfCfgEntry 5 }
		
		hwServiceIfCfgDetectNum OBJECT-TYPE
			SYNTAX Integer32 (2..10)
			MAX-ACCESS read-create
			STATUS current
			DESCRIPTION
				"
				The value of this object identifies the detection times.
				"
			::= { hwServiceIfCfgEntry 6 }
		
		hwServiceIfCfgDetectInterval OBJECT-TYPE
			SYNTAX Integer32 (0..120)
			MAX-ACCESS read-create
			STATUS current
			DESCRIPTION
				"  
				The value of this object identifies the interval between detection attempts.
				"
			::= { hwServiceIfCfgEntry 7 }
		
		hwServiceIfCfgOption82 OBJECT-TYPE
			SYNTAX TruthValue
			MAX-ACCESS read-create
			STATUS current
			DESCRIPTION
				" 
				This object indicates whether to trust Option 82.
 	            True(1): indicates that Option 82 is trusted.
 	            False (2): indicates that Option 82 is not trusted.
                The default value is False (2).
                This object is used to configure the device to trust or not to trust the DHCP Option 82 
                information sent from the client.

				"
			::= { hwServiceIfCfgEntry 8 }
		
		hwServiceIfCfgAccessLimit OBJECT-TYPE
			SYNTAX Integer32 (0..16384)
			MAX-ACCESS read-create
			STATUS current
			DESCRIPTION
				" 
				 The value of this object identifies the user access limit.
                 The default value is 16384.
                 If the number of online users on the interface is more than the value of this object, 
                 the setting of this object fails.

				"
			::= { hwServiceIfCfgEntry 9 }
		
		hwServiceIfCfgOption60 OBJECT-TYPE
			SYNTAX TruthValue
			MAX-ACCESS read-create
			STATUS current
			DESCRIPTION
				"
				This object indicates whether to trust Option 60. 
 	            True(1): indicates that Option 60 is trusted.
 	            False (2): indicates that Option 60 is not trusted.
                The default value is False (2).
                This object is used to configure the device to trust or not to trust the DHCP Option 60 
                information sent from the client.

				"
			::= { hwServiceIfCfgEntry 10 }
		
		hwServiceIfCfgIpTriggerEnable OBJECT-TYPE
			SYNTAX EnabledStatus
			MAX-ACCESS read-create
			STATUS current
			DESCRIPTION
				" This object indicates whether the function of IP packet-triggered user online is enabled.
                 By default, the function is disabled.

				"
			DEFVAL { disabled }
			::= { hwServiceIfCfgEntry 11 }
		
		hwServiceIfCfgArpTriggerEnable OBJECT-TYPE
			SYNTAX EnabledStatus
			MAX-ACCESS read-create
			STATUS current
			DESCRIPTION
				" 
                 This object indicates whether the function of ARP packet-triggered user online is enabled.
                 By default, the function is disabled.
				 
				"
			DEFVAL { disabled }
			::= { hwServiceIfCfgEntry 12 }
		
		hwServiceIfCfgIfBlock OBJECT-TYPE
			SYNTAX TruthValue
			MAX-ACCESS read-create
			STATUS current
			DESCRIPTION
				"  
				 This object indicates whether the interface is blocked.
 	             True(1): indicates that the interface is blocked.
 	             False (2): indicates that the interface is not blocked.
                 The default value is False (2).

				"
			::= { hwServiceIfCfgEntry 13 }
		
		hwServiceIfCfgQosProfile OBJECT-TYPE
			SYNTAX DisplayString (SIZE (1..31))
			MAX-ACCESS read-create
			STATUS current
			DESCRIPTION
				" 
				 This object indicates the QoS profile.
                 This object has no default value.
                 The created QoS profile must be configured. If an interface is already configured 
                 with hwServiceIfCfgCarProfile and has users connected to it, this object cannot be configured.
                 If this object is modified when there are users on the interface, only the subsequent
                 online users are affected. The users that are already on line are not affected.
				"
			::= { hwServiceIfCfgEntry 14 }
		
		hwServiceIfCfgBindingUserPasswordMode OBJECT-TYPE
			SYNTAX INTEGER
				{
				simple(1),
				cipher(2)
				}
			MAX-ACCESS read-create
			STATUS current
			DESCRIPTION
				" 
				  The value of this object identifies the password mode of the binding user.
				"
			::= { hwServiceIfCfgEntry 15 }
		
		hwServiceIfCfgBindingUserNameFormat OBJECT-TYPE
			SYNTAX Integer32 (1..7)
			MAX-ACCESS read-create
			STATUS current
			DESCRIPTION
				" 
				The value of this object identifies the format in which the bound user name is generated:
 	            mac (1): constructs the user name by using the MAC address of the user.
 	            option82 (2): constructs the user name by using the Option 82 information of the user.
 	            Sys-name (3): constructs the user name by using the name of the router.
 	            mac+option82 (4)
 	            mac+sys-name (5)
            	option82+ host-name (6)
            	mac+option82+host-name (7)
                By default, users in host mode and in CE-VLAN mode use the MAC address to construct the user 
                names; users in location mode use the option 82 + MAC address to construct the user names.
 
				"
			::= { hwServiceIfCfgEntry 16 }
		
		hwServiceIfCfgBindingUserPassword OBJECT-TYPE
			SYNTAX DisplayString (SIZE (1..16))
			MAX-ACCESS read-create
			STATUS current
			DESCRIPTION
				"
				This object indicates the password of the bound user.
				"
			::= { hwServiceIfCfgEntry 17 }
		
		hwServiceIfCfgRowStatus OBJECT-TYPE
			SYNTAX RowStatus
			MAX-ACCESS read-create
			STATUS current
			DESCRIPTION
				" 
				This object indicates the row status.				
				"
			::= { hwServiceIfCfgEntry 18 }
		
		hwBRASIfEnableTable OBJECT-TYPE
			SYNTAX SEQUENCE OF HwBRASIfEnableEntry
			MAX-ACCESS not-accessible
			STATUS current
			DESCRIPTION
				"Description."
			::= { hwSrvcfgInterfaceMibObjects 12 }
		
		hwBRASIfEnableEntry OBJECT-TYPE
			SYNTAX HwBRASIfEnableEntry
			MAX-ACCESS not-accessible
			STATUS current
			DESCRIPTION
				"Description."
			INDEX { hwBRASIfEnableIfIndex }
			::= { hwBRASIfEnableTable 1 }
		
		HwBRASIfEnableEntry ::=
			SEQUENCE { 
				hwBRASIfEnableIfIndex
					InterfaceIndex,
				hwBRASIfEnableStatus
					TruthValue
			 }

		hwBRASIfEnableIfIndex OBJECT-TYPE
			SYNTAX InterfaceIndex
			MAX-ACCESS read-only
			STATUS current
			DESCRIPTION
				"Description."
			::= { hwBRASIfEnableEntry 1 }
		
		hwBRASIfEnableStatus OBJECT-TYPE
			SYNTAX TruthValue (1..2)
			MAX-ACCESS read-write
			STATUS current
			DESCRIPTION
				"Description."
			::= { hwBRASIfEnableEntry 2 }
		
--    ============== conformance information ==============
		hwSrvcfgInterfaceConformance OBJECT IDENTIFIER ::= { hwBRASSrvcfgInterface 2 }
		
		hwSrvcfgInterfaceCompliances OBJECT IDENTIFIER ::= { hwSrvcfgInterfaceConformance 1 }
		
--   this module
		hwSrvcfgInterfaceCompliance MODULE-COMPLIANCE
			STATUS current
			DESCRIPTION 
				"
				The compliance statement for systems supporting 
				the this module.
				"
			MODULE -- this module
				MANDATORY-GROUPS { hwBRASIfCfgGroup, hwBRASIfVlanGroup, hwBRASIfPvcGroup, hwSTPRelayServerGroup, hwPortAccessLimitGroup, 
					hwL3SubscriberIspGroup, hwConnTimeOutGroup, hwSrvcfgScalarGroup, hwBRASIfVlanNumGroup, hwServiceIfCfgGroup, 
					hwBRASIfEnableGroup }
			::= { hwSrvcfgInterfaceCompliances 1 }
		
--    ============== groups ==============  
		hwSrvcfgInterfaceGroups OBJECT IDENTIFIER ::= { hwSrvcfgInterfaceConformance 2 }
		
		hwBRASIfCfgGroup OBJECT-GROUP
			OBJECTS { hwBRASIfCfgAccessType, hwBRASIfCfgBRASIfName, hwBRASIfCfgPreAuthDomain, hwBRASIfCfgAuthDomain, hwBRASIfCfgForceAuthDomain, 
				hwBRASIfCfgAcctCpyRdSvr, hwBRASIfCfgAuthMethod, hwBRASIfCfgNasPortType, hwBRASIfCfgLeaseName, hwBRASIfCfgLeasePwd, 
				hwBRASIfCfgArpInterval, hwBRASIfCfgArpFailTimes, hwBRASIfCfgArpProxy, hwBRASIfCfgRoamIsp, hwBRASIfCfgDhcpBroadCast, 
				hwBRASIfCfgHostCar, hwBRASIfCfgRowStatus, hwBRASIfCfgEapTrigger, hwBRASIfCfgWlanSwitch, hwBRASIfCfgWlanAuthorization, 
				hwBRASIfCfgDhcpShortLease, hwBRASIfCfgRoamDomain, hwBRASIfVsiName, hwBRASIfCfgOption82, hwBRASIfVpnInstance, 
				hwBRASIfCopyMulticasePerUser, hwBRASIfCfgNDProxy, hwBRASIfCfgVBasMAC, hwBRASIfCfgVBasAuthMode, hwBRASIfCfgPermitDomain1, 
				hwBRASIfCfgPermitDomain2, hwBRASIfCfgPermitDomain3, hwBRASIfCfgPermitDomain4, hwBRASIfCfgAccessDelayType, hwBRASIfCfgTermlessDelayTime, 
				hwBRASIfCfgOddMacDelayTime, hwBRASIfCfgEvenMacDelayTime, hwBRASIfCfgAccessNodeIdentify, hwBRASIfCfgAniDelayTime, hwBRASIfCfgRemoteBackupProfile, 
				hwBRASIfCfgOption60, hwBRASIfCfgIpTrigger, hwBRASIfCfgArpTrigger, hwBRASIfCfgWlanSSID, hwBRASIfCfgIfIndex, 
				hwBRASIfVlanIfIndex, hwBRASIfVlanVlanId }
			STATUS current
			DESCRIPTION 
				"
				"
			::= { hwSrvcfgInterfaceGroups 1 }
		
		hwBRASIfVlanGroup OBJECT-GROUP
			OBJECTS { hwBRASIfVlanVlanNumber, hwBRASIfVlanAccessLimit, hwBRASIfVlanAccessNumber, hwBRASIfVlanBlock, hwBRASIfVlanDevAccessNumber, 
				hwBRASIfVlanSchedulerVcName, hwBRASIfVlanSchedulerVcGroupName, hwBRASIfVlanSchedulerVpGroupName, hwBRASIfQinQVlanID }
			STATUS current
			DESCRIPTION 
				"
				"
			::= { hwSrvcfgInterfaceGroups 2 }
		
		hwBRASIfPvcGroup OBJECT-GROUP
			OBJECTS { hwBRASIfPvcPvcNumber, hwBRASIfPvcAccessLimit, hwBRASIfPvcAccessNumber, hwBRASIfPvcBlock, hwBRASIfPvcDevAccessNumber, 
				hwBRASIfPvcSchedulerVcGroupName, hwBRASIfPvcSchedulerVpGroupName, hwBRASIfPvcIfIndex, hwBRASIfPvcVpi, hwBRASIfPvcVci
				 }
			STATUS current
			DESCRIPTION 
				"
				"
			::= { hwSrvcfgInterfaceGroups 3 }
		
		hwSTPRelayServerGroup OBJECT-GROUP
			OBJECTS { hwSTPRelayInIfIndex, hwSTPRelayOutIfIndex, hwSTPRelayRowStatus, hwSTPRelayInIfName, hwSTPRelayOutIfName, 
				hwSTPRelayInMac, hwSTPRelayOutMac, hwSTPRelayIndex }
			STATUS current
			DESCRIPTION 
				"
				"
			::= { hwSrvcfgInterfaceGroups 4 }
		
		hwPortAccessLimitGroup OBJECT-GROUP
			OBJECTS { hwPortAccessLimitLimit, hwPortAccessLimitNumber, hwPortAccessLimitDevNumber, hwPortAccessLimitIfIndex }
			STATUS current
			DESCRIPTION 
				"
				"
			::= { hwSrvcfgInterfaceGroups 5 }
		
		hwL3SubscriberIspGroup OBJECT-GROUP
			OBJECTS { hwL3SubscriberIspEndIp, hwL3SubscriberIspDomainName, hwL3SubscriberIspRowStatus, hwL3SubscriberIspStartIp, hwL3SubscriberIspVpnId
				 }
			STATUS current
			DESCRIPTION 
				"
				"
			::= { hwSrvcfgInterfaceGroups 6 }
		
		hwConnTimeOutGroup OBJECT-GROUP
			OBJECTS { hwConnTimeOutTcp, hwConnTimeOutUdp }
			STATUS current
			DESCRIPTION 
				"
				"
			::= { hwSrvcfgInterfaceGroups 7 }
		
		hwSrvcfgScalarGroup OBJECT-GROUP
			OBJECTS { hwDhcpOption60DomainInclude, hwDhcpOption60PartialMatch }
			STATUS current
			DESCRIPTION 
				"
				"
			::= { hwSrvcfgInterfaceGroups 8 }
		
		hwBRASIfVlanNumGroup OBJECT-GROUP
			OBJECTS { hwBRASSlotVlanNum, hwBRASSLotStaticVlanNum, hwBRASIfSlot }
			STATUS current
			DESCRIPTION 
				"
				"
			::= { hwSrvcfgInterfaceGroups 9 }

		hwServiceIfCfgGroup OBJECT-GROUP
			OBJECTS { hwServiceIfCfgIdentificationMode, hwServiceIfCfgDomain, hwServiceIfCfgUserName, hwServiceIfCfgPassword, hwServiceIfCfgDetectNum, 
				hwServiceIfCfgDetectInterval, hwServiceIfCfgOption82, hwServiceIfCfgAccessLimit, hwServiceIfCfgOption60, hwServiceIfCfgIpTriggerEnable, 
				hwServiceIfCfgArpTriggerEnable, hwServiceIfCfgIfBlock, hwServiceIfCfgQosProfile, hwServiceIfCfgBindingUserPasswordMode, hwServiceIfCfgBindingUserNameFormat, 
				hwServiceIfCfgBindingUserPassword, hwServiceIfCfgRowStatus }
			STATUS current
			DESCRIPTION 
				"
				"
			::= { hwSrvcfgInterfaceGroups 10 }
		
		hwBRASIfEnableGroup OBJECT-GROUP
			OBJECTS { hwBRASIfEnableIfIndex, hwBRASIfEnableStatus }
			STATUS current
			DESCRIPTION 
				"Description."
			::= { hwSrvcfgInterfaceGroups 11 }
		
	
	END

--
-- HUAWEI-BRAS-SRVCFGINTERFACE-MIB.mib
--
