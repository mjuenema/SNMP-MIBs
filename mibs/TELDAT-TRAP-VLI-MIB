-- file automatically created


TELDAT-TRAP-VLI-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


vliTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the VLI event subsystem."
    REVISION "201401200930Z"
    DESCRIPTION "Initial implementation"
        ::= { telEventTraps 224 }


vliEventsGroup	OBJECT IDENTIFIER	::= { vliTrapsMIB 1 }

vliNotifications	OBJECT IDENTIFIER	::= { vliTrapsMIB 2 }
vliNotificationsPrefix	OBJECT IDENTIFIER	::= { vliNotifications 0 }

vliEventObjects1 OBJECT-IDENTITY
    STATUS current
    DESCRIPTION
        "Event VLI.1
        VLI generic error."
    ::= { vliEventsGroup 1 }

vli1_error OBJECT-TYPE
    SYNTAX DisplayString
    MAX-ACCESS accessible-for-notify
    STATUS current
    DESCRIPTION
        "Parameter 'error' in event VLI.1"
    ::= { vliEventObjects1 1 }

vliEventObjects2 OBJECT-IDENTITY
    STATUS current
    DESCRIPTION
        "Event VLI.2
        VLI generic information."
    ::= { vliEventsGroup 2 }

vli2_info OBJECT-TYPE
    SYNTAX DisplayString
    MAX-ACCESS accessible-for-notify
    STATUS current
    DESCRIPTION
        "Parameter 'info' in event VLI.2"
    ::= { vliEventObjects2 1 }

vliEventObjects3 OBJECT-IDENTITY
    STATUS current
    DESCRIPTION
        "Event VLI.3
        VLI generic warning."
    ::= { vliEventsGroup 3 }

vli3_warning OBJECT-TYPE
    SYNTAX DisplayString
    MAX-ACCESS accessible-for-notify
    STATUS current
    DESCRIPTION
        "Parameter 'warning' in event VLI.3"
    ::= { vliEventObjects3 1 }

vliEventObjects4 OBJECT-IDENTITY
    STATUS current
    DESCRIPTION
        "Event VLI.4
        VLI generic trace."
    ::= { vliEventsGroup 4 }

vli4_trace OBJECT-TYPE
    SYNTAX DisplayString
    MAX-ACCESS accessible-for-notify
    STATUS current
    DESCRIPTION
        "Parameter 'trace' in event VLI.4"
    ::= { vliEventObjects4 1 }

vliEventObjects5 OBJECT-IDENTITY
    STATUS current
    DESCRIPTION
        "Event VLI.5
        Command sent to the Applications core."
    ::= { vliEventsGroup 5 }

vli5_cmd_id OBJECT-TYPE
    SYNTAX Integer32
    MAX-ACCESS accessible-for-notify
    STATUS current
    DESCRIPTION
        "Parameter 'cmd_id' in event VLI.5"
    ::= { vliEventObjects5 1 }

vli5_pending OBJECT-TYPE
    SYNTAX Integer32
    MAX-ACCESS accessible-for-notify
    STATUS current
    DESCRIPTION
        "Parameter 'pending' in event VLI.5"
    ::= { vliEventObjects5 2 }

vli5_len OBJECT-TYPE
    SYNTAX Integer32
    MAX-ACCESS accessible-for-notify
    STATUS current
    DESCRIPTION
        "Parameter 'len' in event VLI.5"
    ::= { vliEventObjects5 3 }

vli5_data OBJECT-TYPE
    SYNTAX DisplayString
    MAX-ACCESS accessible-for-notify
    STATUS current
    DESCRIPTION
        "Parameter 'data' in event VLI.5"
    ::= { vliEventObjects5 4 }

vliEventObjects6 OBJECT-IDENTITY
    STATUS current
    DESCRIPTION
        "Event VLI.6
        Command received from the Applications core."
    ::= { vliEventsGroup 6 }

vli6_cmd_id OBJECT-TYPE
    SYNTAX Integer32
    MAX-ACCESS accessible-for-notify
    STATUS current
    DESCRIPTION
        "Parameter 'cmd_id' in event VLI.6"
    ::= { vliEventObjects6 1 }

vli6_len OBJECT-TYPE
    SYNTAX Integer32
    MAX-ACCESS accessible-for-notify
    STATUS current
    DESCRIPTION
        "Parameter 'len' in event VLI.6"
    ::= { vliEventObjects6 2 }

vli6_data OBJECT-TYPE
    SYNTAX DisplayString
    MAX-ACCESS accessible-for-notify
    STATUS current
    DESCRIPTION
        "Parameter 'data' in event VLI.6"
    ::= { vliEventObjects6 3 }

vliEventObjects7 OBJECT-IDENTITY
    STATUS current
    DESCRIPTION
        "Event VLI.7
        Event received from the Applications core."
    ::= { vliEventsGroup 7 }

vli7_event OBJECT-TYPE
    SYNTAX DisplayString
    MAX-ACCESS accessible-for-notify
    STATUS current
    DESCRIPTION
        "Parameter 'event' in event VLI.7"
    ::= { vliEventObjects7 1 }

vliEventObjects8 OBJECT-IDENTITY
    STATUS current
    DESCRIPTION
        "Event VLI.8
        Progress notification received from the Applications core."
    ::= { vliEventsGroup 8 }

vli8_stage OBJECT-TYPE
    SYNTAX DisplayString
    MAX-ACCESS accessible-for-notify
    STATUS current
    DESCRIPTION
        "Parameter 'stage' in event VLI.8"
    ::= { vliEventObjects8 1 }

vli8_description OBJECT-TYPE
    SYNTAX DisplayString
    MAX-ACCESS accessible-for-notify
    STATUS current
    DESCRIPTION
        "Parameter 'description' in event VLI.8"
    ::= { vliEventObjects8 2 }

vli8_progress OBJECT-TYPE
    SYNTAX Integer32
    MAX-ACCESS accessible-for-notify
    STATUS current
    DESCRIPTION
        "Parameter 'progress' in event VLI.8"
    ::= { vliEventObjects8 3 }


vliNotification1 NOTIFICATION-TYPE
    OBJECTS { 
              vli1_error 
            }
    STATUS current
    DESCRIPTION
        "Notification of Event VLI.1

        Message: 'Error: $1'

        Parameters list:
              $1: vli1_error

        VLI generic error."
    ::= { vliNotificationsPrefix 1 }

vliNotification2 NOTIFICATION-TYPE
    OBJECTS { 
              vli2_info 
            }
    STATUS current
    DESCRIPTION
        "Notification of Event VLI.2

        Message: 'Info: $1'

        Parameters list:
              $1: vli2_info

        VLI generic information."
    ::= { vliNotificationsPrefix 2 }

vliNotification3 NOTIFICATION-TYPE
    OBJECTS { 
              vli3_warning 
            }
    STATUS current
    DESCRIPTION
        "Notification of Event VLI.3

        Message: 'Warning: $1'

        Parameters list:
              $1: vli3_warning

        VLI generic warning."
    ::= { vliNotificationsPrefix 3 }

vliNotification4 NOTIFICATION-TYPE
    OBJECTS { 
              vli4_trace 
            }
    STATUS current
    DESCRIPTION
        "Notification of Event VLI.4

        Message: 'Trace: $1'

        Parameters list:
              $1: vli4_trace

        VLI generic trace."
    ::= { vliNotificationsPrefix 4 }

vliNotification5 NOTIFICATION-TYPE
    OBJECTS { 
              vli5_cmd_id, 
              vli5_pending,
              vli5_len,
              vli5_data 
            }
    STATUS current
    DESCRIPTION
        "Notification of Event VLI.5

        Message: 'Cmd Sent $1, pend $2, len $3, data: $4'

        Parameters list:
              $1: vli5_cmd_id
              $2: vli5_pending
              $3: vli5_len
              $4: vli5_data

        Command sent to the Applications core."
    ::= { vliNotificationsPrefix 5 }

vliNotification6 NOTIFICATION-TYPE
    OBJECTS { 
              vli6_cmd_id, 
              vli6_len,
              vli6_data 
            }
    STATUS current
    DESCRIPTION
        "Notification of Event VLI.6

        Message: 'Cmd Rvd $1, len $2, data: $3'

        Parameters list:
              $1: vli6_cmd_id
              $2: vli6_len
              $3: vli6_data

        Command received from the Applications core."
    ::= { vliNotificationsPrefix 6 }

vliNotification7 NOTIFICATION-TYPE
    OBJECTS { 
              vli7_event 
            }
    STATUS current
    DESCRIPTION
        "Notification of Event VLI.7

        Message: 'App Event: $1'

        Parameters list:
              $1: vli7_event

        Event received from the Applications core."
    ::= { vliNotificationsPrefix 7 }

vliNotification8 NOTIFICATION-TYPE
    OBJECTS { 
              vli8_stage, 
              vli8_description,
              vli8_progress 
            }
    STATUS current
    DESCRIPTION
        "Notification of Event VLI.8

        Message: 'Progress: Stage $1 Description $2 Progress $3%%'

        Parameters list:
              $1: vli8_stage
              $2: vli8_description
              $3: vli8_progress

        Progress notification received from the Applications core."
    ::= { vliNotificationsPrefix 8 }


END
