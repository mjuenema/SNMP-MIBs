-------------------------------------------------------
-- Copyright 1999 - Sun Microsystems, Inc. All Rights Reserved.
--
--
-------------------------------------------------------
-- Sun Management Center
-------------------------------------------------------

PROCESS-DETAILS-SUNMANAGEMENTCENTER-MIB DEFINITIONS ::= BEGIN

  IMPORTS
        enterprises, MODULE-IDENTITY, OBJECT-TYPE,  Integer32
                FROM SNMPv2-SMI
         OBJECT-GROUP
                FROM SNMPv2-CONF
         DisplayString
               FROM SNMPv2-TC;


processDetails MODULE-IDENTITY
    LAST-UPDATED "9907201505Z"
    ORGANIZATION "Sun Microsystems Inc."
    CONTACT-INFO
        "        Sun Microsystems Inc.
       Customer Support
            Postal: 901 San Antonio Road
       Palo Alto, CA-94303-4900
    USA
                         Tel: 650-960-1300
                E-mail: service@sun.com"
    DESCRIPTION
        "The solaris process detail allows to  monitor the top 10,20,50
         processes that are CPU/Memory intensive. This criteria is part
         of the agent configuration."

    REVISION  "9907201505Z"
    DESCRIPTION
        "Rev 1.0  20th July 1999 15:05, Initial version Of MIB."
    ::= { modules 13 }

sun       OBJECT IDENTIFIER ::= { enterprises 42 }
prod      OBJECT IDENTIFIER ::= { sun 2 }
sunsymon  OBJECT IDENTIFIER ::= { prod 12 }
agent     OBJECT IDENTIFIER ::= { sunsymon 2 }
modules   OBJECT IDENTIFIER ::= { agent 2 }


processTable OBJECT-TYPE
    SYNTAX      SEQUENCE OF ProcessTableEntry
    MAX-ACCESS  not-accessible
    STATUS      current
    DESCRIPTION
                "This table shows the monitoring information for processes
                 running on the host. Each row in this table corresponds to
                 a process."
    ::= { processDetails 1 }

processTableEntry OBJECT-TYPE
    SYNTAX      ProcessTableEntry
    MAX-ACCESS  not-accessible
    STATUS      current
    DESCRIPTION
                "Information about one process."
    INDEX  { psProcessID }
    ::= { processTable 1 }

ProcessTableEntry ::=
    SEQUENCE {
        psProcessID
            Integer32 (1..2147483647) ,
        psParentProcessID
            Integer32,
        psUserID
            Integer32,
        psUserName
            DisplayString,
        psEUserID
            Integer32,
        psGroupID
            Integer32,
        psEGroupID
            Integer32,
        psSessionID
            Integer32,
        psProcessGroupID
            Integer32,
        psControlTTY
            DisplayString,
        psStartTime
            DisplayString,
        psExecutionTime
            DisplayString,
        psState
            DisplayString,
        psWaitChannel
            DisplayString,
        psSchedulingClass
            DisplayString,
        psAddress
            DisplayString,
        psSize
            Integer32,
        psPriority
            Integer32,
        psNice
            Integer32,
        psPercentCPUTime
            DisplayString,
        psPercentMemory
            DisplayString,
        psCommand
            DisplayString,
        psCommandLine
            DisplayString,
	psZoneID
            DisplayString
    }

psProcessID OBJECT-TYPE
    SYNTAX      Integer32 (1..2147483647)
    MAX-ACCESS  read-only
    STATUS      current
    DESCRIPTION
                "The process ID of the process."
    ::= { processTableEntry 1 }

psParentProcessID OBJECT-TYPE
    SYNTAX      Integer32
    MAX-ACCESS  read-only
    STATUS      current
    DESCRIPTION
                "The parent process Id of the process."
    ::= { processTableEntry 2 }

psUserID OBJECT-TYPE
    SYNTAX      Integer32
    MAX-ACCESS  read-only
    STATUS      current
    DESCRIPTION
                "The user ID of the process owner."
    ::= { processTableEntry 3 }

psUserName OBJECT-TYPE
    SYNTAX      DisplayString
    MAX-ACCESS  read-only
    STATUS      current
    DESCRIPTION
                "The user ID of the process owner. This is the login name 
		of the process owner."
    ::= { processTableEntry 4 }

psEUserID OBJECT-TYPE
    SYNTAX      Integer32
    MAX-ACCESS  read-only
    STATUS      current
    DESCRIPTION
                "The effective user ID of the process."
    ::= { processTableEntry 5 }

psGroupID OBJECT-TYPE
    SYNTAX      Integer32
    MAX-ACCESS  read-only
    STATUS      current
    DESCRIPTION
                "The group ID of the process owner."
    ::= { processTableEntry 6 }

psEGroupID OBJECT-TYPE
    SYNTAX      Integer32
    MAX-ACCESS  read-only
    STATUS      current
    DESCRIPTION
                "The effective group ID of the process ."
    ::= { processTableEntry 7 }

psSessionID OBJECT-TYPE
    SYNTAX      Integer32
    MAX-ACCESS  read-only
    STATUS      current
    DESCRIPTION
                "Session Id of the process."
    ::= { processTableEntry 8 }

psProcessGroupID OBJECT-TYPE
    SYNTAX      Integer32
    MAX-ACCESS  read-only
    STATUS      current
    DESCRIPTION
                "Process group ID of the process."
    ::= { processTableEntry 9 }

psControlTTY OBJECT-TYPE
    SYNTAX      DisplayString
    MAX-ACCESS  read-only
    STATUS      current
    DESCRIPTION
                "The controlling terminal for the process (when there is
                no controlling terminal, this value will be '?')."
    ::= { processTableEntry 10 }

psStartTime OBJECT-TYPE
    SYNTAX      DisplayString
    MAX-ACCESS  read-only
    STATUS      current
    DESCRIPTION
                "The starting time of the process, given in hours, minutes, 
		and seconds."
    ::= { processTableEntry 11 }

psExecutionTime OBJECT-TYPE
    SYNTAX      DisplayString
    MAX-ACCESS  read-only
    STATUS      current
    DESCRIPTION
                "The cumulative execution time for the process."
    ::= { processTableEntry 12 }

psState OBJECT-TYPE
    SYNTAX      DisplayString
    MAX-ACCESS  read-only
    STATUS      current
    DESCRIPTION
                "The state of the process:

                        O     Process is running on a processor.
                        S     Sleeping: process is waiting for an
                              event to complete.
                        R     Runnable: process is on run queue.
                        I     Idle: process is being created.
                        Z     Zombie  state:  process  terminated
                              and parent not waiting.
                        T     Traced: process stopped by a signal
                              because parent is tracing it.
                        X     SXBRK state: process is waiting for
                              more primary memory.
		"
    ::= { processTableEntry 13 }

psWaitChannel OBJECT-TYPE
    SYNTAX      DisplayString
    MAX-ACCESS  read-only
    STATUS      current
    DESCRIPTION
                "The address of an event for which the process
		is  sleeping, or in SXBRK state, (if the process 
                is running, this value is blank)."
    ::= { processTableEntry 14 }

psSchedulingClass OBJECT-TYPE
    SYNTAX      DisplayString
    MAX-ACCESS  read-only
    STATUS      current
    DESCRIPTION
                "Scheduling class of the process."
    ::= { processTableEntry 15 }

psAddress OBJECT-TYPE
    SYNTAX      DisplayString
    MAX-ACCESS  read-only
    STATUS      current
    DESCRIPTION
                "The memory address of the process."
    ::= { processTableEntry 16 }

psSize OBJECT-TYPE
    SYNTAX      Integer32
    MAX-ACCESS  read-only
    STATUS      current
    DESCRIPTION
                "The image size( in number of pages) of the swappable
                 process in the main memory."
    ::= { processTableEntry 17 }

psPriority OBJECT-TYPE
    SYNTAX      Integer32
    MAX-ACCESS  read-only
    STATUS      current
    DESCRIPTION
                "The priority of the process. Higher numbers
                 mean higher priority."
    ::= { processTableEntry 18 }

psNice OBJECT-TYPE
    SYNTAX      Integer32
    MAX-ACCESS  read-only
    STATUS      current
    DESCRIPTION
                "Nice value, used in computing priority. Only processes in  
		the time-sharing class have a value for nice."
    ::= { processTableEntry 19 }

psPercentCPUTime OBJECT-TYPE
    SYNTAX      DisplayString
    MAX-ACCESS  read-only
    STATUS      current
    DESCRIPTION
                "Percent of CPU time being consumed by the process."
    ::= { processTableEntry 20 }

psPercentMemory OBJECT-TYPE
    SYNTAX      DisplayString
    MAX-ACCESS  read-only
    STATUS      current
    DESCRIPTION
                "Percent of memory being consumed by the process."
    ::= { processTableEntry 21 }

psCommand OBJECT-TYPE
    SYNTAX      DisplayString
    MAX-ACCESS  read-only
    STATUS      current
    DESCRIPTION
                "The command name by which the process was started."
    ::= { processTableEntry 22 }

psCommandLine OBJECT-TYPE
    SYNTAX      DisplayString
    MAX-ACCESS  read-only
    STATUS      current
    DESCRIPTION
                "Full command line, with command arguments,
		by which the process was started."
    ::= { processTableEntry 23 }

psZoneID OBJECT-TYPE
    SYNTAX      DisplayString
    MAX-ACCESS  read-only
    STATUS      current
    DESCRIPTION
                "Process Zone ID."
    ::= { processTableEntry 24 }

END
