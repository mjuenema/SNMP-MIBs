-------------------------------------------------------
-- Copyright 1999 - Sun Microsystems, Inc. All Rights Reserved.
--
--
-------------------------------------------------------
-- Sun Management Center
-------------------------------------------------------

PROCESS-MONITOR-SUNMANAGEMENTCENTER-MIB DEFINITIONS ::= BEGIN

  IMPORTS
        enterprises, MODULE-IDENTITY, OBJECT-TYPE,  Integer32
                FROM SNMPv2-SMI
         OBJECT-GROUP
                FROM SNMPv2-CONF
         DisplayString, RowStatus
               FROM SNMPv2-TC;


processMonitor MODULE-IDENTITY
    LAST-UPDATED "9908031020Z"
    ORGANIZATION "Sun Microsystems Inc."
    CONTACT-INFO
        "        Sun Microsystems Inc.
       Customer Support
            Postal: 901 San Antonio Road
       Palo Alto, CA-94303-4900
    USA
                         Tel: 650-960-1300
                E-mail: service@sun.com"

    DESCRIPTION
        "The process monitoring allows to monitor the health of one or more 
	processes running on the local host.
        SNMPv2 uses the term 'context' for the MIBs that can have multiple
        instances running on the Agent. If you are using a SNMPv2 based
        thirdparty management station to communicate with such an agent,
        then make sure that you are using the right context information.
        However, if you are using SNMPv1 based management station, then
        add the context information to the SNMP community as follows
        '<community>:<context>'
        This will enable you to access data from multiple instances of
        the same module running on an agent."
    REVISION  "9908031020Z"
    DESCRIPTION
        "Rev 1.0  3rd august 1999 10:20, Initial version Of MIB."

    ::= { modules 20 }


sun       OBJECT IDENTIFIER ::= { enterprises 42 }
prod      OBJECT IDENTIFIER ::= { sun 2 }
sunsymon  OBJECT IDENTIFIER ::= { prod 12 }
agent     OBJECT IDENTIFIER ::= { sunsymon 2 }
modules	OBJECT IDENTIFIER ::= { agent 2 }


pmProcstatsGroup OBJECT-GROUP
        OBJECTS {  pmRowStatus, pmProcEntryName, pmProcCommandNameRX, 
		pmProcArgumentRX, pmProcUIDspec, pmProcEntryDesc, 
		pmProcMonitoringState, pmProcCommandName, pmProcPctCPUTime, 
		pmProcSize, pmProcRSS, pmProcCount, pmAcctProcName,
		pmAcctProcCpuwaittime, pmAcctTextpftime, pmAcctDatapftime,
		pmAcctMajfaults, pmAcctCharios, pmAcctIcontexts,
		pmAcctChildtime, pmAcctUserlocktime, pmAcctTraptime,
		pmAcctTotalswaps, pmAcctDesc, pmAcctProcrule1, 
		pmAcctProcrule2 }
        STATUS current
        DESCRIPTION
		"Processes related statistics."
        ::= { processMonitor 1 }



pmProcTable OBJECT-TYPE
    SYNTAX      SEQUENCE OF PmProcEntry
    MAX-ACCESS  not-accessible
    STATUS      current
    DESCRIPTION
                "Table of entries having information about a group of
		processes."
    ::= { pmProcstatsGroup 1 }

pmProcAcctTable OBJECT-TYPE
    SYNTAX      SEQUENCE OF PmProcAcctEntry
    MAX-ACCESS  not-accessible
    STATUS      current
    DESCRIPTION
                "Table of entries having accounting information about 
		processes."
    ::= { pmProcstatsGroup 2 }

pmProcEntry OBJECT-TYPE
    SYNTAX      PmProcEntry
    MAX-ACCESS  not-accessible
    STATUS      current
    DESCRIPTION
                "Information about a group of processes."
    INDEX  { pmProcEntryName }
    ::= { pmProcTable 1 }

pmProcAcctEntry OBJECT-TYPE
    SYNTAX      PmProcAcctEntry
    MAX-ACCESS  not-accessible
    STATUS      current
    DESCRIPTION
                "Information about processes."
    INDEX  { pmAcctProcName }
    ::= { pmProcAcctTable 1 }

PmProcEntry ::=
    SEQUENCE {
        pmRowStatus
            RowStatus,
        pmProcEntryName
            DisplayString,
        pmProcCommandNameRX
            DisplayString,
        pmProcArgumentRX
            DisplayString,
        pmProcUIDspec
            DisplayString,
        pmProcEntryDesc
            DisplayString,
        pmProcMonitoringState
            DisplayString,
        pmProcCommandName
            DisplayString,
        pmProcPctCPUTime
            DisplayString,
        pmProcSize
            Integer32,
        pmProcRSS
            Integer32,
        pmProcCount
            Integer32,
	pmSystemTime
            DisplayString,
	pmUserTime
            DisplayString
    }

PmProcAcctEntry ::=
    SEQUENCE {
        pmAcctProcName
            DisplayString,
        pmAcctProcCpuwaittime
            DisplayString,
        pmAcctTextpftime
            DisplayString,
        pmAcctDatapftime
            DisplayString,
        pmAcctMajfaults
            DisplayString,
        pmAcctCharios
            DisplayString,
        pmAcctIcontexts
            DisplayString,
        pmAcctChildtime
            DisplayString,
        pmAcctUserlocktime
            DisplayString,
        pmAcctTraptime
            DisplayString,
        pmAcctTotalswaps
            DisplayString,
        pmAcctDesc
            DisplayString,
        pmAcctProcrule1
            DisplayString,
        pmAcctProcrule2
            DisplayString
    }

pmRowStatus OBJECT-TYPE
    SYNTAX      RowStatus 
    MAX-ACCESS  read-write
    STATUS      current
    DESCRIPTION
                "The row status."
    ::= { pmProcEntry 1 }

pmProcEntryName OBJECT-TYPE
    SYNTAX      DisplayString
    MAX-ACCESS  read-only
    STATUS      current
    DESCRIPTION
                "The process entry name that is unique within the table.
		This name represents process(es) grouped depending upon 
                process user id and regular expressions for process 
                command name adn process argument."
    ::= { pmProcEntry 2 }

pmProcCommandNameRX OBJECT-TYPE
    SYNTAX      DisplayString
    MAX-ACCESS  read-write
    STATUS      current
    DESCRIPTION
                "The process command name regular expression pattern.
		This is used as a filter expression and the proceses
		having command name matching this expression are selected."
    ::= { pmProcEntry 3 }

pmProcArgumentRX OBJECT-TYPE
    SYNTAX      DisplayString
    MAX-ACCESS  read-write
    STATUS      current
    DESCRIPTION
                "The process argument regular expression pattern.
		This is used as a filter expression and the proceses
                having argument matching this expression are selected."
    ::= { pmProcEntry 4 }

pmProcUIDspec OBJECT-TYPE
    SYNTAX      DisplayString
    MAX-ACCESS  read-write
    STATUS      current
    DESCRIPTION
                "User ID of the process."
    ::= { pmProcEntry 5 }

pmProcEntryDesc OBJECT-TYPE
    SYNTAX      DisplayString
    MAX-ACCESS  read-write
    STATUS      current
    DESCRIPTION
                "The description of the process entry."
    ::= { pmProcEntry 6 }

pmProcMonitoringState OBJECT-TYPE
    SYNTAX      DisplayString
    MAX-ACCESS  read-only
    STATUS      current
    DESCRIPTION
                "The monitoring state of the entry. The value is
                ON when the row entry is enabled and OFF when the
                row entry is disabled."
    ::= { pmProcEntry 7 }

pmProcCommandName OBJECT-TYPE
    SYNTAX      DisplayString
    MAX-ACCESS  read-only
    STATUS      current
    DESCRIPTION
                "The process command name."
    ::= { pmProcEntry 8 }

pmProcPctCPUTime OBJECT-TYPE
    SYNTAX      DisplayString
    UNITS       "%"
    MAX-ACCESS  read-only
    STATUS      current
    DESCRIPTION
                "The percent CPU used by all the processes in this group."
    ::= { pmProcEntry 9 }

pmProcSize OBJECT-TYPE
    SYNTAX      Integer32
    UNITS        "KB"
    MAX-ACCESS  read-only
    STATUS      current
    DESCRIPTION
                "The total size of all the processes in this group."
    ::= { pmProcEntry 10 }

pmProcRSS OBJECT-TYPE
    SYNTAX      Integer32
    UNITS        "KB"
    MAX-ACCESS  read-only
    STATUS      current
    DESCRIPTION
                "The resident size of all the processes in this group."
    ::= { pmProcEntry 11 }

pmProcCount OBJECT-TYPE
    SYNTAX      Integer32
    MAX-ACCESS  read-only
    STATUS      current
    DESCRIPTION
                "The number of the processes in this group."
    ::= { pmProcEntry 12 }

pmSystemTime OBJECT-TYPE
    SYNTAX      DisplayString
    UNITS       "%"
    MAX-ACCESS  read-only
    STATUS      current
    DESCRIPTION
                "The percent CPU used by the processes doing system calls."
    ::= { pmProcEntry 13 }

pmUserTime OBJECT-TYPE
    SYNTAX      DisplayString
    UNITS       "%"
    MAX-ACCESS  read-only
    STATUS      current
    DESCRIPTION
                "The percent CPU used by the processes doing user level operations."
    ::= { pmProcEntry 14 }

pmAcctProcName OBJECT-TYPE
    SYNTAX      DisplayString
    MAX-ACCESS  read-only
    STATUS      current
    DESCRIPTION
                "The name of the entry"
    ::= { pmProcAcctEntry 1 }

pmAcctProcCpuwaittime OBJECT-TYPE
    SYNTAX      DisplayString
    UNITS       "%"
    MAX-ACCESS  read-only
    STATUS      current
    DESCRIPTION
                "CPU wait time"
    ::= { pmProcAcctEntry 2 }

pmAcctTextpftime OBJECT-TYPE
    SYNTAX      DisplayString
    UNITS       "%"
    MAX-ACCESS  read-only
    STATUS      current
    DESCRIPTION
                "Text page fault sleep time"
    ::= { pmProcAcctEntry 3 }

pmAcctDatapftime OBJECT-TYPE
    SYNTAX      DisplayString
    UNITS       "%"
    MAX-ACCESS  read-only
    STATUS      current
    DESCRIPTION
                "Data page fault sleep time"
    ::= { pmProcAcctEntry 4 }

pmAcctMajfaults OBJECT-TYPE
    SYNTAX      DisplayString
    MAX-ACCESS  read-only
    STATUS      current
    DESCRIPTION
                "Major page faults"
    ::= { pmProcAcctEntry 5 }

pmAcctCharios OBJECT-TYPE
    SYNTAX      DisplayString
    MAX-ACCESS  read-only
    STATUS      current
    DESCRIPTION
                "Characters read and written"
    ::= { pmProcAcctEntry 6 }

pmAcctIcontexts OBJECT-TYPE
    SYNTAX      DisplayString
    MAX-ACCESS  read-only
    STATUS      current
    DESCRIPTION
                "Involuntary context switches"
    ::= { pmProcAcctEntry 7 }

pmAcctChildtime OBJECT-TYPE
    SYNTAX      DisplayString
    UNITS       "%"
    MAX-ACCESS  read-only
    STATUS      current
    DESCRIPTION
                "CPU time for reaped children"
    ::= { pmProcAcctEntry 8 }

pmAcctUserlocktime OBJECT-TYPE
    SYNTAX      DisplayString
    UNITS       "%"
    MAX-ACCESS  read-only
    STATUS      current
    DESCRIPTION
                "User lock time"
    ::= { pmProcAcctEntry 9 }

pmAcctTraptime OBJECT-TYPE
    SYNTAX      DisplayString
    UNITS       "%"
    MAX-ACCESS  read-only
    STATUS      current
    DESCRIPTION
                "System trap time"
    ::= { pmProcAcctEntry 10 }

pmAcctTotalswaps OBJECT-TYPE
    SYNTAX      DisplayString
    UNITS       "%"
    MAX-ACCESS  read-only
    STATUS      current
    DESCRIPTION
                "Total swaps"
    ::= { pmProcAcctEntry 11 }

pmAcctDesc OBJECT-TYPE
    SYNTAX      DisplayString
    MAX-ACCESS  read-only
    STATUS      current
    DESCRIPTION
                "The description of the entry"
    ::= { pmProcAcctEntry 12 }

pmAcctProcrule1 OBJECT-TYPE
    SYNTAX      DisplayString
    MAX-ACCESS  read-only
    STATUS      current
    DESCRIPTION
                "Memory shortage Rule"
    ::= { pmProcAcctEntry 13 }

pmAcctProcrule2 OBJECT-TYPE
    SYNTAX      DisplayString
    MAX-ACCESS  read-only
    STATUS      current
    DESCRIPTION
                "File access rule"
    ::= { pmProcAcctEntry 14 }

END
