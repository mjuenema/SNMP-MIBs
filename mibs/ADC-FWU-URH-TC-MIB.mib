--*****************************************************************
-- ADC-FWU-URH-TC-MIB.mib : MIB file name
-- This is the Texual convention defination MIB.
-- Copyright (c) 2007, 2008, 2009, 2010 by ADC Telecommunications, Inc.
-- All rights reserved.
--
--*****************************************************************

ADC-FWU-URH-TC-MIB	DEFINITIONS ::= BEGIN
	IMPORTS
		TEXTUAL-CONVENTION FROM SNMPv2-TC
		Integer32 FROM SNMPv2-SMI;	

-- TEXTUAL-CONVENTIONS --

ALARMType		::= TEXTUAL-CONVENTION
STATUS			current
DESCRIPTION 	"This defines the severity level of alarms."
SYNTAX 			INTEGER  {	notPresent(-1),
							ok(1),
							minor(2),
							major(3) }

BANDType		::= TEXTUAL-CONVENTION
STATUS			current
DESCRIPTION		"Bands for Flexwave URH."
SYNTAX 			INTEGER  {	undefined (-1),
							classic850(1),
							classic1900(2),
							classicSMR800(3),
							classicSMR900(4),
							classicAws2100(5),
							classic1800(6),
							classicUmts2100(7),
							dualSuperPcs1900(136),
							dualSuper1800(137),
							dualSuperUmts2100(138),
							dualSuperAws2100(139),
							singleSuperPcs1900(200),
							singleSuper1800(201),
							singleSuperUmts2100(202),
							singleSuperAws2100(203),
							singleSuperEgsm900(204),
							superPcs1900(8),
							super1800(9),
							superUmts2100(10),
							superAws2100(11),
							superEgsm900(12),
							superLowerAbc700(13),
							superUpperC700(14),
							superIf850(15),
							superIfPcs1900(16),	
							superIfSmr800(17),
							superIfSmr900(18),
							superIf1800(19),
							superIfUmts2100(20),
							superIfAws2100(21),
							superIfEgsm900(22),
							superIfPath1LowerAbc700(23),
							superIfPath1UpperC700(24),
							superIfPath2LowerAbc700(25),
							superIfPath2UpperC700(26),
							classicApacIden800(27),
							singleSuperLowerAbc700(205),
							singleSuperUpperC700(206),
							singleSuperIf850(207),
							singleSuperIfPcs1900(208),
							singleSuperIfSmr800(209),
							singleSuperIfSmr900(210),
							singleSuperIf1800(211),
							singleSuperIfUmts2100(212),
							singleSuperIfAws2100(213),
							singleSuperIfEgsm900(214),
							singleSuperIfPath1LowerAbc700(215),
							singleSuperIfPath1UpperC700(216),
							singleSuperIfPath2LowerAbc700(217),
							singleSuperIfPath2UpperC700(218),
							dualSuperIfPcs1900(144),
							dualSuperIf1800(147),
							dualSuperIfUmts2100(148),
							dualSuperIfAws2100(149),
							singleSuperIfPath1Aws2100(223), 
							singleSuperIfPath2Aws2100(221), 
							dualSuperIfPath2Pcs1900(156), 
							dualSuperIfPath2Aws2100(157), 
							dualSuperIfPath1Aws2100(159), 
							singleSuperIfPath2850(222), 
							singleSuperIfPath2Pcs1900(220),
							singleSuperIfPath2Smr800(224),
							superIfPath2Smr800(32),
							singleSuperIfPath2Smr900(225),
							superIfPath2Smr900(33),
							superIfPath2850(30),
						        singleSuper2600(226),
                                                        dualSuper2600(162),
						        super2600(34)
						 }

LNAType			::= TEXTUAL-CONVENTION
STATUS			current
DESCRIPTION		"LNA Type for Flexwave URH."
SYNTAX 			INTEGER  { 	undefined (-1),
							cellularA(1),
							cellularB(2),
							smrLow(3),
							smrHigh(4),
							pcs(5),
							aws(6),
							smrLowWide(7),
							fullCellular(8),
							gsm1800(9),
							umts(10),
							egsm900(11),
							lowerABC700(12),
							upperC700(13),
							apac800iDEN(14),
							prismSmr800and900(15),
							prismSmr900and800(16),
							prismSmr800(17),
							prism2600(18) }

DuplexerType	::= TEXTUAL-CONVENTION
STATUS			current
DESCRIPTION		"Duplexer Type for Flexwave URH/Prism."
SYNTAX 			INTEGER  { 	undefined (-1),
							cellularA(1),
							cellularB(2),
							smrLow(3),
							smrHigh(4),
							pcs(5),
							aws(6),
							smrLowWide(7),
							fullCellular(8),
							gsm1800(9),
							umts(10),
							egsm900(11),
							lowerABC(12),
							upperC700(13),
							apac800iDEN(14),
							prismSmr800and900(15),
							prismSmr900and800(16),
							prismSmr800(17),
							cellularApac(18),
							apacEgsm900(19),
							pGsmEgsm900(20),
                                                        prism2600(21) }

OPTICSType		::= TEXTUAL-CONVENTION
STATUS			current
DESCRIPTION		"Defines the type of optics range."
SYNTAX 			INTEGER  {	undefined(-1),
							shortrange(1),
							intermediaterange(2),
							longrange(3) }

MODEType		::= TEXTUAL-CONVENTION
STATUS			current
DESCRIPTION		"Operating modes."
SYNTAX 			INTEGER  {	undefined(-1),
							normal(1),
							standby(2)	}

CONTACTType		::= TEXTUAL-CONVENTION
STATUS			current
DESCRIPTION		"Contact Type."
SYNTAX 			INTEGER  {	notPresent(-1),
							ok(1),
							faulted(2) }

GAINType		::= TEXTUAL-CONVENTION
STATUS			current
DESCRIPTION		"Forward path 0-31dB, Reverse Path 0-31dB) in 1 dB steps.."
SYNTAX 			Integer32  (0 .. 31)

DELAYType		::= TEXTUAL-CONVENTION
STATUS			current
DESCRIPTION		"Delay type in microsecs."
SYNTAX 			Integer32  (1 .. 500)

ALARMManage		::= TEXTUAL-CONVENTION
STATUS			current
DESCRIPTION		"Alarm managing property."
SYNTAX			INTEGER  {	notManageable(0),
							manageable(1)}

MODULEType		::= TEXTUAL-CONVENTION
STATUS			current
DESCRIPTION		"Type of module."
SYNTAX 			INTEGER  {	unknown(-1),
							host(1),
							remote(2),
							serf(3),
							dart(4),
							sfp(5),
							rsi(6),
							rdi(7),
							powerDetector(8),
							lpa(9),
							lna(10),
							duplexer(11) }

ENETType		::= TEXTUAL-CONVENTION
STATUS			current
DESCRIPTION		"Type of Ethernet Port."
SYNTAX 			INTEGER  {	unknown(-1),
							networkPort(1),
							craftPort(2),
							managementPort(3),
							switchPort(4),
							sfpPort(5) }

CATALOGType		::= TEXTUAL-CONVENTION
STATUS			current
DESCRIPTION		"Define the CATALOG state of remote objects."
SYNTAX 			INTEGER  {	normal(1),
							commission(2) }

RauBandType		::= TEXTUAL-CONVENTION
STATUS			current
DESCRIPTION		"The RAU's band type."
SYNTAX 			INTEGER  {	unknown(-1),
							cell850(1),
							pcs1900(2),
							ucabc700(3),
							esmr800(4),
							esmr900(5),
							egsm900(6),
							aws(7),
							wimax2point5(8),
							dcs1800(9),
							umts2100(10),
							psde700(11)	}

UnitID2			::= TEXTUAL-CONVENTION
STATUS			current
DESCRIPTION		"The digital portion of the node address. The sequence of
				digits identifies a unit. One digits = remote at depth 1.
				Two digits = remote at depth 2 and so on.
				No of digits = depth at which the remote lives.
				The sequence has a maximum length of eight (8 Remotes in cascade)."
SYNTAX			Integer32 (1..88888888)

UnitID3			::= TEXTUAL-CONVENTION
STATUS			current
DESCRIPTION		"The analog portion of the node address. Each digit represents
				the port number of the port on the upper level unit from which
				the unit is connected to."
SYNTAX	 		Integer32 (1000..1831)

UnitType		::= TEXTUAL-CONVENTION
STATUS			current
DESCRIPTION		"Type of units present on the system."
SYNTAX			INTEGER  {	unknown(0),
							hostUnit(1),
							urhRemoteUnit(2),                       -- URH Remote
							prismRemoteUnit(3),			-- Prism Remote
							prismIRU(301),                          -- PRM Remote
							remoteDARTChassisUnit(4),		-- IF Remote
							hostExtensionUnit(401),			-- HEU Remote
							ifeu(5), 				-- IF Expansion Unit
							mRau(6), 				-- main RAU
							sRau(7), 				-- secondary  RAU
							converterBox(8),
							fusionRAU(9)	}

ALARMEnable		::= TEXTUAL-CONVENTION
STATUS			current
DESCRIPTION		"enable/disable of alarm."
SYNTAX			INTEGER  {	disable(0),
							enable(1)	}

END
