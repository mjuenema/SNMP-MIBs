-- =============================================================================
-- Copyright (C) 2009 by HUAWEI TECHNOLOGIES. All rights reserved.
--    
-- Description: . 
-- Reference: Huawei Enterprise MIB
-- Version: 1.0
-- History: 
--          V1.0 The initial version created by LiShengbai 90004270. 
-- =============================================================================

HUAWEI-SECURITY-GTP-MIB DEFINITIONS ::= BEGIN
 
	IMPORTS   
		Counter32, Gauge32, Counter64, OBJECT-TYPE, MODULE-IDENTITY
			FROM SNMPv2-SMI 
		MODULE-COMPLIANCE, OBJECT-GROUP, NOTIFICATION-GROUP          
		            FROM SNMPv2-CONF
    		enterprises			
		            FROM RFC1155-SMI; 

		            
		hwGTP MODULE-IDENTITY 
		        LAST-UPDATED "201002020900Z"        -- February 2, 2010 at 09:00 GMT
		        ORGANIZATION 
		            "Huawei Symantec Technologies Co., Ltd."
		        CONTACT-INFO 
		            "3rd Floor,Section D, Keshi Building, No.28, Xinxi Rd., Shangdi,
		         	 Hai-Dian District Beijing P.R. China
			         Zip:100085
			         Http://www.huaweisymantec.com
                     "
		        DESCRIPTION 
		            "V1.00
			         The GTP mib is for Eudemon and USG product series."
		        ::= { hwSecurity 35 }
		
-- ===============================================
-- Node definitions
-- ===============================================
	    
	    -- 1.3.6.1.4.1.2011
		huawei OBJECT IDENTIFIER ::= { enterprises 2011 }
	        
		-- 1.3.6.1.4.1.2011.6
		huaweiUtility OBJECT IDENTIFIER ::= { huawei 6 }
	        
		-- 1.3.6.1.4.1.2011.6.122
		hwSecurity OBJECT IDENTIFIER ::= { huaweiUtility 122 }     
		
-- ===============================================
-- Begin the hwGTPGlobalStats.
-- =============================================== 
	    hwGTPStats OBJECT IDENTIFIER ::= { hwGTP 1 }
		
	    	hwGTPRcvV0GtpC OBJECT-TYPE
			SYNTAX Counter32 
			MAX-ACCESS read-only
			STATUS current
			DESCRIPTION
				"Number of received v0 gtpc packets."
			::= { hwGTPStats 1 }  
			
			hwGTPDiscardV0GtpC OBJECT-TYPE
			SYNTAX Counter32 
			MAX-ACCESS read-only
			STATUS current
			DESCRIPTION
				"Number of discarded v0 gtpc packets."
			::= { hwGTPStats 2 }    
			
			hwGTPRcvV1GtpC OBJECT-TYPE
			SYNTAX Counter32 
			MAX-ACCESS read-only
			STATUS current
			DESCRIPTION
				"Number of received v1 gtpc packets."
			::= { hwGTPStats 3 }  
			
			hwGTPDiscardV1GtpC OBJECT-TYPE
			SYNTAX Counter32 
			MAX-ACCESS read-only
			STATUS current
			DESCRIPTION
				"Number of discarded v1 gtpc packets."
			::= { hwGTPStats 4 }
            
            hwGTPRcvV0GtpU OBJECT-TYPE
			SYNTAX Counter32 
			MAX-ACCESS read-only
			STATUS current
			DESCRIPTION
				"Number of received v0 gtpu packets."
			::= { hwGTPStats 5 }
			
            hwGTPDiscardV0GtpU OBJECT-TYPE
			SYNTAX Counter32 
			MAX-ACCESS read-only
			STATUS current
			DESCRIPTION
				"Number of discarded v0 gtpu packets."
			::= { hwGTPStats 6 }

            hwGTPRcvV1GtpU OBJECT-TYPE
			SYNTAX Counter32 
			MAX-ACCESS read-only
			STATUS current
			DESCRIPTION
				"Number of received v1 gtpu packets."
			::= { hwGTPStats 7 }						        

            hwGTPDiscardV1GtpU OBJECT-TYPE
			SYNTAX Counter32 
			MAX-ACCESS read-only
			STATUS current
			DESCRIPTION
				"Number of discarded v1 gtpu packets."
			::= { hwGTPStats 8 }
			
            hwGTPRcvGtpV0 OBJECT-TYPE
			SYNTAX Counter32 
			MAX-ACCESS read-only
			STATUS current
			DESCRIPTION
				"Number of received v0 gtp packets."
			::= { hwGTPStats 9 }
			
            hwGTPDiscardGtpV0 OBJECT-TYPE
			SYNTAX Counter32 
			MAX-ACCESS read-only
			STATUS current
			DESCRIPTION
				"Number of discarded v0 gtp packets."
			::= { hwGTPStats 10 }
			
            hwGTPRcvGtpV1 OBJECT-TYPE
			SYNTAX Counter32 
			MAX-ACCESS read-only
			STATUS current
			DESCRIPTION
				"Number of received v1 gtp packets ."
			::= { hwGTPStats 11 }
			
            hwGTPDiscardGtpV1 OBJECT-TYPE
			SYNTAX Counter32 
			MAX-ACCESS read-only
			STATUS current
			DESCRIPTION
				"Number of discarded v1 gtp packets."
			::= { hwGTPStats 12 }
			
            hwGTPRcvGtpCharge OBJECT-TYPE
			SYNTAX Counter32 
			MAX-ACCESS read-only
			STATUS current
			DESCRIPTION
				"Number of received gtp' packets."
			::= { hwGTPStats 13 }
			
            hwGTPDiscardGtpCharge OBJECT-TYPE
			SYNTAX Counter32 
			MAX-ACCESS read-only
			STATUS current
			DESCRIPTION
				"Number of discarded gtp' packets."
			::= { hwGTPStats 14 }
			
            hwGTPRcvUnknownVersion OBJECT-TYPE
			SYNTAX Counter32 
			MAX-ACCESS read-only
			STATUS current
			DESCRIPTION
				"Number of received unknown version packets."
			::= { hwGTPStats 15 }
			
            hwGTPDiscardUnknownVersion OBJECT-TYPE
			SYNTAX Counter32 
			MAX-ACCESS read-only
			STATUS current
			DESCRIPTION
				"Number of discarded unknown version packets."
			::= { hwGTPStats 16 }
			
            hwGTPRcvUnknownMessage OBJECT-TYPE
			SYNTAX Counter32 
			MAX-ACCESS read-only
			STATUS current
			DESCRIPTION
				"Number of received unknown message packets."
			::= { hwGTPStats 17 }
			
            hwGTPDiscardUnknownMessage OBJECT-TYPE
			SYNTAX Counter32 
			MAX-ACCESS read-only
			STATUS current
			DESCRIPTION
				"Number of discarded unknown message packets."
			::= { hwGTPStats 18 }
			
            hwGTPRcvGtpCPackets OBJECT-TYPE
			SYNTAX Counter32 
			MAX-ACCESS read-only
			STATUS current
			DESCRIPTION
				"Number of received gtpc packets."
			::= { hwGTPStats 19 }
			
            hwGTPDiscardGtpCPackets OBJECT-TYPE
			SYNTAX Counter32 
			MAX-ACCESS read-only
			STATUS current
			DESCRIPTION
				"Number of discarded gtpc packets."
			::= { hwGTPStats 20 }
			
            hwGTPRcvGtpUPackets OBJECT-TYPE
			SYNTAX Counter32 
			MAX-ACCESS read-only
			STATUS current
			DESCRIPTION
				"Number of received gtpu packets."
			::= { hwGTPStats 21 }
			
            hwGTPDiscardGtpUPackets OBJECT-TYPE
			SYNTAX Counter32 
			MAX-ACCESS read-only
			STATUS current
			DESCRIPTION
				"Number of discarded gtpu packets."
			::= { hwGTPStats 22 }
			
            hwGTPDropGtpTurnnelPackets OBJECT-TYPE
			SYNTAX Counter32 
			MAX-ACCESS read-only
			STATUS current
			DESCRIPTION
				"Number of discarded packets according to gtp tunnel speed."
			::= { hwGTPStats 23 }
			
            hwGTPExchangesNotAcceptedByPeerGsnPackets OBJECT-TYPE
			SYNTAX Counter32 
			MAX-ACCESS read-only
			STATUS current
			DESCRIPTION
				"Number of packets that GTP exchanges not accepted by peer GSN."
			::= { hwGTPStats 24 }	
			
			hwGTPTunnelNum OBJECT-TYPE
			SYNTAX Counter32 
			MAX-ACCESS read-only
			STATUS current
			DESCRIPTION
				"Number of GTP tunnels."
			::= { hwGTPStats 25 }	
	        
-- ===============================================
-- GTPTrapObject.
-- ===============================================
		    hwGTPNotification OBJECT IDENTIFIER ::= { hwGTP 0 } 
		    hwGTPTrapObject OBJECT IDENTIFIER ::= { hwGTPNotification 1 }   

		    hwGTPCtrMsgRate OBJECT-TYPE
        	SYNTAX Gauge32 
        	MAX-ACCESS accessible-for-notify
        	STATUS current
        	DESCRIPTION
            		"The GTP control rate."
        	::= { hwGTPTrapObject 1 } 
        	
		    hwGTPActualRate OBJECT-TYPE
        	SYNTAX Gauge32 
        	MAX-ACCESS accessible-for-notify
        	STATUS current
        	DESCRIPTION
            		"The rate for receiving packets on the management plane."
        	::= { hwGTPTrapObject 2 }   

-- ===============================================
-- definition of traps.      
-- =============================================== 
		    hwGTPTraps OBJECT IDENTIFIER ::= { hwGTPNotification 2 }
       	      	
            hwGTPOverCtrMsgRate NOTIFICATION-TYPE
			OBJECTS {
			          hwGTPCtrMsgRate,
			          hwGTPActualRate
			        }
			STATUS     current
			DESCRIPTION
			    "Send the message when the rate for receiving packets on the management plane exceeds the threshold of the GTP control rate."
			::= { hwGTPTraps 1 }
 
-- ===============================================
-- Conformance Information             
-- ===============================================

		hwGTPMibConformance OBJECT IDENTIFIER ::= { hwGTP 2 }
		
		hwGTPMibCompliances OBJECT IDENTIFIER ::= { hwGTPMibConformance 1 }
		
		hwGTPMibGroups OBJECT IDENTIFIER ::= { hwGTPMibConformance 2 }
  
-- ===============================================
-- Compliance Statements             
-- ===============================================
        hwGTPMibCompliance MODULE-COMPLIANCE
			 STATUS current
			 DESCRIPTION 
				" "
			 MODULE -- this module
			 MANDATORY-GROUPS 
				{  
				hwGTPTrapObjectGroup,
				hwGTPTrapsGroup,  				
				hwGTPGlobalStatsGroup
				}
			::= { hwGTPMibCompliances 1 }   

		hwGTPTrapObjectGroup OBJECT-GROUP
			OBJECTS { 
			        hwGTPCtrMsgRate,
			        hwGTPActualRate		
				}
			STATUS current
			DESCRIPTION 
				"This table specifies the objects used for traps."
			::= { hwGTPMibGroups 1 }
			
	    hwGTPTrapsGroup NOTIFICATION-GROUP
			NOTIFICATIONS {                               
                    hwGTPOverCtrMsgRate
               		}
			STATUS current
			DESCRIPTION 
				"GTP traps."
			::= { hwGTPMibGroups 2 }
	     
		hwIPSecGlobalStatsGroup OBJECT-GROUP
			OBJECTS { 
					hwGTPRcvV0GtpC,
					hwGTPDiscardV0GtpC,
					hwGTPRcvV1GtpC,
					hwGTPDiscardV1GtpC,
					hwGTPRcvV0GtpU,
					hwGTPDiscardV0GtpU,
					hwGTPRcvV1GtpU,
					hwGTPDiscardV1GtpU,
					hwGTPRcvGtpV0,
					hwGTPDiscardGtpV0,
					hwGTPRcvGtpV1,
					hwGTPDiscardGtpV1,
					hwGTPRcvGtpCharge,
					hwGTPDiscardGtpCharge,
					hwGTPRcvUnknownVersion,
					hwGTPDiscardUnknownVersion,
					hwGTPRcvUnknownMessage,
					hwGTPDiscardUnknownMessage,
					hwGTPRcvGtpCPackets,
					hwGTPDiscardGtpCPackets,
					hwGTPRcvGtpUPackets,
					hwGTPDiscardGtpUPackets,
					hwGTPDropGtpTurnnelPackets,
					hwGTPExchangesNotAcceptedByPeerGsnPackets,
					hwGTPTunnelNum						
				}
			STATUS current
			DESCRIPTION 
				"This table specifies the statistics information for GTP."
			::= { hwGTPMibGroups 3 }			     

    																																													        
	END
