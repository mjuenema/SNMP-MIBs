-- =================================================================
-- Copyright (C) 2008 by H3C Technologies. All rights reserved.
--
-- Description:the definition of H3C Entity Vendortype OID
-- Reference:
-- Version: V4.46
-- History:
-- V1.0 2004.05.13  Created by lvzhenfeng, modified by gaolong.
-- V1.1 2004.05.22  Adjusted by gaolong and lvzhenfeng.
--   1. Adjust module name to hh3cEntityVendorTypeOID and its location is set to { hh3c 3 }.
--   2. Rename module name prefix from hh3cevtModule to hh3cevtModuleRt_
--   and hh3cevtModuleSw_ for routers and switches seperately.
--   3. Add hh3cevtSubModuleRouter and hh3cevtSubModuleSwitch under hh3cevtModule.
--   4. Split port type into two groups, one for routers, another for switches.
-- V1.11 2004.6.17 add hh3cevtHotSwapFan node by limeng for garibaldi
-- V1.12 2004.7.19 add hh3cevtModuleSwitchType {117-138}
-- V1.13 2004.7.29 add hh3cevtPortSwitchType {50-58}
-- V1.14 2004.8.12 add hh3cevtModuleSw_LSA1FP8U(hh3cevtModuleSwitchType 139)
-- V1.15 2004.8.25 change enumeration name
--                     from hh3cevtModuleSw_LS81SFCA(120) to hh3cevtModuleSw_LS81SRPG0(120),
--                     from hh3cevtModuleSw_LS81SFCB(121) to hh3cevtModuleSw_LS81SRPG1(121),
--                     from hh3cevtModuleSw_LS81SFCC(122) to hh3cevtModuleSw_LS81SRPG2(122),
--                     from hh3cevtModuleSw_LS81SFCD(123) to hh3cevtModuleSw_LS81SRPG3(123).
--                 modify comments for these enumerations as well.
-- V1.2  2004.8.26 add sub identifier of hh3cevtPortSwitchType from 59 to 71.
-- V1.21  2004.09.08 add sub identifier of hh3cevtModuleSwitchType from 140 to 148.
-- V1.3  2004-09-14 add subidentifier under hh3cevtModuleSwitchType from 149 to 157 by wangyahui
--                  add subidentifier under hh3cevtModuleSwitchType from 158 to 159 by kangyinan
--                  add subidentifier under hh3cevtModuleSwitchType from 72 to 93 by wangyahui
--                  add subidentifier under hh3cevtModuleSwitchType from 94 to 96 by kangyinan
--                  add type description for hh3cevtModuleSw_SP4, hh3cevtModuleSw_UP1, hh3cevtModuleSw_XP4 by kangyinan
-- V2.0 2004-10-12 updated by gaolong
--      Change all underscore('_') characters to hyphen characters('-') because underscore character is not allowed in MIB module.
--      Remove some adjacent hyphens
-- V2.1  2004-10-19 add subidentifier under hh3cevtModuleSwitchType from 160 to 162 by kangyinan
--                  add subidentifier under hh3cevtPortSwitchType 97 by kangyinan
-- V2.2  2004-09-18 add sub identifier for hh3cevtModuleRouterType from 111 to 117 by taotao
-- V2.3  2004-11-18 add sub identifier 2 under hh3cevtFan by liyutao
-- V2.4  2004-11-23 add subidentifier under hh3cevtModuleSwitchType from 163 to 166 by zhangchengmei
-- V2.5  2004-12-04 add subidentifier 118 under hh3cevtModuleRouterType by lizhiyong
-- V2.6  2004-12-23 add sub identifier 4 to 7 under hh3cevtPowerSupply by Zhangjianfeng
--                  add sub identifier 167 to 169 under hh3cevtModuleSwitchType by Zhangjianfeng
-- V2.7  2004-12-26 add subidentifier 170 under hh3cevtModuleSwitchType by wangyahui
-- v2.8  2004-12-23 add subidentifier under hh3cevtModuleSwitchType from 171 to 172 and
--                  add sub identifier 98 to 99 under hh3cevtPortSwitchType by liyue
-- V2.9  2004-12-26 add sub identifier 173 under hh3cevtModuleSwitchType by Zhangjianfeng
--                  add sub identifier 100 for 24G cascade port under hh3cevtPort by Zhangjianfeng
-- V3.0  2004-01-07 add subidentifier 174 and 175 under hh3cevtModuleSwitchType by wangyahui
-- V3.1  2005-01-31 add subidentifier 176 under hh3cevtModuleSwitchType by wangyahui
-- V3.2  2005-02-26 add subidentifier 177 under hh3cevtModuleSwitchType by zhangchengmei
--                  add subidentifier 101 to 137 under hh3cevtPortSwitchType by zhangchengmei
--                  add subidentifier 178 under hh3cevtModuleSwitchType by zhouqiang
--                  add subidentifier 138 under hh3cevtPortSwitchType by zhouqiang
--                  add subidentifier 179 to 180 under hh3cevtModuleSwitchType by wangyahui
--                  remove trailing spaces
-- V3.3  2005-03-22 add subidentifier 181 to 187 under hh3cevtModuleSwitchType by zhangchengmei
-- V3.4  2004-12-29 add subidentifier 119 to 120 under hh3cevtModuleRouterType by lizhiyong
-- V3.5  2005-04-12 add subidentifier 141 to 144 under hh3cevtModuleRouterType by yinxiaoyu
--                  add subidentifier 30 to 33 under hh3cevtPortRouterType by yinxiaoyu
-- V3.6  2005-04-07 add subidentifier 121 to 140 under hh3cevtModuleRouterType by taotao
--                  change the name of subidentifier 118 under hh3cevtModuleRouterType by taotao
--                  adjust file format
-- V3.7  2005-05-10 add subidentifier 188 to 216 under hh3cevtModuleSwitchType by zhangchengmei
-- V3.8  2005-06-12 add subidentifier 145 to 149 under hh3cevtModuleRouterType,
--                  add subidentifier 34 under hh3cevtPortRouterType by wanghanlin
-- V3.9  2005-06-22 add subidentifier 150 under hh3cevtModuleRouterType by yinxiaoyu
-- V4.0  2005-07-18 add subidentifier 217 to 219 under hh3cevtModuleSwitchType by yangliming
--                  add subidentifier 139 to 142 under hh3cevtPortSwitchType by wangyahui
-- V4.01 2005-07-29 add subidentifier 220 to 225 under hh3cevtModuleSwitchType by wangyahui
-- V4.02 2005-07-21 change the name of subidentifier 183 under hh3cevtModuleSwitchType,
--                  add subidentifier 226 to 227 under hh3cevtModuleSwitchType by zhangchengmei
--       2005-08-29 add subidentifier 143 under hh3cevtPortSwitchType by qianxiaoyu
--                  add subidentifier 151 to 161 under hh3cevtModuleRouterType by taotao
--                  add subidentifier 35 to 41 under hh3cevtPortRouterType by taotao
-- V4.03 2005-09-07 add hh3cevtCPU and hh3cevtGeneralCPU by taotao
--                  add subidentifier 162 to 163 under hh3cevtModuleRouterType by taotao
--                  adjust file format by gaolong
-- V4.04 2005-09-13 add subidentifier 228 to 253 under hh3cevtModuleSwitchType by zhangchengmei
--       2005-09-13 add subidentifier 257 to 268 under hh3cevtModuleSwitchType by zhangchengmei
-- V4.05 2005-11-04 add subidentifier 144 to 149 under hh3cevtPortSwitchType by zhangchengmei
--                  add subidentifier 150 under hh3cevtPortSwitchType by huangyuetao
--                  add subidentifier 269 to 271 under hh3cevtModuleSwitchType by yangxiaopeng
--                  add subidentifier 272 under hh3cevtModuleSwitchType by qianxiaoyu
--                  add subidentifier 164 to 165 under hh3cevtModuleRouterType by xuejiayong
-- V4.06 2005-11-24 add subidentifier 500 to 501 under hh3cevtModuleSwitchType by wangyahui
-- V4.07 2005-11-28 add subidentifier 300 to 316 under hh3cevtModuleSwitchType by zhangchengmei
-- V4.08 2005-12-09 add subidentifier 220 to 223 under hh3cevtModuleRouterType by taotao
-- V4.09 2005-12-30 add subidentifier 151 to 170 under hh3cevtPortSwitchType by zhangchengmei
-- V4.10 2006-01-04 add subidentifier 701 under hh3cevtModuleSwitchType by qianxiaoyu
-- V4.11 2006-02-12 add subidentifier 200 to 219 under hh3cevtModuleRouterType by liutinghai
--                  add subidentifier 702 under hh3cevtModuleSwitchType by chenxiaohui
--                  add subidentifier 600 under hh3cevtModuleRouterType by qujin
--                  add subidentifier 317 under hh3cevtModuleSwitchType by zhangchengmei
-- V4.12 2006-02-24 add subidentifier 703 under hh3cevtModuleSwitchType by chijuntao
--                  add subidentifier 224 to 228 under hh3cevtModuleRouterType by taotao
-- V4.13 2006-02-27 add subidentifier 171 to 174 under hh3cevtPortSwitchType by wangshunli
--                  add subidentifier 318 to 336 under hh3cevtModuleSwitchType by zhaiyingying
-- V4.14 2006-03-14 add subidentifier 175 under hh3cevtPortSwitchType by wangyahui
--                  add subidentifier 502 to 504 under hh3cevtModuleSwitchType by wangyahui
-- V4.15 2006-04-03 add subidentifier 176 under hh3cevtPortSwitchType by wangyahui
-- V4.16 2006-04-26 add subidentifier 229 to 233 under hh3cevtModuleRouterType by taotao
-- V4.17 2006-04-21 add subidentifier 337 to 340 under hh3cevtModuleSwitchType by zhaiyingying
-- V4.18 2006-06-05 add subidentifier 704 to 705 under hh3cevtModuleSwitchType by zhangxianguo
--                  add subidentifier 505 to 506 under hh3cevtModuleSwitchType by zhangjianfeng
--                  add subidentifier 341 to 349 under hh3cevtModuleSwitchType by zhaiyingying
--                  add subidentifier 177 to 178 under hh3cevtPortSwitchType by zhangjianfeng
--                  add subidentifier 179 to 180 under hh3cevtPortSwitchType by zhangxianguo
-- V4.19 2006-08-23 add subidentifier 507 to 509 under hh3cevtModuleSwitchType by wangyahui
--                  modify object name of subidentifier 502 and 503 under hh3cevtModuleSwitchType by wangyahui
--                  add subidentifier 234 to 235 under hh3cevtModuleRouterType by liutinghai
--                  add subidentifier 350 to 357 under hh3cevtModuleSwitchType by zhaiyingying
-- V4.20 2006-09-26 add subidentifier 510 to 514 under hh3cevtModuleSwitchType by wangyahui
--                  add subidentifier 601 to 603 under hh3cevtModuleRouterType by zhoujianming
--                  add subidentifier 236 to 239 under hh3cevtModuleRouterType by qikai
--                  add subidentifier 240 to 241 under hh3cevtModuleRouterType by liutinghai
--                  add subidentifier 800 to 801 under hh3cevtModuleSwitchType by luoguixing
-- V4.21 2006-10-26 add subidentifier 358 to 370 under hh3cevtModuleSwitchType by zhaiyingying
--                  add subidentifier 183 under hh3cevtPortSwitchType by zhaiyingying
--                  add subidentifier 515 to 526 under hh3cevtModuleSwitchType by wangyahui
--                  add subidentifier 181 to 182 under hh3cevtPortSwitchType by wangyahui
-- V4.22 2006-11-02 add subidentifier 527 to 536 under hh3cevtModuleSwitchType by wangyahui
--                  modify description of 511 to 513 under hh3cevtModuleSwitchType by wangyahui
--       2006-11-10 add subidentifier 371 to 378 under hh3cevtModuleSwitchType by shuxiongtao
--       2006-11-08 add subidentifier 184 to 185 under hh3cevtPortSwitchType by zhaiyingying
-- V4.23 2006-12-04 add subidentifier 242 to 243 under hh3cevtModuleRouterType by liutinghai
-- V4.24 2006-01-24 add subidentifier 244 to 245 under hh3cevtModuleRouterType by liutinghai
-- V4.25 2007-03-19 add subidentifier 537 under hh3cevtModuleSwitchType by wangyahui
-- V4.26 2007-04-12 add subidentifier 538 to 542 under hh3cevtModuleSwitchType by wangyahui
-- V4.27 2007-04-25 add subidentifier 706 under hh3cevtModuleSwitchType by zhangzongyi
--                  add subidentifier 379 to 380 under hh3cevtModuleSwitchType by zhaiyingying
--                  add subidentifier 246 to 250 under hh3cevtModuleRouterType by liutinghai
--                  add subidentifier 42 under hh3cevtPortRouterType by liutinghai
-- V4.28 2007-05-28 add subidentifier 707 under hh3cevtModuleSwitchType by ligaoxu
--                  add subidentifier 381 to 392 under hh3cevtModuleSwitchType by shuxiongtao
--                  modify name of subidentifier 371 and 374 under hh3cevtModuleSwitchType by shuxiongtao
--                  add subidentifier 251 to 253 under hh3cevtModuleRouterType by qikai
--                  add subidentifier 254 to 255 under hh3cevtModuleRouterType by liutinghai
--                  add subidentifier 186 under hh3cevtPortSwitchType by jinzhaoqiong
-- V4.29 2007-07-09 add subidentifier 543 to 551 under hh3cevtModuleSwitchType by zhangjianfeng
--                  add subidentifier 552 to 554 under hh3cevtModuleSwitchType by wangyahui
-- V4.30 2007-07-26 add subidentifier 400 under hh3cevtModuleRouterType by xuejiayong
--                  add subidentifier 708 under hh3cevtModuleSwitchType by xiuyihong
--                  add subidentifier 256 to 258 under hh3cevtModuleRouterType by qikai
--                  add subidentifier 259 to 263 under hh3cevtModuleRouterType by liutinghai
--                  add subidentifier 3 to 5 under hh3cevtOther by gaolong
-- V4.31 2007-08-27 add subidentifier 187 to 188 under hh3cevtPortSwitchType by ruanhan
--                  add subidentifier 802 to 804 under hh3cevtModuleSwitchType by luoguixing
--                  add subidentifier 393 to 397 under hh3cevtModuleSwitchType by shuxiongtao
-- V4.32 2007-09-25 add subidentifier 555 to 559 under hh3cevtModuleSwitchType by wangyahui
--                  add subidentifier 805 under hh3cevtModuleSwitchType by luoguixing
--                  add subidentifier 401 to 403 under hh3cevtModuleRouterType by tanwen
--                  add subidentifier 43 under hh3cevtPortRouterType by qikai
--                  add subidentifier 266 to 267 under hh3cevtModuleRouterType by qikai
--                  add subidentifier 398 to 399 under hh3cevtModuleSwitchType by hexuefei
-- V4.33 2007-10-22 add subidentifier 189 under hh3cevtPortSwitchType by liaoxin
--                  add subidentifier 268 under hh3cevtModuleRouterType by liutinghai
-- V4.34 2007-11-26 add subidentifier 269 to 273 under hh3cevtModuleRouterType by liutinghai
--                  add subidentifier 274 to 276 under hh3cevtModuleRouterType by qikai
--                  add subidentifier 404 to 406 under hh3cevtModuleRouterType by chaiyaqin
--                  add subidentifier 400 to 407 under hh3cevtModuleSwitchType by shuxiongtao
-- V4.35 2007-12-27 add subidentifier 277 to 278 under hh3cevtModuleRouterType by liutinghai
--                  add subidentifier 560 to 568 under hh3cevtModuleSwitchType by wangyahui
-- V4.36 2008-01-30 add subidentifier 408 under hh3cevtModuleSwitchType by hexuefei
--                  add subidentifier 569 to 572 under hh3cevtModuleSwitchType by wangyahui
--                  add subidentifier 279 to 280 under hh3cevtModuleRouterType by qikai
--                  add subidentifier 190 under hh3cevtPortSwitchType by liujingya
-- V4.37 2008-02-20 add subidentifier 720 to 724 under hh3cevtModuleSwitchType by chaiyaqin
--                  add subidentifier 573 to 574 under hh3cevtModuleSwitchType by zhangjianfeng
--                  modify name of subidentifier 546 and 550 under hh3cevtModuleSwitchType by zhangjianfeng
--                  add subidentifier 575 to 576 under hh3cevtModuleSwitchType by wangyahui
--                  add subidentifier 281 under hh3cevtModuleRouterType by liutinghai
-- V4.38 2008-03-31 add subidentifier 806 to 808 under hh3cevtModuleSwitchType by luoguixing
--                  add subidentifier 709 to 715 under hh3cevtModuleSwitchType by wangcong
--                  add subidentifier 191 to 196 under hh3cevtPortSwitchType by wangcong
--                  add subidentifier 44 under hh3cevtPortRouterType by liutinghai
--                  add subidentifier 409 to 431 under hh3cevtModuleSwitchType by zhaiyingying
--                  add subidentifier 432 under hh3cevtModuleSwitchType by shuxiongtao
-- V4.39 2008-04-29 add subidentifier 577 to 589 under hh3cevtModuleSwitchType by wangyahui
--                  add subidentifier 407 to 409 under hh3cevtModuleRouterType by tanwen
-- V4.40 2008-05-31 add subidentifier 410 to 413 under hh3cevtModuleRouterType by tanwen
--                  add subidentifier 282 to 284 under hh3cevtModuleRouterType by qikai
--                  add subidentifier 285 to 286 under hh3cevtModuleRouterType by liutinghai
-- V4.41 2008-07-28 add subidentifier 590 to 592 under hh3cevtModuleSwitchType by wangyahui
--                  add subidentifier 287 to 289 under hh3cevtModuleRouterType by qikai
--                  add subidentifier 290 to 291 under hh3cevtModuleRouterType by liutinghai
--                  add subidentifier 45 to 46 under hh3cevtPortRouterType by liutinghai
--                  add subidentifier 809 to 810 under hh3cevtModuleSwitchType by luoguixing
-- V4.42 2008-08-26 modify name of 379 and 399 under hh3cevtModuleSwitchType by wangwei
--                  modify description of 408 under hh3cevtModuleSwitchType by wangwei
--                  modify name and description of 804 under hh3cevtModuleSwitchType by wangwei
--                  add subidentifier 433 to 434 under hh3cevtModuleSwitchType by wangwei
--                  add subidentifier 593 to 595 under hh3cevtModuleSwitchType by wangyahui
--                  modify name and description of 256 and 288 under hh3cevtPortRouterType by qikai
--                  add subidentifier 292 to 293 under hh3cevtPortRouterType by qikai
-- V4.43 2008-10-13 add subidentifier 725 under hh3cevtModuleSwitchType by ruanhan
--                  add subidentifier 197 under hh3cevtPortSwitchType by ruanhan
--                  add subidentifier 811 under hh3cevtModuleSwitchType by luoguixing
--                  add subidentifier 596 to 601 under hh3cevtModuleSwitchType by wangyahui
-- V4.44 2008-11-04 add subidentifier 294 under hh3cevtPortRouterType by qikai
--                  add subidentifier 414 under hh3cevtModuleRouterType by tanwen
-- V4.45 2008-12-01 add subidentifier 602 to 619 under hh3cevtModuleSwitchType by wangyahui
--                  add subidentifier 435 to 442 under hh3cevtModuleSwitchType by zhaiyingying
--                  modify name of 546 under hh3cevtModuleSwitchType by zhangjianfeng
--                  add subidentifier 295 under hh3cevtPortRouterType by qikai
--                  add subidentifier 443 under hh3cevtModuleSwitchType by shuxiongtao
-- V4.46 2008-12-25 add subidentifier 620 to 622 under hh3cevtModuleSwitchType by wangyahui
--                  add subidentifier 716 to 718 under hh3cevtModuleSwitchType by zhangshilin
--                  add subidentifier 444 to 445 under hh3cevtModuleSwitchType by wangchang
-- =================================================================
HH3C-ENTITY-VENDORTYPE-OID-MIB DEFINITIONS ::= BEGIN

IMPORTS
    MODULE-IDENTITY
        FROM SNMPv2-SMI
    hh3c
        FROM HH3C-OID-MIB;


hh3cEntityVendorTypeOID MODULE-IDENTITY

        LAST-UPDATED "200403280000Z"
        ORGANIZATION "Hangzhou H3C Technologies Co., Ltd."
        CONTACT-INFO
            "Platform Team H3C Technologies Co., Ltd.
            Hai-Dian District Beijing P.R. China
            Zip:100085
            http://www.h3c.com"
        DESCRIPTION
            "The private MIB includes the definition of the object
            identifiers on H3C products, which are used by the
            entPhysicalTable of the ENTITY-MIB to uniquely identify the
            type of each physical entry."
        ::= { hh3c 3 }


hh3cEntityVendortypeObjects   OBJECT IDENTIFIER ::= { hh3cEntityVendorTypeOID 1 }

-- This MIB assigns OIDs for use as the values of entPhysicalVendorType.
-- The subtrees in which the OID values are assigned, are structured
-- into a hierarchy based on the values of RFC 2037's PhysicalClass
-- textual convention.  For reference, the definition of PhysicalClass
-- is as follows:
--
--      PhysicalClass ::= TEXTUAL-CONVENTION
--      STATUS          current
--      DESCRIPTION
--             "An enumerated value which provides an indication of the
--              general hardware type of a particular physical entity."
--      SYNTAX      INTEGER  {
--              other(1),
--              unknown(2),
--              chassis(3),
--              backplane(4),
--              container(5),    e.g. slot or daughter-card holder
--              powerSupply(6),
--              fan(7),
--              sensor(8),
--              module(9),       e.g. plug-in card or daughter-card
--              port(10),
--              stack(11)        e.g., stack of multiple chassis entities
--          }
--

hh3cevtOther     OBJECT IDENTIFIER ::= { hh3cEntityVendortypeObjects 1 }

-- May be defined detailed in future.

hh3cevtOtherUnknownCard  OBJECT IDENTIFIER ::= { hh3cevtOther 1 }
hh3cevtCPU               OBJECT IDENTIFIER ::= { hh3cevtOther 2 }
hh3cevtDOM               OBJECT IDENTIFIER ::= { hh3cevtOther 3 }  -- Disk on Module
hh3cevtCFCard            OBJECT IDENTIFIER ::= { hh3cevtOther 4 }  -- Compact Flash Card
hh3cevtHardDisk          OBJECT IDENTIFIER ::= { hh3cevtOther 5 }  -- Hard Disk

-- hh3cevtGeneralCPU is a general vendor type of CPU.  It is used only for
-- general purpose.  It is strongly recommended that this object should not
-- be used to present the specific CPU vendor type in most cases.  More
-- accurate and clear vendor types should be defined to present specific CPU.
hh3cevtGeneralCPU        OBJECT IDENTIFIER ::= { hh3cevtCPU 1 }


hh3cevtUnknown   OBJECT IDENTIFIER ::= { hh3cEntityVendortypeObjects 2 }

hh3cevtChassis   OBJECT IDENTIFIER ::= { hh3cEntityVendortypeObjects 3 }

-- chassis OID assignments
-- May be substituted by sysObjectID.  So none is assigned at present.

--
--backplane
--   The enumeration 'backplane' is applicable if the physical
--   entity class is some sort of device for aggregating and
--   forwarding networking traffic, such as a shared backplane in
--   a modular ethernet switch.  Note that an agent may model a
--   backplane as a single physical entity, which is actually
--   implemented as multiple discrete physical components (within
--   a chassis or stack).
--

hh3cevtBackplane     OBJECT IDENTIFIER ::= { hh3cEntityVendortypeObjects 4 }

--
-- hh3cevtContainer section:
--
hh3cevtContainer     OBJECT IDENTIFIER ::= { hh3cEntityVendortypeObjects 5 }
--
-- hh3cevtPowerSupply section:
--

hh3cevtPowerSupply   OBJECT IDENTIFIER ::= { hh3cEntityVendortypeObjects 6 }
hh3cevtPowerSupplyAC         OBJECT IDENTIFIER ::= { hh3cevtPowerSupply 2 }
hh3cevtPowerSupplyDC         OBJECT IDENTIFIER ::= { hh3cevtPowerSupply 3 }
hh3cevtPowerSupplySTD130W    OBJECT IDENTIFIER ::= { hh3cevtPowerSupply 4 }     -- Standard 130W PSU
hh3cevtPowerSupplySTD180W    OBJECT IDENTIFIER ::= { hh3cevtPowerSupply 5 }     -- Standard 180W PSU
hh3cevtPowerSupplyPOE24Port  OBJECT IDENTIFIER ::= { hh3cevtPowerSupply 6 }     -- 24 Port POE PSU 480W
hh3cevtPowerSupplyPOE48Port  OBJECT IDENTIFIER ::= { hh3cevtPowerSupply 7 }     -- 48 Port POE PSU 480W

--
-- hh3cevtFan section:
--

hh3cevtFan       OBJECT IDENTIFIER ::= { hh3cEntityVendortypeObjects 7 }
hh3cevtHotSwapFan        OBJECT IDENTIFIER ::=  { hh3cevtFan 1 }
hh3cevtNonHotSwapFan     OBJECT IDENTIFIER ::=  { hh3cevtFan 2 }

--
-- hh3cevtSensor section:
--
hh3cevtSensor        OBJECT IDENTIFIER ::= { hh3cEntityVendortypeObjects 8 }
hh3cevtSensorTemperature     OBJECT IDENTIFIER ::= { hh3cevtSensor 1 }
hh3cevtSensorVoltage         OBJECT IDENTIFIER ::= { hh3cevtSensor 2 }
hh3cevtSensorFanSpeed        OBJECT IDENTIFIER ::= { hh3cevtSensor 3 }


--
-- hh3cevtModule section:
--

hh3cevtModule        OBJECT IDENTIFIER ::= { hh3cEntityVendortypeObjects 9 }

-- hh3cevtModule is subdivided into sections like Router and Switch. These represent
-- cards used only on the router and switch.
-- hh3cevtModuleCommonCards contains cards that can be used interchangeably
-- across more than one platform


-- Acronyms used in the hh3cevtModule section:
--

hh3cevtModuleUnknownCard     OBJECT IDENTIFIER ::= { hh3cevtModule 1 }

-- hh3cevtModuleCommonCards - cards and subcards common to more
-- than one platform

hh3cevtModuleCommonCards     OBJECT IDENTIFIER ::= { hh3cevtModule 2 }

-- hh3cevtModuleRouterType cards are slot-cards specific to the Router.
hh3cevtModuleRouterType      OBJECT IDENTIFIER ::= { hh3cevtModule 3 }

--hh3cevtModuleRt-Unavailable               OBJECT IDENTIFIER ::= { hh3cevtModuleRouterType 1 }

hh3cevtModuleRt-As                          OBJECT IDENTIFIER ::= { hh3cevtModuleRouterType 2 }

hh3cevtModuleRt-Sa                          OBJECT IDENTIFIER ::= { hh3cevtModuleRouterType 3 }

hh3cevtModuleRt-Bi                          OBJECT IDENTIFIER ::= { hh3cevtModuleRouterType 4 }

hh3cevtModuleRt-E12                         OBJECT IDENTIFIER ::= { hh3cevtModuleRouterType 5 }

hh3cevtModuleRt-E14                         OBJECT IDENTIFIER ::= { hh3cevtModuleRouterType 6 }

hh3cevtModuleRt-Fe1                         OBJECT IDENTIFIER ::= { hh3cevtModuleRouterType 7 }

hh3cevtModuleRt-E1                          OBJECT IDENTIFIER ::= { hh3cevtModuleRouterType 8 }

hh3cevtModuleRt-Fe2                         OBJECT IDENTIFIER ::= { hh3cevtModuleRouterType 9 }

hh3cevtModuleRt-Vi2                         OBJECT IDENTIFIER ::= { hh3cevtModuleRouterType 11 }

hh3cevtModuleRt-Vi4                         OBJECT IDENTIFIER ::= { hh3cevtModuleRouterType 12 }

hh3cevtModuleRt-Vi30                        OBJECT IDENTIFIER ::= { hh3cevtModuleRouterType 13 }

hh3cevtModuleRt-S1b                         OBJECT IDENTIFIER ::= { hh3cevtModuleRouterType 14 }

hh3cevtModuleRt-Sa2                         OBJECT IDENTIFIER ::= { hh3cevtModuleRouterType 15 }

hh3cevtModuleRt-As16                        OBJECT IDENTIFIER ::= { hh3cevtModuleRouterType 16 }

hh3cevtModuleRt-New8as                      OBJECT IDENTIFIER ::= { hh3cevtModuleRouterType 17 }

hh3cevtModuleRt-Sa1                         OBJECT IDENTIFIER ::= { hh3cevtModuleRouterType 18 }

hh3cevtModuleRt-Fxs2                        OBJECT IDENTIFIER ::= { hh3cevtModuleRouterType 19 }

hh3cevtModuleRt-Fxo2                        OBJECT IDENTIFIER ::= { hh3cevtModuleRouterType 20 }

hh3cevtModuleRt-Em2                         OBJECT IDENTIFIER ::= { hh3cevtModuleRouterType 21 }

hh3cevtModuleRt-Fxs4                        OBJECT IDENTIFIER ::= { hh3cevtModuleRouterType 22 }

hh3cevtModuleRt-Fxo4                        OBJECT IDENTIFIER ::= { hh3cevtModuleRouterType 23 }

hh3cevtModuleRt-Em4                         OBJECT IDENTIFIER ::= { hh3cevtModuleRouterType 24 }

hh3cevtModuleRt-Sab                         OBJECT IDENTIFIER ::= { hh3cevtModuleRouterType 25 }

hh3cevtModuleRt-E1vi                        OBJECT IDENTIFIER ::= { hh3cevtModuleRouterType 26 }

hh3cevtModuleRt-Am12                        OBJECT IDENTIFIER ::= { hh3cevtModuleRouterType 27 }

hh3cevtModuleRt-Am6                         OBJECT IDENTIFIER ::= { hh3cevtModuleRouterType 28 }

hh3cevtModuleRt-Ndec                        OBJECT IDENTIFIER ::= { hh3cevtModuleRouterType 29 }

hh3cevtModuleRt-Newsa2                      OBJECT IDENTIFIER ::= { hh3cevtModuleRouterType 30 }

hh3cevtModuleRt-Aux                         OBJECT IDENTIFIER ::= { hh3cevtModuleRouterType 31 }

hh3cevtModuleRt-Console                     OBJECT IDENTIFIER ::= { hh3cevtModuleRouterType 32 }

hh3cevtModuleRt-Sic-wan                     OBJECT IDENTIFIER ::= { hh3cevtModuleRouterType 33 }

hh3cevtModuleRt-Sic-1fe                     OBJECT IDENTIFIER ::= { hh3cevtModuleRouterType 34 }

hh3cevtModuleRt-Sic-1sa                     OBJECT IDENTIFIER ::= { hh3cevtModuleRouterType 35 }

hh3cevtModuleRt-Sic-3as                     OBJECT IDENTIFIER ::= { hh3cevtModuleRouterType 36 }

hh3cevtModuleRt-Sic-1e1                     OBJECT IDENTIFIER ::= { hh3cevtModuleRouterType 37 }

hh3cevtModuleRt-Sic-1t1                     OBJECT IDENTIFIER ::= { hh3cevtModuleRouterType 38 }

hh3cevtModuleRt-Sic-1bu                     OBJECT IDENTIFIER ::= { hh3cevtModuleRouterType 39 }

hh3cevtModuleRt-Sic-2bu                     OBJECT IDENTIFIER ::= { hh3cevtModuleRouterType 40 }

hh3cevtModuleRt-Sic-1bs                     OBJECT IDENTIFIER ::= { hh3cevtModuleRouterType 41 }

hh3cevtModuleRt-Sic-2bs                     OBJECT IDENTIFIER ::= { hh3cevtModuleRouterType 42 }

hh3cevtModuleRt-Sic-1am                     OBJECT IDENTIFIER ::= { hh3cevtModuleRouterType 43 }

hh3cevtModuleRt-Sic-2am                     OBJECT IDENTIFIER ::= { hh3cevtModuleRouterType 44 }

hh3cevtModuleRt-Sic-1em                     OBJECT IDENTIFIER ::= { hh3cevtModuleRouterType 45 }

hh3cevtModuleRt-Sic-2em                     OBJECT IDENTIFIER ::= { hh3cevtModuleRouterType 46 }

hh3cevtModuleRt-Sic-1fxs                    OBJECT IDENTIFIER ::= { hh3cevtModuleRouterType 47 }

hh3cevtModuleRt-Sic-2fxs                    OBJECT IDENTIFIER ::= { hh3cevtModuleRouterType 48 }

hh3cevtModuleRt-Sic-1fxo                    OBJECT IDENTIFIER ::= { hh3cevtModuleRouterType 49 }

hh3cevtModuleRt-Sic-2fxo                    OBJECT IDENTIFIER ::= { hh3cevtModuleRouterType 50 }

hh3cevtModuleRt-Fcm6                        OBJECT IDENTIFIER ::= { hh3cevtModuleRouterType 51 }

hh3cevtModuleRt-Sa8                         OBJECT IDENTIFIER ::= { hh3cevtModuleRouterType 52 }

hh3cevtModuleRt-T11                         OBJECT IDENTIFIER ::= { hh3cevtModuleRouterType 53 }

hh3cevtModuleRt-T12                         OBJECT IDENTIFIER ::= { hh3cevtModuleRouterType 54 }

hh3cevtModuleRt-T14                         OBJECT IDENTIFIER ::= { hh3cevtModuleRouterType 55 }

hh3cevtModuleRt-T1vi                        OBJECT IDENTIFIER ::= { hh3cevtModuleRouterType 56 }

hh3cevtModuleRt-Fcm4                        OBJECT IDENTIFIER ::= { hh3cevtModuleRouterType 57 }

hh3cevtModuleRt-Fcm2                        OBJECT IDENTIFIER ::= { hh3cevtModuleRouterType 58 }

hh3cevtModuleRt-Rtb21ce3                    OBJECT IDENTIFIER ::= { hh3cevtModuleRouterType 59 }

hh3cevtModuleRt-Ame6                        OBJECT IDENTIFIER ::= { hh3cevtModuleRouterType 60 }

hh3cevtModuleRt-Ame12                       OBJECT IDENTIFIER ::= { hh3cevtModuleRouterType 61 }

hh3cevtModuleRt-E11-f                       OBJECT IDENTIFIER ::= { hh3cevtModuleRouterType 65 }

hh3cevtModuleRt-E12-f                       OBJECT IDENTIFIER ::= { hh3cevtModuleRouterType 66 }

hh3cevtModuleRt-E14-f                       OBJECT IDENTIFIER ::= { hh3cevtModuleRouterType 67 }

hh3cevtModuleRt-T11-f                       OBJECT IDENTIFIER ::= { hh3cevtModuleRouterType 68 }

hh3cevtModuleRt-T12-f                       OBJECT IDENTIFIER ::= { hh3cevtModuleRouterType 69 }

hh3cevtModuleRt-T14-f                       OBJECT IDENTIFIER ::= { hh3cevtModuleRouterType 70 }

hh3cevtModuleRt-E11-f-17                    OBJECT IDENTIFIER ::= { hh3cevtModuleRouterType 71 }

hh3cevtModuleRt-T11-f-17                    OBJECT IDENTIFIER ::= { hh3cevtModuleRouterType 72 }

hh3cevtModuleRt-Rtb21ct3                    OBJECT IDENTIFIER ::= { hh3cevtModuleRouterType 73 }

hh3cevtModuleRt-Atmadsl1                    OBJECT IDENTIFIER ::= { hh3cevtModuleRouterType 74 }

hh3cevtModuleRt-Atmadsl2                    OBJECT IDENTIFIER ::= { hh3cevtModuleRouterType 75 }

hh3cevtModuleRt-Atm155m                     OBJECT IDENTIFIER ::= { hh3cevtModuleRouterType 76 }

hh3cevtModuleRt-Ase8                        OBJECT IDENTIFIER ::= { hh3cevtModuleRouterType 77 }

hh3cevtModuleRt-Ase16                       OBJECT IDENTIFIER ::= { hh3cevtModuleRouterType 78 }

hh3cevtModuleRt-Sae4                        OBJECT IDENTIFIER ::= { hh3cevtModuleRouterType 79 }

hh3cevtModuleRt-Sae2                        OBJECT IDENTIFIER ::= { hh3cevtModuleRouterType 80 }

hh3cevtModuleRt-Atmshdsl1                   OBJECT IDENTIFIER ::= { hh3cevtModuleRouterType 90 }

hh3cevtModuleRt-Atmshdsl2                   OBJECT IDENTIFIER ::= { hh3cevtModuleRouterType 91 }

hh3cevtModuleRt-Atmshdsl4                   OBJECT IDENTIFIER ::= { hh3cevtModuleRouterType 92 }

hh3cevtModuleRt-Atm25m                      OBJECT IDENTIFIER ::= { hh3cevtModuleRouterType 93 }

hh3cevtModuleRt-Atme3                       OBJECT IDENTIFIER ::= { hh3cevtModuleRouterType 94 }

hh3cevtModuleRt-Atmt3                       OBJECT IDENTIFIER ::= { hh3cevtModuleRouterType 95 }

hh3cevtModuleRt-Xdsl-fec                    OBJECT IDENTIFIER ::= { hh3cevtModuleRouterType 96 }

hh3cevtModuleRt-Xdsl-adsl                   OBJECT IDENTIFIER ::= { hh3cevtModuleRouterType 97 }

hh3cevtModuleRt-Xdsl-gshdsl                 OBJECT IDENTIFIER ::= { hh3cevtModuleRouterType 98 }

hh3cevtModuleRt-Xdsl-bri                    OBJECT IDENTIFIER ::= { hh3cevtModuleRouterType 99 }

hh3cevtModuleRt-Xdsl-scc                    OBJECT IDENTIFIER ::= { hh3cevtModuleRouterType 100 }

hh3cevtModuleRt-Ge1                         OBJECT IDENTIFIER ::= { hh3cevtModuleRouterType 101 }

hh3cevtModuleRt-Pos155m                     OBJECT IDENTIFIER ::= { hh3cevtModuleRouterType 102 }

hh3cevtModuleRt-Cpos                        OBJECT IDENTIFIER ::= { hh3cevtModuleRouterType 103 }

hh3cevtModuleRt-Fe1op                       OBJECT IDENTIFIER ::= { hh3cevtModuleRouterType 104 }

hh3cevtModuleRt-Sae8                        OBJECT IDENTIFIER ::= { hh3cevtModuleRouterType 105 }

hh3cevtModuleRt-Atm155m-mm                  OBJECT IDENTIFIER ::= { hh3cevtModuleRouterType 106 }

hh3cevtModuleRt-Atm155m-sm                  OBJECT IDENTIFIER ::= { hh3cevtModuleRouterType 107 }

hh3cevtModuleRt-Atm155m-sml                 OBJECT IDENTIFIER ::= { hh3cevtModuleRouterType 108 }

hh3cevtModuleRt-Fe1op-sfx                   OBJECT IDENTIFIER ::= { hh3cevtModuleRouterType 109 }

hh3cevtModuleRt-Fe1op-mfx                   OBJECT IDENTIFIER ::= { hh3cevtModuleRouterType 110 }

hh3cevtModuleRt-Cpos-t1                     OBJECT IDENTIFIER ::= { hh3cevtModuleRouterType 111 }

hh3cevtModuleRt-Ge1op                       OBJECT IDENTIFIER ::= { hh3cevtModuleRouterType 112 }

hh3cevtModuleRt-Ge2op                       OBJECT IDENTIFIER ::= { hh3cevtModuleRouterType 113 }

hh3cevtModuleRt-Ge2                         OBJECT IDENTIFIER ::= { hh3cevtModuleRouterType 114 }

hh3cevtModuleRt-Fix-1wan                    OBJECT IDENTIFIER ::= { hh3cevtModuleRouterType 115 }

hh3cevtModuleRt-Fix-1sae                    OBJECT IDENTIFIER ::= { hh3cevtModuleRouterType 116 }

hh3cevtModuleRt-Cavium                      OBJECT IDENTIFIER ::= { hh3cevtModuleRouterType 117 }

hh3cevtModuleRt-Sic1Eth                     OBJECT IDENTIFIER ::= { hh3cevtModuleRouterType 118 }

hh3cevtModuleRt-atm1ADSLI                   OBJECT IDENTIFIER ::= { hh3cevtModuleRouterType 119 }

hh3cevtModuleRt-atm2ADSLI                   OBJECT IDENTIFIER ::= { hh3cevtModuleRouterType 120 }

hh3cevtModuleRt-fix-e11                     OBJECT IDENTIFIER ::= { hh3cevtModuleRouterType 121 }

hh3cevtModuleRt-fix-t11                     OBJECT IDENTIFIER ::= { hh3cevtModuleRouterType 122 }

hh3cevtModuleRt-e18-75                      OBJECT IDENTIFIER ::= { hh3cevtModuleRouterType 123 }

hh3cevtModuleRt-e18-120                     OBJECT IDENTIFIER ::= { hh3cevtModuleRouterType 124 }

hh3cevtModuleRt-t18                         OBJECT IDENTIFIER ::= { hh3cevtModuleRouterType 125 }

hh3cevtModuleRt-sic-1vifxs                  OBJECT IDENTIFIER ::= { hh3cevtModuleRouterType 126 }

hh3cevtModuleRt-sic-1vifxo                  OBJECT IDENTIFIER ::= { hh3cevtModuleRouterType 127 }

hh3cevtModuleRt-sic-2vifxs                  OBJECT IDENTIFIER ::= { hh3cevtModuleRouterType 128 }

hh3cevtModuleRt-sic-2vifxo                  OBJECT IDENTIFIER ::= { hh3cevtModuleRouterType 129 }

hh3cevtModuleRt-xdsl-fec-new                OBJECT IDENTIFIER ::= { hh3cevtModuleRouterType 130 }

hh3cevtModuleRt-xdsl-sa                     OBJECT IDENTIFIER ::= { hh3cevtModuleRouterType 131 }

hh3cevtModuleRt-bs4                         OBJECT IDENTIFIER ::= { hh3cevtModuleRouterType 132 }

hh3cevtModuleRt-ima-8e175                   OBJECT IDENTIFIER ::= { hh3cevtModuleRouterType 133 }

hh3cevtModuleRt-ima-8e1120                  OBJECT IDENTIFIER ::= { hh3cevtModuleRouterType 134 }

hh3cevtModuleRt-ima-4e175                   OBJECT IDENTIFIER ::= { hh3cevtModuleRouterType 135 }

hh3cevtModuleRt-ima-4e1120                  OBJECT IDENTIFIER ::= { hh3cevtModuleRouterType 136 }

hh3cevtModuleRt-ima-8t1                     OBJECT IDENTIFIER ::= { hh3cevtModuleRouterType 137 }

hh3cevtModuleRt-ima-4t1                     OBJECT IDENTIFIER ::= { hh3cevtModuleRouterType 138 }

hh3cevtModuleRt-sic-1t1f                    OBJECT IDENTIFIER ::= { hh3cevtModuleRouterType 139 }

hh3cevtModuleRt-sic-1e1f                    OBJECT IDENTIFIER ::= { hh3cevtModuleRouterType 140 }

hh3cevtModuleRt-VG-16fxs                    OBJECT IDENTIFIER ::= { hh3cevtModuleRouterType 141 }

hh3cevtModuleRt-VG-32fxs                    OBJECT IDENTIFIER ::= { hh3cevtModuleRouterType 142 }

hh3cevtModuleRt-VG-8fxo                     OBJECT IDENTIFIER ::= { hh3cevtModuleRouterType 143 }

hh3cevtModuleRt-VG-2fe                      OBJECT IDENTIFIER ::= { hh3cevtModuleRouterType 144 }

hh3cevtModuleRt-sib                         OBJECT IDENTIFIER ::= { hh3cevtModuleRouterType 145 } -- SIB card

hh3cevtModuleRt-cie32                       OBJECT IDENTIFIER ::= { hh3cevtModuleRouterType 146 } -- 32M SSRAM CIE card

hh3cevtModuleRt-cie64                       OBJECT IDENTIFIER ::= { hh3cevtModuleRouterType 147 } -- 64M SSRAM CIE card

hh3cevtModuleRt-cie96                       OBJECT IDENTIFIER ::= { hh3cevtModuleRouterType 148 } -- 96M SSRAM CIE card

hh3cevtModuleRt-Fe4                         OBJECT IDENTIFIER ::= { hh3cevtModuleRouterType 149 } -- 4FE card

hh3cevtModuleRt-fxs4fxo1                    OBJECT IDENTIFIER ::= { hh3cevtModuleRouterType 150 } -- 4 Port Foreign Exchange Station and 1 Port Foreign Exchange Office Interface

hh3cevtModuleRt-atm1shdsl4wire              OBJECT IDENTIFIER ::= { hh3cevtModuleRouterType 151 } -- G.SHDSL 4 wire MIM card, 1 port

hh3cevtModuleRt-atmIma4shdsl                OBJECT IDENTIFIER ::= { hh3cevtModuleRouterType 152 } -- G.SHDSL 8 wire MIM card, 4 ports

hh3cevtModuleRt-ls4                         OBJECT IDENTIFIER ::= { hh3cevtModuleRouterType 153 } -- 4 Ports Layer 2 Lanswitch Module

hh3cevtModuleRt-ls8                         OBJECT IDENTIFIER ::= { hh3cevtModuleRouterType 154 } -- 8 Ports Layer 2 Lanswitch Module

hh3cevtModuleRt-ls16                        OBJECT IDENTIFIER ::= { hh3cevtModuleRouterType 155 } -- 16 Ports Layer 2 Lanswitch Module

hh3cevtModuleRt-sic-adls2plus-isdn          OBJECT IDENTIFIER ::= { hh3cevtModuleRouterType 156 } -- ADLS2Plus SIC card, ISDN port

hh3cevtModuleRt-sic-adls2plus-pots          OBJECT IDENTIFIER ::= { hh3cevtModuleRouterType 157 } -- ADLS2Plus SIC card, POTS port

hh3cevtModuleRt-ft3                         OBJECT IDENTIFIER ::= { hh3cevtModuleRouterType 158 } -- 1 Port Fractional T3 module

hh3cevtModuleRt-ce32                        OBJECT IDENTIFIER ::= { hh3cevtModuleRouterType 159 } -- 2 Port Channelized E3 module

hh3cevtModuleRt-bsv2                        OBJECT IDENTIFIER ::= { hh3cevtModuleRouterType 160 } -- 2 Port BSV module

hh3cevtModuleRt-bsv4                        OBJECT IDENTIFIER ::= { hh3cevtModuleRouterType 161 } -- 4 Port BSV module

hh3cevtModuleRt-RPU                         OBJECT IDENTIFIER ::= { hh3cevtModuleRouterType 162 } -- Route processing unit

hh3cevtModuleRt-ERPU                        OBJECT IDENTIFIER ::= { hh3cevtModuleRouterType 163 } -- Enhanced route processing unit

hh3cevtModuleRt-SSL                         OBJECT IDENTIFIER ::= { hh3cevtModuleRouterType 164 } -- SSL Encrypt Card

hh3cevtModuleRt-NSA                         OBJECT IDENTIFIER ::= { hh3cevtModuleRouterType 165 } -- NSA Encrypt Card

--
-- 166 to 199 reserved for other devices
--


--
-- 200 to 399 reserved for normal routers
--

hh3cevtModuleRT-SIC-1GEC                    OBJECT IDENTIFIER ::= { hh3cevtModuleRouterType 200 } -- 1-Port 10M/100M/1000M COMBO Ethernet Interface SIC Module

hh3cevtModuleRT-24FSW                       OBJECT IDENTIFIER ::= { hh3cevtModuleRouterType 201 } -- 24-Port 10M/100M and 2-Port 1000BASE-T/1000BASE-X(COMBO) Ethernet L2 Switch Module

hh3cevtModuleRT-24FSWP                      OBJECT IDENTIFIER ::= { hh3cevtModuleRouterType 202 } -- 24-Port 10M/100M(WITH POE) and 2-Port 1000BASE-T/1000BASE-X(COMBO) Ethernet L2 Switch Module

hh3cevtModuleRT-16FSW                       OBJECT IDENTIFIER ::= { hh3cevtModuleRouterType 203 } -- 16-Port 10M/100M Ethernet L2 Switch Module

hh3cevtModuleRT-16FSWP                      OBJECT IDENTIFIER ::= { hh3cevtModuleRouterType 204 } -- 16-Port 10M/100M(WITH POE) Ethernet L2 Switch Module

hh3cevtModuleRT-1VE1                        OBJECT IDENTIFIER ::= { hh3cevtModuleRouterType 205 } -- 1-Port Voice E1 Module

hh3cevtModuleRT-1VT1                        OBJECT IDENTIFIER ::= { hh3cevtModuleRouterType 206 } -- 1-Port Voice T1 Module

hh3cevtModuleRT-2VE1                        OBJECT IDENTIFIER ::= { hh3cevtModuleRouterType 207 } -- 2-Port Voice E1 Module

hh3cevtModuleRT-2VT1                        OBJECT IDENTIFIER ::= { hh3cevtModuleRouterType 208 } -- 2-Port Voice T1 Module

hh3cevtModuleRT-SIC-4FSW                    OBJECT IDENTIFIER ::= { hh3cevtModuleRouterType 209 } -- 4-Port 10M/100M Ethernet L2 Switch Module (RJ45)

hh3cevtModuleRT-SIC-4FSWP                   OBJECT IDENTIFIER ::= { hh3cevtModuleRouterType 210 } -- 4-Port 10M/100M Ethernet L2 Switch Module(RJ45,WITH POE)

hh3cevtModuleRT-DSIC-9FSW                   OBJECT IDENTIFIER ::= { hh3cevtModuleRouterType 211 } -- 9-Port 10M/100M Ethernet L2 Switch Module(RJ45)

hh3cevtModuleRT-DSIC-9FSWP                  OBJECT IDENTIFIER ::= { hh3cevtModuleRouterType 212 } -- 9-Port 10M/100M Ethernet L2 Switch Module(RJ45,WITH POE)

hh3cevtModuleRT-SIC-1VE1                    OBJECT IDENTIFIER ::= { hh3cevtModuleRouterType 213 } -- 1-Port Voice E1 SIC Interface Module

hh3cevtModuleRT-SIC-1VT1                    OBJECT IDENTIFIER ::= { hh3cevtModuleRouterType 214 } -- 1-Port Voice T1 SIC Interface Module

hh3cevtModuleRT-VCPM                        OBJECT IDENTIFIER ::= { hh3cevtModuleRouterType 215 } -- Voice Co-Processing Module

hh3cevtModuleRT-VPM                         OBJECT IDENTIFIER ::= { hh3cevtModuleRouterType 216 } -- 32-Channels Voice Processing Module

hh3cevtModuleRT-VPMA                        OBJECT IDENTIFIER ::= { hh3cevtModuleRouterType 217 } -- 16-Channels Voice Processing Module

hh3cevtModuleRT-VPMB                        OBJECT IDENTIFIER ::= { hh3cevtModuleRouterType 218 } -- 8-Channels Voice Processing Module

hh3cevtModuleRT-VPMC                        OBJECT IDENTIFIER ::= { hh3cevtModuleRouterType 219 } -- 24-Channels Voice Processing Module

hh3cevtModuleRt-fe18-75                     OBJECT IDENTIFIER ::= { hh3cevtModuleRouterType 220 } -- 8 Port FE1(75 O) module

hh3cevtModuleRt-fe18-120                    OBJECT IDENTIFIER ::= { hh3cevtModuleRouterType 221 } -- 8 Port FE1(120 O) module

hh3cevtModuleRt-ft18                        OBJECT IDENTIFIER ::= { hh3cevtModuleRouterType 222 } -- 8 Port FT1 module

hh3cevtModuleRt-CF                          OBJECT IDENTIFIER ::= { hh3cevtModuleRouterType 223 } -- Compact Flash Card

hh3cevtModuleRt-bsv2-v2                     OBJECT IDENTIFIER ::= { hh3cevtModuleRouterType 224 } -- 2 Port BSV Version 2

hh3cevtModuleRt-e1vi1-v2                    OBJECT IDENTIFIER ::= { hh3cevtModuleRouterType 225 } -- E1VI Version 2

hh3cevtModuleRt-e1vi2                       OBJECT IDENTIFIER ::= { hh3cevtModuleRouterType 226 } -- 2 Port E1VI

hh3cevtModuleRt-t1vi1-v2                    OBJECT IDENTIFIER ::= { hh3cevtModuleRouterType 227 } -- T1VI Version 2

hh3cevtModuleRt-t1vi2                       OBJECT IDENTIFIER ::= { hh3cevtModuleRouterType 228 } -- 2 Port T1VI

hh3cevtModuleRt-osm                         OBJECT IDENTIFIER ::= { hh3cevtModuleRouterType 229 } -- Open Service Module

hh3cevtModuleRt-sd707                       OBJECT IDENTIFIER ::= { hh3cevtModuleRouterType 230 } -- Encryption Accelerator

hh3cevtModuleRt-dm-epri                     OBJECT IDENTIFIER ::= { hh3cevtModuleRouterType 231 } -- E1 Pri Digital Modem

hh3cevtModuleRt-dm-tpri                     OBJECT IDENTIFIER ::= { hh3cevtModuleRouterType 232 } -- T1 Pri Digital Modem

hh3cevtModuleRt-ERPU-H                      OBJECT IDENTIFIER ::= { hh3cevtModuleRouterType 233 } -- Enhanced route processing unit with only one optic GE interface

hh3cevtModuleRT-SIC-1BSV                    OBJECT IDENTIFIER ::= { hh3cevtModuleRouterType 234 } -- 1-Port Bri S/T VoiceInterface SIC Module

hh3cevtModuleRT-SIC-2BSV                    OBJECT IDENTIFIER ::= { hh3cevtModuleRouterType 235 } -- 2-Port Bri S/T VoiceInterface SIC Module

hh3cevtModuleRt-gbe8                        OBJECT IDENTIFIER ::= { hh3cevtModuleRouterType 236 } -- 8-Port Gigabit Ethernet interface card

hh3cevtModuleRt-gbe4                        OBJECT IDENTIFIER ::= { hh3cevtModuleRouterType 237 } -- 4-Port Gigabit Ethernet interface card

hh3cevtModuleRt-cpos2-v2                    OBJECT IDENTIFIER ::= { hh3cevtModuleRouterType 238 } -- 2-Port Channelized Low speed POS interface card

hh3cevtModuleRt-cpos1-v2                    OBJECT IDENTIFIER ::= { hh3cevtModuleRouterType 239 } -- 1-Port Channelized Low speed POS interface card

hh3cevtModuleRt-oap                         OBJECT IDENTIFIER ::= { hh3cevtModuleRouterType 240 } -- Open Application Platform

hh3cevtModuleRT-48FSWP                      OBJECT IDENTIFIER ::= { hh3cevtModuleRouterType 241 } -- 46-Port 10M/100M(With PoE) and 2-Port 1000BASE-T(With PoE) Ethernet L2 Switch Module

hh3cevtModuleRT-48FSW                       OBJECT IDENTIFIER ::= { hh3cevtModuleRouterType 242 } -- 46-Port 10M/100M and 2-Port 1000BASE-T Ethernet L2 Switch Module

hh3cevtModuleRT-ASM                         OBJECT IDENTIFIER ::= { hh3cevtModuleRouterType 243 } -- Anti-virus Security Module

hh3cevtModuleRT-SIC-1FEF                    OBJECT IDENTIFIER ::= { hh3cevtModuleRouterType 244 } -- 1-Port 100M SFP Interface SIC Module

hh3cevtModuleRT-XMIM-24FSW                  OBJECT IDENTIFIER ::= { hh3cevtModuleRouterType 245 } -- 24-Port 10M/100MBASE-TX Ethernet L2 Switch Interface XMIM-Module

hh3cevtModuleRT-WLAN-AG-1RADIO              OBJECT IDENTIFIER ::= { hh3cevtModuleRouterType 246 } -- Mini PCI Interface 802.11ag Radio Frequency Adapter Card

hh3cevtModuleRT-1CE3                        OBJECT IDENTIFIER ::= { hh3cevtModuleRouterType 247 } -- 1-port E3/CE3/FE3 Compatible Interface Module,(M)

hh3cevtModuleRT-XMIM-16FSW                  OBJECT IDENTIFIER ::= { hh3cevtModuleRouterType 248 } -- 16-Port 10M/100MBASE-TX Ethernet L2 Switch Interface XMIM-Module

hh3cevtModuleRT-OAPS                        OBJECT IDENTIFIER ::= { hh3cevtModuleRouterType 249 } -- Open Application System-Smart

hh3cevtModuleRT-NAM                         OBJECT IDENTIFIER ::= { hh3cevtModuleRouterType 250 } -- Network Analysis Module

hh3cevtModuleRT-RPE-X1                      OBJECT IDENTIFIER ::= { hh3cevtModuleRouterType 251 } -- Route Processing Engine

hh3cevtModuleRT-FIP-100                     OBJECT IDENTIFIER ::= { hh3cevtModuleRouterType 252 } -- Flexible Interface Platform-100

hh3cevtModuleRT-FIP-200                     OBJECT IDENTIFIER ::= { hh3cevtModuleRouterType 253 } -- Flexible Interface Platform-200

hh3cevtModuleRT-SIC-8AS                     OBJECT IDENTIFIER ::= { hh3cevtModuleRouterType 254 } -- 8-Port Asynchronous Serial

hh3cevtModuleRT-WAAM                        OBJECT IDENTIFIER ::= { hh3cevtModuleRouterType 255 } -- WAN Application Acceleration Module

hh3cevtModuleRt-msp4p-OC3c                  OBJECT IDENTIFIER ::= { hh3cevtModuleRouterType 256 } -- 4 Port Multi-Speed POS Interface Module (OC-3c Mode)

hh3cevtModuleRt-1pos-oc48                   OBJECT IDENTIFIER ::= { hh3cevtModuleRouterType 257 } -- 1 Port Super-Speed POS Interface Card

hh3cevtModuleRt-xgbe                        OBJECT IDENTIFIER ::= { hh3cevtModuleRouterType 258 } -- 1-Port 10GBASE-R/W Ethernet Optical Interface Card

hh3cevtModuleRT-EADM                        OBJECT IDENTIFIER ::= { hh3cevtModuleRouterType 259 } -- EAD Integrated Module

hh3cevtModuleRT-VCM                         OBJECT IDENTIFIER ::= { hh3cevtModuleRouterType 260 } -- Voice Convergence Module

hh3cevtModuleRT-SIC-2FXS1FXO                OBJECT IDENTIFIER ::= { hh3cevtModuleRouterType 261 } -- 2FXS+1FXO Interface SIC-Module

hh3cevtModuleRT-8FXS8FXO                    OBJECT IDENTIFIER ::= { hh3cevtModuleRouterType 262 } -- 8FXS+8FXO Interface Module

hh3cevtModuleRT-16FXS                       OBJECT IDENTIFIER ::= { hh3cevtModuleRouterType 263 } -- 16-port FXS Interface Module

hh3cevtModuleRT-OAPS-ICM                    OBJECT IDENTIFIER ::= { hh3cevtModuleRouterType 264 } -- OAPS Information Communication Module

hh3cevtModuleRT-OAP-ICM                     OBJECT IDENTIFIER ::= { hh3cevtModuleRouterType 265 } -- OAP Information Communication Module

hh3cevtModuleRT-8fe                         OBJECT IDENTIFIER ::= { hh3cevtModuleRouterType 266 } -- 8-Port 100M Ethernet Electrical Interface Module

hh3cevtModuleRT-4gbp                        OBJECT IDENTIFIER ::= { hh3cevtModuleRouterType 267 } -- 4-Port GigaBit Ethernet Optical Interface Module(SFP)

hh3cevtModuleRT-MPU-G2                      OBJECT IDENTIFIER ::= { hh3cevtModuleRouterType 268 } -- Main Processor Unit

hh3cevtModuleRT-OAPS-OCE                    OBJECT IDENTIFIER ::= { hh3cevtModuleRouterType 269 } -- OAPS Office Communication Engine

hh3cevtModuleRT-OAP-OCE                     OBJECT IDENTIFIER ::= { hh3cevtModuleRouterType 270 } -- OAP Office Communication Engine

hh3cevtModuleRT-OAPS-ICE                    OBJECT IDENTIFIER ::= { hh3cevtModuleRouterType 271 } -- OAPS Information Communication Engine

hh3cevtModuleRT-OAP-ICE                     OBJECT IDENTIFIER ::= { hh3cevtModuleRouterType 272 } -- OAP Information Communication Module

hh3cevtModuleRT-SIC-16AS                    OBJECT IDENTIFIER ::= { hh3cevtModuleRouterType 273 } -- 16-Port Asynchronous Serial

hh3cevtModuleRT-SPE-FWM                     OBJECT IDENTIFIER ::= { hh3cevtModuleRouterType 274 } -- Gigabit Firewall Module

hh3cevtModuleRT-cls2p                       OBJECT IDENTIFIER ::= { hh3cevtModuleRouterType 275 } -- 2 Port Channelized 155M POS to E3/T3 Interface Module

hh3cevtModuleRT-cls1p                       OBJECT IDENTIFIER ::= { hh3cevtModuleRouterType 276 } -- 1 Port Channelized 155M POS to E3/T3 Interface Module

hh3cevtModuleRT-SIC-2E1-F                   OBJECT IDENTIFIER ::= { hh3cevtModuleRouterType 277 } -- 2-Port Fractional E1 Interface SIC-Module

hh3cevtModuleRT-SIC-1E1-F-V2                OBJECT IDENTIFIER ::= { hh3cevtModuleRouterType 278 } -- 1-Port Fractional E1 Interface SIC-Module

hh3cevtModuleRT-MCU                         OBJECT IDENTIFIER ::= { hh3cevtModuleRouterType 279 } -- Main Control Unit

hh3cevtModuleRT-ACU                         OBJECT IDENTIFIER ::= { hh3cevtModuleRouterType 280 } -- Access Control Unit

hh3cevtModuleRT-1ATM-OC3                    OBJECT IDENTIFIER ::= { hh3cevtModuleRouterType 281 } -- 1-Port Asynchronous Transfer Mode OC3 Board

hh3cevtModuleRT-RSE-X1                      OBJECT IDENTIFIER ::= { hh3cevtModuleRouterType 282 } -- Main Processing Unit With XAUI Switch

hh3cevtModuleRT-FIP-210                     OBJECT IDENTIFIER ::= { hh3cevtModuleRouterType 283 } -- Multi-core CPU Line Processing Board with 2 Combo GE Ports

hh3cevtModuleRT-1expa                       OBJECT IDENTIFIER ::= { hh3cevtModuleRouterType 284 } -- 1 Port Ten Gigabit Interface Module

hh3cevtModuleRT-WLAN-SIC-N-1RADIO           OBJECT IDENTIFIER ::= { hh3cevtModuleRouterType 285 } -- 1 wlan-radio 802.11n sic Interface Board

hh3cevtModuleRT-WLAN-SIC-BG-1RADIO          OBJECT IDENTIFIER ::= { hh3cevtModuleRouterType 286 } -- 1 wlan-radio 802.11b/g sic Interface Board

hh3cevtModuleRT-al2p                        OBJECT IDENTIFIER ::= { hh3cevtModuleRouterType 287 } -- 2 Port 155M ATM Interface Module

hh3cevtModuleRT-msp2p-OC3c                  OBJECT IDENTIFIER ::= { hh3cevtModuleRouterType 288 } -- 2-Port Multi-speed POS Interface Module (OC-3c Mode)

hh3cevtModuleRT-8gbp                        OBJECT IDENTIFIER ::= { hh3cevtModuleRouterType 289 } -- 8-Port GigaBit Ethernet Optical Interface Module(SFP)

hh3cevtModuleRT-SIC-EPON                    OBJECT IDENTIFIER ::= { hh3cevtModuleRouterType 290 } -- 1-Port Ethernet Passive Optical Network SIC Card(SFF)

hh3cevtModuleRT-SIC-3G-GSM-H3               OBJECT IDENTIFIER ::= { hh3cevtModuleRouterType 291 } -- 3G Wireless WAN Interface SIC Module Supporting GPRS/EDGE/UMTS/HSDPA

hh3cevtModuleRT-msp2p-OC12c                 OBJECT IDENTIFIER ::= { hh3cevtModuleRouterType 292 } -- 2-Port Multi-speed POS Interface Module (OC-12c Mode)

hh3cevtModuleRt-msp4p-OC12c                 OBJECT IDENTIFIER ::= { hh3cevtModuleRouterType 293 } -- 4-Port Multi-Speed POS Interface Module (OC-12c Mode)

hh3cevtModuleRt-al1p                        OBJECT IDENTIFIER ::= { hh3cevtModuleRouterType 294 } -- 1-Port 155M ATM Interface Module

hh3cevtModuleRt-OAP-100                     OBJECT IDENTIFIER ::= { hh3cevtModuleRouterType 295 } -- Open Application Platform Module

--
-- 400 to 599 reserved for security routers
--
hh3cevtModuleRt-IPU                         OBJECT IDENTIFIER ::= { hh3cevtModuleRouterType 400 } -- IPS Processing Unit

hh3cevtModuleRt-MIM2GEBE-PCIE               OBJECT IDENTIFIER ::= { hh3cevtModuleRouterType 401 } -- 2-port UTM GigabitEthernet Interface Module

hh3cevtModuleRt-HIM12GE-PCIE                OBJECT IDENTIFIER ::= { hh3cevtModuleRouterType 402 } -- 12-port GigabitEthernet Interface Module

hh3cevtModuleRt-HIM2XGE-PCIE                OBJECT IDENTIFIER ::= { hh3cevtModuleRouterType 403 } -- 2-port Ten-GigabitEthernet Interface Module

hh3cevtModuleRt-IPU-T1000-M                 OBJECT IDENTIFIER ::= { hh3cevtModuleRouterType 404 } -- IPS Processing Unit for T1000-M Mainboard Module

hh3cevtModuleRt-IPU-GX4C                    OBJECT IDENTIFIER ::= { hh3cevtModuleRouterType 405 } -- 4 Port Gigabit Fiber Module

hh3cevtModuleRt-IPU-GT4C                    OBJECT IDENTIFIER ::= { hh3cevtModuleRouterType 406 } -- 4 Port 1000BASE-T Module

hh3cevtModuleRt-RPU-IAG2000-A               OBJECT IDENTIFIER ::= { hh3cevtModuleRouterType 407 } -- Intelligence Application Gateway Module

hh3cevtModuleRt-RPU-AFD1000-A               OBJECT IDENTIFIER ::= { hh3cevtModuleRouterType 408 } -- Anomaly Flow Detector Module

hh3cevtModuleRt-RPU-F5000-A                 OBJECT IDENTIFIER ::= { hh3cevtModuleRouterType 409 } -- Advanced Firewall Module

hh3cevtModuleRt-ACG-8800S3-MPU              OBJECT IDENTIFIER ::= { hh3cevtModuleRouterType 410 } -- Main Control Unit,with 24 1000BASE-X/100BASE-FX Optical Ports,including 8 Combo Ports,SFP Req

hh3cevtModuleRt-T5000S3-MPU                 OBJECT IDENTIFIER ::= { hh3cevtModuleRouterType 411 } -- Main Control Unit,with 24 1000BASE-X/100BASE-FX Optical Ports,including 8 Combo Ports,SFP Req

hh3cevtModuleRt-NS21S2MSPB0                 OBJECT IDENTIFIER ::= { hh3cevtModuleRouterType 412 } -- Multi Service Processing Module

hh3cevtModuleRt-NS11S2MSPB0                 OBJECT IDENTIFIER ::= { hh3cevtModuleRouterType 413 } -- Multi Service Processing Module

hh3cevtModuleRt-NSQ1WLAN                    OBJECT IDENTIFIER ::= { hh3cevtModuleRouterType 414 } -- Dual-Band,Multi-Mode 802.11a/b/g Wireless LAN card

--
-- 600 to 799 reserved for voice routers
--

hh3cevtModuleRt-VG-8fxs                     OBJECT IDENTIFIER ::= { hh3cevtModuleRouterType 600 } -- 8 Port Foreign Exchange Station module

hh3cevtModuleRt-VG-24fxs                    OBJECT IDENTIFIER ::= { hh3cevtModuleRouterType 601 } -- 24 Port Foreign Exchange Station module

hh3cevtModuleRt-VG-24fxs24fxo               OBJECT IDENTIFIER ::= { hh3cevtModuleRouterType 602 } -- 24 Port Foreign Exchange Station and 24 Port Foreign Exchange Office module

hh3cevtModuleRt-VG-MPU                      OBJECT IDENTIFIER ::= { hh3cevtModuleRouterType 603 } -- Media Processing Unit


-- hh3cevtModuleSwitchType cards are slot-cards specific to the Switch.
hh3cevtModuleSwitchType  OBJECT IDENTIFIER ::= { hh3cevtModule 4 }

--hh3cevtModuleNULL(0),
hh3cevtModuleSw-10OR100M                    OBJECT IDENTIFIER ::= { hh3cevtModuleSwitchType 1 }

hh3cevtModuleSw-1000BASE-LX-SM              OBJECT IDENTIFIER ::= { hh3cevtModuleSwitchType 2 }

hh3cevtModuleSw-1000BASE-SX-MM              OBJECT IDENTIFIER ::= { hh3cevtModuleSwitchType 3 }

hh3cevtModuleSw-1000BASE-TX                 OBJECT IDENTIFIER ::= { hh3cevtModuleSwitchType 4 }

hh3cevtModuleSw-100M-SINGLEMODE-FX          OBJECT IDENTIFIER ::= { hh3cevtModuleSwitchType 5 }

hh3cevtModuleSw-100M-MULTIMODE-FX           OBJECT IDENTIFIER ::= { hh3cevtModuleSwitchType 6 }

hh3cevtModuleSw-100M-100BASE-TX             OBJECT IDENTIFIER ::= { hh3cevtModuleSwitchType 7 }

hh3cevtModuleSw-100M-HUB                    OBJECT IDENTIFIER ::= { hh3cevtModuleSwitchType 8 }

hh3cevtModuleSw-VDSL                        OBJECT IDENTIFIER ::= { hh3cevtModuleSwitchType 9 }

hh3cevtModuleSw-STACK                       OBJECT IDENTIFIER ::= { hh3cevtModuleSwitchType 10 }

hh3cevtModuleSw-1000BASE-ZENITH-FX          OBJECT IDENTIFIER ::= { hh3cevtModuleSwitchType 11 }

hh3cevtModuleSw-1000BASE-LONG-FX            OBJECT IDENTIFIER ::= { hh3cevtModuleSwitchType 12 }

hh3cevtModuleSw-ADSL                        OBJECT IDENTIFIER ::= { hh3cevtModuleSwitchType 13 }

hh3cevtModuleSw-4T10OR100-4FX100SM          OBJECT IDENTIFIER ::= { hh3cevtModuleSwitchType 14 }

hh3cevtModuleSw-4T10OR100-4FX100MM          OBJECT IDENTIFIER ::= { hh3cevtModuleSwitchType 15 }

hh3cevtModuleSw-VSPL                        OBJECT IDENTIFIER ::= { hh3cevtModuleSwitchType 16 }

hh3cevtModuleSw-ASPL                        OBJECT IDENTIFIER ::= { hh3cevtModuleSwitchType 17 }

hh3cevtModuleSw-1000M-SFP                   OBJECT IDENTIFIER ::= { hh3cevtModuleSwitchType 18 }

hh3cevtModuleSw-LS82O2CM                    OBJECT IDENTIFIER ::= { hh3cevtModuleSwitchType 19 }

hh3cevtModuleSw-LS82P2CM                    OBJECT IDENTIFIER ::= { hh3cevtModuleSwitchType 20 }

hh3cevtModuleSw-LS82O4GM                    OBJECT IDENTIFIER ::= { hh3cevtModuleSwitchType 21 }

hh3cevtModuleSw-LS82GB4C                    OBJECT IDENTIFIER ::= { hh3cevtModuleSwitchType 22 }

hh3cevtModuleSw-LS82GT4C                    OBJECT IDENTIFIER ::= { hh3cevtModuleSwitchType 23 }

hh3cevtModuleSw-LS82ST4C                    OBJECT IDENTIFIER ::= { hh3cevtModuleSwitchType 24 }

hh3cevtModuleSw-BOARD-LS82DSPU              OBJECT IDENTIFIER ::= { hh3cevtModuleSwitchType 25 }

hh3cevtModuleSw-BOARD-LS81GP8U              OBJECT IDENTIFIER ::= { hh3cevtModuleSwitchType 26 }

hh3cevtModuleSw-BOARD-LS82GT20              OBJECT IDENTIFIER ::= { hh3cevtModuleSwitchType 27 }

hh3cevtModuleSw-BOARD-LS82FE48              OBJECT IDENTIFIER ::= { hh3cevtModuleSwitchType 28 }

hh3cevtModuleSw-LS82T24B                    OBJECT IDENTIFIER ::= { hh3cevtModuleSwitchType 29 }

hh3cevtModuleSw-LSB1SRPA                    OBJECT IDENTIFIER ::= { hh3cevtModuleSwitchType 30 }

hh3cevtModuleSw-LSB1FT48A                   OBJECT IDENTIFIER ::= { hh3cevtModuleSwitchType 31 }

hh3cevtModuleSw-LSB1FT48B                   OBJECT IDENTIFIER ::= { hh3cevtModuleSwitchType 32 }

hh3cevtModuleSw-LSB1F48GA                   OBJECT IDENTIFIER ::= { hh3cevtModuleSwitchType 33 }

hh3cevtModuleSw-LSB1F48GB                   OBJECT IDENTIFIER ::= { hh3cevtModuleSwitchType 34 }

hh3cevtModuleSw-LSB1FP20A                   OBJECT IDENTIFIER ::= { hh3cevtModuleSwitchType 35 }

hh3cevtModuleSw-LSB1FP20B                   OBJECT IDENTIFIER ::= { hh3cevtModuleSwitchType 36 }

hh3cevtModuleSw-FT48A                       OBJECT IDENTIFIER ::= { hh3cevtModuleSwitchType 37 }

hh3cevtModuleSw-GP4U                        OBJECT IDENTIFIER ::= { hh3cevtModuleSwitchType 38 }

hh3cevtModuleSw-GP2U                        OBJECT IDENTIFIER ::= { hh3cevtModuleSwitchType 39 }

hh3cevtModuleSw-TGX1A                       OBJECT IDENTIFIER ::= { hh3cevtModuleSwitchType 40 }

hh3cevtModuleSw-1000BASE-LX-SM-IR-SC        OBJECT IDENTIFIER ::= { hh3cevtModuleSwitchType 41 }

hh3cevtModuleSw-1000BASE-SX-MM-SR-SC        OBJECT IDENTIFIER ::= { hh3cevtModuleSwitchType 42 }

hh3cevtModuleSw-1000BASE-T-RJ45             OBJECT IDENTIFIER ::= { hh3cevtModuleSwitchType 43 }

hh3cevtModuleSw-100BASE-FX-SM-IR-SC         OBJECT IDENTIFIER ::= { hh3cevtModuleSwitchType 44 }

hh3cevtModuleSw-100BASE-FX-MM-SR-SC         OBJECT IDENTIFIER ::= { hh3cevtModuleSwitchType 45 }

hh3cevtModuleSw-GIGA-STACK-1M-PC            OBJECT IDENTIFIER ::= { hh3cevtModuleSwitchType 46 }

hh3cevtModuleSw-1000BASE-LX-SM-VLR-LC       OBJECT IDENTIFIER ::= { hh3cevtModuleSwitchType 47 }

hh3cevtModuleSw-1000BASE-LX-SM-LR-LC        OBJECT IDENTIFIER ::= { hh3cevtModuleSwitchType 48 }

hh3cevtModuleSw-100BASE-FX-SM-LR-SC         OBJECT IDENTIFIER ::= { hh3cevtModuleSwitchType 49 }

hh3cevtModuleSw-1000BASE-X-GBIC             OBJECT IDENTIFIER ::= { hh3cevtModuleSwitchType 50 }

hh3cevtModuleSw-100M-SINGLEMODE-FX-LC       OBJECT IDENTIFIER ::= { hh3cevtModuleSwitchType 51 }

hh3cevtModuleSw-100M-MULTIMODE-FX-LC        OBJECT IDENTIFIER ::= { hh3cevtModuleSwitchType 52 }

hh3cevtModuleSw-1000BASE-4SFP               OBJECT IDENTIFIER ::= { hh3cevtModuleSwitchType 53 }

hh3cevtModuleSw-1000BASE-4GBIC              OBJECT IDENTIFIER ::= { hh3cevtModuleSwitchType 54 }

hh3cevtModuleSw-1000BASE-FIXED-4SFP         OBJECT IDENTIFIER ::= { hh3cevtModuleSwitchType 55 }

hh3cevtModuleSw-1000BASE-FIXED-4GBIC        OBJECT IDENTIFIER ::= { hh3cevtModuleSwitchType 56 }

hh3cevtModuleSw-LSB1GP12A                   OBJECT IDENTIFIER ::= { hh3cevtModuleSwitchType 57 }

hh3cevtModuleSw-LSB1GP12B                   OBJECT IDENTIFIER ::= { hh3cevtModuleSwitchType 58 }

hh3cevtModuleSw-LSB1TGX1A                   OBJECT IDENTIFIER ::= { hh3cevtModuleSwitchType 59 }

hh3cevtModuleSw-LSB1TGX1B                   OBJECT IDENTIFIER ::= { hh3cevtModuleSwitchType 60 }

hh3cevtModuleSw-LSB1P4G8A                   OBJECT IDENTIFIER ::= { hh3cevtModuleSwitchType 61 }

hh3cevtModuleSw-LSB1P4G8B                   OBJECT IDENTIFIER ::= { hh3cevtModuleSwitchType 62 }

hh3cevtModuleSw-LSB1A4G8A                   OBJECT IDENTIFIER ::= { hh3cevtModuleSwitchType 63 }

hh3cevtModuleSw-LSB1A4G8B                   OBJECT IDENTIFIER ::= { hh3cevtModuleSwitchType 64 }

hh3cevtModuleSw-FT48C                       OBJECT IDENTIFIER ::= { hh3cevtModuleSwitchType 65 }

hh3cevtModuleSw-FP20                        OBJECT IDENTIFIER ::= { hh3cevtModuleSwitchType 66 }

hh3cevtModuleSw-BOARD-LS81FT48              OBJECT IDENTIFIER ::= { hh3cevtModuleSwitchType 67 }

hh3cevtModuleSw-BOARD-LS81GB8U              OBJECT IDENTIFIER ::= { hh3cevtModuleSwitchType 68 }

hh3cevtModuleSw-BOARD-LS81GT8U              OBJECT IDENTIFIER ::= { hh3cevtModuleSwitchType 69 }

hh3cevtModuleSw-BOARD-LS81FS24              OBJECT IDENTIFIER ::= { hh3cevtModuleSwitchType 70 }

hh3cevtModuleSw-BOARD-LS81FM24              OBJECT IDENTIFIER ::= { hh3cevtModuleSwitchType 71 }

hh3cevtModuleSw-BOARD-LS82GP20              OBJECT IDENTIFIER ::= { hh3cevtModuleSwitchType 72 }

hh3cevtModuleSw-LSB1SRPB                    OBJECT IDENTIFIER ::= { hh3cevtModuleSwitchType 73 }

hh3cevtModuleSw-LSB1F32GA                   OBJECT IDENTIFIER ::= { hh3cevtModuleSwitchType 74 }

hh3cevtModuleSw-LSB1F32GB                   OBJECT IDENTIFIER ::= { hh3cevtModuleSwitchType 75 }

hh3cevtModuleSw-LSB2FT48A                   OBJECT IDENTIFIER ::= { hh3cevtModuleSwitchType 76 }

hh3cevtModuleSw-LSB2FT48B                   OBJECT IDENTIFIER ::= { hh3cevtModuleSwitchType 77 }

hh3cevtModuleSw-LSB1GT12A                   OBJECT IDENTIFIER ::= { hh3cevtModuleSwitchType 78 }

hh3cevtModuleSw-LSB1GT12B                   OBJECT IDENTIFIER ::= { hh3cevtModuleSwitchType 79 }

hh3cevtModuleSw-PC4U                        OBJECT IDENTIFIER ::= { hh3cevtModuleSwitchType 80 }

hh3cevtModuleSw-FT32A                       OBJECT IDENTIFIER ::= { hh3cevtModuleSwitchType 81 }

hh3cevtModuleSw-GT4U                        OBJECT IDENTIFIER ::= { hh3cevtModuleSwitchType 82 }

hh3cevtModuleSw-BOARD-LS83FP20A             OBJECT IDENTIFIER ::= { hh3cevtModuleSwitchType 83 }

hh3cevtModuleSw-BOARD-LS82HGMU              OBJECT IDENTIFIER ::= { hh3cevtModuleSwitchType 84 }

hh3cevtModuleSw-LSB1GP8TB                   OBJECT IDENTIFIER ::= { hh3cevtModuleSwitchType 85 }

hh3cevtModuleSw-LSB1GP8TC                   OBJECT IDENTIFIER ::= { hh3cevtModuleSwitchType 86 }

hh3cevtModuleSw-LSB1GT8PB                   OBJECT IDENTIFIER ::= { hh3cevtModuleSwitchType 87 }

hh3cevtModuleSw-LSB1GT8PC                   OBJECT IDENTIFIER ::= { hh3cevtModuleSwitchType 88 }

hh3cevtModuleSw-LSB1FT48C                   OBJECT IDENTIFIER ::= { hh3cevtModuleSwitchType 89 }

hh3cevtModuleSw-LSB1FP20C                   OBJECT IDENTIFIER ::= { hh3cevtModuleSwitchType 90 }

hh3cevtModuleSw-LSB1F32GC                   OBJECT IDENTIFIER ::= { hh3cevtModuleSwitchType 91 }

hh3cevtModuleSw-LSB1GT12C                   OBJECT IDENTIFIER ::= { hh3cevtModuleSwitchType 92 }

hh3cevtModuleSw-LSB1GP12C                   OBJECT IDENTIFIER ::= { hh3cevtModuleSwitchType 93 }

hh3cevtModuleSw-LSB1P4G8C                   OBJECT IDENTIFIER ::= { hh3cevtModuleSwitchType 94 }

hh3cevtModuleSw-LSB1TGX1C                   OBJECT IDENTIFIER ::= { hh3cevtModuleSwitchType 95 }

hh3cevtModuleSw-LSB1GT24B                   OBJECT IDENTIFIER ::= { hh3cevtModuleSwitchType 96 }

hh3cevtModuleSw-LSB1GT24C                   OBJECT IDENTIFIER ::= { hh3cevtModuleSwitchType 97 }

hh3cevtModuleSw-LSB1GP24B                   OBJECT IDENTIFIER ::= { hh3cevtModuleSwitchType 98 }

hh3cevtModuleSw-LSB1GP24C                   OBJECT IDENTIFIER ::= { hh3cevtModuleSwitchType 99 }

hh3cevtModuleSw-LSB1XP2B                    OBJECT IDENTIFIER ::= { hh3cevtModuleSwitchType 100 }

hh3cevtModuleSw-LSB1XP2C                    OBJECT IDENTIFIER ::= { hh3cevtModuleSwitchType 101 }

hh3cevtModuleSw-LSB1GV48B                   OBJECT IDENTIFIER ::= { hh3cevtModuleSwitchType 102 }

hh3cevtModuleSw-LSB1GV48C                   OBJECT IDENTIFIER ::= { hh3cevtModuleSwitchType 103 }

hh3cevtModuleSw-LSB1SRPC                    OBJECT IDENTIFIER ::= { hh3cevtModuleSwitchType 104 }

hh3cevtModuleSw-LSB1SRP1N0                  OBJECT IDENTIFIER ::= { hh3cevtModuleSwitchType 105 }

hh3cevtModuleSw-LSB1SRP1N1                  OBJECT IDENTIFIER ::= { hh3cevtModuleSwitchType 106 }

hh3cevtModuleSw-LSB1SRP1N2                  OBJECT IDENTIFIER ::= { hh3cevtModuleSwitchType 107 }

hh3cevtModuleSw-GT24                        OBJECT IDENTIFIER ::= { hh3cevtModuleSwitchType 108 }

hh3cevtModuleSw-GP24                        OBJECT IDENTIFIER ::= { hh3cevtModuleSwitchType 109 }

hh3cevtModuleSw-XP2                         OBJECT IDENTIFIER ::= { hh3cevtModuleSwitchType 110 }

hh3cevtModuleSw-GV48                        OBJECT IDENTIFIER ::= { hh3cevtModuleSwitchType 111 }

hh3cevtModuleSw-LSG1GP8U                    OBJECT IDENTIFIER ::= { hh3cevtModuleSwitchType 112 }

hh3cevtModuleSw-LSG1GT8U                    OBJECT IDENTIFIER ::= { hh3cevtModuleSwitchType 113 }

hh3cevtModuleSw-LSG1TG1U                    OBJECT IDENTIFIER ::= { hh3cevtModuleSwitchType 114 }

hh3cevtModuleSw-LSG1TD1U                    OBJECT IDENTIFIER ::= { hh3cevtModuleSwitchType 115 }

hh3cevtModuleSw-LSB2FT48C                   OBJECT IDENTIFIER ::= { hh3cevtModuleSwitchType 116 } -- 48-Ports 100Base-TX Ethernet Interface module C

hh3cevtModuleSw-LSB1GT48B                   OBJECT IDENTIFIER ::= { hh3cevtModuleSwitchType 117 } -- 48-Ports 10/100/1000Base-T Ethernet Interface Module B

hh3cevtModuleSw-LSB1GT48C                   OBJECT IDENTIFIER ::= { hh3cevtModuleSwitchType 118 } -- 48-Ports 10/100/1000Base-T Ethernet Interface Module C

hh3cevtModuleSw-LS81GT48                    OBJECT IDENTIFIER ::= { hh3cevtModuleSwitchType 119 } -- 48 Port Gigabit Ethernet Electric Interface Unit

hh3cevtModuleSw-LS81SRPG0                   OBJECT IDENTIFIER ::= { hh3cevtModuleSwitchType 120 } -- Salience III, Switch and Route Processing Board

hh3cevtModuleSw-LS81SRPG1                   OBJECT IDENTIFIER ::= { hh3cevtModuleSwitchType 121 } -- Salience III Plus

hh3cevtModuleSw-LS81SRPG2                   OBJECT IDENTIFIER ::= { hh3cevtModuleSwitchType 122 } -- Salience III Lite

hh3cevtModuleSw-LS81SRPG3                   OBJECT IDENTIFIER ::= { hh3cevtModuleSwitchType 123 } -- Salience III Edge

--hh3cevtModuleSw-LS81SRPG                  OBJECT IDENTIFIER ::= { hh3cevtModuleSwitchType 124 } Switch And Route Processing Unit, Salience III. not used.

hh3cevtModuleSw-SR01SRPUB                   OBJECT IDENTIFIER ::= { hh3cevtModuleSwitchType 125 } -- SR8812 Switching and Route Processing Unit

hh3cevtModuleSw-SR01SRPUA                   OBJECT IDENTIFIER ::= { hh3cevtModuleSwitchType 126 } -- SR8805 Switching and Route Processing Unit

hh3cevtModuleSw-SR01GP12L                   OBJECT IDENTIFIER ::= { hh3cevtModuleSwitchType 127 } -- 12-Port 1000Base-X Ethernet SFP Optical Interface Line Card(L)

hh3cevtModuleSw-SR01GP12W                   OBJECT IDENTIFIER ::= { hh3cevtModuleSwitchType 128 } -- 12-Port 1000Base-X Ethernet SFP Optical Interface Line Card(W)

hh3cevtModuleSw-SR01FT48L                   OBJECT IDENTIFIER ::= { hh3cevtModuleSwitchType 129 } -- 48-Port 10/100Base-TX Ethernet RJ45 Electrical Interface Line Card (L)

hh3cevtModuleSw-SR01FT48W                   OBJECT IDENTIFIER ::= { hh3cevtModuleSwitchType 130 } -- 48-Port 10/100Base-TX Ethernet RJ45 Electrical Interface Line Card (W)

hh3cevtModuleSw-SR01XK1W                    OBJECT IDENTIFIER ::= { hh3cevtModuleSwitchType 131 } -- 1-Port 10GBase-R Ethernet XENPAK Optical Interface Line Card (W)

hh3cevtModuleSw-SR01FP20W                   OBJECT IDENTIFIER ::= { hh3cevtModuleSwitchType 132 } -- 20-Port 100Base-FX Ethernet SFP Optical Interface Line Card (W)

hh3cevtModuleSw-SR01GT12W                   OBJECT IDENTIFIER ::= { hh3cevtModuleSwitchType 133 } -- 12-Port 10/100/1000Base-T Ethernet RJ45 Electrical Interface Line Card (W)

hh3cevtModuleSw-SR01F32GL                   OBJECT IDENTIFIER ::= { hh3cevtModuleSwitchType 134 } -- 32-Port 10/100Base-TX Ethernet RJ45 Electrical Interface + 4-Port 1000Base-X Ethernet SFP Optical interface Line Card (L)

hh3cevtModuleSw-SR01F32GW                   OBJECT IDENTIFIER ::= { hh3cevtModuleSwitchType 135 } -- 32-Port 10/100Base-TX Ethernet RJ45 Electrical Interface  + 4-Port 1000Base-X  Ethernet SFP Optical interface Line Card (W)

hh3cevtModuleSw-SR01GT8PL                   OBJECT IDENTIFIER ::= { hh3cevtModuleSwitchType 136 } -- 8-Port 10/100/1000Base-T Ethernet RJ45 Electrical Interface + 4-Port 1000Base-X Ethernet SFP Optical Line Card (L)

hh3cevtModuleSw-SR01GT8PW                   OBJECT IDENTIFIER ::= { hh3cevtModuleSwitchType 137 } -- 8-Port 10/100/1000Base-T Ethernet RJ45 Electrical Interface + 4-Port 1000Base-X Ethernet SFP Optical Line Card (W)

hh3cevtModuleSw-SR01P4G8W                   OBJECT IDENTIFIER ::= { hh3cevtModuleSwitchType 138 } -- 4-Port 155M POS Optical Interface + 8-Port 1000Base-X Ethernet SFP Optical Interface Line Card (W)

hh3cevtModuleSw-LSA1FP8U                    OBJECT IDENTIFIER ::= { hh3cevtModuleSwitchType 139 } -- 8 Ports 100Base-FX Ethernet SFP Card

hh3cevtModuleSw-LSB1SP4B                    OBJECT IDENTIFIER ::= { hh3cevtModuleSwitchType 140 } -- 4-Port OC-48 POS SFP Optical Interface Board B

hh3cevtModuleSw-LSB1SP4C                    OBJECT IDENTIFIER ::= { hh3cevtModuleSwitchType 141 } -- 4-Port OC-48 POS SFP Optical Interface Board C

hh3cevtModuleSw-LSB1UP1B                    OBJECT IDENTIFIER ::= { hh3cevtModuleSwitchType 142 } -- 1-Port OC-192 POS XFP Optical Interface Board B

hh3cevtModuleSw-LSB1UP1C                    OBJECT IDENTIFIER ::= { hh3cevtModuleSwitchType 143 } -- 1-Port OC-192 POS XFP Optical Interface Board C

hh3cevtModuleSw-LSB1XP4B                    OBJECT IDENTIFIER ::= { hh3cevtModuleSwitchType 144 } -- 4-Port 10GBase Ethernet XFP Optical Interface Board B

hh3cevtModuleSw-LSB1XP4C                    OBJECT IDENTIFIER ::= { hh3cevtModuleSwitchType 145 } -- 4-Port 10GBase Ethernet XFP Optical Interface Board C

hh3cevtModuleSw-SP4                         OBJECT IDENTIFIER ::= { hh3cevtModuleSwitchType 146 } -- 4-Port OC-48 POS SFP Optical Interface Module

hh3cevtModuleSw-UP1                         OBJECT IDENTIFIER ::= { hh3cevtModuleSwitchType 147 } -- 1-Port OC-192 POS XFP Optical Interface Module

hh3cevtModuleSw-XP4                         OBJECT IDENTIFIER ::= { hh3cevtModuleSwitchType 148 } -- 4-Port 10GBase Ethernet XFP Optical Interface Module

hh3cevtModuleSw-LS81VSNP                    OBJECT IDENTIFIER ::= { hh3cevtModuleSwitchType 149 } -- VerSatile Network Processing Board

hh3cevtModuleSw-LS81T12P                    OBJECT IDENTIFIER ::= { hh3cevtModuleSwitchType 150 } -- 12-Port 1000Base-T Gigabit Ethernet Interface(RJ45)+4-Port 1000BASE-X  Gigabit Ethernet Optical Interface Board(SFP,LC)

hh3cevtModuleSw-LS81P12T                    OBJECT IDENTIFIER ::= { hh3cevtModuleSwitchType 151 } -- 12-Port 1000BASE-X Gigabit Ethernet Optical Interface(SFP,LC)+4-Port 1000BASE-T Gigabit Ethernet Interface Board(RJ45)

hh3cevtModuleSw-LS81GP8UB                   OBJECT IDENTIFIER ::= { hh3cevtModuleSwitchType 152 } -- 8-Port 1000M Ethernet Optical Interface Board(SFP,LC),LC Connector

hh3cevtModuleSw-LS81FT48E                   OBJECT IDENTIFIER ::= { hh3cevtModuleSwitchType 153 } -- 48-Port 100M Ethernet Electrical Interface Switch Unit(RJ45)

hh3cevtModuleSw-LS81GP4UB                   OBJECT IDENTIFIER ::= { hh3cevtModuleSwitchType 154 } -- 4-Port 1000M Ethernet Optical Interface Board(SFP,LC)

hh3cevtModuleSw-LS81GT8UE                   OBJECT IDENTIFIER ::= { hh3cevtModuleSwitchType 155 } -- 8-Port 1000M Ethernet Electrical Interface Switch Unit (RJ45)

hh3cevtModuleSw-LS81GT48A                   OBJECT IDENTIFIER ::= { hh3cevtModuleSwitchType 156 } -- 48 Port Gigabit Ethernet Electric Interface Unit

hh3cevtModuleSw-LS81FP48                    OBJECT IDENTIFIER ::= { hh3cevtModuleSwitchType 157 } -- 48 Port 100M Ethernet Optical Interface Board(SFP,LC)

hh3cevtModuleSw-LSB1XK1B                    OBJECT IDENTIFIER ::= { hh3cevtModuleSwitchType 158 } -- 1-Port 10GBase-R Ethernet XENPAK Optical Interface Board B

hh3cevtModuleSw-LSB1XK1C                    OBJECT IDENTIFIER ::= { hh3cevtModuleSwitchType 159 } -- 1-Port 10GBase-R Ethernet XENPAK Optical Interface Board C

hh3cevtModuleSw-SR01SRPUC                   OBJECT IDENTIFIER ::= { hh3cevtModuleSwitchType 160 } -- Switching and Route Processing Unit C

hh3cevtModuleSw-SR01SRPUD                   OBJECT IDENTIFIER ::= { hh3cevtModuleSwitchType 161 } -- Switching and Route Processing Unit D

hh3cevtModuleSw-SR01SRPUE                   OBJECT IDENTIFIER ::= { hh3cevtModuleSwitchType 162 } -- Switching and Route Processing Unit E

hh3cevtModuleSw-LSB1SRP1N3                  OBJECT IDENTIFIER ::= { hh3cevtModuleSwitchType 163 } -- Switching and Route Process Unit, Clock Module

hh3cevtModuleSw-LSB1VP2B                    OBJECT IDENTIFIER ::= { hh3cevtModuleSwitchType 164 } -- 2*10G Resilient Packet Ring Interface Line Card

hh3cevtModuleSw-LSB1NATB                    OBJECT IDENTIFIER ::= { hh3cevtModuleSwitchType 165 } -- NAT Service Processing Card (B)

hh3cevtModuleSw-LSB1VPNB                    OBJECT IDENTIFIER ::= { hh3cevtModuleSwitchType 166 } -- VPN Service Processing Card (B)

hh3cevtModuleSw-LSGP8P                      OBJECT IDENTIFIER ::= { hh3cevtModuleSwitchType 167 } -- 8-Port 1000M SFP Module

hh3cevtModuleSw-LSXK1P                      OBJECT IDENTIFIER ::= { hh3cevtModuleSwitchType 168 } -- 1-Port 10G Xenpak Module

hh3cevtModuleSw-LSXP2P                      OBJECT IDENTIFIER ::= { hh3cevtModuleSwitchType 169 } -- 2-Port 10G XFP Module

hh3cevtModuleSw-LS81FT48F                   OBJECT IDENTIFIER ::= { hh3cevtModuleSwitchType 170 } -- 48-Port 100M Ethernet Electrical Interface Switch Unit(RJ45)

hh3cevtModuleSw-LS81PT8G                    OBJECT IDENTIFIER ::= { hh3cevtModuleSwitchType 171 } -- 8 Port 1000BASE-X Gigabit Passive Optical Line Interface Board

hh3cevtModuleSw-LS81PT4G                    OBJECT IDENTIFIER ::= { hh3cevtModuleSwitchType 172 } -- 4 Port 1000BASE-X Gigabit Passive Optical Line Interface Board

hh3cevtModuleSw-LSSTK24G                    OBJECT IDENTIFIER ::= { hh3cevtModuleSwitchType 173 } -- 24G Stacking Ports Module

hh3cevtModuleSw-LS82GT20A                   OBJECT IDENTIFIER ::= { hh3cevtModuleSwitchType 174 } -- 20-Port 1000Base-T Gigabit Ethernet Electrical Interface Board(RJ45), BCM5697

hh3cevtModuleSw-LS82GP20A                   OBJECT IDENTIFIER ::= { hh3cevtModuleSwitchType 175 } -- 20-Port 1000BASE-X Gigabit Ethernet Optical Interface Board(SFP,LC), BCM5697

hh3cevtModuleSw-LS81TGX1C                   OBJECT IDENTIFIER ::= { hh3cevtModuleSwitchType 176 } -- 1-Port 10G Base-R Ethernet Board

hh3cevtModuleSw-VP2                         OBJECT IDENTIFIER ::= { hh3cevtModuleSwitchType 177 } -- 2*10G Resilient Packet Ring Interface Module

hh3cevtModuleSw-LSA1FB8U                    OBJECT IDENTIFIER ::= { hh3cevtModuleSwitchType 178 } -- 8-Port 100Base-Fx BIDI Ethernet Board

hh3cevtModuleSw-LS81T12PE                   OBJECT IDENTIFIER ::= { hh3cevtModuleSwitchType 179 } -- 12-Port 1000Base-T GE Interface+4-Port 1000BASE-X GE Optical Interface Board(SFP,LC)

hh3cevtModuleSw-LS81P12TE                   OBJECT IDENTIFIER ::= { hh3cevtModuleSwitchType 180 } -- 12-Port 1000BASE-X GE Optical Interface(SFP,LC)+4-Port 1000 BASE-T GE Interface Board(RJ45)

hh3cevtModuleSw-LSB1SRP2N0                  OBJECT IDENTIFIER ::= { hh3cevtModuleSwitchType 181 } -- Switching and Route Process Unit,12*LPU

hh3cevtModuleSw-LSB1SRP2N3                  OBJECT IDENTIFIER ::= { hh3cevtModuleSwitchType 182 } -- Switching and Route Process Unit, Clock Module

hh3cevtModuleSw-LSB1GV48DB                  OBJECT IDENTIFIER ::= { hh3cevtModuleSwitchType 183 } -- 48 Ports 1000Base-T Ethernet Interface Line Card with POE(DB)

hh3cevtModuleSw-LSB1FW8B                    OBJECT IDENTIFIER ::= { hh3cevtModuleSwitchType 184 } -- Firewall Service Processing Board with 8GE (B)

hh3cevtModuleSw-LSB1IPSEC8B                 OBJECT IDENTIFIER ::= { hh3cevtModuleSwitchType 185 } -- VPN Service Processing Board with 8GE (B)

hh3cevtModuleSw-LSB1IDSB                    OBJECT IDENTIFIER ::= { hh3cevtModuleSwitchType 186 } -- IDS Service Processing Board (B)

hh3cevtModuleSw-LSB1IPSB                    OBJECT IDENTIFIER ::= { hh3cevtModuleSwitchType 187 } -- IPS Service Processing Board (B)

hh3cevtModuleSw-LSB2FT48CA                  OBJECT IDENTIFIER ::= { hh3cevtModuleSwitchType 188 } -- 48 Ports 100Base-TX Ethernet Line Card (CA)

hh3cevtModuleSw-LSB1FP20CA                  OBJECT IDENTIFIER ::= { hh3cevtModuleSwitchType 189 } -- 20 Ports 100Base-FX Ethernet Interface Service Card (CA)

hh3cevtModuleSw-LSB1F32GCA                  OBJECT IDENTIFIER ::= { hh3cevtModuleSwitchType 190 } -- 32 Ports FE and 4 Ports GE Line Card(CA)

hh3cevtModuleSw-LSB1P4G8CA                  OBJECT IDENTIFIER ::= { hh3cevtModuleSwitchType 191 } -- 4 Ports OC-3c POS and 8 Ports GE Line Card(CA)

hh3cevtModuleSw-LSB1GT12CA                  OBJECT IDENTIFIER ::= { hh3cevtModuleSwitchType 192 } -- 12 Ports 1000Base-T Ethernet Interface Line Card(CA)

hh3cevtModuleSw-LSB1GT24CA                  OBJECT IDENTIFIER ::= { hh3cevtModuleSwitchType 193 } -- 24 Ports 1000Base-T Ethernet Interface Line Card(CA)

hh3cevtModuleSw-LSB1GP12CA                  OBJECT IDENTIFIER ::= { hh3cevtModuleSwitchType 194 } -- 12 Ports 1000Base Ethernet Optical Interface Service Card(CA)

hh3cevtModuleSw-LSB1GP24CA                  OBJECT IDENTIFIER ::= { hh3cevtModuleSwitchType 195 } -- 24 Ports 1000Base-X Ethernet Interface Line Card (CA)

hh3cevtModuleSw-LSB1GT8PCA                  OBJECT IDENTIFIER ::= { hh3cevtModuleSwitchType 196 } -- 8 Ports 1000Base-T Ethernet Interface & 4 Ports 1000Base-X Ethernet SFP Interface Line Card(CA)

hh3cevtModuleSw-LSB1XP2CA                   OBJECT IDENTIFIER ::= { hh3cevtModuleSwitchType 197 } -- 2-Port 10GBase-R/W Ethernet XFP Optical Interface Card(CA)

hh3cevtModuleSw-LSB1XK1CA                   OBJECT IDENTIFIER ::= { hh3cevtModuleSwitchType 198 } -- 10GBase-R Ethernet XENPAK Optical Interface Line Card(CA)

hh3cevtModuleSw-LSB1XP4CA                   OBJECT IDENTIFIER ::= { hh3cevtModuleSwitchType 199 } -- 4-Port 10GBase-R/X Ethernet Optical Interface Line Card(CA)

hh3cevtModuleSw-LSB1UP1CA                   OBJECT IDENTIFIER ::= { hh3cevtModuleSwitchType 200 } -- Single Port OC-192c POS XFP Optical Interface Card(CA)

hh3cevtModuleSw-LSB1SP4CA                   OBJECT IDENTIFIER ::= { hh3cevtModuleSwitchType 201 } -- 4-Port OC-48c POS SFP Optical Interface Card(CA)

hh3cevtModuleSw-LSB1VP2CA                   OBJECT IDENTIFIER ::= { hh3cevtModuleSwitchType 202 } -- 2*10G RPR Process Unit(CA)

hh3cevtModuleSw-SR01FT48WA                  OBJECT IDENTIFIER ::= { hh3cevtModuleSwitchType 203 } -- 48 Ports 100Base-TX Ethernet Line Card (WA)

hh3cevtModuleSw-SR01FP20WA                  OBJECT IDENTIFIER ::= { hh3cevtModuleSwitchType 204 } -- 20 Ports 100Base-FX Ethernet Interface Service Card (WA)

hh3cevtModuleSw-SR01F32GWA                  OBJECT IDENTIFIER ::= { hh3cevtModuleSwitchType 205 } -- 32 Ports FE and 4 Ports GE Line Card(WA)

hh3cevtModuleSw-SR01P4G8WA                  OBJECT IDENTIFIER ::= { hh3cevtModuleSwitchType 206 } -- 4 Ports OC-3c POS and 8 Ports GE Line Card(WA)

hh3cevtModuleSw-SR01GT12WA                  OBJECT IDENTIFIER ::= { hh3cevtModuleSwitchType 207 } -- 12 Ports 1000Base-T Ethernet Interface Line Card(WA)

hh3cevtModuleSw-SR01GT24WA                  OBJECT IDENTIFIER ::= { hh3cevtModuleSwitchType 208 } -- 24 Ports 1000Base-T Ethernet Interface Line Card(WA)

hh3cevtModuleSw-SR01GP12WA                  OBJECT IDENTIFIER ::= { hh3cevtModuleSwitchType 209 } -- 12 Ports 1000Base Ethernet Optical Interface Service Card(WA)

hh3cevtModuleSw-SR01GP24WA                  OBJECT IDENTIFIER ::= { hh3cevtModuleSwitchType 210 } -- 24 Ports 1000Base-X Ethernet Interface Line Card (WA)

hh3cevtModuleSw-SR01GT8PWA                  OBJECT IDENTIFIER ::= { hh3cevtModuleSwitchType 211 } -- 8 Ports 1000Base-T Ethernet Interface & 4 Ports 1000Base-X Ethernet SFP Interface Line Card(WA)

hh3cevtModuleSw-SR01XP2WA                   OBJECT IDENTIFIER ::= { hh3cevtModuleSwitchType 212 } -- 2-Port 10GBase-R/W Ethernet XFP Optical Interface Card(WA)

hh3cevtModuleSw-SR01XK1WA                   OBJECT IDENTIFIER ::= { hh3cevtModuleSwitchType 213 } -- 10GBase-R Ethernet XENPAK Optical Interface Line Card(WA)

hh3cevtModuleSw-SR01UP1WA                   OBJECT IDENTIFIER ::= { hh3cevtModuleSwitchType 214 } -- Single Port OC-192c POS XFP Optical Interface Card(WA)

hh3cevtModuleSw-SR01SP4WA                   OBJECT IDENTIFIER ::= { hh3cevtModuleSwitchType 215 } -- 4-Port OC-48c POS SFP Optical Interface Card(WA)

hh3cevtModuleSw-GP8U                        OBJECT IDENTIFIER ::= { hh3cevtModuleSwitchType 216 } -- 8-Port 1000Base-X SFP Optical Interface Module

hh3cevtModuleSw-LSEXP1P                     OBJECT IDENTIFIER ::= { hh3cevtModuleSwitchType 217 } -- Single 10G SFP Optical Interface Module

hh3cevtModuleSw-LSEXK1P                     OBJECT IDENTIFIER ::= { hh3cevtModuleSwitchType 218 } -- Single 10G XENPAK Interface Module

hh3cevtModuleSw-LSEXS1P                     OBJECT IDENTIFIER ::= { hh3cevtModuleSwitchType 219 } -- Single 10G STACK Interface Module

hh3cevtModuleSw-LS81GP48                    OBJECT IDENTIFIER ::= { hh3cevtModuleSwitchType 220 } -- 48-Port 1000M Ethernet Optical Interface Board(SFP,LC),LC Connector

hh3cevtModuleSw-LS81GT48B                   OBJECT IDENTIFIER ::= { hh3cevtModuleSwitchType 221 } -- 48-Port 1000Base-T Gigabit Ethernet Interface Board(RJ45)

hh3cevtModuleSw-LS81T16P                    OBJECT IDENTIFIER ::= { hh3cevtModuleSwitchType 222 } -- 16-Port 1000Base-T Gigabit Ethernet Interface(RJ45) + 8-Port 1000BASE-X Gigabit Ethernet Optical Interface Board(SFP,LC)

hh3cevtModuleSw-LS81T32P                    OBJECT IDENTIFIER ::= { hh3cevtModuleSwitchType 223 } -- 32-Port 1000Base-T Gigabit Ethernet Interface(RJ45) + 16-Port 1000BASE-X Gigabit Ethernet Optical Interface Board(SFP,LC)

hh3cevtModuleSw-LS81TGX2                    OBJECT IDENTIFIER ::= { hh3cevtModuleSwitchType 224 } -- 2-Port 10GBASE Ethernet Interface Board(XFP,LC)

hh3cevtModuleSw-LS81TGX4                    OBJECT IDENTIFIER ::= { hh3cevtModuleSwitchType 225 } -- 4-Port 10GBASE Ethernet Interface Module(XFP,LC),XG

hh3cevtModuleSw-LSB1GV48DA                  OBJECT IDENTIFIER ::= { hh3cevtModuleSwitchType 226 } -- 48 Ports 1000Base-T Ethernet Interface Line Card with POE(DA)

hh3cevtModuleSw-SR01GV48VB                  OBJECT IDENTIFIER ::= { hh3cevtModuleSwitchType 227 } -- 48 Ports 1000Base-T Ethernet Interface Line Card with POE(VB)

hh3cevtModuleSw-LSB1GT24DB                  OBJECT IDENTIFIER ::= { hh3cevtModuleSwitchType 228 } -- 24 Ports 1000Base-T Ethernet Interface Line Card(DB)

hh3cevtModuleSw-LSB1GP24DB                  OBJECT IDENTIFIER ::= { hh3cevtModuleSwitchType 229 } -- 24 Ports 1000Base-X Ethernet Interface Line Card(DB)

hh3cevtModuleSw-LSB1GP24DC                  OBJECT IDENTIFIER ::= { hh3cevtModuleSwitchType 230 } -- 24 Ports 1000Base-X Ethernet Interface Line Card(DC)

hh3cevtModuleSw-LSB1FW8DB                   OBJECT IDENTIFIER ::= { hh3cevtModuleSwitchType 231 } -- 8-port 1000BASE-X (SFP) Firewall Service Card(DB)

hh3cevtModuleSw-LSB1IPSEC8DB                OBJECT IDENTIFIER ::= { hh3cevtModuleSwitchType 232 } -- 8-port 1000BASE-X (SFP) IPSEC Service Card(DB)

hh3cevtModuleSw-SR01GT24VB                  OBJECT IDENTIFIER ::= { hh3cevtModuleSwitchType 233 } -- 24 Ports 1000Base-T Ethernet Interface Line Card(VB)

hh3cevtModuleSw-SR01GP24VC                  OBJECT IDENTIFIER ::= { hh3cevtModuleSwitchType 234 } -- 24 Ports 1000Base-X Ethernet Interface Line Card(VC)

hh3cevtModuleSw-SR01VP2WA                   OBJECT IDENTIFIER ::= { hh3cevtModuleSwitchType 235 } -- 2*10G RPR Process Unit(WA)

hh3cevtModuleSw-SR01FW8VB                   OBJECT IDENTIFIER ::= { hh3cevtModuleSwitchType 236 } -- 8-port 1000BASE-X (SFP) Firewall Service Card(VB)

hh3cevtModuleSw-SR01IPSEC8VB                OBJECT IDENTIFIER ::= { hh3cevtModuleSwitchType 237 } -- 8-port 1000BASE-X (SFP) IPSEC Service Card(VB)

hh3cevtModuleSw-SR01NATL                    OBJECT IDENTIFIER ::= { hh3cevtModuleSwitchType 238 } -- NAT Service Processing Card (L)

hh3cevtModuleSw-SR01VPNL                    OBJECT IDENTIFIER ::= { hh3cevtModuleSwitchType 239 } -- VPN Service Processing Card (L)

hh3cevtModuleSw-LSB1GP24CB                  OBJECT IDENTIFIER ::= { hh3cevtModuleSwitchType 240 } -- 24 Ports 1000Base-X Ethernet Interface Line Card(CB)

hh3cevtModuleSw-LSB1GP48DB                  OBJECT IDENTIFIER ::= { hh3cevtModuleSwitchType 241 } -- 48-Port Gigabit Ethernet Optical Interface Line Card(DB)

hh3cevtModuleSw-LSB1XP2CB                   OBJECT IDENTIFIER ::= { hh3cevtModuleSwitchType 242 } -- 2-Port 10Gigabit Ethernet Optical Interface Card(CB)

hh3cevtModuleSw-XP4L                        OBJECT IDENTIFIER ::= { hh3cevtModuleSwitchType 243 } -- 4 Port 1000BASE Optic Interface Module (XFP)

hh3cevtModuleSw-LSB1XP4LDB                  OBJECT IDENTIFIER ::= { hh3cevtModuleSwitchType 244 } -- 4-Port 10GBase-R/W Ethernet XFP Optical Interface Line Speed Card(DB)

hh3cevtModuleSw-LSB1XP4LDC                  OBJECT IDENTIFIER ::= { hh3cevtModuleSwitchType 245 } -- 4-Port 10GBase-R/W Ethernet XFP Optical Interface Line Speed Card(DC)

hh3cevtModuleSw-AHP4                        OBJECT IDENTIFIER ::= { hh3cevtModuleSwitchType 246 } -- 2-Port OC-3 ATM and 2-Port OC-3/12 ATM Interface Module (SFP)

hh3cevtModuleSw-LSB1AHP4GCA                 OBJECT IDENTIFIER ::= { hh3cevtModuleSwitchType 247 } -- 2-Port OC-3 ATM and 2-Port OC-3/12 ATM and 8-Port 1000Base-X Ethernet Optical Interface Line Card(CA)

hh3cevtModuleSw-CLP4                        OBJECT IDENTIFIER ::= { hh3cevtModuleSwitchType 248 } -- 4 Ports OC-3/STM-1 CPOS Optical Interface Module (SFP)

hh3cevtModuleSw-LSB1CLP4GCA                 OBJECT IDENTIFIER ::= { hh3cevtModuleSwitchType 249 } -- 4 Ports OC-3/STM-1 CPOS Optical Interface and 4-Port 1000Base-X Ethernet Optical Interface Line Card(CA)

hh3cevtModuleSw-ET32                        OBJECT IDENTIFIER ::= { hh3cevtModuleSwitchType 250 } -- 32-Port Channelized E1/T1 Interface Module

hh3cevtModuleSw-LSB1ET32GCA                 OBJECT IDENTIFIER ::= { hh3cevtModuleSwitchType 251 } -- 32-Port Channelized E1/T1 Interface and 4-Port 1000Base-X Ethernet Optical Interface Line Card(CA)

hh3cevtModuleSw-LSB1IDSDB                   OBJECT IDENTIFIER ::= { hh3cevtModuleSwitchType 252 } -- Intrusion Detection Service Card(DB)

hh3cevtModuleSw-LSB1SRP2N1                  OBJECT IDENTIFIER ::= { hh3cevtModuleSwitchType 253 } -- Switching and Route Processing Board,8*LPU

hh3cevtModuleSw-BOARD-LS82SRPB              OBJECT IDENTIFIER ::= { hh3cevtModuleSwitchType 254 }

hh3cevtModuleSw-BORAD-LS83SRPC              OBJECT IDENTIFIER ::= { hh3cevtModuleSwitchType 255 }

hh3cevtModuleSw-Main                        OBJECT IDENTIFIER ::= { hh3cevtModuleSwitchType 256 }

hh3cevtModuleSw-LSB1SRP2N2                  OBJECT IDENTIFIER ::= { hh3cevtModuleSwitchType 257 } -- Switching and Route Processing Board,5*LPU

hh3cevtModuleSw-LSB1NAMB                    OBJECT IDENTIFIER ::= { hh3cevtModuleSwitchType 258 } -- NAM Service Processing Card (B)

hh3cevtModuleSw-RSP2                        OBJECT IDENTIFIER ::= { hh3cevtModuleSwitchType 259 } -- 2*2.5G Resilient Packet Ring Interface

hh3cevtModuleSw-LSB1RSP2CA                  OBJECT IDENTIFIER ::= { hh3cevtModuleSwitchType 260 } -- 2*2.5G Resilient Packet Ring Interface Line Card(CA)

hh3cevtModuleSw-SR01XP4LVC                  OBJECT IDENTIFIER ::= { hh3cevtModuleSwitchType 261 } -- 4-Port 10GBase-R/W Ethernet XFP Optical Interface Line Speed Card(VC)

hh3cevtModuleSw-SR01AHP4GWA                 OBJECT IDENTIFIER ::= { hh3cevtModuleSwitchType 262 } -- 2-Port OC-3 ATM and 2-Port OC-3/12 ATM and 8-Port 1000Base-X Ethernet Optical Interface Line Card(WA)

hh3cevtModuleSw-SR01CLP4GWA                 OBJECT IDENTIFIER ::= { hh3cevtModuleSwitchType 263 } -- 4 Ports OC-3/STM-1 CPOS Optical Interface and 4-Port 1000Base-X Ethernet Optical Interface Line Card(WA)

hh3cevtModuleSw-SR01ET32GWA                 OBJECT IDENTIFIER ::= { hh3cevtModuleSwitchType 264 } -- 32-Port Channelized E1/T1 Interface and 4-Port 1000Base-X Ethernet Optical Interface Line Card(WA)

hh3cevtModuleSw-SR01IDSVB                   OBJECT IDENTIFIER ::= { hh3cevtModuleSwitchType 265 } -- Intrusion Detection Service Card(VB)

hh3cevtModuleSw-SR01SRPUF                   OBJECT IDENTIFIER ::= { hh3cevtModuleSwitchType 266 } -- Switching and Route Processing Board,12*LPU

hh3cevtModuleSw-SR01NAML                    OBJECT IDENTIFIER ::= { hh3cevtModuleSwitchType 267 } -- NAM Service Processing Card (L)

hh3cevtModuleSw-SR01RSP2WA                  OBJECT IDENTIFIER ::= { hh3cevtModuleSwitchType 268 } -- 2*2.5G Resilient Packet Ring Interface Line Card(WA)

hh3cevtModuleSw-LSPM1XP1P                   OBJECT IDENTIFIER ::= { hh3cevtModuleSwitchType 269 } -- 1-Port 10G XFP Module

hh3cevtModuleSw-LSPM1XP2P                   OBJECT IDENTIFIER ::= { hh3cevtModuleSwitchType 270 } -- 2-Port 10G XFP Module

hh3cevtModuleSw-LSPM1CX2P                   OBJECT IDENTIFIER ::= { hh3cevtModuleSwitchType 271 } -- 2-Port 10G CX4 Module

hh3cevtModuleSw-STK-1000BASE-T              OBJECT IDENTIFIER ::= { hh3cevtModuleSwitchType 272 } -- Single Port 1000BASE-T Stack Ethernet Interface Card

--
-- 273 to 299 reserved for other product
--


--
-- 300 to 499 reserved for advanced switches
--
hh3cevtModuleSw-LSB1SRP1M0                  OBJECT IDENTIFIER ::= { hh3cevtModuleSwitchType 300 } -- Switching and Route Process Unit,2*LPU or 3*LPU

hh3cevtModuleSw-LSB1SRP1M1                  OBJECT IDENTIFIER ::= { hh3cevtModuleSwitchType 301 } -- Switching and Route Process Unit

hh3cevtModuleSw-LSB1GP12DB                  OBJECT IDENTIFIER ::= { hh3cevtModuleSwitchType 302 } -- 12 Ports 1000Base Ethernet Optical Interface Service Card(DB)

hh3cevtModuleSw-LSB1GT12DB                  OBJECT IDENTIFIER ::= { hh3cevtModuleSwitchType 303 } -- 12 Ports 1000Base-T Ethernet Interface Line Card(DB)

hh3cevtModuleSw-LSB1XK1DB                   OBJECT IDENTIFIER ::= { hh3cevtModuleSwitchType 304 } -- 10GBase-R Ethernet XENPAK Optical Interface Line Card(DB)

hh3cevtModuleSw-LSB1XP2DB                   OBJECT IDENTIFIER ::= { hh3cevtModuleSwitchType 305 } -- 2-Port 10GBase-R/W Ethernet XFP Optical Interface Card(DB)

hh3cevtModuleSw-LSB1XP2DC                   OBJECT IDENTIFIER ::= { hh3cevtModuleSwitchType 306 } -- 2-Port 10GBase-R/W Ethernet XFP Optical Interface Card(DC)

hh3cevtModuleSw-LSB1GT48LDB                 OBJECT IDENTIFIER ::= { hh3cevtModuleSwitchType 307 } -- 48-Port Gigabit Ethernet RJ45 Electrical Interface Card (DB)

hh3cevtModuleSw-LSB1XP4TDB                  OBJECT IDENTIFIER ::= { hh3cevtModuleSwitchType 308 } -- 4-Port 10GBase-R/W Ethernet XFP Optical Interface Line Speed Test Card(DB)

hh3cevtModuleSw-LSB1XP4TDC                  OBJECT IDENTIFIER ::= { hh3cevtModuleSwitchType 309 } -- 4-Port 10GBase-R/W Ethernet XFP Optical Interface Line Speed Test Card(DC)

hh3cevtModuleSw-LSB1RSP2DC                  OBJECT IDENTIFIER ::= { hh3cevtModuleSwitchType 310 } -- 2*2.5G Resilient Packet Ring Interface Line Card(DC)

hh3cevtModuleSw-LSB1VP2DC                   OBJECT IDENTIFIER ::= { hh3cevtModuleSwitchType 311 } -- 2*10G Resilient Packet Ring Process Unit(DC)

hh3cevtModuleSw-LSB1XP4DB                   OBJECT IDENTIFIER ::= { hh3cevtModuleSwitchType 312 } -- 4-Port 10GBase-R/X Ethernet Optical Interface Line Card(DB)

hh3cevtModuleSw-LSB1SRP2E0                  OBJECT IDENTIFIER ::= { hh3cevtModuleSwitchType 313 } -- Switching and Route Process Unit,12*LPU

hh3cevtModuleSw-LSB1SRP2E1                  OBJECT IDENTIFIER ::= { hh3cevtModuleSwitchType 314 } -- Switching and Route Process Unit,8*LPU

hh3cevtModuleSw-LSB1SRP2E2                  OBJECT IDENTIFIER ::= { hh3cevtModuleSwitchType 315 } -- Switching and Route Process Unit,5*LPU

hh3cevtModuleSw-LSB1SRP2E3                  OBJECT IDENTIFIER ::= { hh3cevtModuleSwitchType 316 } -- Switching and Route Process Unit, Clock module

hh3cevtModuleSw-SR01SRPUQ                   OBJECT IDENTIFIER ::= { hh3cevtModuleSwitchType 317 } -- Switching and Route Processing Unit Q

hh3cevtModuleSw-AHP1                        OBJECT IDENTIFIER ::= { hh3cevtModuleSwitchType 318 } -- 1-Port OC-12c(3c)/STM-4(1) ATM Optical Interface Module(SFP)

hh3cevtModuleSw-AHP2                        OBJECT IDENTIFIER ::= { hh3cevtModuleSwitchType 319 } -- 2-Port OC-12c(3c)/STM-4(1) ATM Optical Interface Module(SFP)

hh3cevtModuleSw-CLP1                        OBJECT IDENTIFIER ::= { hh3cevtModuleSwitchType 320 } -- 1-Port OC-3/STM-1 CPOS Optical Interface Module(SFP)

hh3cevtModuleSw-CLP2                        OBJECT IDENTIFIER ::= { hh3cevtModuleSwitchType 321 } -- 2-Port OC-3/STM-1 CPOS Optical Interface Module(SFP)

hh3cevtModuleSw-ET16                        OBJECT IDENTIFIER ::= { hh3cevtModuleSwitchType 322 } -- 16-Port Channelized E1/T1 Interface Module

hh3cevtModuleSw-LSB1SRP1NA0                 OBJECT IDENTIFIER ::= { hh3cevtModuleSwitchType 323 } -- Switching and Route Process Unit,12*LPU

hh3cevtModuleSw-LSB1SRP1NA1                 OBJECT IDENTIFIER ::= { hh3cevtModuleSwitchType 324 } -- Switching and Route Process Unit,8*LPU

hh3cevtModuleSw-LSB1SRP1NA2                 OBJECT IDENTIFIER ::= { hh3cevtModuleSwitchType 325 } -- Switching and Route Process Unit,5*LPU

hh3cevtModuleSw-LSB1SRP1NA3                 OBJECT IDENTIFIER ::= { hh3cevtModuleSwitchType 326 } -- Switching and Route Process Unit, Clock module

hh3cevtModuleSw-SR01AHP1GWA                 OBJECT IDENTIFIER ::= { hh3cevtModuleSwitchType 327 } -- 1-Port OC-12c(3c)/STM-4(1) ATM Optical Interface and 4-Port 1000Base-X Ethernet Optical Interface Line Card(WA)

hh3cevtModuleSw-SR01AHP2GWA                 OBJECT IDENTIFIER ::= { hh3cevtModuleSwitchType 328 } -- 2-Port OC-12c(3c)/STM-4(1) ATM Optical Interface and 4-Port 1000Base-X Ethernet Optical Interface Line Card(WA)

hh3cevtModuleSw-SR01CLP1GWA                 OBJECT IDENTIFIER ::= { hh3cevtModuleSwitchType 329 } -- 1-Port OC-3/STM-1 CPOS Optical Interface and 4-Port 1000Base-X Ethernet Optical Interface Line Card(WA)

hh3cevtModuleSw-SR01CLP2GWA                 OBJECT IDENTIFIER ::= { hh3cevtModuleSwitchType 330 } -- 2-Port OC-3/STM-1 CPOS Optical Interface and 4-Port 1000Base-X Ethernet Optical Interface Line Card(WA)

hh3cevtModuleSw-SR01ET16GWA                 OBJECT IDENTIFIER ::= { hh3cevtModuleSwitchType 331 } -- 16-Port Channelized E1/T1 Interface and  4-Port 1000Base-X Ethernet Optical Interface Line Card(WA)

hh3cevtModuleSw-SR01GP12VB                  OBJECT IDENTIFIER ::= { hh3cevtModuleSwitchType 332 } -- 12-Port Gigabit Ethernet Optical Interface Card(VB)

hh3cevtModuleSw-SR01XK1VB                   OBJECT IDENTIFIER ::= { hh3cevtModuleSwitchType 333 } -- 1-Port 10Gigabit Ethernet Optical Interface Card(VB)

hh3cevtModuleSw-SR01XP2VC                   OBJECT IDENTIFIER ::= { hh3cevtModuleSwitchType 334 } -- 2-Port 10GBase-RW Ethernet XFP Optical Interface Line Card(VC)

hh3cevtModuleSw-SR01XP4LVB                  OBJECT IDENTIFIER ::= { hh3cevtModuleSwitchType 335 } -- 4-Port 10GBase-R/W Ethernet XFP Optical Interface Line Speed Card(VB)

hh3cevtModuleSw-SR01SRPUEA                  OBJECT IDENTIFIER ::= { hh3cevtModuleSwitchType 336 } -- Switching and Route Process Unit, Clock Module

hh3cevtModuleSw-LSB1SRP1N4                  OBJECT IDENTIFIER ::= { hh3cevtModuleSwitchType 337 } -- Switching and Route Process Unit, 12*LPU

hh3cevtModuleSw-LSB1SRP1N5                  OBJECT IDENTIFIER ::= { hh3cevtModuleSwitchType 338 } -- Switching and Route Process Unit, 8*LPU

hh3cevtModuleSw-LSB1SRP1N6                  OBJECT IDENTIFIER ::= { hh3cevtModuleSwitchType 339 } -- Switching and Route Process Unit, 5*LPU

hh3cevtModuleSw-LSB1SRP1N7                  OBJECT IDENTIFIER ::= { hh3cevtModuleSwitchType 340 } -- Switching and Route Process Unit, Clock Module

hh3cevtModuleSw-LSB1SRP2N4                  OBJECT IDENTIFIER ::= { hh3cevtModuleSwitchType 341 } -- Switching and Route Process Unit, 12*LPU

hh3cevtModuleSw-LSB1SRP2N5                  OBJECT IDENTIFIER ::= { hh3cevtModuleSwitchType 342 } -- Switching and Route Process Unit, 8*LPU

hh3cevtModuleSw-LSB1SRP2N6                  OBJECT IDENTIFIER ::= { hh3cevtModuleSwitchType 343 } -- Switching and Route Process Unit, 5*LPU

hh3cevtModuleSw-LSB1SRP2N7                  OBJECT IDENTIFIER ::= { hh3cevtModuleSwitchType 344 } -- Switching and Route Process Unit, Clock Module

hh3cevtModuleSw-LSB1SRP1NA4                 OBJECT IDENTIFIER ::= { hh3cevtModuleSwitchType 345 } -- Switching and Route Process Unit, 12*LPU

hh3cevtModuleSw-LSB1SRP1NA5                 OBJECT IDENTIFIER ::= { hh3cevtModuleSwitchType 346 } -- Switching and Route Process Unit, 8*LPU

hh3cevtModuleSw-LSB1SRP1NA6                 OBJECT IDENTIFIER ::= { hh3cevtModuleSwitchType 347 } -- Switching and Route Process Unit, 5*LPU

hh3cevtModuleSw-LSB1SRP1NA7                 OBJECT IDENTIFIER ::= { hh3cevtModuleSwitchType 348 } -- Switching and Route Process Unit, Clock Module

hh3cevtModuleSw-LSB2GV48DA                  OBJECT IDENTIFIER ::= { hh3cevtModuleSwitchType 349 } -- 48-Ports 1000Base-T Ethernet Interface Line Card with POE(DA)

hh3cevtModuleSw-LSB1RGP2GDB                 OBJECT IDENTIFIER ::= { hh3cevtModuleSwitchType 350 } -- 2-Port GE RPR and 8-Port GE Optical Interface Service Card(DB)

hh3cevtModuleSw-LSB1RGP4GDB                 OBJECT IDENTIFIER ::= { hh3cevtModuleSwitchType 351 } -- 4-Port GE RPR and 8-Port GE Optical Interface Service Card(DB)

hh3cevtModuleSw-LSB2GP24DB                  OBJECT IDENTIFIER ::= { hh3cevtModuleSwitchType 352 } -- 24-Port 1000BASE-X  Interface Module(DB),(SFP,LC)

hh3cevtModuleSw-LSB2GP24DC                  OBJECT IDENTIFIER ::= { hh3cevtModuleSwitchType 353 } -- 24-Port 1000BASE-X  Interface Module(DC),(SFP,LC)

hh3cevtModuleSw-LSB2GT24DB                  OBJECT IDENTIFIER ::= { hh3cevtModuleSwitchType 354 } -- 24-Port 10/100/1000BASE-T Interface Module(DB),(RJ45)

hh3cevtModuleSw-LSB2FW8DB                   OBJECT IDENTIFIER ::= { hh3cevtModuleSwitchType 355 } -- 8-Port 1000BASE-X Interface Firewall Service Module(DB),(SFP,LC)

hh3cevtModuleSw-LSB2IPSEC8DB                OBJECT IDENTIFIER ::= { hh3cevtModuleSwitchType 356 } -- 8-Port 1000BASE-X Interface IPSEC Service Module(DB),(SFP,LC)

hh3cevtModuleSw-LSB2GV48DB                  OBJECT IDENTIFIER ::= { hh3cevtModuleSwitchType 357 } -- 48-Port 10/100/1000BASE-T Interface Module(DB),(PoE,RJ45)

hh3cevtModuleSw-RGP2                        OBJECT IDENTIFIER ::= { hh3cevtModuleSwitchType 358 } -- 2-Port GE Resilient Packet Ring Interface Module

hh3cevtModuleSw-RGP4                        OBJECT IDENTIFIER ::= { hh3cevtModuleSwitchType 359 } -- 4-Port GE Resilient Packet Ring Interface Module

hh3cevtModuleSw-SR02FW8VB                   OBJECT IDENTIFIER ::= { hh3cevtModuleSwitchType 360 } -- 8-Port 1000BASE-X Interface Firewall Service Module(VB),(SFP,LC)

hh3cevtModuleSw-SR02IPSEC8VB                OBJECT IDENTIFIER ::= { hh3cevtModuleSwitchType 361 } -- 8-Port 1000BASE-X Interface IPSEC Service Module(VB),(SFP,LC)

hh3cevtModuleSw-LSB2SRP1N0                  OBJECT IDENTIFIER ::= { hh3cevtModuleSwitchType 362 } -- Switching and Route Process Unit, 12*LPU

hh3cevtModuleSw-LSB2SRP1N1                  OBJECT IDENTIFIER ::= { hh3cevtModuleSwitchType 363 } -- Switching and Route Process Unit, 8*LPU

hh3cevtModuleSw-LSB2SRP1N2                  OBJECT IDENTIFIER ::= { hh3cevtModuleSwitchType 364 } -- Switching and Route Process Unit, 5*LPU

hh3cevtModuleSw-LSB2SRP1N3                  OBJECT IDENTIFIER ::= { hh3cevtModuleSwitchType 365 } -- Switching and Route Process Unit, Clock module

hh3cevtModuleSw-LSB2SRP1N4                  OBJECT IDENTIFIER ::= { hh3cevtModuleSwitchType 366 } -- Switching and Route Process Unit, 12*LPU

hh3cevtModuleSw-LSB2SRP1N5                  OBJECT IDENTIFIER ::= { hh3cevtModuleSwitchType 367 } -- Switching and Route Process Unit, 8*LPU

hh3cevtModuleSw-LSB2SRP1N6                  OBJECT IDENTIFIER ::= { hh3cevtModuleSwitchType 368 } -- Switching and Route Process Unit, 5*LPU

hh3cevtModuleSw-LSB2SRP1N7                  OBJECT IDENTIFIER ::= { hh3cevtModuleSwitchType 369 } -- Switching and Route Process Unit, Clock module

hh3cevtModuleSw-SR02SRPUE                   OBJECT IDENTIFIER ::= { hh3cevtModuleSwitchType 370 } -- Switching and Route Process Unit, Clock module

hh3cevtModuleSw-SR01LN1BQH0                 OBJECT IDENTIFIER ::= { hh3cevtModuleSwitchType 371 } -- Single XG Service Board(BQH)

hh3cevtModuleSw-SR01DXP1L                   OBJECT IDENTIFIER ::= { hh3cevtModuleSwitchType 372 } -- 1-Port 10GBASE-R/W Ethernet Optical Interface Card,(XFP,LC)

hh3cevtModuleSw-SR01DGP10L                  OBJECT IDENTIFIER ::= { hh3cevtModuleSwitchType 373 } -- 10-Port 1000BASE-X Optical Interface Card,(SFP,LC)

hh3cevtModuleSw-SR01DRSP2L                  OBJECT IDENTIFIER ::= { hh3cevtModuleSwitchType 374 } -- 2-Port 2.5G RPR Optical Interface Card,(SFP,LC)

hh3cevtModuleSw-SR01DRUP1L                  OBJECT IDENTIFIER ::= { hh3cevtModuleSwitchType 375 } -- 1-Port 10G RPR Optical Interface Card,(XFP,LC)

hh3cevtModuleSw-SR01DGP20R                  OBJECT IDENTIFIER ::= { hh3cevtModuleSwitchType 376 } -- 20-Port 1000BASE-X Optical Interface Card,(SFP,LC)

hh3cevtModuleSw-SR01DPLP8L                  OBJECT IDENTIFIER ::= { hh3cevtModuleSwitchType 377 } -- 8-Port 155M POS Optical Interface Card,(SFP,LC)

hh3cevtModuleSw-SR01DXP2R                   OBJECT IDENTIFIER ::= { hh3cevtModuleSwitchType 378 } -- 2-Port 10GBASE-R/W Ethernet Optical Interface Card,(XFP,LC)

hh3cevtModuleSw-LSB1FW2A0                   OBJECT IDENTIFIER ::= { hh3cevtModuleSwitchType 379 } -- Gigabit Firewall Card, 4 Gigabit Port for Management

hh3cevtModuleSw-LSB1GP48LDB                 OBJECT IDENTIFIER ::= { hh3cevtModuleSwitchType 380 } -- 48-Port Line Rate Gigabit Ethernet Optical Interface Card(DB)

hh3cevtModuleSw-SR01LN1BNA0                 OBJECT IDENTIFIER ::= { hh3cevtModuleSwitchType 381 } -- Single XG Service Board(BNA)

hh3cevtModuleSw-SR01LN2BQH0                 OBJECT IDENTIFIER ::= { hh3cevtModuleSwitchType 382 } -- Dual XG Service Board(BQH)

hh3cevtModuleSw-SR01LN2BNA0                 OBJECT IDENTIFIER ::= { hh3cevtModuleSwitchType 383 } -- Dual XG Service Board(BNA)

hh3cevtModuleSw-SR01DGT20R                  OBJECT IDENTIFIER ::= { hh3cevtModuleSwitchType 384 } -- 20-Port 10/100/1000BASE-T Electrical Interface Card,(RJ45)

hh3cevtModuleSw-SR01DPSP4L                  OBJECT IDENTIFIER ::= { hh3cevtModuleSwitchType 385 } -- 4-Port 2.5G POS Optical Interface Card(SFP,LC)

hh3cevtModuleSw-SR01DPUP1L                  OBJECT IDENTIFIER ::= { hh3cevtModuleSwitchType 386 } -- 1-Port 10G POS Optical Interface Card,(XFP,LC)

hh3cevtModuleSw-SR01DPL2G6L                 OBJECT IDENTIFIER ::= { hh3cevtModuleSwitchType 387 } -- 2-Port 155M POS Optical Interface(SFP,LC)+6-Port 1000BASE-X Optical Interface Card(SFP,LC)

hh3cevtModuleSw-SR01DPH2G6L                 OBJECT IDENTIFIER ::= { hh3cevtModuleSwitchType 388 } -- 2-Port 622M POS Optical Interface(SFP,LC)+6-Port 1000BASE-X Optical Interface Card(SFP,LC)

hh3cevtModuleSw-SR01DPS2G4L                 OBJECT IDENTIFIER ::= { hh3cevtModuleSwitchType 389 } -- 2-Port 2.5G POS Optical Interface(SFP,LC)+4-Port 1000BASE-X Optical Interface Card(SFP,LC)

hh3cevtModuleSw-SR01DCL1G8L                 OBJECT IDENTIFIER ::= { hh3cevtModuleSwitchType 390 } -- 1-Port 155M CPOS Optical Interface(SFP,LC)+8-Port 1000BASE-X Optical Interface Card(SFP,LC)

hh3cevtModuleSw-SR01DCL2G8L                 OBJECT IDENTIFIER ::= { hh3cevtModuleSwitchType 391 } -- 2-Port 155M CPOS Optical Interface(SFP,LC)+8-Port 1000BASE-X Optical Interface Card(SFP,LC)

hh3cevtModuleSw-SR01DET8G8L                 OBJECT IDENTIFIER ::= { hh3cevtModuleSwitchType 392 } -- 8-Port E1/T1 Electrical Interface(RJ45)+8-Port 1000BASE-X Optical Interface Card(SFP,LC)

hh3cevtModuleSw-SR02SRP2E3                  OBJECT IDENTIFIER ::= { hh3cevtModuleSwitchType 393 } -- Switching and Route Process Unit, Clock module

hh3cevtModuleSw-SR02SRP1E3                  OBJECT IDENTIFIER ::= { hh3cevtModuleSwitchType 394 } -- Switching and Route Process Unit, Clock module

hh3cevtModuleSw-SR02SRP1M3                  OBJECT IDENTIFIER ::= { hh3cevtModuleSwitchType 395 } -- Switching and Route Process Unit, Clock module

hh3cevtModuleSw-SR01DQCP4L                  OBJECT IDENTIFIER ::= { hh3cevtModuleSwitchType 396 } -- 4-Port OC-3c/OC-12c/OC-48c POS/GE Optical Interface Card,(SFP,LC)

hh3cevtModuleSw-SR01DTCP8L                  OBJECT IDENTIFIER ::= { hh3cevtModuleSwitchType 397 } -- 8-Port OC-3c/OC-12c POS/GE Optical Interface Card,(SFP,LC)

hh3cevtModuleSw-LSB1AFC1A0                  OBJECT IDENTIFIER ::= { hh3cevtModuleSwitchType 398 } -- Anomaly Flow Cleaner Board

hh3cevtModuleSw-LSB1SSL1A0                  OBJECT IDENTIFIER ::= { hh3cevtModuleSwitchType 399 } -- SSL VPN High-end Board

hh3cevtModuleSw-IMNAM                       OBJECT IDENTIFIER ::= { hh3cevtModuleSwitchType 400 } -- Net Analysis Service Processing Board

hh3cevtModuleSw-IMNAT                       OBJECT IDENTIFIER ::= { hh3cevtModuleSwitchType 401 } -- Network Address Translation Service Processing Board

hh3cevtModuleSw-PICAHP1L                    OBJECT IDENTIFIER ::= { hh3cevtModuleSwitchType 402 } -- 1-Port OC-12c/STM-4c ATM Optical Interface Card,(SFP,LC)

hh3cevtModuleSw-PICALP4L                    OBJECT IDENTIFIER ::= { hh3cevtModuleSwitchType 403 } -- 4-Port OC-3c/STM-1c ATM Optical Interface Card,(SFP,LC)

hh3cevtModuleSw-PICCHP4L                    OBJECT IDENTIFIER ::= { hh3cevtModuleSwitchType 404 } -- 4-Port 622M CPOS Optical Interface Card(SFP,LC)

hh3cevtModuleSw-PICCHS1G4L                  OBJECT IDENTIFIER ::= { hh3cevtModuleSwitchType 405 } -- 1-Port 622M CPOS Optical Interface(Channelized to E3/T3)+4-Port 1000BASE-X Optical Interface Card(SFP,LC)

hh3cevtModuleSw-PICCLS4G4L                  OBJECT IDENTIFIER ::= { hh3cevtModuleSwitchType 406 } -- 4-Port 155M CPOS Optical Interface(Channelized to E3/T3)+4-Port 1000BASE-X Optical Interface Card(SFP,LC)

hh3cevtModuleSw-PICCSP1L                    OBJECT IDENTIFIER ::= { hh3cevtModuleSwitchType 407 } -- 1-Port 2.5G CPOS Optical Interface Card(SFP,LC)

hh3cevtModuleSw-LSB1ACG1A0                  OBJECT IDENTIFIER ::= { hh3cevtModuleSwitchType 408 } -- Application Control Gateway Board

hh3cevtModuleSw-LST1MRPNC1                  OBJECT IDENTIFIER ::= { hh3cevtModuleSwitchType 409 } -- Management and Route Process Unit

hh3cevtModuleSw-LST1SF18B1                  OBJECT IDENTIFIER ::= { hh3cevtModuleSwitchType 410 } -- S12518 Switch Fabric Card

hh3cevtModuleSw-LST1SF08B1                  OBJECT IDENTIFIER ::= { hh3cevtModuleSwitchType 411 } -- S12508 Switch Fabric Card

hh3cevtModuleSw-LST1GT48LEC1                OBJECT IDENTIFIER ::= { hh3cevtModuleSwitchType 412 } -- 48-Port 10/100/1000BASE-T Interface Module(LEC),(RJ45)

hh3cevtModuleSw-LST1GP48LEC1                OBJECT IDENTIFIER ::= { hh3cevtModuleSwitchType 413 } -- 48-Port 1000BASE-X Interface Module (LEC),(SFP,LC)

hh3cevtModuleSw-LST1XP4LEC1                 OBJECT IDENTIFIER ::= { hh3cevtModuleSwitchType 414 } -- 4-Port 10GBASE-R/W Interface Module (LEC),(XFP,LC)

hh3cevtModuleSw-LST1XP8LEC1                 OBJECT IDENTIFIER ::= { hh3cevtModuleSwitchType 415 } -- 8-Port 10GBASE-R/W Interface Module (LEC),(XFP,LC)

hh3cevtModuleSw-LSR1SRP2B1                  OBJECT IDENTIFIER ::= { hh3cevtModuleSwitchType 416 } -- Switching and Route Process Unit

hh3cevtModuleSw-LSR1SRP2C1                  OBJECT IDENTIFIER ::= { hh3cevtModuleSwitchType 417 } -- Switching and Route Process Unit

hh3cevtModuleSw-LSR1SRP2B2                  OBJECT IDENTIFIER ::= { hh3cevtModuleSwitchType 418 } -- Switching and Route Process Unit

hh3cevtModuleSw-LSR1SRP2C2                  OBJECT IDENTIFIER ::= { hh3cevtModuleSwitchType 419 } -- Switching and Route Process Unit

hh3cevtModuleSw-LSR1GT24LEC1                OBJECT IDENTIFIER ::= { hh3cevtModuleSwitchType 420 } -- 16-Port 10/100/1000BASE-T Interface and 8-port 1000BASE-T/1000BASE-X Combo Interface Service Card(LEC)

hh3cevtModuleSw-LSR1GP24LEB1                OBJECT IDENTIFIER ::= { hh3cevtModuleSwitchType 421 } -- 16-Port 1000BASE-X Interface and 8-port 1000BASE-T/1000BASE-X Combo Interface Service Card(LEB)

hh3cevtModuleSw-LSR1GP24LEC1                OBJECT IDENTIFIER ::= { hh3cevtModuleSwitchType 422 } -- 16-Port 1000BASE-X Interface and 8-port 1000BASE-T/1000BASE-X Combo Interface Service Card(LEC)

hh3cevtModuleSw-LSR1GT48LEB1                OBJECT IDENTIFIER ::= { hh3cevtModuleSwitchType 423 } -- 48-Port 10/100/1000BASE-T Interface Module(LEB),(RJ45)

hh3cevtModuleSw-LSR1GT48LEC1                OBJECT IDENTIFIER ::= { hh3cevtModuleSwitchType 424 } -- 48-Port 10/100/1000BASE-T Interface Module(LEC),(RJ45)

hh3cevtModuleSw-LSR1GP48LEB1                OBJECT IDENTIFIER ::= { hh3cevtModuleSwitchType 425 } -- 48-Port 1000BASE-X Interface Module(LEB),(SFP,LC)

hh3cevtModuleSw-LSR1GP48LEC1                OBJECT IDENTIFIER ::= { hh3cevtModuleSwitchType 426 } -- 48-Port 1000BASE-X Interface Module(LEC),(SFP,LC)

hh3cevtModuleSw-LSR2GV48REB1                OBJECT IDENTIFIER ::= { hh3cevtModuleSwitchType 427 } -- 48-Port 10/100/1000BASE-T Interface Module(REB),(PoE,RJ45)

hh3cevtModuleSw-LSR1XP2LEB1                 OBJECT IDENTIFIER ::= { hh3cevtModuleSwitchType 428 } -- 2-Port 10GBase-R/W Interface Module (LEB),(XFP,LC)

hh3cevtModuleSw-LSR1XP2LEC1                 OBJECT IDENTIFIER ::= { hh3cevtModuleSwitchType 429 } -- 2-Port 10GBase-R/W Interface Module (LEC),(XFP,LC)

hh3cevtModuleSw-LSR1XP4LEB1                 OBJECT IDENTIFIER ::= { hh3cevtModuleSwitchType 430 } -- 4-Port 10GBase-R/W Interface Module (LEB),(XFP,LC)

hh3cevtModuleSw-LSR1XP4LEC1                 OBJECT IDENTIFIER ::= { hh3cevtModuleSwitchType 431 } -- 4-Port 10GBase-R/W Interface Module (LEC),(XFP,LC)

hh3cevtModuleSw-IMFW                        OBJECT IDENTIFIER ::= { hh3cevtModuleSwitchType 432 } -- Firewall Service Processing Board

hh3cevtModuleSw-LSB1LB1A0                   OBJECT IDENTIFIER ::= { hh3cevtModuleSwitchType 433 } -- Load Balance Board

hh3cevtModuleSw-LSB1IPS1A0                  OBJECT IDENTIFIER ::= { hh3cevtModuleSwitchType 434 } -- Gigabit IPS Card

hh3cevtModuleSw-LST1GT48LEB1                OBJECT IDENTIFIER ::= { hh3cevtModuleSwitchType 435 } -- 48-Port 10/100/1000BASE-T Interface Module(LEB),(RJ45)

hh3cevtModuleSw-LST1GP48LEB1                OBJECT IDENTIFIER ::= { hh3cevtModuleSwitchType 436 } -- 48-Port 1000BASE-X Interface Module (LEB),(SFP,LC)

hh3cevtModuleSw-LST1XP4LEB1                 OBJECT IDENTIFIER ::= { hh3cevtModuleSwitchType 437 } -- 4-Port 10GBASE-R/W Interface Module (LEB),(XFP,LC)

hh3cevtModuleSw-LST1XP8LEB1                 OBJECT IDENTIFIER ::= { hh3cevtModuleSwitchType 438 } -- 8-Port 10GBASE-R/W Interface Module (LEB),(XFP,LC)

hh3cevtModuleSw-LST1XP32REB1                OBJECT IDENTIFIER ::= { hh3cevtModuleSwitchType 439 } -- 32-Port 10GBASE-R Interface Module (REB),(SFP+,LC)

hh3cevtModuleSw-LST1XP32REC1                OBJECT IDENTIFIER ::= { hh3cevtModuleSwitchType 440 } -- 32-Port 10GBASE-R Interface Module (REC),(SFP+,LC)

hh3cevtModuleSw-LSR1FW2A1                   OBJECT IDENTIFIER ::= { hh3cevtModuleSwitchType 441 } -- Firewall Service Module

hh3cevtModuleSw-LSR1SSL1A1                  OBJECT IDENTIFIER ::= { hh3cevtModuleSwitchType 442 } -- SSL VPN Service Module

hh3cevtModuleSw-SR01DET32G2L                OBJECT IDENTIFIER ::= { hh3cevtModuleSwitchType 443 } -- 32-Port E1/T1 75ohm Electrical Interface(DB56 Female Socket)+2-Port 1000BASE-X Optical Interface Card(SFP,LC)

hh3cevtModuleSw-LSR1GP24LEF1                OBJECT IDENTIFIER ::= { hh3cevtModuleSwitchType 444 } -- 16-Port 1000BASE-X Interface and 8-port 1000BASE-T/1000BASE-X Combo Interface Service Card(LEF)

hh3cevtModuleSw-LSR1XP4LEF1                 OBJECT IDENTIFIER ::= { hh3cevtModuleSwitchType 445 } -- 4-Port 10GBASE-R/W Interface Module (LEF),(XFP,LC)

--
-- 500 to 699 reserved for secondary switches
--
hh3cevtModuleSw-LS81GP16TM                  OBJECT IDENTIFIER ::= { hh3cevtModuleSwitchType 500 } -- 12-port 1000BASE-X SFP Interface and 4-port 1000BASE-T/1000BASE-X Combo Interface Metro Switch and Route Processing Board

hh3cevtModuleSw-LS81VP4C                    OBJECT IDENTIFIER ::= { hh3cevtModuleSwitchType 501 } -- 4-port 1000BASE-X SFP Interface Virtual Daughter Card

hh3cevtModuleSw-LS8M1PT8P0                  OBJECT IDENTIFIER ::= { hh3cevtModuleSwitchType 502 } -- 8-Port 1000BASE-PX Optical Line Interface Board, SFP Req

hh3cevtModuleSw-LS8M1PT8GB0                 OBJECT IDENTIFIER ::= { hh3cevtModuleSwitchType 503 } -- 8-Port 1000BASE-PX20 Gigabit Passive Optical Line Interface Board B(20km, SFF), SC Connector

hh3cevtModuleSw-LS8M1PT4GB0                 OBJECT IDENTIFIER ::= { hh3cevtModuleSwitchType 504 } -- 4-Port 1000BASE-PX20 Gigabit Passive Optical Line Interface Board B(20km, SFF), SC Connector

hh3cevtModuleSw-LS81GP2R                    OBJECT IDENTIFIER ::= { hh3cevtModuleSwitchType 505 } -- 2-port 1000M Ethernet Optical Interface RPR Board

hh3cevtModuleSw-LS81GP4R                    OBJECT IDENTIFIER ::= { hh3cevtModuleSwitchType 506 } -- 4-port 1000M Ethernet Optical Interface RPR Board

hh3cevtModuleSw-LS81IPSECA                  OBJECT IDENTIFIER ::= { hh3cevtModuleSwitchType 507 } -- IPSec Service Board

hh3cevtModuleSw-LS81FWA                     OBJECT IDENTIFIER ::= { hh3cevtModuleSwitchType 508 } -- Firewall Service Board

hh3cevtModuleSw-LS82VSNP                    OBJECT IDENTIFIER ::= { hh3cevtModuleSwitchType 509 } -- Versatile Network Processing Service Module (PBR/NAT/NetStream) with 12-port 1000BASE-X SFP, XGBUS Uplink

hh3cevtModuleSw-LSQ1GV48SA                  OBJECT IDENTIFIER ::= { hh3cevtModuleSwitchType 510 } -- 48-Port 1000Base-T Gigabit Ethernet Interface Board(RJ45)

hh3cevtModuleSw-LSQ1SRPB                    OBJECT IDENTIFIER ::= { hh3cevtModuleSwitchType 511 } -- Salience VI

hh3cevtModuleSw-LSQ1SRP2XB                  OBJECT IDENTIFIER ::= { hh3cevtModuleSwitchType 512 } -- Salience VI-10GE

hh3cevtModuleSw-LSQ1SRP1CB                  OBJECT IDENTIFIER ::= { hh3cevtModuleSwitchType 513 } -- Salience VI-Turbo

hh3cevtModuleSw-LSQ1FV48SA                  OBJECT IDENTIFIER ::= { hh3cevtModuleSwitchType 514 } -- 48-Port 100M Ethernet Electrical Interface Switch Unit(RJ45)

hh3cevtModuleSw-LSD1MPUA                    OBJECT IDENTIFIER ::= { hh3cevtModuleSwitchType 515 } -- Main Control Unit

hh3cevtModuleSw-LSD1GP20A0                  OBJECT IDENTIFIER ::= { hh3cevtModuleSwitchType 516 } -- 16-port 1000BASE-X SFP Interface and 4-port 1000BASE-T/1000BASE-X Combo Interface Line Card

hh3cevtModuleSw-LSD1GP20TA0                 OBJECT IDENTIFIER ::= { hh3cevtModuleSwitchType 517 } -- 16-port 1000BASE-X SFP Interface and 4-port 1000BASE-T/1000BASE-X Combo Interface and 16 1000BASE-T Interface Line Card

hh3cevtModuleSw-LSD1GP36A0                  OBJECT IDENTIFIER ::= { hh3cevtModuleSwitchType 518 } -- 32-port 1000BASE-X SFP Interface and 4-port 1000BASE-T/1000BASE-X Combo Interface Line Card

hh3cevtModuleSw-LSD1GP20XA0                 OBJECT IDENTIFIER ::= { hh3cevtModuleSwitchType 519 } -- 16-port 1000BASE-X SFP Interface and 4-port 1000BASE-T/1000BASE-X Combo Interface and 2-port 10GBASE-X XFP Interface Line Card

hh3cevtModuleSw-LSD1GP20EA0                 OBJECT IDENTIFIER ::= { hh3cevtModuleSwitchType 520 } -- 16-port 1000BASE-X SFP Interface and 4-port 1000BASE-T/1000BASE-X Combo Interface and 2-port GE RPR Interface Line Card

hh3cevtModuleSw-LSD1GP20RA0                 OBJECT IDENTIFIER ::= { hh3cevtModuleSwitchType 521 } -- 16-port 1000BASE-X SFP Interface and 4-port 1000BASE-T/1000BASE-X Combo Interface and 2-port OC48 RPR Interface Line Card

hh3cevtModuleSw-LSD1GP16A0                  OBJECT IDENTIFIER ::= { hh3cevtModuleSwitchType 522 } -- 16-port 1000BASE-X SFP Ethernet Interface SubCard

hh3cevtModuleSw-LSD1GT16A0                  OBJECT IDENTIFIER ::= { hh3cevtModuleSwitchType 523 } -- 16-port 1000BASE-T Ethernet Interface SubCard

hh3cevtModuleSw-LSD1XP2A0                   OBJECT IDENTIFIER ::= { hh3cevtModuleSwitchType 524 } -- 2-port 10GBASE-X XFP Ethernet Interface SubCard

hh3cevtModuleSw-LSD1EP2A0                   OBJECT IDENTIFIER ::= { hh3cevtModuleSwitchType 525 } -- 2-port 1000BASE-T Ethernet RPR Interface SubCard

hh3cevtModuleSw-LSD1RP2A0                   OBJECT IDENTIFIER ::= { hh3cevtModuleSwitchType 526 } -- 2-port OC48 RPR Interface SubCard

hh3cevtModuleSw-LSQ1GV48SC                  OBJECT IDENTIFIER ::= { hh3cevtModuleSwitchType 527 } -- 48-Port 1000Base-T Gigabit Ethernet Interface Board(RJ45)-POE

hh3cevtModuleSw-LSQ1FP48SA                  OBJECT IDENTIFIER ::= { hh3cevtModuleSwitchType 528 } -- 48 Port 100M Ethernet Optical Interface Board(SFP,LC)

hh3cevtModuleSw-LSQ1GP24SC                  OBJECT IDENTIFIER ::= { hh3cevtModuleSwitchType 529 } -- 24 Port 1000BASE-X Ethernet Optical Interface Board(SFP,LC)

hh3cevtModuleSw-LSQ1GT24SC                  OBJECT IDENTIFIER ::= { hh3cevtModuleSwitchType 530 } -- 24-Port 1000BASE-T Ethernet Interface Board (RJ45)

hh3cevtModuleSw-LSQ1TGX2SC                  OBJECT IDENTIFIER ::= { hh3cevtModuleSwitchType 531 } -- 2-Port 10GBASE Ethernet Optical Interface Board(XFP,LC)

hh3cevtModuleSw-LSQ1GP12EA                  OBJECT IDENTIFIER ::= { hh3cevtModuleSwitchType 532 } -- 12-Port 1000BASE-X Ethernet Optical Interface Board(SFP,LC)

hh3cevtModuleSw-LSQ1TGX1EA                  OBJECT IDENTIFIER ::= { hh3cevtModuleSwitchType 533 } -- 1-Port 10GBASE Ethernet Optical Interface Module(XFP,LC)

hh3cevtModuleSw-LSQ1P24XGSC                 OBJECT IDENTIFIER ::= { hh3cevtModuleSwitchType 534 } -- 24-Port 1000BASE-X Gigabit Ethernet Optical Interface(SFP,LC)+2-Port 10GBASE Ethernet Optical Interface Board(XFP,LC)

hh3cevtModuleSw-LSQ1T24XGSC                 OBJECT IDENTIFIER ::= { hh3cevtModuleSwitchType 535 } -- 24-Port 1000BASE-T Gigabit Ethernet Interface(RJ45)+2-Port 10GBASE Ethernet Optical Interface Board(XFP,LC)

hh3cevtModuleSw-LS81TGX1B                   OBJECT IDENTIFIER ::= { hh3cevtModuleSwitchType 536 } -- 1 Port 10GBase-R Ethernet Interface Board(XENPAK,SC)

hh3cevtModuleSw-LSQ1PT4PSC0                 OBJECT IDENTIFIER ::= { hh3cevtModuleSwitchType 537 } -- 4-Port 1000Base-PX Optical Line Terminal(EPON OLT SFP,SC)+8-Port 1000BASE-X Optical Interface Board(SFP,LC)

hh3cevtModuleSw-LS81SRPG13                  OBJECT IDENTIFIER ::= { hh3cevtModuleSwitchType 538 } -- Salience V, Switch and Route Processing Board

hh3cevtModuleSw-LS81SRPG14                  OBJECT IDENTIFIER ::= { hh3cevtModuleSwitchType 539 } -- Salience V Edge

hh3cevtModuleSw-LS81SRPG15                  OBJECT IDENTIFIER ::= { hh3cevtModuleSwitchType 540 } -- Salience V Plus

hh3cevtModuleSw-LSQ1GP48SC0                 OBJECT IDENTIFIER ::= { hh3cevtModuleSwitchType 541 } -- 48-Port 1000BASE Ethernet Optical Interface Board(SFP,LC)

hh3cevtModuleSw-LSQ1GP12SC0                 OBJECT IDENTIFIER ::= { hh3cevtModuleSwitchType 542 } -- 12-Port 1000BASE-X Ethernet Optical Interface Board(SFP,LC)

hh3cevtModuleSw-LSD1SRPA                    OBJECT IDENTIFIER ::= { hh3cevtModuleSwitchType 543 } -- Salience VIII 160

hh3cevtModuleSw-LSD1SRPB                    OBJECT IDENTIFIER ::= { hh3cevtModuleSwitchType 544 } -- Salience VIII 480

hh3cevtModuleSw-LSD1SRPC                    OBJECT IDENTIFIER ::= { hh3cevtModuleSwitchType 545 } -- Salience VIII 800

hh3cevtModuleSw-LSD1GT16PES0                OBJECT IDENTIFIER ::= { hh3cevtModuleSwitchType 546 } -- 16-Port 10/100/1000BASE-T and 8-Port 100/1000BASE-X SFP Interface Card

hh3cevtModuleSw-LSD1GP24ES0                 OBJECT IDENTIFIER ::= { hh3cevtModuleSwitchType 547 } -- 24-Port 1000BASE-X Ethernet SFP Interface Card

hh3cevtModuleSw-LSD1GT24XES0                OBJECT IDENTIFIER ::= { hh3cevtModuleSwitchType 548 } -- 24-Port 10/100/1000BASE-T and 2-port 10GBASE-X Ethernet XFP Optical Interface Card

hh3cevtModuleSw-LSD1GP24XES0                OBJECT IDENTIFIER ::= { hh3cevtModuleSwitchType 549 } -- 24-Port 1000BASE-X Ethernet SFP interface and 2-port 10GBASE-X Ethernet XFP Optical Interface Card

hh3cevtModuleSw-LSD1XP2ES0                  OBJECT IDENTIFIER ::= { hh3cevtModuleSwitchType 550 } -- 2-Port 10GBASE-X Ethernet XFP Optical Interface Card

hh3cevtModuleSw-LSD1GP48ES0                 OBJECT IDENTIFIER ::= { hh3cevtModuleSwitchType 551 } -- 48-Port 1000BASE-X Ethernet SFP Interface Card

hh3cevtModuleSw-LSQ1MPUA0                   OBJECT IDENTIFIER ::= { hh3cevtModuleSwitchType 552 } -- Master Process Board

hh3cevtModuleSw-LSQ1MPUA1                   OBJECT IDENTIFIER ::= { hh3cevtModuleSwitchType 553 } -- Master Process Unit

hh3cevtModuleSw-LSQ1FWBSC0                  OBJECT IDENTIFIER ::= { hh3cevtModuleSwitchType 554 } -- Gigabit Firewall Cardú¼4 Gigabit Port for Management

hh3cevtModuleSw-LSQ1PT8PSC0                 OBJECT IDENTIFIER ::= { hh3cevtModuleSwitchType 555 } -- 8-Port 1000Base-PX Optical Line Terminal(EPON OLT SFP,SC)+8-Port 1000BASE-X Optical Interface Board(SFP,LC)

hh3cevtModuleSw-LSQ1PT16PSC0                OBJECT IDENTIFIER ::= { hh3cevtModuleSwitchType 556 } -- 16-Port 1000Base-PX Optical Line Terminal(EPON OLT SFP,SC)+8-Port 1000BASE-X Optical Interface Board(SFP,LC)

hh3cevtModuleSw-SA11MPUA0                   OBJECT IDENTIFIER ::= { hh3cevtModuleSwitchType 557 } -- SmartEngine I-Lite

hh3cevtModuleSw-SA11MPUB0                   OBJECT IDENTIFIER ::= { hh3cevtModuleSwitchType 558 } -- SmartEngine I

hh3cevtModuleSw-LSQ1AFCBSC0                 OBJECT IDENTIFIER ::= { hh3cevtModuleSwitchType 559 } -- Anomaly Flow Cleaner Board Interface Board(SFP,LC)

hh3cevtModuleSw-LSQ1MPUB0                   OBJECT IDENTIFIER ::= { hh3cevtModuleSwitchType 560 } -- Salience VI-Lite

hh3cevtModuleSw-LSQ1MPUB1                   OBJECT IDENTIFIER ::= { hh3cevtModuleSwitchType 561 } -- Salience VI-Lite

hh3cevtModuleSw-LSQ1PT4PSC1                 OBJECT IDENTIFIER ::= { hh3cevtModuleSwitchType 562 } -- 4-Port 1000Base-PX Optical Line Terminal(EPON OLT SFP,SC)+8-Port 1000BASE-X Optical Interface Board(SFP,LC)

hh3cevtModuleSw-LSQ1PT8PSC1                 OBJECT IDENTIFIER ::= { hh3cevtModuleSwitchType 563 } -- 8-Port 1000Base-PX Optical Line Terminal(EPON OLT SFP,SC)+8-Port 1000BASE-X Optical Interface Board(SFP,LC)

hh3cevtModuleSw-LSQ1PT16PSC1                OBJECT IDENTIFIER ::= { hh3cevtModuleSwitchType 564 } -- 16-Port 1000Base-PX Optical Line Terminal(EPON OLT SFP,SC)+8-Port 1000BASE-X Optical Interface Board(SFP,LC)

hh3cevtModuleSw-LSQ1FP48USA0                OBJECT IDENTIFIER ::= { hh3cevtModuleSwitchType 565 } -- 48-Port 100M Ethernet Optical Interface Switch Unit(SFP,LC)

hh3cevtModuleSw-LSQ1FP48USA1                OBJECT IDENTIFIER ::= { hh3cevtModuleSwitchType 566 } -- 48-Port 100M Ethernet Optical Interface Switch Unit(SFP,LC)

hh3cevtModuleSw-LSQ1FV48USA0                OBJECT IDENTIFIER ::= { hh3cevtModuleSwitchType 567 } -- 48-Port 100M Ethernet Electrical Interface Switch Unit(RJ45),PoE

hh3cevtModuleSw-LSQ1FV48USA1                OBJECT IDENTIFIER ::= { hh3cevtModuleSwitchType 568 } -- 48-Port 100M Ethernet Electrical Interface Switch Unit(RJ45),PoE

hh3cevtModuleSw-LSQ1SRPD0                   OBJECT IDENTIFIER ::= { hh3cevtModuleSwitchType 569 } -- Switch and Route Processing Unit, Salience VI-Plus

hh3cevtModuleSw-LSQ1CGP24TSC0               OBJECT IDENTIFIER ::= { hh3cevtModuleSwitchType 570 } -- Switching and Routing Processing Unit with 24 1000BASE-X Gigabit Ethernet Optical Ports,including 8 Combo Ports,SFP Req.

hh3cevtModuleSw-LSQ1GP24TSC0                OBJECT IDENTIFIER ::= { hh3cevtModuleSwitchType 571 } -- 16-Port 1000BASE-X Gigabit Ethernet Optical(SFP,LC) And 8-Port 10/100/1000BASE-T RJ45/1000BASE-X SFP Combo Interface Board

hh3cevtModuleSw-LSQ1ACGASC0                 OBJECT IDENTIFIER ::= { hh3cevtModuleSwitchType 572 } -- Application Control Gateway Board

hh3cevtModuleSw-LSD1XP1ES0                  OBJECT IDENTIFIER ::= { hh3cevtModuleSwitchType 573 } -- 1-Port 10GBASE-X Ethernet XFP Optical Interface Card

hh3cevtModuleSw-LSD1GP12ES0                 OBJECT IDENTIFIER ::= { hh3cevtModuleSwitchType 574 } -- 12-Port 1000BASE-X Ethernet SFP Interface Card

hh3cevtModuleSw-LSQ1SRP12GB0                OBJECT IDENTIFIER ::= { hh3cevtModuleSwitchType 575 } -- Switch And Route Processing Unit with 12 1000BASE Ethernet Optical Interfaces(SFP,LC),Salience VI-GE

hh3cevtModuleSw-LSQ1GV40PSC0                OBJECT IDENTIFIER ::= { hh3cevtModuleSwitchType 576 } -- 40-Port 10/100/1000BASE-T Electrical(RJ45) And 8-Port 1000BASE-X Optical Ethernet Interface Board(SFP,LC),PoE

hh3cevtModuleSw-LSQ1FWBSC1                  OBJECT IDENTIFIER ::= { hh3cevtModuleSwitchType 577 } -- Firewall Board

hh3cevtModuleSw-LSQ1NSMSC0                  OBJECT IDENTIFIER ::= { hh3cevtModuleSwitchType 578 } -- NetStream Board

hh3cevtModuleSw-LSQ1NSMSC1                  OBJECT IDENTIFIER ::= { hh3cevtModuleSwitchType 579 } -- NetStream Board

hh3cevtModuleSw-LSQ1AFDBSC0                 OBJECT IDENTIFIER ::= { hh3cevtModuleSwitchType 580 } -- Anomaly Flow Detector Board

hh3cevtModuleSw-LS81MPUB                    OBJECT IDENTIFIER ::= { hh3cevtModuleSwitchType 581 } -- Salience IV

hh3cevtModuleSw-LS81FP48XL                  OBJECT IDENTIFIER ::= { hh3cevtModuleSwitchType 582 } -- 48-Port 100M Ethernet Optical Interface Module,(SFP,LC)

hh3cevtModuleSw-LS81FT48XL                  OBJECT IDENTIFIER ::= { hh3cevtModuleSwitchType 583 } -- 48-Port 10/100M Ethernet Electrical Interface Module(RJ45)

hh3cevtModuleSw-LS81GP12XL                  OBJECT IDENTIFIER ::= { hh3cevtModuleSwitchType 584 } -- 12-Port 1000/100M Ethernet Optical Interface Module(SFP,LC)

hh3cevtModuleSw-LS81GP24XL                  OBJECT IDENTIFIER ::= { hh3cevtModuleSwitchType 585 } -- 24-Port 1000/100M Ethernet Optical Interface Module(SFP,LC)

hh3cevtModuleSw-LS81GP48XL                  OBJECT IDENTIFIER ::= { hh3cevtModuleSwitchType 586 } -- 48-Port 1000/100M Ethernet Optical Interface Module(SFP,LC)

hh3cevtModuleSw-LS81GT24XL                  OBJECT IDENTIFIER ::= { hh3cevtModuleSwitchType 587 } -- 24-Port 10/100/1000M Ethernet Electrical Interface Module(RJ45)

hh3cevtModuleSw-LS81GT48XL                  OBJECT IDENTIFIER ::= { hh3cevtModuleSwitchType 588 } -- 48-Port 10/100/1000M Ethernet Electrical Interface Module(RJ45)

hh3cevtModuleSw-LS81TGX2XL                  OBJECT IDENTIFIER ::= { hh3cevtModuleSwitchType 589 } -- 2-Port 10GBASE Ethernet Optical Interface Module(XFP,LC)

hh3cevtModuleSw-LSQ1GV48SD0                 OBJECT IDENTIFIER ::= { hh3cevtModuleSwitchType 590 } -- 48-Port 1000Base-T Gigabit Ethernet Interface Board(RJ45),PoE

hh3cevtModuleSw-LSQ1GP48EB0                 OBJECT IDENTIFIER ::= { hh3cevtModuleSwitchType 591 } -- 48-Port Enhanced 1000BASE-X Ethernet Optical Interface Board(SFP,LC)

hh3cevtModuleSw-LSQ1IPSSC0                  OBJECT IDENTIFIER ::= { hh3cevtModuleSwitchType 592 } -- Gigabit IPS Card

hh3cevtModuleSw-LSQ1GV48SD1                 OBJECT IDENTIFIER ::= { hh3cevtModuleSwitchType 593 } -- 48-Port 1000Base-T Gigabit Ethernet Interface Board(RJ45),PoE

hh3cevtModuleSw-LSQ1GP48SD0                 OBJECT IDENTIFIER ::= { hh3cevtModuleSwitchType 594 } -- 48-Port 1000BASE-X Gigabit Ethernet Optical Interface(SFP,LC) Interface Board

hh3cevtModuleSw-LSQ1GP48SD1                 OBJECT IDENTIFIER ::= { hh3cevtModuleSwitchType 595 } -- 48-Port 1000BASE-X Gigabit Ethernet Optical Interface(SFP,LC) Interface Board

hh3cevtModuleSw-LSQ1SRPA0                   OBJECT IDENTIFIER ::= { hh3cevtModuleSwitchType 596 } -- Salience VI-Smart

hh3cevtModuleSw-LSQ1SRPA1                   OBJECT IDENTIFIER ::= { hh3cevtModuleSwitchType 597 } -- Salience VI-Smart

hh3cevtModuleSw-LSQ2FP48SA0                 OBJECT IDENTIFIER ::= { hh3cevtModuleSwitchType 598 } -- 48 Port 100M Ethernet Optical Interface Board(SFP,LC)

hh3cevtModuleSw-LSQ2FP48SA1                 OBJECT IDENTIFIER ::= { hh3cevtModuleSwitchType 599 } -- 48 Port 100M Ethernet Optical Interface Board(SFP,LC)

hh3cevtModuleSw-LSQ2FT48SA0                 OBJECT IDENTIFIER ::= { hh3cevtModuleSwitchType 600 } -- 48-Port 100M Ethernet Electrical Interface Switch Unit(RJ45)

hh3cevtModuleSw-LSQ2FT48SA1                 OBJECT IDENTIFIER ::= { hh3cevtModuleSwitchType 601 } -- 48-Port 100M Ethernet Electrical Interface Switch Unit(RJ45)

hh3cevtModuleSw-LSQ1GV24PSC0                OBJECT IDENTIFIER ::= { hh3cevtModuleSwitchType 602 } -- 24-Port 10/100/1000BASE-T Electrical(RJ45) Interface Board,including 4 Combo Ports,SFP Req,PoE,No Spell

hh3cevtModuleSw-LSQ1GV24PSC1                OBJECT IDENTIFIER ::= { hh3cevtModuleSwitchType 603 } -- 24-Port 10/100/1000BASE-T Electrical(RJ45) Interface Board,including 4 Combo Ports,SFP Req,PoE,No Spell

hh3cevtModuleSw-LSQ1CGV24PSC0               OBJECT IDENTIFIER ::= { hh3cevtModuleSwitchType 604 } -- Switching and Routing Processing Unit with 24 10/100/1000BASE-T Electrical Ports(RJ45),including 4 Combo Ports,SFP Req,PoE,No Spell

hh3cevtModuleSw-LSQ1CGV24PSC1               OBJECT IDENTIFIER ::= { hh3cevtModuleSwitchType 605 } -- Switching and Routing Processing Unit with 24 10/100/1000BASE-T Electrical Ports(RJ45),including 4 Combo Ports,SFP Req,PoE,No Spell

hh3cevtModuleSw-LSQ1GP24TEB0                OBJECT IDENTIFIER ::= { hh3cevtModuleSwitchType 606 } -- 16-Port 1000BASE-X Gigabit Ethernet Optical Interface(SFP,LC)+8-Port Combo Interface Board

hh3cevtModuleSw-LSQ1GP24TEB1                OBJECT IDENTIFIER ::= { hh3cevtModuleSwitchType 607 } -- 16-Port 1000BASE-X Gigabit Ethernet Optical Interface(SFP,LC)+8-Port Combo Interface Board

hh3cevtModuleSw-LSQ1GP24TSD0                OBJECT IDENTIFIER ::= { hh3cevtModuleSwitchType 608 } -- 16-Port 1000BASE-X Gigabit Ethernet Optical Interface(SFP,LC)+8-Port Combo Interface Board

hh3cevtModuleSw-LSQ1GP24TSD1                OBJECT IDENTIFIER ::= { hh3cevtModuleSwitchType 609 } -- 16-Port 1000BASE-X Gigabit Ethernet Optical Interface(SFP,LC)+8-Port Combo Interface Board

hh3cevtModuleSw-LSQ1GP24TXSD0               OBJECT IDENTIFIER ::= { hh3cevtModuleSwitchType 610 } -- 16-Port GE Optical Interface(SFP,LC)+8-Port Combo Interface+2-Port 10GE Optical Interface Board(XFP,LC)

hh3cevtModuleSw-LSQ1GP24TXSD1               OBJECT IDENTIFIER ::= { hh3cevtModuleSwitchType 611 } -- 16-Port GE Optical Interface(SFP,LC)+8-Port Combo Interface+2-Port 10GE Optical Interface Board(XFP,LC)

hh3cevtModuleSw-LSQ1TGX2EB0                 OBJECT IDENTIFIER ::= { hh3cevtModuleSwitchType 612 } -- 2-Port 10GBASE Ethernet Optical Interface Board(XFP,LC)

hh3cevtModuleSw-LSQ1TGX2EB1                 OBJECT IDENTIFIER ::= { hh3cevtModuleSwitchType 613 } -- 2-Port 10GBASE Ethernet Optical Interface Board(XFP,LC)

hh3cevtModuleSw-LSQ1TGX2SD0                 OBJECT IDENTIFIER ::= { hh3cevtModuleSwitchType 614 } -- 2-Port 10GBASE Ethernet Optical Interface Board(XFP,LC)

hh3cevtModuleSw-LSQ1TGX2SD1                 OBJECT IDENTIFIER ::= { hh3cevtModuleSwitchType 615 } -- 2-Port 10GBASE Ethernet Optical Interface Board(XFP,LC)

hh3cevtModuleSw-LSQ1TGX4SD0                 OBJECT IDENTIFIER ::= { hh3cevtModuleSwitchType 616 } -- 4-Port 10GBASE Ethernet Optical Interface Board(XFP,LC)

hh3cevtModuleSw-LSQ1TGX4SD1                 OBJECT IDENTIFIER ::= { hh3cevtModuleSwitchType 617 } -- 4-Port 10GBASE Ethernet Optical Interface Board(XFP,LC)

hh3cevtModuleSw-LSQ1TGX8SD0                 OBJECT IDENTIFIER ::= { hh3cevtModuleSwitchType 618 } -- 8-Port 10GBASE Ethernet Optical Interface Board(XFP,LC)

hh3cevtModuleSw-LSQ1TGX8SD1                 OBJECT IDENTIFIER ::= { hh3cevtModuleSwitchType 619 } -- 8-Port 10GBASE Ethernet Optical Interface Board(XFP,LC)

hh3cevtModuleSw-LSQ1GP48EB1                 OBJECT IDENTIFIER ::= { hh3cevtModuleSwitchType 620 } -- 48-Port Enhanced 1000BASE-X Ethernet Optical Interface Board(SFP,LC)

hh3cevtModuleSw-LSQ1TGX4EB0                 OBJECT IDENTIFIER ::= { hh3cevtModuleSwitchType 621 } -- 4-Port 10GBASE Ethernet Optical Interface Board(XFP,LC)

hh3cevtModuleSw-LSQ1TGX4EB1                 OBJECT IDENTIFIER ::= { hh3cevtModuleSwitchType 622 } -- 4-Port 10GBASE Ethernet Optical Interface Board(XFP,LC)

--
-- 700 to 799 reserved for primary switches
--
hh3cevtModuleSw-1000BASE-X-COMBO            OBJECT IDENTIFIER ::= { hh3cevtModuleSwitchType 701 } -- Single port 10/100/1000BASE-T/1000BASE-X Combo Interface Board

hh3cevtModuleSw-EPON-1000M                  OBJECT IDENTIFIER ::= { hh3cevtModuleSwitchType 702 } -- Optical Network Unit Interface Board

hh3cevtModuleSw-1000BASE-FIXED-2SFP-T-2RJ45         OBJECT IDENTIFIER ::= { hh3cevtModuleSwitchType 703 } -- 2 port 10/100/1000BASE-T and 2 port 1000BASE-X Interface Board

hh3cevtModuleSw-100M-1550-BIDI              OBJECT IDENTIFIER ::= { hh3cevtModuleSwitchType 704 }  -- 100BASE-X BIDI Interface Board, Tx 1550nm, Rx 1310nm

hh3cevtModuleSw-100M-1310-BIDI              OBJECT IDENTIFIER ::= { hh3cevtModuleSwitchType 705 }  -- 100BASE-X reverse Interface Board, Tx 1310nm, Rx 1550nm

hh3cevtModuleSw-1000BASE-FIXED-4RJ45-4SFP-COMBO     OBJECT IDENTIFIER ::= { hh3cevtModuleSwitchType 706 } -- 4 port 10/100/1000BASE-T and 4 port 1000BASE-X COMBO Interface Board

hh3cevtModuleSw-LSH1PK2T                    OBJECT IDENTIFIER ::= { hh3cevtModuleSwitchType 707 } -- OSM Interface Board

hh3cevtModuleSw-LSPM2GP2P                   OBJECT IDENTIFIER ::= { hh3cevtModuleSwitchType 708 } -- 2-Port 1000BASE-X SFP Module

hh3cevtModuleSw-LSWM1GT16P                  OBJECT IDENTIFIER ::= { hh3cevtModuleSwitchType 709 } -- 16-Port 10/100/1000BASE-T Ethernet Electrical Interface Module

hh3cevtModuleSw-LSWM1GP16P                  OBJECT IDENTIFIER ::= { hh3cevtModuleSwitchType 710 } -- 16-Port 100/1000BASE-X Ethernet Optical Interface Module

hh3cevtModuleSw-LSWM1XP2P                   OBJECT IDENTIFIER ::= { hh3cevtModuleSwitchType 711 } -- 2-Port 10G Ethernet XFP Optical Interface Module

hh3cevtModuleSw-LSWM1XP4P                   OBJECT IDENTIFIER ::= { hh3cevtModuleSwitchType 712 } -- 4-Port 10G Ethernet XFP Optical Interface Module

hh3cevtModuleSw-LSWM1SP2P                   OBJECT IDENTIFIER ::= { hh3cevtModuleSwitchType 713 } -- 2-Port 10G Ethernet SFP PLUS Optical Interface Module

hh3cevtModuleSw-LSWM1SP4P                   OBJECT IDENTIFIER ::= { hh3cevtModuleSwitchType 714 } -- 4-Port 10G Ethernet SFP PLUS Optical Interface Module

hh3cevtModuleSw-LSWM148POEM                 OBJECT IDENTIFIER ::= { hh3cevtModuleSwitchType 715 } -- 48 Port Mid Power PoE Module

hh3cevtModuleSw-LSWM1FW10                   OBJECT IDENTIFIER ::= { hh3cevtModuleSwitchType 716 } -- RMI CPU XLR 732, with Firewall software

hh3cevtModuleSw-LSWM1WCM10                  OBJECT IDENTIFIER ::= { hh3cevtModuleSwitchType 717 } -- RMI CPU XLR 732, with Wireless Access Controller software

hh3cevtModuleSw-LSWM1IPS10                  OBJECT IDENTIFIER ::= { hh3cevtModuleSwitchType 718 } -- RMI CPU XLR 732, with IPS/AV software

hh3cevtModuleSw-IPS-T1000-M                 OBJECT IDENTIFIER ::= { hh3cevtModuleSwitchType 720 } -- IPS for T1000-M mainboardú¡module

hh3cevtModuleSw-IPS-T1000-A                 OBJECT IDENTIFIER ::= { hh3cevtModuleSwitchType 721 } -- IPS for T1000-A mainboardú¡module

hh3cevtModuleSw-IPS-T1000-S                 OBJECT IDENTIFIER ::= { hh3cevtModuleSwitchType 722 } -- IPS for T1000-S mainboardú¡module

hh3cevtModuleSw-IPS-GX4C                    OBJECT IDENTIFIER ::= { hh3cevtModuleSwitchType 723 } -- four-port-gigabit-fiber-boardú¡module

hh3cevtModuleSw-IPS-GT4C                    OBJECT IDENTIFIER ::= { hh3cevtModuleSwitchType 724 } -- four-port-1000BASET-boardú¡module

hh3cevtModuleSw-LSPM2SP2P                   OBJECT IDENTIFIER ::= { hh3cevtModuleSwitchType 725 } -- 2-Port 10G Ethernet SFP PLUS Optical Interface Module


-- 800 to 899 reserved for WLAN products
hh3cevtModuleSw-WX5002MPU                   OBJECT IDENTIFIER ::= { hh3cevtModuleSwitchType 800 } -- Wireless Lan Control Board with 2-port 1000BASE-T/1000BASE-X Combo Interface

hh3cevtModuleSw-LS8M1WCMA                   OBJECT IDENTIFIER ::= { hh3cevtModuleSwitchType 801 } -- Wireless Lan Service Board

hh3cevtModuleSw-EWPX1G24XA0                 OBJECT IDENTIFIER ::= { hh3cevtModuleSwitchType 802 } -- 24-Port 1000BASE-T Gigabit Ethernet Interface(RJ45) and 4-port 1000BASE-T/1000BASE-X Combo Interface and 2-port 10GBASE Interface Line Card

hh3cevtModuleSw-LSQ1WCMB0                   OBJECT IDENTIFIER ::= { hh3cevtModuleSwitchType 803 } -- 1 Port 10GBASE Interface Board

hh3cevtModuleSw-LSB1WCM2A0                  OBJECT IDENTIFIER ::= { hh3cevtModuleSwitchType 804 } -- Wireless Controller Module Board

hh3cevtModuleSw-EWPX1WCMB0                  OBJECT IDENTIFIER ::= { hh3cevtModuleSwitchType 805 } -- 1 Port 10GBASE Interface Board

hh3cevtModuleSw-EWPX1G24XC0                 OBJECT IDENTIFIER ::= { hh3cevtModuleSwitchType 806 } -- 24-Port 1000BASE-T Gigabit Ethernet Interface(RJ45) and 4-port 1000BASE-T/1000BASE-X Combo Interface Line Card

hh3cevtModuleSw-EWPX1WCMC0                  OBJECT IDENTIFIER ::= { hh3cevtModuleSwitchType 807 } -- 1-Port 1000BASE-T Gigabit Ethernet of wireless Lan Service Board

hh3cevtModuleSw-EWPX1FWA0                   OBJECT IDENTIFIER ::= { hh3cevtModuleSwitchType 808 } -- Firewall Service Board

hh3cevtModuleSw-EWPX1G10XC0                 OBJECT IDENTIFIER ::= { hh3cevtModuleSwitchType 809 } -- 8-Port 1000BASE-T Gigabit Ethernet Interface(RJ45) and 2-port 1000BASE-X SFP Interface Line Card

hh3cevtModuleSw-EWPX1WCM10C0                OBJECT IDENTIFIER ::= { hh3cevtModuleSwitchType 810 } -- 1-Port 1000BASE-T Gigabit Ethernet of wireless Lan Service Board

hh3cevtModuleSw-LSR1WCM2A1                  OBJECT IDENTIFIER ::= { hh3cevtModuleSwitchType 811 } -- 1-Port 1000BASE-T Gigabit Ethernet of wireless Lan Service Board


-- Here define submodule for routers
hh3cevtSubModuleRouter       OBJECT IDENTIFIER ::= { hh3cevtModule 5 }


-- Here define submodule for switches
hh3cevtSubModuleSwitch       OBJECT IDENTIFIER ::= { hh3cevtModule 6 }

--
-- hh3cevtPort section:
--

hh3cevtPort          OBJECT IDENTIFIER ::= { hh3cEntityVendortypeObjects 10 }
hh3cevtPortUnknownPorts      OBJECT IDENTIFIER ::= { hh3cevtPort 1 }
hh3cevtPortCommonPorts       OBJECT IDENTIFIER ::= { hh3cevtPort 2 }
hh3cevtPortRouterType        OBJECT IDENTIFIER ::= { hh3cevtPort 3 }
hh3cevtPortSwitchType        OBJECT IDENTIFIER ::= { hh3cevtPort 4 }


-- Below are ports used to router
hh3cevtPortRt-Async          OBJECT IDENTIFIER ::= { hh3cevtPortRouterType 1 }    -- Async interface

hh3cevtPortRt-Analogmodem    OBJECT IDENTIFIER ::= { hh3cevtPortRouterType 2 }    -- Analog modem interface

hh3cevtPortRt-Atm            OBJECT IDENTIFIER ::= { hh3cevtPortRouterType 3 }    --

hh3cevtPortRt-AtmAdsl        OBJECT IDENTIFIER ::= { hh3cevtPortRouterType 4 }    --

hh3cevtPortRt-AtmShdsl       OBJECT IDENTIFIER ::= { hh3cevtPortRouterType 5 }    --

hh3cevtPortRt-AtmE1          OBJECT IDENTIFIER ::= { hh3cevtPortRouterType 6 }    --

hh3cevtPortRt-AtmT1          OBJECT IDENTIFIER ::= { hh3cevtPortRouterType 7 }    --

hh3cevtPortRt-AtmE3          OBJECT IDENTIFIER ::= { hh3cevtPortRouterType 8 }    --

hh3cevtPortRt-AtmT3          OBJECT IDENTIFIER ::= { hh3cevtPortRouterType 9 }    --

hh3cevtPortRt-Atm622M        OBJECT IDENTIFIER ::= { hh3cevtPortRouterType 10 }   --

hh3cevtPortRt-AtmImaE1       OBJECT IDENTIFIER ::= { hh3cevtPortRouterType 11 }   --

hh3cevtPortRt-AtmImaT1       OBJECT IDENTIFIER ::= { hh3cevtPortRouterType 12 }   --

hh3cevtPortRt-Atm25M         OBJECT IDENTIFIER ::= { hh3cevtPortRouterType 13 }   --

hh3cevtPortRt-Bri            OBJECT IDENTIFIER ::= { hh3cevtPortRouterType 14 }   --

hh3cevtPortRt-Console        OBJECT IDENTIFIER ::= { hh3cevtPortRouterType 15 }   --

hh3cevtPortRt-E1             OBJECT IDENTIFIER ::= { hh3cevtPortRouterType 16 }   --

hh3cevtPortRt-E3             OBJECT IDENTIFIER ::= { hh3cevtPortRouterType 17 }   --

hh3cevtPortRt-T1             OBJECT IDENTIFIER ::= { hh3cevtPortRouterType 18 }   --

hh3cevtPortRt-T3             OBJECT IDENTIFIER ::= { hh3cevtPortRouterType 19 }   --

hh3cevtPortRt-Cpos           OBJECT IDENTIFIER ::= { hh3cevtPortRouterType 20 }   --

hh3cevtPortRt-Ethernet       OBJECT IDENTIFIER ::= { hh3cevtPortRouterType 21 }   --

hh3cevtPortRt-Serial         OBJECT IDENTIFIER ::= { hh3cevtPortRouterType 22 }   --

hh3cevtPortRt-E1f            OBJECT IDENTIFIER ::= { hh3cevtPortRouterType 23 }   --

hh3cevtPortRt-T1f            OBJECT IDENTIFIER ::= { hh3cevtPortRouterType 24 }   --

hh3cevtPortRt-Pos            OBJECT IDENTIFIER ::= { hh3cevtPortRouterType 25 }   --

hh3cevtPortRt-Ge             OBJECT IDENTIFIER ::= { hh3cevtPortRouterType 26 }   --

hh3cevtPortRt-Aux            OBJECT IDENTIFIER ::= { hh3cevtPortRouterType 27 }   --

--hh3cevtPortRt-Null         OBJECT IDENTIFIER ::= { hh3cevtPortRouterType 28 }   reserved

--hh3cevtPortRt-Max          OBJECT IDENTIFIER ::= { hh3cevtPortRouterType 29 }   reserved

hh3cevtPortRt-VG-Fxs         OBJECT IDENTIFIER ::= { hh3cevtPortRouterType 30 }   --

hh3cevtPortRt-VG-Fxo         OBJECT IDENTIFIER ::= { hh3cevtPortRouterType 31 }   --

hh3cevtPortRt-VG-E1vi        OBJECT IDENTIFIER ::= { hh3cevtPortRouterType 32 }   --

hh3cevtPortRt-VG-T1vi        OBJECT IDENTIFIER ::= { hh3cevtPortRouterType 33 }   --

hh3cevtPortRt-Usb            OBJECT IDENTIFIER ::= { hh3cevtPortRouterType 34 }   --

hh3cevtPortRt-Ndec           OBJECT IDENTIFIER ::= { hh3cevtPortRouterType 35 }   -- NDEC port, Encrypt card version 1.0

hh3cevtPortRt-Cavium         OBJECT IDENTIFIER ::= { hh3cevtPortRouterType 36 }   -- NDEC port, Encrypt card version 2.0

hh3cevtPortRt-Fcm            OBJECT IDENTIFIER ::= { hh3cevtPortRouterType 37 }   -- POS/Fast connect module port

hh3cevtPortRt-E1vi           OBJECT IDENTIFIER ::= { hh3cevtPortRouterType 38 }   -- E1VI port

hh3cevtPortRt-T1vi           OBJECT IDENTIFIER ::= { hh3cevtPortRouterType 39 }   -- T1VI port

hh3cevtPortRt-Vi             OBJECT IDENTIFIER ::= { hh3cevtPortRouterType 40 }   -- Voice port

hh3cevtPortRt-Adls2Plus      OBJECT IDENTIFIER ::= { hh3cevtPortRouterType 41 }   -- ADSL2Plus port

hh3cevtPortRt-RADIO-AG       OBJECT IDENTIFIER ::= { hh3cevtPortRouterType 42 }   -- 802.11ag Radio port

hh3cevtPortRt-1exp           OBJECT IDENTIFIER ::= { hh3cevtPortRouterType 43 }   -- 10GBASE-R/W Ethernet port

hh3cevtPortRt-G-SHDSL-BIS    OBJECT IDENTIFIER ::= { hh3cevtPortRouterType 44 }   -- 4 wire G.SHDSL.BIS interface

hh3cevtPortRt-ONU-1000BASE-BX-SFF-SC    OBJECT IDENTIFIER ::= { hh3cevtPortRouterType 45 }   -- 1000 BASE-BX SFF SC ONU Interface

hh3cevtPortRt-CELLULAR       OBJECT IDENTIFIER ::= { hh3cevtPortRouterType 46 }   -- 3G Wireless WAN Interface

-- Below are ports used to switches
--hh3cevtPortSw-Unknown              OBJECT IDENTIFIER ::= { hh3cevtPortSwitchType 0 }

hh3cevtPortSw-10or100M               OBJECT IDENTIFIER ::= { hh3cevtPortSwitchType 1 }    --

hh3cevtPortSw-1000BaseLxSm           OBJECT IDENTIFIER ::= { hh3cevtPortSwitchType 2 }    --

hh3cevtPortSw-1000BaseSxMm           OBJECT IDENTIFIER ::= { hh3cevtPortSwitchType 3 }    --

hh3cevtPortSw-1000BaseTx             OBJECT IDENTIFIER ::= { hh3cevtPortSwitchType 4 }    --

hh3cevtPortSw-100MSinglemodeFx       OBJECT IDENTIFIER ::= { hh3cevtPortSwitchType 5 }    --

hh3cevtPortSw-100MMultimodeFx        OBJECT IDENTIFIER ::= { hh3cevtPortSwitchType 6 }    --

hh3cevtPortSw-100M100BaseTx          OBJECT IDENTIFIER ::= { hh3cevtPortSwitchType 7 }    --

hh3cevtPortSw-100MHub                OBJECT IDENTIFIER ::= { hh3cevtPortSwitchType 8 }    --

hh3cevtPortSw-Vdsl                   OBJECT IDENTIFIER ::= { hh3cevtPortSwitchType 9 }    --

hh3cevtPortSw-Stack                  OBJECT IDENTIFIER ::= { hh3cevtPortSwitchType 10 }   --

hh3cevtPortSw-1000BaseZenithFx       OBJECT IDENTIFIER ::= { hh3cevtPortSwitchType 11 }   --

hh3cevtPortSw-1000BaseLongFx         OBJECT IDENTIFIER ::= { hh3cevtPortSwitchType 12 }   --

hh3cevtPortSw-Adsl                   OBJECT IDENTIFIER ::= { hh3cevtPortSwitchType 13 }   --

hh3cevtPortSw-10or100MDb             OBJECT IDENTIFIER ::= { hh3cevtPortSwitchType 14 }   --

hh3cevtPortSw-10GBaseLrSm            OBJECT IDENTIFIER ::= { hh3cevtPortSwitchType 15 }   --

hh3cevtPortSw-10GBaseLx4Mm           OBJECT IDENTIFIER ::= { hh3cevtPortSwitchType 16 }   --

hh3cevtPortSw-10GBaseLx4Sm           OBJECT IDENTIFIER ::= { hh3cevtPortSwitchType 17 }   --

hh3cevtPortSw-100MLongFx             OBJECT IDENTIFIER ::= { hh3cevtPortSwitchType 18 }   --

hh3cevtPortSw-1000BaseCx             OBJECT IDENTIFIER ::= { hh3cevtPortSwitchType 19 }   --

hh3cevtPortSw-1000BaseZenithFxLc     OBJECT IDENTIFIER ::= { hh3cevtPortSwitchType 20 }   --

hh3cevtPortSw-1000BaseLongFxLc       OBJECT IDENTIFIER ::= { hh3cevtPortSwitchType 21 }   --

hh3cevtPortSw-100MSmFxSc             OBJECT IDENTIFIER ::= { hh3cevtPortSwitchType 22 }   --

hh3cevtPortSw-100MMmFxSc             OBJECT IDENTIFIER ::= { hh3cevtPortSwitchType 23 }   --

hh3cevtPortSw-100MSmFxLc             OBJECT IDENTIFIER ::= { hh3cevtPortSwitchType 24 }   --

hh3cevtPortSw-100MMmFxLc             OBJECT IDENTIFIER ::= { hh3cevtPortSwitchType 25 }   --

hh3cevtPortSw-GbicNoConnector        OBJECT IDENTIFIER ::= { hh3cevtPortSwitchType 26 }   --

hh3cevtPortSw-Gbic1000BaseT          OBJECT IDENTIFIER ::= { hh3cevtPortSwitchType 27 }   --

hh3cevtPortSw-Gbic1000BaseLx         OBJECT IDENTIFIER ::= { hh3cevtPortSwitchType 28 }   --

hh3cevtPortSw-Gbic1000BaseSx         OBJECT IDENTIFIER ::= { hh3cevtPortSwitchType 29 }   --

hh3cevtPortSw-Gbic1000BaseZx         OBJECT IDENTIFIER ::= { hh3cevtPortSwitchType 30 }   --

hh3cevtPortSw-ComboNoConnector       OBJECT IDENTIFIER ::= { hh3cevtPortSwitchType 31 }   --

hh3cevtPortSw-Combo1000BaseLx        OBJECT IDENTIFIER ::= { hh3cevtPortSwitchType 32 }   --

hh3cevtPortSw-Combo1000BaseLxFiber   OBJECT IDENTIFIER ::= { hh3cevtPortSwitchType 33 }   --

hh3cevtPortSw-Combo1000BaseLxCopper  OBJECT IDENTIFIER ::= { hh3cevtPortSwitchType 34 }   --

hh3cevtPortSw-Combo1000BaseSx        OBJECT IDENTIFIER ::= { hh3cevtPortSwitchType 35 }   --

hh3cevtPortSw-Combo1000BaseSxFiber   OBJECT IDENTIFIER ::= { hh3cevtPortSwitchType 36 }   --

hh3cevtPortSw-Combo1000BaseSxCopper  OBJECT IDENTIFIER ::= { hh3cevtPortSwitchType 37 }   --

hh3cevtPortSw-Combo1000BaseZx        OBJECT IDENTIFIER ::= { hh3cevtPortSwitchType 38 }   --

hh3cevtPortSw-Combo1000BaseZxFiber   OBJECT IDENTIFIER ::= { hh3cevtPortSwitchType 39 }   --

hh3cevtPortSw-Combo1000BaseZxCopper  OBJECT IDENTIFIER ::= { hh3cevtPortSwitchType 40 }   --

hh3cevtPortSw-155PosSxMmf            OBJECT IDENTIFIER ::= { hh3cevtPortSwitchType 41 }   --

hh3cevtPortSw-155PosLxSmf            OBJECT IDENTIFIER ::= { hh3cevtPortSwitchType 42 }   --

-- added by Garibaldi

hh3cevtPortSw-1000BASE-T             OBJECT IDENTIFIER ::= { hh3cevtPortSwitchType 43 }   -- 1000 Base-T Port

hh3cevtPortSw-1000BASE-SX-SFP        OBJECT IDENTIFIER ::= { hh3cevtPortSwitchType 44 }   -- 1000 Base-SX SFP Port

hh3cevtPortSw-1000BASE-LX-SFP        OBJECT IDENTIFIER ::= { hh3cevtPortSwitchType 45 }   -- 1000 Base-LX SFP Port

hh3cevtPortSw-1000BASE-T-AN-SFP      OBJECT IDENTIFIER ::= { hh3cevtPortSwitchType 46 }   -- 1000 Base-T AN SFP Port

hh3cevtPortSw-10GBASE-LX4-XENPAK     OBJECT IDENTIFIER ::= { hh3cevtPortSwitchType 47 }   -- 10G Base-LX4 XENPAK Port

hh3cevtPortSw-10GBASE-LR-XENPAK      OBJECT IDENTIFIER ::= { hh3cevtPortSwitchType 48 }   -- 10G Base-LR XENPAK Port

hh3cevtPortSw-10GBASE-CX4            OBJECT IDENTIFIER ::= { hh3cevtPortSwitchType 49 }   -- 10G Base-CX4 Port

hh3cevtPortSw-1000BASE-ZX-SFP        OBJECT IDENTIFIER ::= { hh3cevtPortSwitchType 50 }    -- 1000 Base-ZX SFP Port

hh3cevtPortSw-1000BASE-MM-SFP        OBJECT IDENTIFIER ::= { hh3cevtPortSwitchType 51 }    -- 1000 Base-MM SFP Port

hh3cevtPortSw-100BASE-SX-SFP         OBJECT IDENTIFIER ::= { hh3cevtPortSwitchType 52 }    -- 100 Base-SX SFP Port

hh3cevtPortSw-100BASE-LX-SFP         OBJECT IDENTIFIER ::= { hh3cevtPortSwitchType 53 }    -- 100 Base-LX SFP Port

hh3cevtPortSw-100BASE-T-AN-SFP       OBJECT IDENTIFIER ::= { hh3cevtPortSwitchType 54 }    -- 100 Base-T SFP Port

hh3cevtPortSw-100BASE-ZX-SFP         OBJECT IDENTIFIER ::= { hh3cevtPortSwitchType 55 }    -- 100 Base-ZX SFP Port

hh3cevtPortSw-100BASE-MM-SFP         OBJECT IDENTIFIER ::= { hh3cevtPortSwitchType 56 }    -- 100 Base-MM SFP Port

hh3cevtPortSw-SFP-NO-CONNECTOR       OBJECT IDENTIFIER ::= { hh3cevtPortSwitchType 57 }    -- No Connector SFP Port

hh3cevtPortSw-SFP-UNKNOWN-CONNECTOR  OBJECT IDENTIFIER ::= { hh3cevtPortSwitchType 58 }    -- Unknown SFP Port

hh3cevtPortSw-POS-NO-CONNECTOR       OBJECT IDENTIFIER ::= { hh3cevtPortSwitchType 59 }    -- POS no connector

hh3cevtPortSw-10G-BASE-SR            OBJECT IDENTIFIER ::= { hh3cevtPortSwitchType 60 }    -- 10GBASE-SR Fiber Optic Transceivers with SC Connector

hh3cevtPortSw-10G-BASE-ER            OBJECT IDENTIFIER ::= { hh3cevtPortSwitchType 61 }    -- 10GBASE-ER Fiber Optic Transceivers with SC Connector

hh3cevtPortSw-10G-BASE-LX4           OBJECT IDENTIFIER ::= { hh3cevtPortSwitchType 62 }    -- 10GBASE-LX4 Fiber Optic Transceivers with SC Connector

hh3cevtPortSw-10G-BASE-SW            OBJECT IDENTIFIER ::= { hh3cevtPortSwitchType 63 }    -- 10GBASE-SW Fiber Optic Transceivers with SC Connector

hh3cevtPortSw-10G-BASE-LW            OBJECT IDENTIFIER ::= { hh3cevtPortSwitchType 64 }    -- 10GBASE-LW Fiber Optic Transceivers with SC Connector

hh3cevtPortSw-10G-BASE-EW            OBJECT IDENTIFIER ::= { hh3cevtPortSwitchType 65 }    -- 10GBASE-EW Fiber Optic Transceivers with SC Connector

hh3cevtPortSw-10G-LR-SM-LC           OBJECT IDENTIFIER ::= { hh3cevtPortSwitchType 66 }    -- 10GBASE-LR Single Mode Fiber Optic Transceivers with LC Connector

hh3cevtPortSw-10G-SR-MM-LC           OBJECT IDENTIFIER ::= { hh3cevtPortSwitchType 67 }    -- 10GBASE-SR Multi Mode Fiber Optic Transceivers with LC Connector

hh3cevtPortSw-10G-ER-SM-LC           OBJECT IDENTIFIER ::= { hh3cevtPortSwitchType 68 }    -- 10GBASE-ER Single Mode Fiber Optic Transceivers with LC Connector

hh3cevtPortSw-10G-LW-SM-LC           OBJECT IDENTIFIER ::= { hh3cevtPortSwitchType 69 }    -- 10GBASE-LW Single Mode Fiber Optic Transceivers with LC Connector

hh3cevtPortSw-10G-SW-MM-LC           OBJECT IDENTIFIER ::= { hh3cevtPortSwitchType 70 }    -- 10GBASE-SW Multi Mode Fiber Optic Transceivers with LC Connector

hh3cevtPortSw-10G-EW-SM-LC           OBJECT IDENTIFIER ::= { hh3cevtPortSwitchType 71 }    -- 10GBASE-EW Single Mode Fiber Optic Transceivers with LC Connector

hh3cevtPortSw-100BASE-SM-MTRJ        OBJECT IDENTIFIER ::= { hh3cevtPortSwitchType 72 }    -- 100 Base-SM MTRJ Port

hh3cevtPortSw-100BASE-MM-MTRJ        OBJECT IDENTIFIER ::= { hh3cevtPortSwitchType 73 }    -- 100 Base-MM MTRJ Port

hh3cevtPortSw-XFP-NO-CONNECTOR       OBJECT IDENTIFIER ::= { hh3cevtPortSwitchType 74 }    -- XFP without Transceiver

hh3cevtPortSw-XFP-10GBASE-SR         OBJECT IDENTIFIER ::= { hh3cevtPortSwitchType 75 }    -- 10GBASE-SR XFP Transceiver

hh3cevtPortSw-XFP-10GBASE-LR         OBJECT IDENTIFIER ::= { hh3cevtPortSwitchType 76 }    -- 10GBASE-LR XFP Transceiver

hh3cevtPortSw-XFP-10GBASE-ER         OBJECT IDENTIFIER ::= { hh3cevtPortSwitchType 77 }    -- 10GBASE-ER XFP Transceiver

hh3cevtPortSw-XFP-10GBASE-SW         OBJECT IDENTIFIER ::= { hh3cevtPortSwitchType 78 }    -- 10GBASE-SW XFP Transceiver

hh3cevtPortSw-XFP-10GBASE-LW         OBJECT IDENTIFIER ::= { hh3cevtPortSwitchType 79 }    -- 10GBASE-LW XFP Transceiver

hh3cevtPortSw-XFP-10GBASE-EW         OBJECT IDENTIFIER ::= { hh3cevtPortSwitchType 80 }    -- 10GBASE-EW XFP Transceiver

hh3cevtPortSw-XFP-10GBASE-CX4        OBJECT IDENTIFIER ::= { hh3cevtPortSwitchType 81 }    -- 10GBASE-CX4 XFP Transceiver

hh3cevtPortSw-XFP-10GBASE-LX4        OBJECT IDENTIFIER ::= { hh3cevtPortSwitchType 82 }    -- 10GBASE-LX4 XFP Transceiver

hh3cevtPortSw-XFP-UNKNOWN            OBJECT IDENTIFIER ::= { hh3cevtPortSwitchType 83 }    -- Unknown  XFP Transceiver

hh3cevtPortSw-XPK-NOCONNECTOR        OBJECT IDENTIFIER ::= { hh3cevtPortSwitchType 84 }    -- Xenpak without Transceiver

hh3cevtPortSw-XPK-10GBASE-SR         OBJECT IDENTIFIER ::= { hh3cevtPortSwitchType 85 }    -- 10GBASE-SR Xenpak Transceiver

hh3cevtPortSw-XPK-10GBASE-LR         OBJECT IDENTIFIER ::= { hh3cevtPortSwitchType 86 }    -- 10GBASE-LR Xenpak Transceiver

hh3cevtPortSw-XPK-10GBASE-ER         OBJECT IDENTIFIER ::= { hh3cevtPortSwitchType 87 }    -- 10GBASE-ER Xenpak Transceiver

hh3cevtPortSw-XPK-10GBASE-SW         OBJECT IDENTIFIER ::= { hh3cevtPortSwitchType 88 }    -- 10GBASE-SW Xenpak Transceiver

hh3cevtPortSw-XPK-10GBASE-LW         OBJECT IDENTIFIER ::= { hh3cevtPortSwitchType 89 }    -- 10GBASE-LW Xenpak Transceiver

hh3cevtPortSw-XPK-10GBASE-EW         OBJECT IDENTIFIER ::= { hh3cevtPortSwitchType 90 }    -- 10GBASE-EW Xenpak Transceiver

hh3cevtPortSw-XPK-10GBASE-CX4        OBJECT IDENTIFIER ::= { hh3cevtPortSwitchType 91 }    -- 10GBASE-CX4 Xenpak Transceiver

hh3cevtPortSw-XPK-10GBASE-LX4        OBJECT IDENTIFIER ::= { hh3cevtPortSwitchType 92 }    -- 10GBASE-LX4 Xenpak Transceiver

hh3cevtPortSw-XPK-UNKNOWN            OBJECT IDENTIFIER ::= { hh3cevtPortSwitchType 93 }    -- Unknown Xenpak Transceiver

hh3cevtPortSw-POS-OC48-SR-SM-LC      OBJECT IDENTIFIER ::= { hh3cevtPortSwitchType 94 }    -- OC48-SR Single Mode Fiber Optic Transceivers with LC Connector

hh3cevtPortSw-POS-OC48-IR-SM-LC      OBJECT IDENTIFIER ::= { hh3cevtPortSwitchType 95 }    -- OC48-IR Single Mode Fiber Optic Transceivers with LC Connector

hh3cevtPortSw-POS-OC48-LR-SM-LC      OBJECT IDENTIFIER ::= { hh3cevtPortSwitchType 96 }    -- OC48-LR Single Mode Fiber Optic Transceivers with LC Connector

hh3cevtPortSw-10G-BASE-CX4           OBJECT IDENTIFIER ::= { hh3cevtPortSwitchType 97 }    -- 10G BASE-CX4 Electrical Interface

hh3cevtPortSw-OLT-1000BASE-BX-SFF-SC OBJECT IDENTIFIER ::= { hh3cevtPortSwitchType 98 }   -- 1000 BASE-BX SFF SC OLT Interface

hh3cevtPortSw-ONU-1000BASE-BX-SFF-SC OBJECT IDENTIFIER ::= { hh3cevtPortSwitchType 99 }   -- 1000 BASE-BX SFF SC ONU Interface

hh3cevtPortSw-24G-CASCADE            OBJECT IDENTIFIER ::= { hh3cevtPortSwitchType 100 }  -- 24G Cascade port

hh3cevtPortSw-POS-OC3-SR-MM          OBJECT IDENTIFIER ::= { hh3cevtPortSwitchType 101 }  --  STM1/OC3 Short Reach Multi Mode Fiber Optic Transceivers with LC Connector

hh3cevtPortSw-POS-OC3-IR-SM          OBJECT IDENTIFIER ::= { hh3cevtPortSwitchType 102 }  --  STM1/OC3 Intermediate Reach Single Mode Fiber Optic Transceivers with LC Connector

hh3cevtPortSw-POS-OC3-IR-1-SM        OBJECT IDENTIFIER ::= { hh3cevtPortSwitchType 103 }  --  STM1/OC3 Intermediate Reach Single Mode Fiber Optic Transceivers with LC Connector(variation 1)

hh3cevtPortSw-POS-OC3-IR-2-SM        OBJECT IDENTIFIER ::= { hh3cevtPortSwitchType 104 }  --  STM1/OC3 Intermediate Reach Single Mode Fiber Optic Transceivers with LC Connector(variation 2)

hh3cevtPortSw-POS-OC3-LR-SM          OBJECT IDENTIFIER ::= { hh3cevtPortSwitchType 105 }  --  STM1/OC3 Long Reach Single Mode Fiber Optic Transceivers with LC Connector

hh3cevtPortSw-POS-OC3-LR-1-SM        OBJECT IDENTIFIER ::= { hh3cevtPortSwitchType 106 }  --  STM1/OC3 Long Reach Single Mode Fiber Optic Transceivers with LC Connector(variation 1)

hh3cevtPortSw-POS-OC3-LR-2-SM        OBJECT IDENTIFIER ::= { hh3cevtPortSwitchType 107 }  --  STM1/OC3 Long Reach Single Mode Fiber Optic Transceivers with LC Connector(variation 2)

hh3cevtPortSw-POS-OC3-LR-3-SM        OBJECT IDENTIFIER ::= { hh3cevtPortSwitchType 108 }  --  STM1/OC3 Long Reach Single Mode Fiber Optic Transceivers with LC Connector(variation 3)

hh3cevtPortSw-POS-OC12-SR-MM         OBJECT IDENTIFIER ::= { hh3cevtPortSwitchType 109 }  --  STM4/OC12 Short Reach Multi Mode Fiber Optic Transceivers with LC Connector

hh3cevtPortSw-POS-OC12-IR-SM         OBJECT IDENTIFIER ::= { hh3cevtPortSwitchType 110 }  --  STM4/OC12 Intermediate Reach Single Mode Fiber Optic Transceivers with LC Connector

hh3cevtPortSw-POS-OC12-IR-1-SM       OBJECT IDENTIFIER ::= { hh3cevtPortSwitchType 111 }  --  STM4/OC12 Intermediate Reach Single Mode Fiber Optic Transceivers with LC Connector(variation 1)

hh3cevtPortSw-POS-OC12-IR-2-SM       OBJECT IDENTIFIER ::= { hh3cevtPortSwitchType 112 }  --  STM4/OC12 Intermediate Reach Single Mode Fiber Optic Transceivers with LC Connector(variation 2)

hh3cevtPortSw-POS-OC12-LR-SM         OBJECT IDENTIFIER ::= { hh3cevtPortSwitchType 113 }  --  STM4/OC12 Long Reach Single Mode Fiber Optic Transceivers with LC Connector

hh3cevtPortSw-POS-OC12-LR-1-SM       OBJECT IDENTIFIER ::= { hh3cevtPortSwitchType 114 }  --  STM4/OC12 Long Reach Single Mode Fiber Optic Transceivers with LC Connector(variation 1)

hh3cevtPortSw-POS-OC12-LR-2-SM       OBJECT IDENTIFIER ::= { hh3cevtPortSwitchType 115 }  --  STM4/OC12 Long Reach Single Mode Fiber Optic Transceivers with LC Connector(variation 2)

hh3cevtPortSw-POS-OC12-LR-3-SM       OBJECT IDENTIFIER ::= { hh3cevtPortSwitchType 116 }  --  STM4/OC12 Long Reach Single Mode Fiber Optic Transceivers with LC Connector(variation 3)

hh3cevtPortSw-POS-OC48-SR-SM         OBJECT IDENTIFIER ::= { hh3cevtPortSwitchType 117 }  --  STM16/OC48 Short Reach Single Mode Fiber Optic Transceivers with LC Connector

hh3cevtPortSw-POS-OC48-IR-SM         OBJECT IDENTIFIER ::= { hh3cevtPortSwitchType 118 }  --  STM16/OC48 Intermediate Reach Single Mode Fiber Optic Transceivers with LC Connector

hh3cevtPortSw-POS-OC48-IR-1-SM       OBJECT IDENTIFIER ::= { hh3cevtPortSwitchType 119 }  --  STM16/OC48 Intermediate Reach Single Mode Fiber Optic Transceivers with LC Connector(variation 1)

hh3cevtPortSw-POS-OC48-IR-2-SM       OBJECT IDENTIFIER ::= { hh3cevtPortSwitchType 120 }  --  STM16/OC48 Intermediate Reach Single Mode Fiber Optic Transceivers with LC Connector(variation 2)

hh3cevtPortSw-POS-OC48-LR-SM         OBJECT IDENTIFIER ::= { hh3cevtPortSwitchType 121 }  --  STM16/OC48 Long Reach Single Mode Fiber Optic Transceivers with LC Connector

hh3cevtPortSw-POS-OC48-LR-1-SM       OBJECT IDENTIFIER ::= { hh3cevtPortSwitchType 122 }  --  STM16/OC48 Long Reach Single Mode Fiber Optic Transceivers with LC Connector(variation 1)

hh3cevtPortSw-POS-OC48-LR-2-SM       OBJECT IDENTIFIER ::= { hh3cevtPortSwitchType 123 }  --  STM16/OC48 Long Reach Single Mode Fiber Optic Transceivers with LC Connector(variation 2)

hh3cevtPortSw-POS-OC48-LR-3-SM       OBJECT IDENTIFIER ::= { hh3cevtPortSwitchType 124 }  --  STM16/OC48 Long Reach Single Mode Fiber Optic Transceivers with LC Connector(variation 3)

hh3cevtPortSw-POS-I-64-1             OBJECT IDENTIFIER ::= { hh3cevtPortSwitchType 125 }  --  STM64/OC192 Interconnect Fiber Optic Transceivers with LC Connector(wavelength 1310nm G.652 fiber)

hh3cevtPortSw-POS-I-64-2             OBJECT IDENTIFIER ::= { hh3cevtPortSwitchType 126 }  --  STM64/OC192 Interconnect Fiber Optic Transceivers with LC Connector(wavelength 1550nm G.652 fiber)

hh3cevtPortSw-POS-I-64-3             OBJECT IDENTIFIER ::= { hh3cevtPortSwitchType 127 }  --  STM64/OC192 Interconnect Fiber Optic Transceivers with LC Connector(wavelength 1550nm G.653 fiber)

hh3cevtPortSw-POS-I-64-5             OBJECT IDENTIFIER ::= { hh3cevtPortSwitchType 128 }  --  STM64/OC192 Interconnect Fiber Optic Transceivers with LC Connector(wavelength 1550nm G.655 fiber)

hh3cevtPortSw-POS-S-64-1             OBJECT IDENTIFIER ::= { hh3cevtPortSwitchType 129 }  --  STM64/OC192 Short Haul Fiber Optic Transceivers with LC Connector(wavelength 1310nm G.652 fiber)

hh3cevtPortSw-POS-S-64-2             OBJECT IDENTIFIER ::= { hh3cevtPortSwitchType 130 }  --  STM64/OC192 Short Haul Fiber Optic Transceivers with LC Connector(wavelength 1550nm G.652 fiber)

hh3cevtPortSw-POS-S-64-3             OBJECT IDENTIFIER ::= { hh3cevtPortSwitchType 131 }  --  STM64/OC192 Short Haul Fiber Optic Transceivers with LC Connector(wavelength 1550nm G.653 fiber)

hh3cevtPortSw-POS-S-64-5             OBJECT IDENTIFIER ::= { hh3cevtPortSwitchType 132 }  --  STM64/OC192 Short Haul Fiber Optic Transceivers with LC Connector(wavelength 1550nm G.655 fiber)

hh3cevtPortSw-POS-L-64-1             OBJECT IDENTIFIER ::= { hh3cevtPortSwitchType 133 }  --  STM64/OC192 Long Haul Fiber Optic Transceivers with LC Connector(wavelength 1310nm G.652 fiber)

hh3cevtPortSw-POS-L-64-2             OBJECT IDENTIFIER ::= { hh3cevtPortSwitchType 134 }  --  STM64/OC192 Long Haul Fiber Optic Transceivers with LC Connector(wavelength 1550nm G.652 fiber)

hh3cevtPortSw-POS-L-64-3             OBJECT IDENTIFIER ::= { hh3cevtPortSwitchType 135 }  --  STM64/OC192 Long Haul Fiber Optic Transceivers with LC Connector(wavelength 1550nm G.653 fiber)

hh3cevtPortSw-POS-V-64-2             OBJECT IDENTIFIER ::= { hh3cevtPortSwitchType 136 }  --  STM64/OC192 Very Long Haul Fiber Optic Transceivers with LC Connector(wavelength 1550nm G.652 fiber)

hh3cevtPortSw-POS-V-64-3             OBJECT IDENTIFIER ::= { hh3cevtPortSwitchType 137 }  --  STM64/OC192 Very Long Haul Fiber Optic Transceivers with LC Connector(wavelength 1550nm G.653 fiber)

hh3cevtPortSw-100BASE-FX-BIDI        OBJECT IDENTIFIER ::= { hh3cevtPortSwitchType 138 }  --  100 BASE-FX BIDI Port

hh3cevtPortSw-100BASE-BX10-U-SFP     OBJECT IDENTIFIER ::= { hh3cevtPortSwitchType 139 }  --  100 BASE-BX10-U-SFP Port

hh3cevtPortSw-100BASE-BX10-D-SFP     OBJECT IDENTIFIER ::= { hh3cevtPortSwitchType 140 }  --  100 BASE-BX10-D-SFP Port

hh3cevtPortSw-1000BASE-BX10-U-SFP    OBJECT IDENTIFIER ::= { hh3cevtPortSwitchType 141 }  --  1000 BASE-BX10-U-SFP Port

hh3cevtPortSw-1000BASE-BX10-D-SFP    OBJECT IDENTIFIER ::= { hh3cevtPortSwitchType 142 }  --  1000 BASE-BX10-D-SFP Port

hh3cevtPortSw-STK-1000BASE-T         OBJECT IDENTIFIER ::= { hh3cevtPortSwitchType 143 }  --  1000 BASE-T Stack Port

hh3cevtPortSw-RPR-PHYPOS-CONNECTOR     OBJECT IDENTIFIER ::= { hh3cevtPortSwitchType 144 }  --  Resilient Packet Ring POS physical port

hh3cevtPortSw-RPR-PHY10GE-CONNECTOR    OBJECT IDENTIFIER ::= { hh3cevtPortSwitchType 145 }  --  10G Resilient Packet Ring physical port

hh3cevtPortSw-RPR-LOGICPOS-CONNECTOR   OBJECT IDENTIFIER ::= { hh3cevtPortSwitchType 146 }  --  Resilient Packet Ring POS logical port

hh3cevtPortSw-RPR-LOGIC10GE-CONNECTOR  OBJECT IDENTIFIER ::= { hh3cevtPortSwitchType 147 }  --  10G Resilient Packet Ring logical port

hh3cevtPortSw-10GBASE-ZR               OBJECT IDENTIFIER ::= { hh3cevtPortSwitchType 148 }  --  Fiber Optic Transceivers with SC Connector, XENPAK

hh3cevtPortSw-TYPE-ERROR-CONNECTOR     OBJECT IDENTIFIER ::= { hh3cevtPortSwitchType 149 }  --  Error Optic Transceivers type

hh3cevtPortSw-10G-STACK                OBJECT IDENTIFIER ::= { hh3cevtPortSwitchType 150 }  --  10G Stack Port

hh3cevtPortSw-155-ATM-SX-MMF             OBJECT IDENTIFIER ::= { hh3cevtPortSwitchType 151 }  -- ATM OC-3 Multi-mode Short Reach Optical Transceiver

hh3cevtPortSw-155-ATM-LX-SMF             OBJECT IDENTIFIER ::= { hh3cevtPortSwitchType 152 }  -- ATM OC-3 Single Mode Long Reach Optical Transceiver

hh3cevtPortSw-622-ATM-SX-MMF             OBJECT IDENTIFIER ::= { hh3cevtPortSwitchType 153 }  -- ATM OC-12 Multi-mode Short Reach Optical Transceiver

hh3cevtPortSw-622-ATM-LX-SMF             OBJECT IDENTIFIER ::= { hh3cevtPortSwitchType 154 }  -- ATM OC-12 Single Mode Long Reach Optical Transceiver

hh3cevtPortSw-155-ATM-NO-CONNECTOR       OBJECT IDENTIFIER ::= { hh3cevtPortSwitchType 155 }  -- ATM OC-3 No Connector

hh3cevtPortSw-622-ATM-NO-CONNECTOR       OBJECT IDENTIFIER ::= { hh3cevtPortSwitchType 156 }  -- ATM OC-12 No Connector

hh3cevtPortSw-155-CPOS-E1-NO-CONNECTOR   OBJECT IDENTIFIER ::= { hh3cevtPortSwitchType 157 }  -- CPOS(E1) OC-3 No Connector

hh3cevtPortSw-155-CPOS-T1-NO-CONNECTOR   OBJECT IDENTIFIER ::= { hh3cevtPortSwitchType 158 }  -- CPOS(T1) OC-3 No Connector

hh3cevtPortSw-622-CPOS-E1-NO-CONNECTOR   OBJECT IDENTIFIER ::= { hh3cevtPortSwitchType 159 }  -- CPOS(E1) OC-12 No Connector

hh3cevtPortSw-622-CPOS-T1-NO-CONNECTOR   OBJECT IDENTIFIER ::= { hh3cevtPortSwitchType 160 }  -- CPOS(T1) OC-12 No Connector

hh3cevtPortSw-155-CPOS-E1-SX-MMF         OBJECT IDENTIFIER ::= { hh3cevtPortSwitchType 161 }  -- CPOS(E1) OC-3 Multi-mode Short Reach Optical Transceiver

hh3cevtPortSw-155-CPOS-T1-SX-MMF         OBJECT IDENTIFIER ::= { hh3cevtPortSwitchType 162 }  -- CPOS(T1) OC-3 Multi-mode Short Reach Optical Transceiver

hh3cevtPortSw-155-CPOS-E1-LX-SMF         OBJECT IDENTIFIER ::= { hh3cevtPortSwitchType 163 }  -- CPOS(E1) OC-3 Single Mode Long Reach Optical Transceiver

hh3cevtPortSw-155-CPOS-T1-LX-SMF         OBJECT IDENTIFIER ::= { hh3cevtPortSwitchType 164 }  -- CPOS(T1) OC-3 Single Mode Long Reach Optical Transceiver

hh3cevtPortSw-622-CPOS-E1-SX-MMF         OBJECT IDENTIFIER ::= { hh3cevtPortSwitchType 165 }  -- CPOS(E1) OC-12 Multi-mode Short Reach Optical Transceiver

hh3cevtPortSw-622-CPOS-T1-SX-MMF         OBJECT IDENTIFIER ::= { hh3cevtPortSwitchType 166 }  -- CPOS(T1) OC-12 Multi-mode Short Reach Optical Transceiver

hh3cevtPortSw-622-CPOS-E1-LX-SMF         OBJECT IDENTIFIER ::= { hh3cevtPortSwitchType 167 }  -- CPOS(E1) OC-12 Multi-mode Short Reach Optical Transceiver

hh3cevtPortSw-622-CPOS-T1-LX-SMF         OBJECT IDENTIFIER ::= { hh3cevtPortSwitchType 168 }  -- CPOS(T1) OC-12 Single Mode Long Reach Optical Transceiver

hh3cevtPortSw-E1-CONNECTOR               OBJECT IDENTIFIER ::= { hh3cevtPortSwitchType 169 }  -- E1 RJ45 Transceiver

hh3cevtPortSw-T1-CONNECTOR               OBJECT IDENTIFIER ::= { hh3cevtPortSwitchType 170 }  -- T1 RJ45 Transceiver

hh3cevtPortSw-1000BASE-STK-SFP           OBJECT IDENTIFIER ::= { hh3cevtPortSwitchType 171 } -- 1-port 1000 Base-STK SFP Module

hh3cevtPortSw-1000BASE-BIDI-SFP          OBJECT IDENTIFIER ::= { hh3cevtPortSwitchType 172 } -- 1-port 1000 Base-BIDI SFP Module

hh3cevtPortSw-1000BASE-CWDM-SFP          OBJECT IDENTIFIER ::= { hh3cevtPortSwitchType 173 } -- 1-port 1000 Base-CWDM SFP Module

hh3cevtPortSw-100BASE-BIDI-SFP           OBJECT IDENTIFIER ::= { hh3cevtPortSwitchType 174 } -- 1-port 100 Base-BIDI SFP Module

hh3cevtPortSw-OLT-1000BASE-PX-SFP        OBJECT IDENTIFIER ::= { hh3cevtPortSwitchType 175 }  -- 1000BASE-PX SFP OLT Interface

hh3cevtPortSw-OLT-1000BASE-NO-CONNECTOR  OBJECT IDENTIFIER ::= { hh3cevtPortSwitchType 176 }  -- 1000BASE OLT No Connector

hh3cevtPortSw-RPR-PHYGE-CONNECTOR        OBJECT IDENTIFIER ::= { hh3cevtPortSwitchType 177 }  --  Resilient Packet Ring GE physical port

hh3cevtPortSw-RPR-LOGICGE-CONNECTOR      OBJECT IDENTIFIER ::= { hh3cevtPortSwitchType 178 }  --  Resilient Packet Ring GE logical port

hh3cevtPortSw-100M-1550-BIDI             OBJECT IDENTIFIER ::= { hh3cevtPortSwitchType 179 }  -- Single Port 100M Ethernet Bi-direction Optical Interface Module(TX1550nm, RX1310nm, 15km, SC)

hh3cevtPortSw-100M-1310-BIDI             OBJECT IDENTIFIER ::= { hh3cevtPortSwitchType 180 }  -- Single Port 100M Ethernet Bi-direction Optical reverse Interface Module(TX1310nm, RX1550nm, 15km, SC)

hh3cevtPortSw-RPR-PHYOC48-CONNECTOR      OBJECT IDENTIFIER ::= { hh3cevtPortSwitchType 181 }  -- Resilient Packet Ring OC48 physical port

hh3cevtPortSw-RPR-LOGICOC48-CONNECTOR    OBJECT IDENTIFIER ::= { hh3cevtPortSwitchType 182 }  -- Resilient Packet Ring OC48 logical port

hh3cevtPortSw-100-1000-BASE-LX-SMF       OBJECT IDENTIFIER ::= { hh3cevtPortSwitchType 183 }  -- 100BASE-LX/1000BASE-LX Single Mode Fiber Optic Transceivers

hh3cevtPortSw-10G-ZW-SM-LC               OBJECT IDENTIFIER ::= { hh3cevtPortSwitchType 184 }  -- 10GBASE-ZW Single Mode Fiber Optic Transceivers with LC Connector

hh3cevtPortSw-10G-ZR-SM-LC               OBJECT IDENTIFIER ::= { hh3cevtPortSwitchType 185 }  -- 10GBASE-ZR Single Mode Fiber Optic Transceivers with LC Connector

hh3cevtPortSw-XPK-10GBASE-ZR             OBJECT IDENTIFIER ::= { hh3cevtPortSwitchType 186 }  -- 10GBASE-ZR Xenpak Transceiver:LH80,SM1550

hh3cevtPortSw-SGMII-100-BASE-LX-SFP      OBJECT IDENTIFIER ::= { hh3cevtPortSwitchType 187 }  -- SGMII-100-BASE-LX-SFP Transceiver

hh3cevtPortSw-SGMII-100-BASE-FX-SFP      OBJECT IDENTIFIER ::= { hh3cevtPortSwitchType 188 }  -- SGMII-100-BASE-FX-SFP Transceiver

hh3cevtPortSw-WLAN-RADIO                 OBJECT IDENTIFIER ::= { hh3cevtPortSwitchType 189 }  -- WLAN-RADIO Transceiver

hh3cevtPortSw-CABLE                      OBJECT IDENTIFIER ::= { hh3cevtPortSwitchType 190 }  -- Cable Port

hh3cevtPortSw-SFP-PLUS-NO-CONNECTOR      OBJECT IDENTIFIER ::= { hh3cevtPortSwitchType 191 }  -- SFP+ without Transceiver

hh3cevtPortSw-SFP-PLUS-10GBASE-SR        OBJECT IDENTIFIER ::= { hh3cevtPortSwitchType 192 }  -- 10GBASE-SR SFP+ Transceiver

hh3cevtPortSw-SFP-PLUS-10GBASE-LR        OBJECT IDENTIFIER ::= { hh3cevtPortSwitchType 193 }  -- 10GBASE-LR SFP+ Transceiver

hh3cevtPortSw-SFP-PLUS-10GBASE-LRM       OBJECT IDENTIFIER ::= { hh3cevtPortSwitchType 194 }  -- 10GBASE-LRM SFP+ Transceiver

hh3cevtPortSw-SFP-PLUS-10GBASE-Cu        OBJECT IDENTIFIER ::= { hh3cevtPortSwitchType 195 }  -- 10GBASE-Cu SFP+ Transceiver

hh3cevtPortSw-SFP-PLUS-UNKNOWN           OBJECT IDENTIFIER ::= { hh3cevtPortSwitchType 196 }  -- Unknown SFP+ Transceiver

hh3cevtPortSw-SFP-PLUS-STACK-CONNECTOR   OBJECT IDENTIFIER ::= { hh3cevtPortSwitchType 197 }  -- SFP+ STACK Transceiver

--
-- hh3cevtStack section:
--

hh3cevtStack     OBJECT IDENTIFIER ::= { hh3cEntityVendortypeObjects 11 }


END
