-- ************************************************************************
-- Copyright (C) 2007 by H3C TECHNOLOGIES. All rights reserved.
--
-- Description: WAPI extension mib
-- Reference:
-- Version: V1.0
-- History:
--   V1.0 created by zhanglianglun
--     Initial version 2007-5-20
-- ************************************************************************
H3C-WAPI-MIB DEFINITIONS ::= BEGIN

    IMPORTS
        Counter32, Unsigned32, MODULE-IDENTITY, OBJECT-TYPE
            FROM SNMPv2-SMI
        TruthValue
            FROM SNMPv2-TC
        InetAddressType, InetAddress
            FROM INET-ADDRESS-MIB
        h3cCommon
            FROM HUAWEI-3COM-OID-MIB;

    h3cwapiMIB MODULE-IDENTITY
        LAST-UPDATED "200705251757Z"
        ORGANIZATION
            "H3C Technologies Co., Ltd."
        CONTACT-INFO
            "Platform Team H3C Technologies Co., Ltd.
            Hai-Dian District Beijing P.R. China
            http://www.h3c.com
            Zip:100085
            "
        DESCRIPTION
            "H3C-WAPI-MIB is an extension of MIB in WAPI
            protocol. This MIB contains objects to
 	          manage configuration and monitor running state
 	          for WAPI feature."
        ::= { h3cCommon 77 }

    h3cwapiMIBObjects OBJECT IDENTIFIER ::= { h3cwapiMIB 1 }
    h3cwapiMIBStatsObjects OBJECT IDENTIFIER ::= { h3cwapiMIB 2 }

--*************************************************************************
-- * h3cwapiModeEnabled OBJECT
--*************************************************************************
    h3cwapiModeEnabled OBJECT-TYPE
        SYNTAX TruthValue
        MAX-ACCESS read-write
        STATUS current
        DESCRIPTION
            "When this object is set to TRUE, it shall indicate that WAPI
            is enabled. Otherwise, it shall indicate that WAPI is disabled."
        ::= { h3cwapiMIBObjects 1 }

--*************************************************************************
-- * h3cwapiASIPAddress OBJECT
--*************************************************************************
    h3cwapiASIPAddressType OBJECT-TYPE
        SYNTAX  InetAddressType
        MAX-ACCESS read-write
        STATUS current
        DESCRIPTION
               "This object is used to set IP addresses
               type (IPv4 or IPv6) of AS."
        DEFVAL { ipv4 }
        ::= { h3cwapiMIBObjects 2 }

    h3cwapiASIPAddress OBJECT-TYPE
        SYNTAX InetAddress
        MAX-ACCESS read-write
        STATUS current
        DESCRIPTION
            "This object is used to set the IP address of AS."
        ::= { h3cwapiMIBObjects 3 }

-- ************************************************************************
-- * 9 statistics OBJECTS
-- ************************************************************************
    h3cwapiStatsWAISignatureErrors OBJECT-TYPE
        SYNTAX Counter32
        MAX-ACCESS read-only
        STATUS current
        DESCRIPTION
            "This counter increases when the received packet of
            WAI signature is wrong."
        ::= { h3cwapiMIBStatsObjects 1 }

    h3cwapiStatsWAIHMACErrors OBJECT-TYPE
        SYNTAX Counter32
        MAX-ACCESS read-only
        STATUS current
        DESCRIPTION
            "This counter increases when the received packet of
            WAI message authentication key checking error occurs."
        ::= { h3cwapiMIBStatsObjects 2 }

    h3cwapiStatsWAIAuthRsltFailures OBJECT-TYPE
        SYNTAX Counter32
        MAX-ACCESS read-only
        STATUS current
        DESCRIPTION
            "This counter increases when the WAI authentication result is
            unsuccessful."
        ::= { h3cwapiMIBStatsObjects 3 }

    h3cwapiStatsWAIDiscardCounters OBJECT-TYPE
        SYNTAX Counter32
        MAX-ACCESS read-only
        STATUS current
        DESCRIPTION
            "This counter increases when the received packet of WAI are
            discarded."
        ::= { h3cwapiMIBStatsObjects 4 }

    h3cwapiStatsWAITimeoutCounters OBJECT-TYPE
        SYNTAX Counter32
        MAX-ACCESS read-only
        STATUS current
        DESCRIPTION
            "This counter increases when the packet of WAI overtime are
            detected."
        ::= { h3cwapiMIBStatsObjects 5 }

    h3cwapiStatsWAIFormatErrors OBJECT-TYPE
        SYNTAX Counter32
        MAX-ACCESS read-only
        STATUS current
        DESCRIPTION
            "This counter increases when the WAI packet of WAI format
            error is detected."
        ::= { h3cwapiMIBStatsObjects 6 }

    h3cwapiStatsWAICtfHskFailures OBJECT-TYPE
        SYNTAX Counter32
        MAX-ACCESS read-only
        STATUS current
        DESCRIPTION
            "This counter increases when the WAI certificate authenticates
            unsuccessfully."
        ::= { h3cwapiMIBStatsObjects 7 }

    h3cwapiStatsWAIUniHskFailures OBJECT-TYPE
        SYNTAX Counter32
        MAX-ACCESS read-only
        STATUS current
        DESCRIPTION
            "This counter increases when the WAI unicast cipher key
            negotiates unsuccessfully."
        ::= { h3cwapiMIBStatsObjects 8 }

    h3cwapiStatsWAIMulHskFailures OBJECT-TYPE
        SYNTAX Counter32
        MAX-ACCESS read-only
        STATUS current
        DESCRIPTION
            "This counter increases when the WAI multicast cipher key
            announces unsuccessfully."
        ::= { h3cwapiMIBStatsObjects 9 }

END
