-- file automatically created


TELDAT-TRAP-SPF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


spfTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SPF event subsystem."
    REVISION "201401200930Z"
    DESCRIPTION "Initial implementation"
        ::= { telEventTraps 17 }


spfEventsGroup	OBJECT IDENTIFIER	::= { spfTrapsMIB 1 }

spfNotifications	OBJECT IDENTIFIER	::= { spfTrapsMIB 2 }
spfNotificationsPrefix	OBJECT IDENTIFIER	::= { spfNotifications 0 }

spfEventObjects1 OBJECT-IDENTITY
    STATUS current
    DESCRIPTION
        "Event SPF.1
        An OSPF packet has been received. The OSPF length field indicates
        a longer packet than indicated by the IP header length field.
        The packet is discarded."
    ::= { spfEventsGroup 1 }

spf1_IP_source OBJECT-TYPE
    SYNTAX IpAddress
    MAX-ACCESS accessible-for-notify
    STATUS current
    DESCRIPTION
        "Parameter 'IP_source' in event SPF.1"
    ::= { spfEventObjects1 1 }

spf1_OSPF_packet_type OBJECT-TYPE
    SYNTAX Integer32
    MAX-ACCESS accessible-for-notify
    STATUS current
    DESCRIPTION
        "Parameter 'OSPF_packet_type' in event SPF.1"
    ::= { spfEventObjects1 2 }

spfEventObjects2 OBJECT-IDENTITY
    STATUS current
    DESCRIPTION
        "Event SPF.2
        An OSPF packet has been received. The packet has an invalid
        OSPF checksum. The packet is discarded."
    ::= { spfEventsGroup 2 }

spf2_IP_source OBJECT-TYPE
    SYNTAX IpAddress
    MAX-ACCESS accessible-for-notify
    STATUS current
    DESCRIPTION
        "Parameter 'IP_source' in event SPF.2"
    ::= { spfEventObjects2 1 }

spf2_OSPF_packet_type OBJECT-TYPE
    SYNTAX Integer32
    MAX-ACCESS accessible-for-notify
    STATUS current
    DESCRIPTION
        "Parameter 'OSPF_packet_type' in event SPF.2"
    ::= { spfEventObjects2 2 }

spfEventObjects3 OBJECT-IDENTITY
    STATUS current
    DESCRIPTION
        "Event SPF.3
        An OSPF packet has been received. The version field in the OSPF
        header is not equal to 1. The packet is discarded."
    ::= { spfEventsGroup 3 }

spf3_IP_source OBJECT-TYPE
    SYNTAX IpAddress
    MAX-ACCESS accessible-for-notify
    STATUS current
    DESCRIPTION
        "Parameter 'IP_source' in event SPF.3"
    ::= { spfEventObjects3 1 }

spf3_OSPF_packet_type OBJECT-TYPE
    SYNTAX Integer32
    MAX-ACCESS accessible-for-notify
    STATUS current
    DESCRIPTION
        "Parameter 'OSPF_packet_type' in event SPF.3"
    ::= { spfEventObjects3 2 }

spfEventObjects4 OBJECT-IDENTITY
    STATUS current
    DESCRIPTION
        "Event SPF.4
        An OSPF packet has been received. The router ID specified in
        the OSPF header is equal to the router's own ID. Either two interfaces
        are attached to the same network (OK) or there is a conflict
        in the assignment of OSPF router IDs (serious). The packet is discarded."
    ::= { spfEventsGroup 4 }

spf4_IP_source OBJECT-TYPE
    SYNTAX IpAddress
    MAX-ACCESS accessible-for-notify
    STATUS current
    DESCRIPTION
        "Parameter 'IP_source' in event SPF.4"
    ::= { spfEventObjects4 1 }

spf4_OSPF_packet_type OBJECT-TYPE
    SYNTAX Integer32
    MAX-ACCESS accessible-for-notify
    STATUS current
    DESCRIPTION
        "Parameter 'OSPF_packet_type' in event SPF.4"
    ::= { spfEventObjects4 2 }

spfEventObjects5 OBJECT-IDENTITY
    STATUS current
    DESCRIPTION
        "Event SPF.5
        An OSPF packet has been received. Either the IP destination specified
        in the packet is not acceptable, or the parameters in the OSPF header
        (like area ID) do not match the parameters configured for the receiving
        interface. The packet is discarded."
    ::= { spfEventsGroup 5 }

spf5_IP_source OBJECT-TYPE
    SYNTAX IpAddress
    MAX-ACCESS accessible-for-notify
    STATUS current
    DESCRIPTION
        "Parameter 'IP_source' in event SPF.5"
    ::= { spfEventObjects5 1 }

spf5_OSPF_packet_type OBJECT-TYPE
    SYNTAX Integer32
    MAX-ACCESS accessible-for-notify
    STATUS current
    DESCRIPTION
        "Parameter 'OSPF_packet_type' in event SPF.5"
    ::= { spfEventObjects5 2 }

spfEventObjects6 OBJECT-IDENTITY
    STATUS current
    DESCRIPTION
        "Event SPF.6
        An OSPF packet has been received which fails to authenticate.
        The packet is discarded."
    ::= { spfEventsGroup 6 }

spf6_IP_source OBJECT-TYPE
    SYNTAX IpAddress
    MAX-ACCESS accessible-for-notify
    STATUS current
    DESCRIPTION
        "Parameter 'IP_source' in event SPF.6"
    ::= { spfEventObjects6 1 }

spf6_OSPF_packet_type OBJECT-TYPE
    SYNTAX Integer32
    MAX-ACCESS accessible-for-notify
    STATUS current
    DESCRIPTION
        "Parameter 'OSPF_packet_type' in event SPF.6"
    ::= { spfEventObjects6 2 }

spfEventObjects7 OBJECT-IDENTITY
    STATUS current
    DESCRIPTION
        "Event SPF.7
        An OSPF packet has been received. The packet is not a hello packet,
        and does not match any existing OSPF neighbor. The packet is discarded."
    ::= { spfEventsGroup 7 }

spf7_IP_source OBJECT-TYPE
    SYNTAX IpAddress
    MAX-ACCESS accessible-for-notify
    STATUS current
    DESCRIPTION
        "Parameter 'IP_source' in event SPF.7"
    ::= { spfEventObjects7 1 }

spf7_OSPF_packet_type OBJECT-TYPE
    SYNTAX Integer32
    MAX-ACCESS accessible-for-notify
    STATUS current
    DESCRIPTION
        "Parameter 'OSPF_packet_type' in event SPF.7"
    ::= { spfEventObjects7 2 }

spfEventObjects8 OBJECT-IDENTITY
    STATUS current
    DESCRIPTION
        "Event SPF.8
        An OSPF packet has been received. The OSPF packet type field is invalid.
        The packet is discarded."
    ::= { spfEventsGroup 8 }

spf8_IP_source OBJECT-TYPE
    SYNTAX IpAddress
    MAX-ACCESS accessible-for-notify
    STATUS current
    DESCRIPTION
        "Parameter 'IP_source' in event SPF.8"
    ::= { spfEventObjects8 1 }

spf8_OSPF_packet_type OBJECT-TYPE
    SYNTAX Integer32
    MAX-ACCESS accessible-for-notify
    STATUS current
    DESCRIPTION
        "Parameter 'OSPF_packet_type' in event SPF.8"
    ::= { spfEventObjects8 2 }

spfEventObjects9 OBJECT-IDENTITY
    STATUS current
    DESCRIPTION
        "Event SPF.9
        An attempt was made to send a multicast packet on a non-broadcast
        network by expanding the packet on the link level. This expansion
        failed due to insufficient buffer resources."
    ::= { spfEventsGroup 9 }

spf9_IP_destination OBJECT-TYPE
    SYNTAX IpAddress
    MAX-ACCESS accessible-for-notify
    STATUS current
    DESCRIPTION
        "Parameter 'IP_destination' in event SPF.9"
    ::= { spfEventObjects9 1 }

spfEventObjects10 OBJECT-IDENTITY
    STATUS current
    DESCRIPTION
        "Event SPF.10
        An OSPF packet of the specified type was received."
    ::= { spfEventsGroup 10 }

spf10_OSPF_packet_type OBJECT-TYPE
    SYNTAX Integer32
    MAX-ACCESS accessible-for-notify
    STATUS current
    DESCRIPTION
        "Parameter 'OSPF_packet_type' in event SPF.10"
    ::= { spfEventObjects10 1 }

spf10_IP_source OBJECT-TYPE
    SYNTAX IpAddress
    MAX-ACCESS accessible-for-notify
    STATUS current
    DESCRIPTION
        "Parameter 'IP_source' in event SPF.10"
    ::= { spfEventObjects10 2 }

spfEventObjects11 OBJECT-IDENTITY
    STATUS current
    DESCRIPTION
        "Event SPF.11
        Unicast OSPF packet of specified type has been sent to the specified
        IP destination."
    ::= { spfEventsGroup 11 }

spf11_OSPF_packet_type OBJECT-TYPE
    SYNTAX Integer32
    MAX-ACCESS accessible-for-notify
    STATUS current
    DESCRIPTION
        "Parameter 'OSPF_packet_type' in event SPF.11"
    ::= { spfEventObjects11 1 }

spf11_IP_destination OBJECT-TYPE
    SYNTAX IpAddress
    MAX-ACCESS accessible-for-notify
    STATUS current
    DESCRIPTION
        "Parameter 'IP_destination' in event SPF.11"
    ::= { spfEventObjects11 2 }

spfEventObjects12 OBJECT-IDENTITY
    STATUS current
    DESCRIPTION
        "Event SPF.12
        Multicast OSPF packet of specified type sent out through specified
        interface."
    ::= { spfEventsGroup 12 }

spf12_OSPF_packet_type OBJECT-TYPE
    SYNTAX Integer32
    MAX-ACCESS accessible-for-notify
    STATUS current
    DESCRIPTION
        "Parameter 'OSPF_packet_type' in event SPF.12"
    ::= { spfEventObjects12 1 }

spf12_IP_destination OBJECT-TYPE
    SYNTAX IpAddress
    MAX-ACCESS accessible-for-notify
    STATUS current
    DESCRIPTION
        "Parameter 'IP_destination' in event SPF.12"
    ::= { spfEventObjects12 2 }

spf12_interface OBJECT-TYPE
    SYNTAX DisplayString
    MAX-ACCESS accessible-for-notify
    STATUS current
    DESCRIPTION
        "Parameter 'interface' in event SPF.12"
    ::= { spfEventObjects12 3 }

spfEventObjects13 OBJECT-IDENTITY
    STATUS current
    DESCRIPTION
        "Event SPF.13
        Unicast OSPF packet of specified type is being retransmitted."
    ::= { spfEventsGroup 13 }

spf13_OSPF_packet_type OBJECT-TYPE
    SYNTAX Integer32
    MAX-ACCESS accessible-for-notify
    STATUS current
    DESCRIPTION
        "Parameter 'OSPF_packet_type' in event SPF.13"
    ::= { spfEventObjects13 1 }

spf13_IP_source OBJECT-TYPE
    SYNTAX IpAddress
    MAX-ACCESS accessible-for-notify
    STATUS current
    DESCRIPTION
        "Parameter 'IP_source' in event SPF.13"
    ::= { spfEventObjects13 2 }

spf13_IP_destination OBJECT-TYPE
    SYNTAX IpAddress
    MAX-ACCESS accessible-for-notify
    STATUS current
    DESCRIPTION
        "Parameter 'IP_destination' in event SPF.13"
    ::= { spfEventObjects13 3 }

spfEventObjects14 OBJECT-IDENTITY
    STATUS current
    DESCRIPTION
        "Event SPF.14
        The specified event occurred while an interface was in the specified
        state. This occurrence was not covered by the interface
        Finite State Machine. The event is ignored."
    ::= { spfEventsGroup 14 }

spf14_interface_IP_address OBJECT-TYPE
    SYNTAX IpAddress
    MAX-ACCESS accessible-for-notify
    STATUS current
    DESCRIPTION
        "Parameter 'interface_IP_address' in event SPF.14"
    ::= { spfEventObjects14 1 }

spf14_interface_state OBJECT-TYPE
    SYNTAX Integer32
    MAX-ACCESS accessible-for-notify
    STATUS current
    DESCRIPTION
        "Parameter 'interface_state' in event SPF.14"
    ::= { spfEventObjects14 2 }

spf14_interface_event OBJECT-TYPE
    SYNTAX Integer32
    MAX-ACCESS accessible-for-notify
    STATUS current
    DESCRIPTION
        "Parameter 'interface_event' in event SPF.14"
    ::= { spfEventObjects14 3 }

spfEventObjects15 OBJECT-IDENTITY
    STATUS current
    DESCRIPTION
        "Event SPF.15
        The specified event occurred on the specified interface, causing
        its state to transition."
    ::= { spfEventsGroup 15 }

spf15_interface_IP_address OBJECT-TYPE
    SYNTAX IpAddress
    MAX-ACCESS accessible-for-notify
    STATUS current
    DESCRIPTION
        "Parameter 'interface_IP_address' in event SPF.15"
    ::= { spfEventObjects15 1 }

spf15_new_interface_state OBJECT-TYPE
    SYNTAX Integer32
    MAX-ACCESS accessible-for-notify
    STATUS current
    DESCRIPTION
        "Parameter 'new_interface_state' in event SPF.15"
    ::= { spfEventObjects15 2 }

spf15_interface_event OBJECT-TYPE
    SYNTAX Integer32
    MAX-ACCESS accessible-for-notify
    STATUS current
    DESCRIPTION
        "Parameter 'interface_event' in event SPF.15"
    ::= { spfEventObjects15 3 }

spfEventObjects16 OBJECT-IDENTITY
    STATUS current
    DESCRIPTION
        "Event SPF.16
        A hello packet was received that could only match a virtual link,
        yet that link is not configured. The packet is discarded."
    ::= { spfEventsGroup 16 }

spf16_IP_source OBJECT-TYPE
    SYNTAX IpAddress
    MAX-ACCESS accessible-for-notify
    STATUS current
    DESCRIPTION
        "Parameter 'IP_source' in event SPF.16"
    ::= { spfEventObjects16 1 }

spf16_OSPF_packet_type OBJECT-TYPE
    SYNTAX Integer32
    MAX-ACCESS accessible-for-notify
    STATUS current
    DESCRIPTION
        "Parameter 'OSPF_packet_type' in event SPF.16"
    ::= { spfEventObjects16 2 }

spfEventObjects17 OBJECT-IDENTITY
    STATUS current
    DESCRIPTION
        "Event SPF.17
        Hello packet received from neighbor. Neighbor disagrees with
        this router concerning the network mask of their common network.
        The packet is discarded."
    ::= { spfEventsGroup 17 }

spf17_IP_source OBJECT-TYPE
    SYNTAX IpAddress
    MAX-ACCESS accessible-for-notify
    STATUS current
    DESCRIPTION
        "Parameter 'IP_source' in event SPF.17"
    ::= { spfEventObjects17 1 }

spf17_OSPF_packet_type OBJECT-TYPE
    SYNTAX Integer32
    MAX-ACCESS accessible-for-notify
    STATUS current
    DESCRIPTION
        "Parameter 'OSPF_packet_type' in event SPF.17"
    ::= { spfEventObjects17 2 }

spfEventObjects18 OBJECT-IDENTITY
    STATUS current
    DESCRIPTION
        "Event SPF.18
        Hello packet received from neighbor. Neighbor disagrees with this router
        concerning the hello interval to be used on the common network.
        The packet is discarded."
    ::= { spfEventsGroup 18 }

spf18_IP_source OBJECT-TYPE
    SYNTAX IpAddress
    MAX-ACCESS accessible-for-notify
    STATUS current
    DESCRIPTION
        "Parameter 'IP_source' in event SPF.18"
    ::= { spfEventObjects18 1 }

spf18_OSPF_packet_type OBJECT-TYPE
    SYNTAX Integer32
    MAX-ACCESS accessible-for-notify
    STATUS current
    DESCRIPTION
        "Parameter 'OSPF_packet_type' in event SPF.18"
    ::= { spfEventObjects18 2 }

spfEventObjects19 OBJECT-IDENTITY
    STATUS current
    DESCRIPTION
        "Event SPF.19
        Hello packet received from neighbor. Neighbor disagrees with this router
        concerning the dead router interval to be used on the common network.
        The packet is discarded."
    ::= { spfEventsGroup 19 }

spf19_IP_source OBJECT-TYPE
    SYNTAX IpAddress
    MAX-ACCESS accessible-for-notify
    STATUS current
    DESCRIPTION
        "Parameter 'IP_source' in event SPF.19"
    ::= { spfEventObjects19 1 }

spf19_OSPF_packet_type OBJECT-TYPE
    SYNTAX Integer32
    MAX-ACCESS accessible-for-notify
    STATUS current
    DESCRIPTION
        "Parameter 'OSPF_packet_type' in event SPF.19"
    ::= { spfEventObjects19 2 }

spfEventObjects20 OBJECT-IDENTITY
    STATUS current
    DESCRIPTION
        "Event SPF.20
        The specified event has been generated for the specified neighbor,
        which is currently in the specified state. This was not anticipated
        by the neighbor Finite State Machine. The event is ignored."
    ::= { spfEventsGroup 20 }

spf20_neighbor_IP_address OBJECT-TYPE
    SYNTAX IpAddress
    MAX-ACCESS accessible-for-notify
    STATUS current
    DESCRIPTION
        "Parameter 'neighbor_IP_address' in event SPF.20"
    ::= { spfEventObjects20 1 }

spf20_neighbor_state OBJECT-TYPE
    SYNTAX Integer32
    MAX-ACCESS accessible-for-notify
    STATUS current
    DESCRIPTION
        "Parameter 'neighbor_state' in event SPF.20"
    ::= { spfEventObjects20 2 }

spf20_neighbor_event OBJECT-TYPE
    SYNTAX Integer32
    MAX-ACCESS accessible-for-notify
    STATUS current
    DESCRIPTION
        "Parameter 'neighbor_event' in event SPF.20"
    ::= { spfEventObjects20 3 }

spfEventObjects21 OBJECT-IDENTITY
    STATUS current
    DESCRIPTION
        "Event SPF.21
        The specified event has been generated, causing the specified neighbor
        to transfer to a new state."
    ::= { spfEventsGroup 21 }

spf21_neighbor_IP_address OBJECT-TYPE
    SYNTAX IpAddress
    MAX-ACCESS accessible-for-notify
    STATUS current
    DESCRIPTION
        "Parameter 'neighbor_IP_address' in event SPF.21"
    ::= { spfEventObjects21 1 }

spf21_neighbor_state OBJECT-TYPE
    SYNTAX Integer32
    MAX-ACCESS accessible-for-notify
    STATUS current
    DESCRIPTION
        "Parameter 'neighbor_state' in event SPF.21"
    ::= { spfEventObjects21 2 }

spf21_neighbor_event OBJECT-TYPE
    SYNTAX Integer32
    MAX-ACCESS accessible-for-notify
    STATUS current
    DESCRIPTION
        "Parameter 'neighbor_event' in event SPF.21"
    ::= { spfEventObjects21 3 }

spfEventObjects22 OBJECT-IDENTITY
    STATUS current
    DESCRIPTION
        "Event SPF.22
        An attempt was made to retransmit a Database Description packet
        to the specified neighbor, but the packet could not be found.
        Retransmission is aborted."
    ::= { spfEventsGroup 22 }

spf22_neighbor_IP_address OBJECT-TYPE
    SYNTAX IpAddress
    MAX-ACCESS accessible-for-notify
    STATUS current
    DESCRIPTION
        "Parameter 'neighbor_IP_address' in event SPF.22"
    ::= { spfEventObjects22 1 }

spfEventObjects23 OBJECT-IDENTITY
    STATUS current
    DESCRIPTION
        "Event SPF.23
        An attempt was made to send an OSPF packet to the specified destination.
        The specified interface has been aborted due to lack of buffers."
    ::= { spfEventsGroup 23 }

spf23_IP_destination OBJECT-TYPE
    SYNTAX IpAddress
    MAX-ACCESS accessible-for-notify
    STATUS current
    DESCRIPTION
        "Parameter 'IP_destination' in event SPF.23"
    ::= { spfEventObjects23 1 }

spf23_interface_IP_address OBJECT-TYPE
    SYNTAX IpAddress
    MAX-ACCESS accessible-for-notify
    STATUS current
    DESCRIPTION
        "Parameter 'interface_IP_address' in event SPF.23"
    ::= { spfEventObjects23 2 }

spfEventObjects24 OBJECT-IDENTITY
    STATUS current
    DESCRIPTION
        "Event SPF.24
        A link state advertisement has been received from the specified
        neighbor, and the advertisement's length field indicates that the
        entire advertisement is NOT fully contained in the received
        Link State Update Packet. The partial advertisement is discarded."
    ::= { spfEventsGroup 24 }

spf24_neighbor_IP_address OBJECT-TYPE
    SYNTAX IpAddress
    MAX-ACCESS accessible-for-notify
    STATUS current
    DESCRIPTION
        "Parameter 'neighbor_IP_address' in event SPF.24"
    ::= { spfEventObjects24 1 }

spfEventObjects25 OBJECT-IDENTITY
    STATUS current
    DESCRIPTION
        "Event SPF.25
        A link state advertisement has been received. The advertisement is
        identified by its LS type and two-part originating ID (see OSPF
        specification section 12.1). The checksum field contained in the
        advertisement is invalid. The advertisement is ignored."
    ::= { spfEventsGroup 25 }

spf25_neighbor_IP_address OBJECT-TYPE
    SYNTAX IpAddress
    MAX-ACCESS accessible-for-notify
    STATUS current
    DESCRIPTION
        "Parameter 'neighbor_IP_address' in event SPF.25"
    ::= { spfEventObjects25 1 }

spf25_LS_type OBJECT-TYPE
    SYNTAX Integer32
    MAX-ACCESS accessible-for-notify
    STATUS current
    DESCRIPTION
        "Parameter 'LS_type' in event SPF.25"
    ::= { spfEventObjects25 2 }

spf25_advertisement_ID OBJECT-TYPE
    SYNTAX IpAddress
    MAX-ACCESS accessible-for-notify
    STATUS current
    DESCRIPTION
        "Parameter 'advertisement_ID' in event SPF.25"
    ::= { spfEventObjects25 3 }

spfEventObjects26 OBJECT-IDENTITY
    STATUS current
    DESCRIPTION
        "Event SPF.26
        A link state advertisement has been received. The advertisement's
        LS type field is invalid. The advertisement is ignored."
    ::= { spfEventsGroup 26 }

spf26_neighbor_IP_address OBJECT-TYPE
    SYNTAX IpAddress
    MAX-ACCESS accessible-for-notify
    STATUS current
    DESCRIPTION
        "Parameter 'neighbor_IP_address' in event SPF.26"
    ::= { spfEventObjects26 1 }

spf26_LS_type OBJECT-TYPE
    SYNTAX Integer32
    MAX-ACCESS accessible-for-notify
    STATUS current
    DESCRIPTION
        "Parameter 'LS_type' in event SPF.26"
    ::= { spfEventObjects26 2 }

spf26_advertisement_ID OBJECT-TYPE
    SYNTAX IpAddress
    MAX-ACCESS accessible-for-notify
    STATUS current
    DESCRIPTION
        "Parameter 'advertisement_ID' in event SPF.26"
    ::= { spfEventObjects26 3 }

spfEventObjects27 OBJECT-IDENTITY
    STATUS current
    DESCRIPTION
        "Event SPF.27
        A link state advertisement has been received. It was received over
        a virtual link, yet its LS type is equal to AS external link.
        The advertisement is ignored."
    ::= { spfEventsGroup 27 }

spf27_neighbor_IP_address OBJECT-TYPE
    SYNTAX IpAddress
    MAX-ACCESS accessible-for-notify
    STATUS current
    DESCRIPTION
        "Parameter 'neighbor_IP_address' in event SPF.27"
    ::= { spfEventObjects27 1 }

spf27_LS_type OBJECT-TYPE
    SYNTAX Integer32
    MAX-ACCESS accessible-for-notify
    STATUS current
    DESCRIPTION
        "Parameter 'LS_type' in event SPF.27"
    ::= { spfEventObjects27 2 }

spf27_advertisement_ID OBJECT-TYPE
    SYNTAX IpAddress
    MAX-ACCESS accessible-for-notify
    STATUS current
    DESCRIPTION
        "Parameter 'advertisement_ID' in event SPF.27"
    ::= { spfEventObjects27 3 }

spfEventObjects28 OBJECT-IDENTITY
    STATUS current
    DESCRIPTION
        "Event SPF.28
        A link state advertisement has been received. The advertisement is older
        than the current database copy. The received advertisement is ignored."
    ::= { spfEventsGroup 28 }

spf28_neighbor_IP_address OBJECT-TYPE
    SYNTAX IpAddress
    MAX-ACCESS accessible-for-notify
    STATUS current
    DESCRIPTION
        "Parameter 'neighbor_IP_address' in event SPF.28"
    ::= { spfEventObjects28 1 }

spf28_LS_type OBJECT-TYPE
    SYNTAX Integer32
    MAX-ACCESS accessible-for-notify
    STATUS current
    DESCRIPTION
        "Parameter 'LS_type' in event SPF.28"
    ::= { spfEventObjects28 2 }

spf28_advertisement_ID OBJECT-TYPE
    SYNTAX IpAddress
    MAX-ACCESS accessible-for-notify
    STATUS current
    DESCRIPTION
        "Parameter 'advertisement_ID' in event SPF.28"
    ::= { spfEventObjects28 3 }

spfEventObjects29 OBJECT-IDENTITY
    STATUS current
    DESCRIPTION
        "Event SPF.29
        A link state advertisement has been received. The advertisement
        was originated by the router itself, yet is newer than the database
        copy. This indicates that it originated before the router was last
        started. This causes the router to advance the LS sequence number and
        originate a new instantiation of the advertisement."
    ::= { spfEventsGroup 29 }

spf29_neighbor_IP_address OBJECT-TYPE
    SYNTAX IpAddress
    MAX-ACCESS accessible-for-notify
    STATUS current
    DESCRIPTION
        "Parameter 'neighbor_IP_address' in event SPF.29"
    ::= { spfEventObjects29 1 }

spf29_LS_type OBJECT-TYPE
    SYNTAX Integer32
    MAX-ACCESS accessible-for-notify
    STATUS current
    DESCRIPTION
        "Parameter 'LS_type' in event SPF.29"
    ::= { spfEventObjects29 2 }

spf29_advertisement_ID OBJECT-TYPE
    SYNTAX IpAddress
    MAX-ACCESS accessible-for-notify
    STATUS current
    DESCRIPTION
        "Parameter 'advertisement_ID' in event SPF.29"
    ::= { spfEventObjects29 3 }

spfEventObjects30 OBJECT-IDENTITY
    STATUS current
    DESCRIPTION
        "Event SPF.30
        A link state advertisement has been received. The advertisement is
        newer than the current database copy. This advertisement is flooded out
        all other interfaces, and installed in the routing database."
    ::= { spfEventsGroup 30 }

spf30_neighbor_IP_address OBJECT-TYPE
    SYNTAX IpAddress
    MAX-ACCESS accessible-for-notify
    STATUS current
    DESCRIPTION
        "Parameter 'neighbor_IP_address' in event SPF.30"
    ::= { spfEventObjects30 1 }

spf30_LS_type OBJECT-TYPE
    SYNTAX Integer32
    MAX-ACCESS accessible-for-notify
    STATUS current
    DESCRIPTION
        "Parameter 'LS_type' in event SPF.30"
    ::= { spfEventObjects30 2 }

spf30_advertisement_ID OBJECT-TYPE
    SYNTAX IpAddress
    MAX-ACCESS accessible-for-notify
    STATUS current
    DESCRIPTION
        "Parameter 'advertisement_ID' in event SPF.30"
    ::= { spfEventObjects30 3 }

spfEventObjects31 OBJECT-IDENTITY
    STATUS current
    DESCRIPTION
        "Event SPF.31
        An unexpected link state acknowledgement has been received.
        The acknowledgement, however, is for a previous instantiation of the
        link state advertisement."
    ::= { spfEventsGroup 31 }

spf31_neighbor_IP_address OBJECT-TYPE
    SYNTAX IpAddress
    MAX-ACCESS accessible-for-notify
    STATUS current
    DESCRIPTION
        "Parameter 'neighbor_IP_address' in event SPF.31"
    ::= { spfEventObjects31 1 }

spf31_LS_type OBJECT-TYPE
    SYNTAX Integer32
    MAX-ACCESS accessible-for-notify
    STATUS current
    DESCRIPTION
        "Parameter 'LS_type' in event SPF.31"
    ::= { spfEventObjects31 2 }

spf31_advertisement_ID OBJECT-TYPE
    SYNTAX IpAddress
    MAX-ACCESS accessible-for-notify
    STATUS current
    DESCRIPTION
        "Parameter 'advertisement_ID' in event SPF.31"
    ::= { spfEventObjects31 3 }

spfEventObjects32 OBJECT-IDENTITY
    STATUS current
    DESCRIPTION
        "Event SPF.32
        An unexpected link state acknowledgement has been received. The
        acknowledgement however is for the current instantiation of the
        link state advertisement."
    ::= { spfEventsGroup 32 }

spf32_neighbor_IP_address OBJECT-TYPE
    SYNTAX IpAddress
    MAX-ACCESS accessible-for-notify
    STATUS current
    DESCRIPTION
        "Parameter 'neighbor_IP_address' in event SPF.32"
    ::= { spfEventObjects32 1 }

spf32_LS_type OBJECT-TYPE
    SYNTAX Integer32
    MAX-ACCESS accessible-for-notify
    STATUS current
    DESCRIPTION
        "Parameter 'LS_type' in event SPF.32"
    ::= { spfEventObjects32 2 }

spf32_advertisement_ID OBJECT-TYPE
    SYNTAX IpAddress
    MAX-ACCESS accessible-for-notify
    STATUS current
    DESCRIPTION
        "Parameter 'advertisement_ID' in event SPF.32"
    ::= { spfEventObjects32 3 }

spfEventObjects33 OBJECT-IDENTITY
    STATUS current
    DESCRIPTION
        "Event SPF.33
        A Link State Update packet containing retransmitted link state
        advertisements has been unicast to the specified neighbor.
        This probably indicates packet loss during the flooding procedure."
    ::= { spfEventsGroup 33 }

spf33_neighbor_IP_address OBJECT-TYPE
    SYNTAX IpAddress
    MAX-ACCESS accessible-for-notify
    STATUS current
    DESCRIPTION
        "Parameter 'neighbor_IP_address' in event SPF.33"
    ::= { spfEventObjects33 1 }

spfEventObjects34 OBJECT-IDENTITY
    STATUS current
    DESCRIPTION
        "Event SPF.34
        A Link State Acknowledgement packet has been sent directly
        to the specified neighbor. This is in response to duplicate link state
        advertisements received from the neighbor. This probably indicates
        packet loss during the flooding procedure."
    ::= { spfEventsGroup 34 }

spf34_neighbor_IP_address OBJECT-TYPE
    SYNTAX IpAddress
    MAX-ACCESS accessible-for-notify
    STATUS current
    DESCRIPTION
        "Parameter 'neighbor_IP_address' in event SPF.34"
    ::= { spfEventObjects34 1 }

spfEventObjects35 OBJECT-IDENTITY
    STATUS current
    DESCRIPTION
        "Event SPF.35
        A link state advertisement contained in the link state database
        has not been refreshed for 2 hours. The advertisement is deleted from
        the database. This probably indicates that the originator of the
        advertisement is unreachable. See section 14 of the OSPF specification."
    ::= { spfEventsGroup 35 }

spf35_LS_type OBJECT-TYPE
    SYNTAX Integer32
    MAX-ACCESS accessible-for-notify
    STATUS current
    DESCRIPTION
        "Parameter 'LS_type' in event SPF.35"
    ::= { spfEventObjects35 1 }

spf35_advertisement_ID OBJECT-TYPE
    SYNTAX IpAddress
    MAX-ACCESS accessible-for-notify
    STATUS current
    DESCRIPTION
        "Parameter 'advertisement_ID' in event SPF.35"
    ::= { spfEventObjects35 2 }

spfEventObjects36 OBJECT-IDENTITY
    STATUS current
    DESCRIPTION
        "Event SPF.36
        A link state advertisement is being (re)originated by the router.
        This can be due to topological change, or the necessity to refresh."
    ::= { spfEventsGroup 36 }

spf36_LS_type OBJECT-TYPE
    SYNTAX Integer32
    MAX-ACCESS accessible-for-notify
    STATUS current
    DESCRIPTION
        "Parameter 'LS_type' in event SPF.36"
    ::= { spfEventObjects36 1 }

spf36_advertisement_ID OBJECT-TYPE
    SYNTAX IpAddress
    MAX-ACCESS accessible-for-notify
    STATUS current
    DESCRIPTION
        "Parameter 'advertisement_ID' in event SPF.36"
    ::= { spfEventObjects36 2 }

spfEventObjects37 OBJECT-IDENTITY
    STATUS current
    DESCRIPTION
        "Event SPF.37
        The SPF routing table build process has detected a new best route
        to specified destination, having the specified cost."
    ::= { spfEventsGroup 37 }

spf37_dst_type OBJECT-TYPE
    SYNTAX DisplayString
    MAX-ACCESS accessible-for-notify
    STATUS current
    DESCRIPTION
        "Parameter 'dst_type' in event SPF.37"
    ::= { spfEventObjects37 1 }

spf37_destination OBJECT-TYPE
    SYNTAX IpAddress
    MAX-ACCESS accessible-for-notify
    STATUS current
    DESCRIPTION
        "Parameter 'destination' in event SPF.37"
    ::= { spfEventObjects37 2 }

spf37_route_type OBJECT-TYPE
    SYNTAX DisplayString
    MAX-ACCESS accessible-for-notify
    STATUS current
    DESCRIPTION
        "Parameter 'route_type' in event SPF.37"
    ::= { spfEventObjects37 3 }

spf37_route_cost OBJECT-TYPE
    SYNTAX Integer32
    MAX-ACCESS accessible-for-notify
    STATUS current
    DESCRIPTION
        "Parameter 'route_cost' in event SPF.37"
    ::= { spfEventObjects37 4 }

spfEventObjects38 OBJECT-IDENTITY
    STATUS current
    DESCRIPTION
        "Event SPF.38
        An OSPF hello has been sent to the specified IP destination.
        This has been done over a non-broadcast, multi-access interface."
    ::= { spfEventsGroup 38 }

spf38_neighbor_IP_address OBJECT-TYPE
    SYNTAX IpAddress
    MAX-ACCESS accessible-for-notify
    STATUS current
    DESCRIPTION
        "Parameter 'neighbor_IP_address' in event SPF.38"
    ::= { spfEventObjects38 1 }

spfEventObjects39 OBJECT-IDENTITY
    STATUS current
    DESCRIPTION
        "Event SPF.39
        Printed on router startup. Indicates operational status
        of the SPF protocol."
    ::= { spfEventsGroup 39 }

spf39_en_dis OBJECT-TYPE
    SYNTAX DisplayString
    MAX-ACCESS accessible-for-notify
    STATUS current
    DESCRIPTION
        "Parameter 'en/dis' in event SPF.39"
    ::= { spfEventObjects39 1 }

spfEventObjects40 OBJECT-IDENTITY
    STATUS current
    DESCRIPTION
        "Event SPF.40
        Printed on router startup when an OSPF interface address is configured,
        yet this address has not also been configured in the IP console.
        OSPF interface is not installed."
    ::= { spfEventsGroup 40 }

spf40_interface_IP_address OBJECT-TYPE
    SYNTAX IpAddress
    MAX-ACCESS accessible-for-notify
    STATUS current
    DESCRIPTION
        "Parameter 'interface_IP_address' in event SPF.40"
    ::= { spfEventObjects40 1 }

spfEventObjects41 OBJECT-IDENTITY
    STATUS current
    DESCRIPTION
        "Event SPF.41
        Printed on router startup when OSPF non-broadcast parameters have been
        configured for a non-existent OSPF interface. These configuration
        parameters are ignored."
    ::= { spfEventsGroup 41 }

spf41_interface_IP_address OBJECT-TYPE
    SYNTAX IpAddress
    MAX-ACCESS accessible-for-notify
    STATUS current
    DESCRIPTION
        "Parameter 'interface_IP_address' in event SPF.41"
    ::= { spfEventObjects41 1 }

spfEventObjects42 OBJECT-IDENTITY
    STATUS current
    DESCRIPTION
        "Event SPF.42
        The OSPF protocol is disabled, yet an OSPF protocol packet has been
        received. The packet is discarded."
    ::= { spfEventsGroup 42 }

spf42_IP_source OBJECT-TYPE
    SYNTAX IpAddress
    MAX-ACCESS accessible-for-notify
    STATUS current
    DESCRIPTION
        "Parameter 'IP_source' in event SPF.42"
    ::= { spfEventObjects42 1 }

spf42_IP_destination OBJECT-TYPE
    SYNTAX IpAddress
    MAX-ACCESS accessible-for-notify
    STATUS current
    DESCRIPTION
        "Parameter 'IP_destination' in event SPF.42"
    ::= { spfEventObjects42 2 }

spf42_OSPF_packet_type OBJECT-TYPE
    SYNTAX Integer32
    MAX-ACCESS accessible-for-notify
    STATUS current
    DESCRIPTION
        "Parameter 'OSPF_packet_type' in event SPF.42"
    ::= { spfEventObjects42 3 }

spfEventObjects43 OBJECT-IDENTITY
    STATUS current
    DESCRIPTION
        "Event SPF.43
        Unexpected link state acknowledgements have been received from
        the specified neighbor. This probably indicates packet loss during
        the flooding procedure."
    ::= { spfEventsGroup 43 }

spf43_neighbor_IP_address OBJECT-TYPE
    SYNTAX IpAddress
    MAX-ACCESS accessible-for-notify
    STATUS current
    DESCRIPTION
        "Parameter 'neighbor_IP_address' in event SPF.43"
    ::= { spfEventObjects43 1 }

spfEventObjects44 OBJECT-IDENTITY
    STATUS current
    DESCRIPTION
        "Event SPF.44
        A link state advertisement has been received. The advertisement's
        LS age field is invalid. The advertisement is ignored."
    ::= { spfEventsGroup 44 }

spf44_neighbor_IP_address OBJECT-TYPE
    SYNTAX IpAddress
    MAX-ACCESS accessible-for-notify
    STATUS current
    DESCRIPTION
        "Parameter 'neighbor_IP_address' in event SPF.44"
    ::= { spfEventObjects44 1 }

spf44_LS_type OBJECT-TYPE
    SYNTAX Integer32
    MAX-ACCESS accessible-for-notify
    STATUS current
    DESCRIPTION
        "Parameter 'LS_type' in event SPF.44"
    ::= { spfEventObjects44 2 }

spf44_advertisement_ID OBJECT-TYPE
    SYNTAX IpAddress
    MAX-ACCESS accessible-for-notify
    STATUS current
    DESCRIPTION
        "Parameter 'advertisement_ID' in event SPF.44"
    ::= { spfEventObjects44 3 }

spfEventObjects45 OBJECT-IDENTITY
    STATUS current
    DESCRIPTION
        "Event SPF.45
        A virtual link has been configured to have a certain transit area, yet
        that area has not been defined. The virtual link is ignored."
    ::= { spfEventsGroup 45 }

spf45_proposed_transit_area OBJECT-TYPE
    SYNTAX IpAddress
    MAX-ACCESS accessible-for-notify
    STATUS current
    DESCRIPTION
        "Parameter 'proposed_transit_area' in event SPF.45"
    ::= { spfEventObjects45 1 }

spfEventObjects47 OBJECT-IDENTITY
    STATUS current
    DESCRIPTION
        "Event SPF.47
        The destination has been found to be unreachable during
        the routing table build process."
    ::= { spfEventsGroup 47 }

spf47_dst_type OBJECT-TYPE
    SYNTAX DisplayString
    MAX-ACCESS accessible-for-notify
    STATUS current
    DESCRIPTION
        "Parameter 'dst_type' in event SPF.47"
    ::= { spfEventObjects47 1 }

spf47_destination OBJECT-TYPE
    SYNTAX IpAddress
    MAX-ACCESS accessible-for-notify
    STATUS current
    DESCRIPTION
        "Parameter 'destination' in event SPF.47"
    ::= { spfEventObjects47 2 }

spfEventObjects50 OBJECT-IDENTITY
    STATUS current
    DESCRIPTION
        "Event SPF.50
        A link state advertisement has been received. Its age is MaxAge, and
        there is no current instantiation of the advertisement in
        the router's database. The advertisement is acknowledged and then
        discarded without flooding."
    ::= { spfEventsGroup 50 }

spf50_neighbor_IP_address OBJECT-TYPE
    SYNTAX IpAddress
    MAX-ACCESS accessible-for-notify
    STATUS current
    DESCRIPTION
        "Parameter 'neighbor_IP_address' in event SPF.50"
    ::= { spfEventObjects50 1 }

spf50_LS_type OBJECT-TYPE
    SYNTAX Integer32
    MAX-ACCESS accessible-for-notify
    STATUS current
    DESCRIPTION
        "Parameter 'LS_type' in event SPF.50"
    ::= { spfEventObjects50 2 }

spf50_advertisement_ID OBJECT-TYPE
    SYNTAX IpAddress
    MAX-ACCESS accessible-for-notify
    STATUS current
    DESCRIPTION
        "Parameter 'advertisement_ID' in event SPF.50"
    ::= { spfEventObjects50 3 }

spfEventObjects51 OBJECT-IDENTITY
    STATUS current
    DESCRIPTION
        "Event SPF.51
        A link state advertisement has been received. The advertisement
        contains an error, or cannot be added to the database due to
        routing table overflow. In any case, the advertisement is discarded."
    ::= { spfEventsGroup 51 }

spf51_LS_type OBJECT-TYPE
    SYNTAX Integer32
    MAX-ACCESS accessible-for-notify
    STATUS current
    DESCRIPTION
        "Parameter 'LS_type' in event SPF.51"
    ::= { spfEventObjects51 1 }

spf51_advertisement_ID OBJECT-TYPE
    SYNTAX IpAddress
    MAX-ACCESS accessible-for-notify
    STATUS current
    DESCRIPTION
        "Parameter 'advertisement_ID' in event SPF.51"
    ::= { spfEventObjects51 2 }

spfEventObjects52 OBJECT-IDENTITY
    STATUS current
    DESCRIPTION
        "Event SPF.52
        Hello packet received from neighbor. Neighbor disagrees with this router
        concerning the attached area's ability to process AS external link
        advertisements. Hello packet is ignored."
    ::= { spfEventsGroup 52 }

spf52_IP_source OBJECT-TYPE
    SYNTAX IpAddress
    MAX-ACCESS accessible-for-notify
    STATUS current
    DESCRIPTION
        "Parameter 'IP_source' in event SPF.52"
    ::= { spfEventObjects52 1 }

spf52_OSPF_packet_type OBJECT-TYPE
    SYNTAX Integer32
    MAX-ACCESS accessible-for-notify
    STATUS current
    DESCRIPTION
        "Parameter 'OSPF_packet_type' in event SPF.52"
    ::= { spfEventObjects52 2 }

spfEventObjects53 OBJECT-IDENTITY
    STATUS current
    DESCRIPTION
        "Event SPF.53
        A type 5 link state advertisement has been received. The advertisement
        is being flooded through a stub area, and is therefore ignored."
    ::= { spfEventsGroup 53 }

spf53_neighbor_IP_address OBJECT-TYPE
    SYNTAX IpAddress
    MAX-ACCESS accessible-for-notify
    STATUS current
    DESCRIPTION
        "Parameter 'neighbor_IP_address' in event SPF.53"
    ::= { spfEventObjects53 1 }

spf53_LS_type OBJECT-TYPE
    SYNTAX Integer32
    MAX-ACCESS accessible-for-notify
    STATUS current
    DESCRIPTION
        "Parameter 'LS_type' in event SPF.53"
    ::= { spfEventObjects53 2 }

spf53_advertisement_ID OBJECT-TYPE
    SYNTAX IpAddress
    MAX-ACCESS accessible-for-notify
    STATUS current
    DESCRIPTION
        "Parameter 'advertisement_ID' in event SPF.53"
    ::= { spfEventObjects53 3 }

spfEventObjects54 OBJECT-IDENTITY
    STATUS current
    DESCRIPTION
        "Event SPF.54
        As a result of a topology change, the routing table has been
        recalculated, starting with the Dijkstra calculation."
    ::= { spfEventsGroup 54 }

spf54_Number_areas OBJECT-TYPE
    SYNTAX Integer32
    MAX-ACCESS accessible-for-notify
    STATUS current
    DESCRIPTION
        "Parameter 'Number_areas' in event SPF.54"
    ::= { spfEventObjects54 1 }

spfEventObjects55 OBJECT-IDENTITY
    STATUS current
    DESCRIPTION
        "Event SPF.55
        A network links advertisement having one of our addresses as
        Link State ID, but whose Advertising Router is not our Router ID,
        has been received. These advertisements are flushed, as they are
        assumed to be out-of-date."
    ::= { spfEventsGroup 55 }

spf55_LS_type OBJECT-TYPE
    SYNTAX Integer32
    MAX-ACCESS accessible-for-notify
    STATUS current
    DESCRIPTION
        "Parameter 'LS_type' in event SPF.55"
    ::= { spfEventObjects55 1 }

spf55_advertisement_ID OBJECT-TYPE
    SYNTAX IpAddress
    MAX-ACCESS accessible-for-notify
    STATUS current
    DESCRIPTION
        "Parameter 'advertisement_ID' in event SPF.55"
    ::= { spfEventObjects55 2 }

spfEventObjects56 OBJECT-IDENTITY
    STATUS current
    DESCRIPTION
        "Event SPF.56
        A network link is being reparsed, owing to the fact that there are
        multiple network-LSAs in the network with the same Link State ID.
        This indicates that a router has changed OSPF Router IDs, and
        has originated the same router-LSA before and after the change.
        This is a normal, but rare, event."
    ::= { spfEventsGroup 56 }

spf56_Link_State_ID OBJECT-TYPE
    SYNTAX IpAddress
    MAX-ACCESS accessible-for-notify
    STATUS current
    DESCRIPTION
        "Parameter 'Link_State_ID' in event SPF.56"
    ::= { spfEventObjects56 1 }

spfEventObjects57 OBJECT-IDENTITY
    STATUS current
    DESCRIPTION
        "Event SPF.57
        Sending of a unicast OSPF packet of specified type failed
        to the specified IP destination.
        The reason_code is the internal error code for the failure."
    ::= { spfEventsGroup 57 }

spf57_OSPF_packet_type OBJECT-TYPE
    SYNTAX Integer32
    MAX-ACCESS accessible-for-notify
    STATUS current
    DESCRIPTION
        "Parameter 'OSPF_packet_type' in event SPF.57"
    ::= { spfEventObjects57 1 }

spf57_IP_destination OBJECT-TYPE
    SYNTAX IpAddress
    MAX-ACCESS accessible-for-notify
    STATUS current
    DESCRIPTION
        "Parameter 'IP_destination' in event SPF.57"
    ::= { spfEventObjects57 2 }

spf57_reason_code OBJECT-TYPE
    SYNTAX Integer32
    MAX-ACCESS accessible-for-notify
    STATUS current
    DESCRIPTION
        "Parameter 'reason_code' in event SPF.57"
    ::= { spfEventObjects57 3 }

spf57_interface_name OBJECT-TYPE
    SYNTAX DisplayString
    MAX-ACCESS accessible-for-notify
    STATUS current
    DESCRIPTION
        "Parameter 'interface_name' in event SPF.57"
    ::= { spfEventObjects57 4 }

spfEventObjects58 OBJECT-IDENTITY
    STATUS current
    DESCRIPTION
        "Event SPF.58
        Sending of a multicast OSPF packet of specified type failed
        to the specified IP destination.
        The reason_code is the internal error code for the failure."
    ::= { spfEventsGroup 58 }

spf58_OSPF_packet_type OBJECT-TYPE
    SYNTAX Integer32
    MAX-ACCESS accessible-for-notify
    STATUS current
    DESCRIPTION
        "Parameter 'OSPF_packet_type' in event SPF.58"
    ::= { spfEventObjects58 1 }

spf58_IP_destination OBJECT-TYPE
    SYNTAX IpAddress
    MAX-ACCESS accessible-for-notify
    STATUS current
    DESCRIPTION
        "Parameter 'IP_destination' in event SPF.58"
    ::= { spfEventObjects58 2 }

spf58_reason_code OBJECT-TYPE
    SYNTAX Integer32
    MAX-ACCESS accessible-for-notify
    STATUS current
    DESCRIPTION
        "Parameter 'reason_code' in event SPF.58"
    ::= { spfEventObjects58 3 }

spf58_interface_name OBJECT-TYPE
    SYNTAX DisplayString
    MAX-ACCESS accessible-for-notify
    STATUS current
    DESCRIPTION
        "Parameter 'interface_name' in event SPF.58"
    ::= { spfEventObjects58 4 }

spfEventObjects59 OBJECT-IDENTITY
    STATUS current
    DESCRIPTION
        "Event SPF.59
        Retransmission of unicast OSPF packet of specified type failed.
        The reason_code is the internal error code for the failure."
    ::= { spfEventsGroup 59 }

spf59_OSPF_packet_type OBJECT-TYPE
    SYNTAX Integer32
    MAX-ACCESS accessible-for-notify
    STATUS current
    DESCRIPTION
        "Parameter 'OSPF_packet_type' in event SPF.59"
    ::= { spfEventObjects59 1 }

spf59_IP_source OBJECT-TYPE
    SYNTAX IpAddress
    MAX-ACCESS accessible-for-notify
    STATUS current
    DESCRIPTION
        "Parameter 'IP_source' in event SPF.59"
    ::= { spfEventObjects59 2 }

spf59_IP_destination OBJECT-TYPE
    SYNTAX IpAddress
    MAX-ACCESS accessible-for-notify
    STATUS current
    DESCRIPTION
        "Parameter 'IP_destination' in event SPF.59"
    ::= { spfEventObjects59 3 }

spf59_reason_code OBJECT-TYPE
    SYNTAX Integer32
    MAX-ACCESS accessible-for-notify
    STATUS current
    DESCRIPTION
        "Parameter 'reason_code' in event SPF.59"
    ::= { spfEventObjects59 4 }

spf59_interface_name OBJECT-TYPE
    SYNTAX DisplayString
    MAX-ACCESS accessible-for-notify
    STATUS current
    DESCRIPTION
        "Parameter 'interface_name' in event SPF.59"
    ::= { spfEventObjects59 5 }

spfEventObjects60 OBJECT-IDENTITY
    STATUS current
    DESCRIPTION
        "Event SPF.60
        An OSPF hello was discarded when attempting to send it to the specified
        IP destination.
        This was attempted over a non-broadcast, multi-access interface.
        The reason_code is the internal error code for the failure."
    ::= { spfEventsGroup 60 }

spf60_neighbor_IP_address OBJECT-TYPE
    SYNTAX IpAddress
    MAX-ACCESS accessible-for-notify
    STATUS current
    DESCRIPTION
        "Parameter 'neighbor_IP_address' in event SPF.60"
    ::= { spfEventObjects60 1 }

spf60_reason_code OBJECT-TYPE
    SYNTAX Integer32
    MAX-ACCESS accessible-for-notify
    STATUS current
    DESCRIPTION
        "Parameter 'reason_code' in event SPF.60"
    ::= { spfEventObjects60 2 }

spf60_interface_name OBJECT-TYPE
    SYNTAX DisplayString
    MAX-ACCESS accessible-for-notify
    STATUS current
    DESCRIPTION
        "Parameter 'interface_name' in event SPF.60"
    ::= { spfEventObjects60 3 }

spfEventObjects61 OBJECT-IDENTITY
    STATUS current
    DESCRIPTION
        "Event SPF.61
        Printed on router startup when an OSPF interface address is configured,
        but the attached area is not defined. Hence, the OSPF interface
        is not installed."
    ::= { spfEventsGroup 61 }

spf61_proposed_area OBJECT-TYPE
    SYNTAX IpAddress
    MAX-ACCESS accessible-for-notify
    STATUS current
    DESCRIPTION
        "Parameter 'proposed_area' in event SPF.61"
    ::= { spfEventObjects61 1 }

spf61_interface_IP_address OBJECT-TYPE
    SYNTAX IpAddress
    MAX-ACCESS accessible-for-notify
    STATUS current
    DESCRIPTION
        "Parameter 'interface_IP_address' in event SPF.61"
    ::= { spfEventObjects61 2 }

spfEventObjects62 OBJECT-IDENTITY
    STATUS current
    DESCRIPTION
        "Event SPF.62
        Printed on route prevented from install in route table due to
        configured input filter."
    ::= { spfEventsGroup 62 }

spf62_map_entry OBJECT-TYPE
    SYNTAX Integer32
    MAX-ACCESS accessible-for-notify
    STATUS current
    DESCRIPTION
        "Parameter 'map_entry' in event SPF.62"
    ::= { spfEventObjects62 1 }

spf62_network_address OBJECT-TYPE
    SYNTAX IpAddress
    MAX-ACCESS accessible-for-notify
    STATUS current
    DESCRIPTION
        "Parameter 'network_address' in event SPF.62"
    ::= { spfEventObjects62 2 }

spf62_network_mask OBJECT-TYPE
    SYNTAX IpAddress
    MAX-ACCESS accessible-for-notify
    STATUS current
    DESCRIPTION
        "Parameter 'network_mask' in event SPF.62"
    ::= { spfEventObjects62 3 }

spf62_route_type OBJECT-TYPE
    SYNTAX DisplayString
    MAX-ACCESS accessible-for-notify
    STATUS current
    DESCRIPTION
        "Parameter 'route_type' in event SPF.62"
    ::= { spfEventObjects62 4 }

spf62_route_cost OBJECT-TYPE
    SYNTAX Integer32
    MAX-ACCESS accessible-for-notify
    STATUS current
    DESCRIPTION
        "Parameter 'route_cost' in event SPF.62"
    ::= { spfEventObjects62 5 }

spf62_route_tag OBJECT-TYPE
    SYNTAX Integer32
    MAX-ACCESS accessible-for-notify
    STATUS current
    DESCRIPTION
        "Parameter 'route_tag' in event SPF.62"
    ::= { spfEventObjects62 6 }

spfEventObjects63 OBJECT-IDENTITY
    STATUS current
    DESCRIPTION
        "Event SPF.63
        Printed on error detected in link id of a stub network, link id should
        be the network address. It is internaly fixed."
    ::= { spfEventsGroup 63 }

spf63_link-id OBJECT-TYPE
    SYNTAX IpAddress
    MAX-ACCESS accessible-for-notify
    STATUS current
    DESCRIPTION
        "Parameter 'link-id' in event SPF.63"
    ::= { spfEventObjects63 1 }

spf63_mask OBJECT-TYPE
    SYNTAX IpAddress
    MAX-ACCESS accessible-for-notify
    STATUS current
    DESCRIPTION
        "Parameter 'mask' in event SPF.63"
    ::= { spfEventObjects63 2 }

spf63_fixed-val OBJECT-TYPE
    SYNTAX IpAddress
    MAX-ACCESS accessible-for-notify
    STATUS current
    DESCRIPTION
        "Parameter 'fixed-val' in event SPF.63"
    ::= { spfEventObjects63 3 }

spfEventObjects64 OBJECT-IDENTITY
    STATUS current
    DESCRIPTION
        "Event SPF.64
        Check to see that an incoming packet is authentic."
    ::= { spfEventsGroup 64 }

spf64_auth OBJECT-TYPE
    SYNTAX DisplayString
    MAX-ACCESS accessible-for-notify
    STATUS current
    DESCRIPTION
        "Parameter 'auth' in event SPF.64"
    ::= { spfEventObjects64 1 }

spf64_state OBJECT-TYPE
    SYNTAX DisplayString
    MAX-ACCESS accessible-for-notify
    STATUS current
    DESCRIPTION
        "Parameter 'state' in event SPF.64"
    ::= { spfEventObjects64 2 }

spf64_area OBJECT-TYPE
    SYNTAX IpAddress
    MAX-ACCESS accessible-for-notify
    STATUS current
    DESCRIPTION
        "Parameter 'area' in event SPF.64"
    ::= { spfEventObjects64 3 }

spfEventObjects65 OBJECT-IDENTITY
    STATUS current
    DESCRIPTION
        "Event SPF.65
        Set the authentication fields in a packet we are sending."
    ::= { spfEventsGroup 65 }

spf65_auth OBJECT-TYPE
    SYNTAX DisplayString
    MAX-ACCESS accessible-for-notify
    STATUS current
    DESCRIPTION
        "Parameter 'auth' in event SPF.65"
    ::= { spfEventObjects65 1 }

spf65_spi_addr OBJECT-TYPE
    SYNTAX IpAddress
    MAX-ACCESS accessible-for-notify
    STATUS current
    DESCRIPTION
        "Parameter 'spi_addr' in event SPF.65"
    ::= { spfEventObjects65 2 }

spfEventObjects66 OBJECT-IDENTITY
    STATUS current
    DESCRIPTION
        "Event SPF.66
        Allocate a buffer and format the IP and SPF headers"
    ::= { spfEventsGroup 66 }

spf66_ptype OBJECT-TYPE
    SYNTAX Integer32
    MAX-ACCESS accessible-for-notify
    STATUS current
    DESCRIPTION
        "Parameter 'ptype' in event SPF.66"
    ::= { spfEventObjects66 1 }

spf66_IP_destination OBJECT-TYPE
    SYNTAX IpAddress
    MAX-ACCESS accessible-for-notify
    STATUS current
    DESCRIPTION
        "Parameter 'IP_destination' in event SPF.66"
    ::= { spfEventObjects66 2 }

spf66_interface_IP_address OBJECT-TYPE
    SYNTAX IpAddress
    MAX-ACCESS accessible-for-notify
    STATUS current
    DESCRIPTION
        "Parameter 'interface_IP_address' in event SPF.66"
    ::= { spfEventObjects66 3 }

spfEventObjects67 OBJECT-IDENTITY
    STATUS current
    DESCRIPTION
        "Event SPF.67
        Add/delete an interface from an area"
    ::= { spfEventsGroup 67 }

spf67_action OBJECT-TYPE
    SYNTAX DisplayString
    MAX-ACCESS accessible-for-notify
    STATUS current
    DESCRIPTION
        "Parameter 'action' in event SPF.67"
    ::= { spfEventObjects67 1 }

spf67_spi_addr OBJECT-TYPE
    SYNTAX IpAddress
    MAX-ACCESS accessible-for-notify
    STATUS current
    DESCRIPTION
        "Parameter 'spi_addr' in event SPF.67"
    ::= { spfEventObjects67 2 }

spf67_area_id OBJECT-TYPE
    SYNTAX IpAddress
    MAX-ACCESS accessible-for-notify
    STATUS current
    DESCRIPTION
        "Parameter 'area_id' in event SPF.67"
    ::= { spfEventObjects67 3 }

spfEventObjects68 OBJECT-IDENTITY
    STATUS current
    DESCRIPTION
        "Event SPF.68
        Not configured interfaces in an area"
    ::= { spfEventsGroup 68 }

spf68_area_id OBJECT-TYPE
    SYNTAX IpAddress
    MAX-ACCESS accessible-for-notify
    STATUS current
    DESCRIPTION
        "Parameter 'area_id' in event SPF.68"
    ::= { spfEventObjects68 1 }

spfEventObjects69 OBJECT-IDENTITY
    STATUS current
    DESCRIPTION
        "Event SPF.69
        Import external routes (Cand - Candidate, Disc - Discard , Redist - Redistribute)."
    ::= { spfEventsGroup 69 }

spf69_state OBJECT-TYPE
    SYNTAX DisplayString
    MAX-ACCESS accessible-for-notify
    STATUS current
    DESCRIPTION
        "Parameter 'state' in event SPF.69"
    ::= { spfEventObjects69 1 }

spf69_network_address OBJECT-TYPE
    SYNTAX IpAddress
    MAX-ACCESS accessible-for-notify
    STATUS current
    DESCRIPTION
        "Parameter 'network_address' in event SPF.69"
    ::= { spfEventObjects69 2 }

spf69_network_mask OBJECT-TYPE
    SYNTAX IpAddress
    MAX-ACCESS accessible-for-notify
    STATUS current
    DESCRIPTION
        "Parameter 'network_mask' in event SPF.69"
    ::= { spfEventObjects69 3 }

spf69_route_type OBJECT-TYPE
    SYNTAX DisplayString
    MAX-ACCESS accessible-for-notify
    STATUS current
    DESCRIPTION
        "Parameter 'route_type' in event SPF.69"
    ::= { spfEventObjects69 4 }

spf69_route_cost OBJECT-TYPE
    SYNTAX Integer32
    MAX-ACCESS accessible-for-notify
    STATUS current
    DESCRIPTION
        "Parameter 'route_cost' in event SPF.69"
    ::= { spfEventObjects69 5 }

spfEventObjects70 OBJECT-IDENTITY
    STATUS current
    DESCRIPTION
        "Event SPF.70
        Install a link state advertisement into the link state database."
    ::= { spfEventsGroup 70 }

spf70_lsa_type OBJECT-TYPE
    SYNTAX Integer32
    MAX-ACCESS accessible-for-notify
    STATUS current
    DESCRIPTION
        "Parameter 'lsa_type' in event SPF.70"
    ::= { spfEventObjects70 1 }

spf70_area_id OBJECT-TYPE
    SYNTAX IpAddress
    MAX-ACCESS accessible-for-notify
    STATUS current
    DESCRIPTION
        "Parameter 'area_id' in event SPF.70"
    ::= { spfEventObjects70 2 }

spfEventObjects71 OBJECT-IDENTITY
    STATUS current
    DESCRIPTION
        "Event SPF.71
        Install a SPF route."
    ::= { spfEventsGroup 71 }

spf71_network_address OBJECT-TYPE
    SYNTAX IpAddress
    MAX-ACCESS accessible-for-notify
    STATUS current
    DESCRIPTION
        "Parameter 'network_address' in event SPF.71"
    ::= { spfEventObjects71 1 }

spf71_network_mask OBJECT-TYPE
    SYNTAX IpAddress
    MAX-ACCESS accessible-for-notify
    STATUS current
    DESCRIPTION
        "Parameter 'network_mask' in event SPF.71"
    ::= { spfEventObjects71 2 }

spf71_route_type OBJECT-TYPE
    SYNTAX DisplayString
    MAX-ACCESS accessible-for-notify
    STATUS current
    DESCRIPTION
        "Parameter 'route_type' in event SPF.71"
    ::= { spfEventObjects71 3 }

spf71_route_cost OBJECT-TYPE
    SYNTAX Integer32
    MAX-ACCESS accessible-for-notify
    STATUS current
    DESCRIPTION
        "Parameter 'route_cost' in event SPF.71"
    ::= { spfEventObjects71 4 }

spfEventObjects73 OBJECT-IDENTITY
    STATUS current
    DESCRIPTION
        "Event SPF.73
        Form a new instantiation of a link state advertisement."
    ::= { spfEventsGroup 73 }

spf73_message OBJECT-TYPE
    SYNTAX DisplayString
    MAX-ACCESS accessible-for-notify
    STATUS current
    DESCRIPTION
        "Parameter 'message' in event SPF.73"
    ::= { spfEventObjects73 1 }

spf73_network_address OBJECT-TYPE
    SYNTAX IpAddress
    MAX-ACCESS accessible-for-notify
    STATUS current
    DESCRIPTION
        "Parameter 'network_address' in event SPF.73"
    ::= { spfEventObjects73 2 }

spf73_network_mask OBJECT-TYPE
    SYNTAX IpAddress
    MAX-ACCESS accessible-for-notify
    STATUS current
    DESCRIPTION
        "Parameter 'network_mask' in event SPF.73"
    ::= { spfEventObjects73 3 }

spf73_route_type OBJECT-TYPE
    SYNTAX DisplayString
    MAX-ACCESS accessible-for-notify
    STATUS current
    DESCRIPTION
        "Parameter 'route_type' in event SPF.73"
    ::= { spfEventObjects73 4 }

spf73_route_cost OBJECT-TYPE
    SYNTAX Integer32
    MAX-ACCESS accessible-for-notify
    STATUS current
    DESCRIPTION
        "Parameter 'route_cost' in event SPF.73"
    ::= { spfEventObjects73 5 }

spfEventObjects74 OBJECT-IDENTITY
    STATUS current
    DESCRIPTION
        "Event SPF.74
        The specified event has been generated, causing the specified neighbor
        to transfer to a new state."
    ::= { spfEventsGroup 74 }

spf74_neighbor_IP_address OBJECT-TYPE
    SYNTAX IpAddress
    MAX-ACCESS accessible-for-notify
    STATUS current
    DESCRIPTION
        "Parameter 'neighbor_IP_address' in event SPF.74"
    ::= { spfEventObjects74 1 }

spf74_neighbor_state OBJECT-TYPE
    SYNTAX Integer32
    MAX-ACCESS accessible-for-notify
    STATUS current
    DESCRIPTION
        "Parameter 'neighbor_state' in event SPF.74"
    ::= { spfEventObjects74 2 }

spf74_neighbor_event OBJECT-TYPE
    SYNTAX Integer32
    MAX-ACCESS accessible-for-notify
    STATUS current
    DESCRIPTION
        "Parameter 'neighbor_event' in event SPF.74"
    ::= { spfEventObjects74 3 }

spf74_event_descr OBJECT-TYPE
    SYNTAX DisplayString
    MAX-ACCESS accessible-for-notify
    STATUS current
    DESCRIPTION
        "Parameter 'event_descr' in event SPF.74"
    ::= { spfEventObjects74 4 }

spfEventObjects75 OBJECT-IDENTITY
    STATUS current
    DESCRIPTION
        "Event SPF.75
        An OSPF packet of the specified type was received."
    ::= { spfEventsGroup 75 }

spf75_OSPF_packet_type OBJECT-TYPE
    SYNTAX Integer32
    MAX-ACCESS accessible-for-notify
    STATUS current
    DESCRIPTION
        "Parameter 'OSPF_packet_type' in event SPF.75"
    ::= { spfEventObjects75 1 }

spf75_OSPF_packet_type_str OBJECT-TYPE
    SYNTAX DisplayString
    MAX-ACCESS accessible-for-notify
    STATUS current
    DESCRIPTION
        "Parameter 'OSPF_packet_type_str' in event SPF.75"
    ::= { spfEventObjects75 2 }

spf75_IP_source OBJECT-TYPE
    SYNTAX IpAddress
    MAX-ACCESS accessible-for-notify
    STATUS current
    DESCRIPTION
        "Parameter 'IP_source' in event SPF.75"
    ::= { spfEventObjects75 3 }

spfEventObjects76 OBJECT-IDENTITY
    STATUS current
    DESCRIPTION
        "Event SPF.76
        Multicast OSPF packet of specified type sent out through specified
        interface."
    ::= { spfEventsGroup 76 }

spf76_OSPF_packet_type OBJECT-TYPE
    SYNTAX Integer32
    MAX-ACCESS accessible-for-notify
    STATUS current
    DESCRIPTION
        "Parameter 'OSPF_packet_type' in event SPF.76"
    ::= { spfEventObjects76 1 }

spf76_OSPF_packet_type_str OBJECT-TYPE
    SYNTAX DisplayString
    MAX-ACCESS accessible-for-notify
    STATUS current
    DESCRIPTION
        "Parameter 'OSPF_packet_type_str' in event SPF.76"
    ::= { spfEventObjects76 2 }

spf76_IP_destination OBJECT-TYPE
    SYNTAX IpAddress
    MAX-ACCESS accessible-for-notify
    STATUS current
    DESCRIPTION
        "Parameter 'IP_destination' in event SPF.76"
    ::= { spfEventObjects76 3 }

spf76_interface OBJECT-TYPE
    SYNTAX DisplayString
    MAX-ACCESS accessible-for-notify
    STATUS current
    DESCRIPTION
        "Parameter 'interface' in event SPF.76"
    ::= { spfEventObjects76 4 }


spfNotification1 NOTIFICATION-TYPE
    OBJECTS { 
              spf1_IP_source, 
              spf1_OSPF_packet_type 
            }
    STATUS current
    DESCRIPTION
        "Notification of Event SPF.1

        Message: 'Bad length packet, from $1, type $2'

        Parameters list:
              $1: spf1_IP_source
              $2: spf1_OSPF_packet_type

        An OSPF packet has been received. The OSPF length field indicates
        a longer packet than indicated by the IP header length field.
        The packet is discarded."
    ::= { spfNotificationsPrefix 1 }

spfNotification2 NOTIFICATION-TYPE
    OBJECTS { 
              spf2_IP_source, 
              spf2_OSPF_packet_type 
            }
    STATUS current
    DESCRIPTION
        "Notification of Event SPF.2

        Message: 'Bad packet checksum, from $1, type $2'

        Parameters list:
              $1: spf2_IP_source
              $2: spf2_OSPF_packet_type

        An OSPF packet has been received. The packet has an invalid
        OSPF checksum. The packet is discarded."
    ::= { spfNotificationsPrefix 2 }

spfNotification3 NOTIFICATION-TYPE
    OBJECTS { 
              spf3_IP_source, 
              spf3_OSPF_packet_type 
            }
    STATUS current
    DESCRIPTION
        "Notification of Event SPF.3

        Message: 'Bad OSPF version, from $1, type $2'

        Parameters list:
              $1: spf3_IP_source
              $2: spf3_OSPF_packet_type

        An OSPF packet has been received. The version field in the OSPF
        header is not equal to 1. The packet is discarded."
    ::= { spfNotificationsPrefix 3 }

spfNotification4 NOTIFICATION-TYPE
    OBJECTS { 
              spf4_IP_source, 
              spf4_OSPF_packet_type 
            }
    STATUS current
    DESCRIPTION
        "Notification of Event SPF.4

        Message: 'Duplicate Router ID, from $1, type $2'

        Parameters list:
              $1: spf4_IP_source
              $2: spf4_OSPF_packet_type

        An OSPF packet has been received. The router ID specified in
        the OSPF header is equal to the router's own ID. Either two interfaces
        are attached to the same network (OK) or there is a conflict
        in the assignment of OSPF router IDs (serious). The packet is discarded."
    ::= { spfNotificationsPrefix 4 }

spfNotification5 NOTIFICATION-TYPE
    OBJECTS { 
              spf5_IP_source, 
              spf5_OSPF_packet_type 
            }
    STATUS current
    DESCRIPTION
        "Notification of Event SPF.5

        Message: 'No matching SPF-interface for packet from $1, type $2'

        Parameters list:
              $1: spf5_IP_source
              $2: spf5_OSPF_packet_type

        An OSPF packet has been received. Either the IP destination specified
        in the packet is not acceptable, or the parameters in the OSPF header
        (like area ID) do not match the parameters configured for the receiving
        interface. The packet is discarded."
    ::= { spfNotificationsPrefix 5 }

spfNotification6 NOTIFICATION-TYPE
    OBJECTS { 
              spf6_IP_source, 
              spf6_OSPF_packet_type 
            }
    STATUS current
    DESCRIPTION
        "Notification of Event SPF.6

        Message: 'Packet authentication failure, from $1, type $2'

        Parameters list:
              $1: spf6_IP_source
              $2: spf6_OSPF_packet_type

        An OSPF packet has been received which fails to authenticate.
        The packet is discarded."
    ::= { spfNotificationsPrefix 6 }

spfNotification7 NOTIFICATION-TYPE
    OBJECTS { 
              spf7_IP_source, 
              spf7_OSPF_packet_type 
            }
    STATUS current
    DESCRIPTION
        "Notification of Event SPF.7

        Message: 'No matching OSPF neighbor for packet from $1, type $2'

        Parameters list:
              $1: spf7_IP_source
              $2: spf7_OSPF_packet_type

        An OSPF packet has been received. The packet is not a hello packet,
        and does not match any existing OSPF neighbor. The packet is discarded."
    ::= { spfNotificationsPrefix 7 }

spfNotification8 NOTIFICATION-TYPE
    OBJECTS { 
              spf8_IP_source, 
              spf8_OSPF_packet_type 
            }
    STATUS current
    DESCRIPTION
        "Notification of Event SPF.8

        Message: 'Bad packet type received from $1, type $2'

        Parameters list:
              $1: spf8_IP_source
              $2: spf8_OSPF_packet_type

        An OSPF packet has been received. The OSPF packet type field is invalid.
        The packet is discarded."
    ::= { spfNotificationsPrefix 8 }

spfNotification9 NOTIFICATION-TYPE
    OBJECTS { 
              spf9_IP_destination 
            }
    STATUS current
    DESCRIPTION
        "Notification of Event SPF.9

        Message: 'No buffer for multicast packet to $1'

        Parameters list:
              $1: spf9_IP_destination

        An attempt was made to send a multicast packet on a non-broadcast
        network by expanding the packet on the link level. This expansion
        failed due to insufficient buffer resources."
    ::= { spfNotificationsPrefix 9 }

spfNotification10 NOTIFICATION-TYPE
    OBJECTS { 
              spf10_OSPF_packet_type, 
              spf10_IP_source 
            }
    STATUS current
    DESCRIPTION
        "Notification of Event SPF.10

        Message: 'Received packet type $1 from $2'

        Parameters list:
              $1: spf10_OSPF_packet_type
              $2: spf10_IP_source

        An OSPF packet of the specified type was received."
    ::= { spfNotificationsPrefix 10 }

spfNotification11 NOTIFICATION-TYPE
    OBJECTS { 
              spf11_OSPF_packet_type, 
              spf11_IP_destination 
            }
    STATUS current
    DESCRIPTION
        "Notification of Event SPF.11

        Message: 'Sending unicast type $1 dst $2'

        Parameters list:
              $1: spf11_OSPF_packet_type
              $2: spf11_IP_destination

        Unicast OSPF packet of specified type has been sent to the specified
        IP destination."
    ::= { spfNotificationsPrefix 11 }

spfNotification12 NOTIFICATION-TYPE
    OBJECTS { 
              spf12_OSPF_packet_type, 
              spf12_IP_destination,
              spf12_interface 
            }
    STATUS current
    DESCRIPTION
        "Notification of Event SPF.12

        Message: 'Sending multicast, type $1, destination $2 interface $3'

        Parameters list:
              $1: spf12_OSPF_packet_type
              $2: spf12_IP_destination
              $3: spf12_interface

        Multicast OSPF packet of specified type sent out through specified
        interface."
    ::= { spfNotificationsPrefix 12 }

spfNotification13 NOTIFICATION-TYPE
    OBJECTS { 
              spf13_OSPF_packet_type, 
              spf13_IP_source,
              spf13_IP_destination 
            }
    STATUS current
    DESCRIPTION
        "Notification of Event SPF.13

        Message: 'Retransmitting packet, type $1, $2 -> $3'

        Parameters list:
              $1: spf13_OSPF_packet_type
              $2: spf13_IP_source
              $3: spf13_IP_destination

        Unicast OSPF packet of specified type is being retransmitted."
    ::= { spfNotificationsPrefix 13 }

spfNotification14 NOTIFICATION-TYPE
    OBJECTS { 
              spf14_interface_IP_address, 
              spf14_interface_state,
              spf14_interface_event 
            }
    STATUS current
    DESCRIPTION
        "Notification of Event SPF.14

        Message: 'No FSM match, interface $1, state $2, event $3'

        Parameters list:
              $1: spf14_interface_IP_address
              $2: spf14_interface_state
              $3: spf14_interface_event

        The specified event occurred while an interface was in the specified
        state. This occurrence was not covered by the interface
        Finite State Machine. The event is ignored."
    ::= { spfNotificationsPrefix 14 }

spfNotification15 NOTIFICATION-TYPE
    OBJECTS { 
              spf15_interface_IP_address, 
              spf15_new_interface_state,
              spf15_interface_event 
            }
    STATUS current
    DESCRIPTION
        "Notification of Event SPF.15

        Message: 'State change, interface $1, new state $2, event $3'

        Parameters list:
              $1: spf15_interface_IP_address
              $2: spf15_new_interface_state
              $3: spf15_interface_event

        The specified event occurred on the specified interface, causing
        its state to transition."
    ::= { spfNotificationsPrefix 15 }

spfNotification16 NOTIFICATION-TYPE
    OBJECTS { 
              spf16_IP_source, 
              spf16_OSPF_packet_type 
            }
    STATUS current
    DESCRIPTION
        "Notification of Event SPF.16

        Message: 'No match for hello received on virtual link, from $1, type $2'

        Parameters list:
              $1: spf16_IP_source
              $2: spf16_OSPF_packet_type

        A hello packet was received that could only match a virtual link,
        yet that link is not configured. The packet is discarded."
    ::= { spfNotificationsPrefix 16 }

spfNotification17 NOTIFICATION-TYPE
    OBJECTS { 
              spf17_IP_source, 
              spf17_OSPF_packet_type 
            }
    STATUS current
    DESCRIPTION
        "Notification of Event SPF.17

        Message: 'Network mask mismatch in hello from $1, type $2'

        Parameters list:
              $1: spf17_IP_source
              $2: spf17_OSPF_packet_type

        Hello packet received from neighbor. Neighbor disagrees with
        this router concerning the network mask of their common network.
        The packet is discarded."
    ::= { spfNotificationsPrefix 17 }

spfNotification18 NOTIFICATION-TYPE
    OBJECTS { 
              spf18_IP_source, 
              spf18_OSPF_packet_type 
            }
    STATUS current
    DESCRIPTION
        "Notification of Event SPF.18

        Message: 'Hello interval mismatch in hello from $1, type $2'

        Parameters list:
              $1: spf18_IP_source
              $2: spf18_OSPF_packet_type

        Hello packet received from neighbor. Neighbor disagrees with this router
        concerning the hello interval to be used on the common network.
        The packet is discarded."
    ::= { spfNotificationsPrefix 18 }

spfNotification19 NOTIFICATION-TYPE
    OBJECTS { 
              spf19_IP_source, 
              spf19_OSPF_packet_type 
            }
    STATUS current
    DESCRIPTION
        "Notification of Event SPF.19

        Message: 'Dead interval mismatch in hello from $1, type $2'

        Parameters list:
              $1: spf19_IP_source
              $2: spf19_OSPF_packet_type

        Hello packet received from neighbor. Neighbor disagrees with this router
        concerning the dead router interval to be used on the common network.
        The packet is discarded."
    ::= { spfNotificationsPrefix 19 }

spfNotification20 NOTIFICATION-TYPE
    OBJECTS { 
              spf20_neighbor_IP_address, 
              spf20_neighbor_state,
              spf20_neighbor_event 
            }
    STATUS current
    DESCRIPTION
        "Notification of Event SPF.20

        Message: 'No FSM match, neighbor $1, state $2, event $3'

        Parameters list:
              $1: spf20_neighbor_IP_address
              $2: spf20_neighbor_state
              $3: spf20_neighbor_event

        The specified event has been generated for the specified neighbor,
        which is currently in the specified state. This was not anticipated
        by the neighbor Finite State Machine. The event is ignored."
    ::= { spfNotificationsPrefix 20 }

spfNotification21 NOTIFICATION-TYPE
    OBJECTS { 
              spf21_neighbor_IP_address, 
              spf21_neighbor_state,
              spf21_neighbor_event 
            }
    STATUS current
    DESCRIPTION
        "Notification of Event SPF.21

        Message: 'State change, neighbor $1, new state $2, event $3'

        Parameters list:
              $1: spf21_neighbor_IP_address
              $2: spf21_neighbor_state
              $3: spf21_neighbor_event

        The specified event has been generated, causing the specified neighbor
        to transfer to a new state."
    ::= { spfNotificationsPrefix 21 }

spfNotification22 NOTIFICATION-TYPE
    OBJECTS { 
              spf22_neighbor_IP_address 
            }
    STATUS current
    DESCRIPTION
        "Notification of Event SPF.22

        Message: 'Outstanding Database Description packet not avail for neighbor $1'

        Parameters list:
              $1: spf22_neighbor_IP_address

        An attempt was made to retransmit a Database Description packet
        to the specified neighbor, but the packet could not be found.
        Retransmission is aborted."
    ::= { spfNotificationsPrefix 22 }

spfNotification23 NOTIFICATION-TYPE
    OBJECTS { 
              spf23_IP_destination, 
              spf23_interface_IP_address 
            }
    STATUS current
    DESCRIPTION
        "Notification of Event SPF.23

        Message: 'Unable to get packet to send to $1, out interface $2'

        Parameters list:
              $1: spf23_IP_destination
              $2: spf23_interface_IP_address

        An attempt was made to send an OSPF packet to the specified destination.
        The specified interface has been aborted due to lack of buffers."
    ::= { spfNotificationsPrefix 23 }

spfNotification24 NOTIFICATION-TYPE
    OBJECTS { 
              spf24_neighbor_IP_address 
            }
    STATUS current
    DESCRIPTION
        "Notification of Event SPF.24

        Message: 'Bad length Link state advertisement received from $1'

        Parameters list:
              $1: spf24_neighbor_IP_address

        A link state advertisement has been received from the specified
        neighbor, and the advertisement's length field indicates that the
        entire advertisement is NOT fully contained in the received
        Link State Update Packet. The partial advertisement is discarded."
    ::= { spfNotificationsPrefix 24 }

spfNotification25 NOTIFICATION-TYPE
    OBJECTS { 
              spf25_neighbor_IP_address, 
              spf25_LS_type,
              spf25_advertisement_ID,
              spf25_advertisement_ID 
            }
    STATUS current
    DESCRIPTION
        "Notification of Event SPF.25

        Message: 'from $1, LS advertisement checksum fails: LS type $2 id $3 org $4'

        Parameters list:
              $1: spf25_neighbor_IP_address
              $2: spf25_LS_type
              $3: spf25_advertisement_ID
              $4: spf25_advertisement_ID

        A link state advertisement has been received. The advertisement is
        identified by its LS type and two-part originating ID (see OSPF
        specification section 12.1). The checksum field contained in the
        advertisement is invalid. The advertisement is ignored."
    ::= { spfNotificationsPrefix 25 }

spfNotification26 NOTIFICATION-TYPE
    OBJECTS { 
              spf26_neighbor_IP_address, 
              spf26_LS_type,
              spf26_advertisement_ID,
              spf26_advertisement_ID 
            }
    STATUS current
    DESCRIPTION
        "Notification of Event SPF.26

        Message: 'from $1, bad LS type, advertisement: typ $2 id $3 org $4'

        Parameters list:
              $1: spf26_neighbor_IP_address
              $2: spf26_LS_type
              $3: spf26_advertisement_ID
              $4: spf26_advertisement_ID

        A link state advertisement has been received. The advertisement's
        LS type field is invalid. The advertisement is ignored."
    ::= { spfNotificationsPrefix 26 }

spfNotification27 NOTIFICATION-TYPE
    OBJECTS { 
              spf27_neighbor_IP_address, 
              spf27_LS_type,
              spf27_advertisement_ID,
              spf27_advertisement_ID 
            }
    STATUS current
    DESCRIPTION
        "Notification of Event SPF.27

        Message: 'from $1, AS external link adv. on Virtual Link: typ $2 id $3 org $4'

        Parameters list:
              $1: spf27_neighbor_IP_address
              $2: spf27_LS_type
              $3: spf27_advertisement_ID
              $4: spf27_advertisement_ID

        A link state advertisement has been received. It was received over
        a virtual link, yet its LS type is equal to AS external link.
        The advertisement is ignored."
    ::= { spfNotificationsPrefix 27 }

spfNotification28 NOTIFICATION-TYPE
    OBJECTS { 
              spf28_neighbor_IP_address, 
              spf28_LS_type,
              spf28_advertisement_ID,
              spf28_advertisement_ID 
            }
    STATUS current
    DESCRIPTION
        "Notification of Event SPF.28

        Message: 'from $1, old LS advertisement: typ $2 id $3 org $4'

        Parameters list:
              $1: spf28_neighbor_IP_address
              $2: spf28_LS_type
              $3: spf28_advertisement_ID
              $4: spf28_advertisement_ID

        A link state advertisement has been received. The advertisement is older
        than the current database copy. The received advertisement is ignored."
    ::= { spfNotificationsPrefix 28 }

spfNotification29 NOTIFICATION-TYPE
    OBJECTS { 
              spf29_neighbor_IP_address, 
              spf29_LS_type,
              spf29_advertisement_ID,
              spf29_advertisement_ID 
            }
    STATUS current
    DESCRIPTION
        "Notification of Event SPF.29

        Message: 'from $1, self update: typ $2 id $3 org $4'

        Parameters list:
              $1: spf29_neighbor_IP_address
              $2: spf29_LS_type
              $3: spf29_advertisement_ID
              $4: spf29_advertisement_ID

        A link state advertisement has been received. The advertisement
        was originated by the router itself, yet is newer than the database
        copy. This indicates that it originated before the router was last
        started. This causes the router to advance the LS sequence number and
        originate a new instantiation of the advertisement."
    ::= { spfNotificationsPrefix 29 }

spfNotification30 NOTIFICATION-TYPE
    OBJECTS { 
              spf30_neighbor_IP_address, 
              spf30_LS_type,
              spf30_advertisement_ID,
              spf30_advertisement_ID 
            }
    STATUS current
    DESCRIPTION
        "Notification of Event SPF.30

        Message: 'from $1, new LS advertisement: typ $2 id $3 org $4'

        Parameters list:
              $1: spf30_neighbor_IP_address
              $2: spf30_LS_type
              $3: spf30_advertisement_ID
              $4: spf30_advertisement_ID

        A link state advertisement has been received. The advertisement is
        newer than the current database copy. This advertisement is flooded out
        all other interfaces, and installed in the routing database."
    ::= { spfNotificationsPrefix 30 }

spfNotification31 NOTIFICATION-TYPE
    OBJECTS { 
              spf31_neighbor_IP_address, 
              spf31_LS_type,
              spf31_advertisement_ID,
              spf31_advertisement_ID 
            }
    STATUS current
    DESCRIPTION
        "Notification of Event SPF.31

        Message: 'from $1, Old acknowledgement for advertisement: typ $2 id $3 org $4'

        Parameters list:
              $1: spf31_neighbor_IP_address
              $2: spf31_LS_type
              $3: spf31_advertisement_ID
              $4: spf31_advertisement_ID

        An unexpected link state acknowledgement has been received.
        The acknowledgement, however, is for a previous instantiation of the
        link state advertisement."
    ::= { spfNotificationsPrefix 31 }

spfNotification32 NOTIFICATION-TYPE
    OBJECTS { 
              spf32_neighbor_IP_address, 
              spf32_LS_type,
              spf32_advertisement_ID,
              spf32_advertisement_ID 
            }
    STATUS current
    DESCRIPTION
        "Notification of Event SPF.32

        Message: 'Bad acknowledgment from $1 for advertisement: typ $2 id $3 org $4'

        Parameters list:
              $1: spf32_neighbor_IP_address
              $2: spf32_LS_type
              $3: spf32_advertisement_ID
              $4: spf32_advertisement_ID

        An unexpected link state acknowledgement has been received. The
        acknowledgement however is for the current instantiation of the
        link state advertisement."
    ::= { spfNotificationsPrefix 32 }

spfNotification33 NOTIFICATION-TYPE
    OBJECTS { 
              spf33_neighbor_IP_address 
            }
    STATUS current
    DESCRIPTION
        "Notification of Event SPF.33

        Message: 'LS update retransmission to neighbor $1'

        Parameters list:
              $1: spf33_neighbor_IP_address

        A Link State Update packet containing retransmitted link state
        advertisements has been unicast to the specified neighbor.
        This probably indicates packet loss during the flooding procedure."
    ::= { spfNotificationsPrefix 33 }

spfNotification34 NOTIFICATION-TYPE
    OBJECTS { 
              spf34_neighbor_IP_address 
            }
    STATUS current
    DESCRIPTION
        "Notification of Event SPF.34

        Message: 'LS acknowledgement sent directly to neighbor $1'

        Parameters list:
              $1: spf34_neighbor_IP_address

        A Link State Acknowledgement packet has been sent directly
        to the specified neighbor. This is in response to duplicate link state
        advertisements received from the neighbor. This probably indicates
        packet loss during the flooding procedure."
    ::= { spfNotificationsPrefix 34 }

spfNotification35 NOTIFICATION-TYPE
    OBJECTS { 
              spf35_LS_type, 
              spf35_advertisement_ID,
              spf35_advertisement_ID 
            }
    STATUS current
    DESCRIPTION
        "Notification of Event SPF.35

        Message: 'Flushing advertisement: typ $1 id $2 org $3'

        Parameters list:
              $1: spf35_LS_type
              $2: spf35_advertisement_ID
              $3: spf35_advertisement_ID

        A link state advertisement contained in the link state database
        has not been refreshed for 2 hours. The advertisement is deleted from
        the database. This probably indicates that the originator of the
        advertisement is unreachable. See section 14 of the OSPF specification."
    ::= { spfNotificationsPrefix 35 }

spfNotification36 NOTIFICATION-TYPE
    OBJECTS { 
              spf36_LS_type, 
              spf36_advertisement_ID,
              spf36_advertisement_ID 
            }
    STATUS current
    DESCRIPTION
        "Notification of Event SPF.36

        Message: 'Originating LS advertisement: typ $1 id $2 org $3'

        Parameters list:
              $1: spf36_LS_type
              $2: spf36_advertisement_ID
              $3: spf36_advertisement_ID

        A link state advertisement is being (re)originated by the router.
        This can be due to topological change, or the necessity to refresh."
    ::= { spfNotificationsPrefix 36 }

spfNotification37 NOTIFICATION-TYPE
    OBJECTS { 
              spf37_dst_type, 
              spf37_destination,
              spf37_route_type,
              spf37_route_cost 
            }
    STATUS current
    DESCRIPTION
        "Notification of Event SPF.37

        Message: 'New route to destination $1 $2, type $3 cost $4'

        Parameters list:
              $1: spf37_dst_type
              $2: spf37_destination
              $3: spf37_route_type
              $4: spf37_route_cost

        The SPF routing table build process has detected a new best route
        to specified destination, having the specified cost."
    ::= { spfNotificationsPrefix 37 }

spfNotification38 NOTIFICATION-TYPE
    OBJECTS { 
              spf38_neighbor_IP_address 
            }
    STATUS current
    DESCRIPTION
        "Notification of Event SPF.38

        Message: 'NBMA hello sent to IP destination $1'

        Parameters list:
              $1: spf38_neighbor_IP_address

        An OSPF hello has been sent to the specified IP destination.
        This has been done over a non-broadcast, multi-access interface."
    ::= { spfNotificationsPrefix 38 }

spfNotification39 NOTIFICATION-TYPE
    OBJECTS { 
              spf39_en_dis 
            }
    STATUS current
    DESCRIPTION
        "Notification of Event SPF.39

        Message: 'The OSPF routing protocol is $1abled'

        Parameters list:
              $1: spf39_en_dis

        Printed on router startup. Indicates operational status
        of the SPF protocol."
    ::= { spfNotificationsPrefix 39 }

spfNotification40 NOTIFICATION-TYPE
    OBJECTS { 
              spf40_interface_IP_address 
            }
    STATUS current
    DESCRIPTION
        "Notification of Event SPF.40

        Message: 'SPF Interface $1 is not an IP address, Interface not installed'

        Parameters list:
              $1: spf40_interface_IP_address

        Printed on router startup when an OSPF interface address is configured,
        yet this address has not also been configured in the IP console.
        OSPF interface is not installed."
    ::= { spfNotificationsPrefix 40 }

spfNotification41 NOTIFICATION-TYPE
    OBJECTS { 
              spf41_interface_IP_address 
            }
    STATUS current
    DESCRIPTION
        "Notification of Event SPF.41

        Message: 'Non-Broadcast net $1 is not an SPF interface'

        Parameters list:
              $1: spf41_interface_IP_address

        Printed on router startup when OSPF non-broadcast parameters have been
        configured for a non-existent OSPF interface. These configuration
        parameters are ignored."
    ::= { spfNotificationsPrefix 41 }

spfNotification42 NOTIFICATION-TYPE
    OBJECTS { 
              spf42_IP_source, 
              spf42_IP_destination,
              spf42_OSPF_packet_type 
            }
    STATUS current
    DESCRIPTION
        "Notification of Event SPF.42

        Message: 'protocol (disabled): $1 -> $2, type $3 discarded'

        Parameters list:
              $1: spf42_IP_source
              $2: spf42_IP_destination
              $3: spf42_OSPF_packet_type

        The OSPF protocol is disabled, yet an OSPF protocol packet has been
        received. The packet is discarded."
    ::= { spfNotificationsPrefix 42 }

spfNotification43 NOTIFICATION-TYPE
    OBJECTS { 
              spf43_neighbor_IP_address 
            }
    STATUS current
    DESCRIPTION
        "Notification of Event SPF.43

        Message: 'Duplicate LS acknowledgment received from neighbor $1'

        Parameters list:
              $1: spf43_neighbor_IP_address

        Unexpected link state acknowledgements have been received from
        the specified neighbor. This probably indicates packet loss during
        the flooding procedure."
    ::= { spfNotificationsPrefix 43 }

spfNotification44 NOTIFICATION-TYPE
    OBJECTS { 
              spf44_neighbor_IP_address, 
              spf44_LS_type,
              spf44_advertisement_ID,
              spf44_advertisement_ID 
            }
    STATUS current
    DESCRIPTION
        "Notification of Event SPF.44

        Message: 'from $1, bad age field, advertisement: typ $2 id $3 org $4'

        Parameters list:
              $1: spf44_neighbor_IP_address
              $2: spf44_LS_type
              $3: spf44_advertisement_ID
              $4: spf44_advertisement_ID

        A link state advertisement has been received. The advertisement's
        LS age field is invalid. The advertisement is ignored."
    ::= { spfNotificationsPrefix 44 }

spfNotification45 NOTIFICATION-TYPE
    OBJECTS { 
              spf45_proposed_transit_area 
            }
    STATUS current
    DESCRIPTION
        "Notification of Event SPF.45

        Message: 'Transit area $1 not configured, virtual link discarded'

        Parameters list:
              $1: spf45_proposed_transit_area

        A virtual link has been configured to have a certain transit area, yet
        that area has not been defined. The virtual link is ignored."
    ::= { spfNotificationsPrefix 45 }

spfNotification46 NOTIFICATION-TYPE
    STATUS current
    DESCRIPTION
        "Notification of Event SPF.46

        Message: 'Backbone area is not configured, all virtual links discarded'

        Virtual links cannot be used unless a backbone area is configured."
    ::= { spfNotificationsPrefix 46 }

spfNotification47 NOTIFICATION-TYPE
    OBJECTS { 
              spf47_dst_type, 
              spf47_destination 
            }
    STATUS current
    DESCRIPTION
        "Notification of Event SPF.47

        Message: 'Destination $1 $2 now unreachable'

        Parameters list:
              $1: spf47_dst_type
              $2: spf47_destination

        The destination has been found to be unreachable during
        the routing table build process."
    ::= { spfNotificationsPrefix 47 }

spfNotification48 NOTIFICATION-TYPE
    STATUS current
    DESCRIPTION
        "Notification of Event SPF.48

        Message: 'Limit of AS external advertisements exceeded; advertisement discarded'

        The estimated number of advertisements has been exceeded.
        New AS external advertisements are ignored in order to put a limit
        on router heap usage."
    ::= { spfNotificationsPrefix 48 }

spfNotification49 NOTIFICATION-TYPE
    STATUS current
    DESCRIPTION
        "Notification of Event SPF.49

        Message: 'Limit of AS external advertisements exceeded; origination deferred'

        The estimated number of advertisements has been exceeded.
        The origination of new AS external advertisements is deferred in order
        to put a limit on router heap usage."
    ::= { spfNotificationsPrefix 49 }

spfNotification50 NOTIFICATION-TYPE
    OBJECTS { 
              spf50_neighbor_IP_address, 
              spf50_LS_type,
              spf50_advertisement_ID,
              spf50_advertisement_ID 
            }
    STATUS current
    DESCRIPTION
        "Notification of Event SPF.50

        Message: 'from $1, received unexpected MaxAge: typ $2 id $3 org $4'

        Parameters list:
              $1: spf50_neighbor_IP_address
              $2: spf50_LS_type
              $3: spf50_advertisement_ID
              $4: spf50_advertisement_ID

        A link state advertisement has been received. Its age is MaxAge, and
        there is no current instantiation of the advertisement in
        the router's database. The advertisement is acknowledged and then
        discarded without flooding."
    ::= { spfNotificationsPrefix 50 }

spfNotification51 NOTIFICATION-TYPE
    OBJECTS { 
              spf51_LS_type, 
              spf51_advertisement_ID,
              spf51_advertisement_ID 
            }
    STATUS current
    DESCRIPTION
        "Notification of Event SPF.51

        Message: 'error in advertisement or routing overflow: typ $1 id $2 org $3'

        Parameters list:
              $1: spf51_LS_type
              $2: spf51_advertisement_ID
              $3: spf51_advertisement_ID

        A link state advertisement has been received. The advertisement
        contains an error, or cannot be added to the database due to
        routing table overflow. In any case, the advertisement is discarded."
    ::= { spfNotificationsPrefix 51 }

spfNotification52 NOTIFICATION-TYPE
    OBJECTS { 
              spf52_IP_source, 
              spf52_OSPF_packet_type 
            }
    STATUS current
    DESCRIPTION
        "Notification of Event SPF.52

        Message: 'Stub area mismatch in hello from $1, type $2'

        Parameters list:
              $1: spf52_IP_source
              $2: spf52_OSPF_packet_type

        Hello packet received from neighbor. Neighbor disagrees with this router
        concerning the attached area's ability to process AS external link
        advertisements. Hello packet is ignored."
    ::= { spfNotificationsPrefix 52 }

spfNotification53 NOTIFICATION-TYPE
    OBJECTS { 
              spf53_neighbor_IP_address, 
              spf53_LS_type,
              spf53_advertisement_ID,
              spf53_advertisement_ID 
            }
    STATUS current
    DESCRIPTION
        "Notification of Event SPF.53

        Message: 'from $1, type 5 LSA in stub area, adv: typ $2 id $3 org $4'

        Parameters list:
              $1: spf53_neighbor_IP_address
              $2: spf53_LS_type
              $3: spf53_advertisement_ID
              $4: spf53_advertisement_ID

        A type 5 link state advertisement has been received. The advertisement
        is being flooded through a stub area, and is therefore ignored."
    ::= { spfNotificationsPrefix 53 }

spfNotification54 NOTIFICATION-TYPE
    OBJECTS { 
              spf54_Number_areas 
            }
    STATUS current
    DESCRIPTION
        "Notification of Event SPF.54

        Message: 'Dijkstra calculation performed, on $1 area(s)'

        Parameters list:
              $1: spf54_Number_areas

        As a result of a topology change, the routing table has been
        recalculated, starting with the Dijkstra calculation."
    ::= { spfNotificationsPrefix 54 }

spfNotification55 NOTIFICATION-TYPE
    OBJECTS { 
              spf55_LS_type, 
              spf55_advertisement_ID,
              spf55_advertisement_ID 
            }
    STATUS current
    DESCRIPTION
        "Notification of Event SPF.55

        Message: 'Network LSA with old Advertising Router: ($1,$2,$3)'

        Parameters list:
              $1: spf55_LS_type
              $2: spf55_advertisement_ID
              $3: spf55_advertisement_ID

        A network links advertisement having one of our addresses as
        Link State ID, but whose Advertising Router is not our Router ID,
        has been received. These advertisements are flushed, as they are
        assumed to be out-of-date."
    ::= { spfNotificationsPrefix 55 }

spfNotification56 NOTIFICATION-TYPE
    OBJECTS { 
              spf56_Link_State_ID 
            }
    STATUS current
    DESCRIPTION
        "Notification of Event SPF.56

        Message: 'Reparsing Network LSA: $1'

        Parameters list:
              $1: spf56_Link_State_ID

        A network link is being reparsed, owing to the fact that there are
        multiple network-LSAs in the network with the same Link State ID.
        This indicates that a router has changed OSPF Router IDs, and
        has originated the same router-LSA before and after the change.
        This is a normal, but rare, event."
    ::= { spfNotificationsPrefix 56 }

spfNotification57 NOTIFICATION-TYPE
    OBJECTS { 
              spf57_OSPF_packet_type, 
              spf57_IP_destination,
              spf57_reason_code,
              spf57_interface_name 
            }
    STATUS current
    DESCRIPTION
        "Notification of Event SPF.57

        Message: 'Sending unicast type $1 dst $2 failed, reason $3, interface $4'

        Parameters list:
              $1: spf57_OSPF_packet_type
              $2: spf57_IP_destination
              $3: spf57_reason_code
              $4: spf57_interface_name

        Sending of a unicast OSPF packet of specified type failed
        to the specified IP destination.
        The reason_code is the internal error code for the failure."
    ::= { spfNotificationsPrefix 57 }

spfNotification58 NOTIFICATION-TYPE
    OBJECTS { 
              spf58_OSPF_packet_type, 
              spf58_IP_destination,
              spf58_reason_code,
              spf58_interface_name 
            }
    STATUS current
    DESCRIPTION
        "Notification of Event SPF.58

        Message: 'Sending multicast type $1 dst $2 failed, reason $3, interface $4'

        Parameters list:
              $1: spf58_OSPF_packet_type
              $2: spf58_IP_destination
              $3: spf58_reason_code
              $4: spf58_interface_name

        Sending of a multicast OSPF packet of specified type failed
        to the specified IP destination.
        The reason_code is the internal error code for the failure."
    ::= { spfNotificationsPrefix 58 }

spfNotification59 NOTIFICATION-TYPE
    OBJECTS { 
              spf59_OSPF_packet_type, 
              spf59_IP_source,
              spf59_IP_destination,
              spf59_reason_code,
              spf59_interface_name 
            }
    STATUS current
    DESCRIPTION
        "Notification of Event SPF.59

        Message: 'Retransmitting packet failed, type $1, $2 -> $3, reason $4, interface $5'

        Parameters list:
              $1: spf59_OSPF_packet_type
              $2: spf59_IP_source
              $3: spf59_IP_destination
              $4: spf59_reason_code
              $5: spf59_interface_name

        Retransmission of unicast OSPF packet of specified type failed.
        The reason_code is the internal error code for the failure."
    ::= { spfNotificationsPrefix 59 }

spfNotification60 NOTIFICATION-TYPE
    OBJECTS { 
              spf60_neighbor_IP_address, 
              spf60_reason_code,
              spf60_interface_name 
            }
    STATUS current
    DESCRIPTION
        "Notification of Event SPF.60

        Message: 'NBMA hello disc to IP destination $1, reason $2, interface $3'

        Parameters list:
              $1: spf60_neighbor_IP_address
              $2: spf60_reason_code
              $3: spf60_interface_name

        An OSPF hello was discarded when attempting to send it to the specified
        IP destination.
        This was attempted over a non-broadcast, multi-access interface.
        The reason_code is the internal error code for the failure."
    ::= { spfNotificationsPrefix 60 }

spfNotification61 NOTIFICATION-TYPE
    OBJECTS { 
              spf61_proposed_area, 
              spf61_interface_IP_address 
            }
    STATUS current
    DESCRIPTION
        "Notification of Event SPF.61

        Message: 'OSPF area $1 not configured, interface $2 not installed'

        Parameters list:
              $1: spf61_proposed_area
              $2: spf61_interface_IP_address

        Printed on router startup when an OSPF interface address is configured,
        but the attached area is not defined. Hence, the OSPF interface
        is not installed."
    ::= { spfNotificationsPrefix 61 }

spfNotification62 NOTIFICATION-TYPE
    OBJECTS { 
              spf62_map_entry, 
              spf62_network_address,
              spf62_network_mask,
              spf62_route_type,
              spf62_route_cost,
              spf62_route_tag 
            }
    STATUS current
    DESCRIPTION
        "Notification of Event SPF.62

        Message: 'route-map entry $1 filtered nwk $2 msk $3 type $4 cost $5 tag $6'

        Parameters list:
              $1: spf62_map_entry
              $2: spf62_network_address
              $3: spf62_network_mask
              $4: spf62_route_type
              $5: spf62_route_cost
              $6: spf62_route_tag

        Printed on route prevented from install in route table due to
        configured input filter."
    ::= { spfNotificationsPrefix 62 }

spfNotification63 NOTIFICATION-TYPE
    OBJECTS { 
              spf63_link-id, 
              spf63_mask,
              spf63_fixed-val 
            }
    STATUS current
    DESCRIPTION
        "Notification of Event SPF.63

        Message: 'Fixing wrong stub network on RL: id $1/$2->$3'

        Parameters list:
              $1: spf63_link-id
              $2: spf63_mask
              $3: spf63_fixed-val

        Printed on error detected in link id of a stub network, link id should
        be the network address. It is internaly fixed."
    ::= { spfNotificationsPrefix 63 }

spfNotification64 NOTIFICATION-TYPE
    OBJECTS { 
              spf64_auth, 
              spf64_state,
              spf64_area 
            }
    STATUS current
    DESCRIPTION
        "Notification of Event SPF.64

        Message: 'Auth $1 $2 in the area $3'

        Parameters list:
              $1: spf64_auth
              $2: spf64_state
              $3: spf64_area

        Check to see that an incoming packet is authentic."
    ::= { spfNotificationsPrefix 64 }

spfNotification65 NOTIFICATION-TYPE
    OBJECTS { 
              spf65_auth, 
              spf65_spi_addr 
            }
    STATUS current
    DESCRIPTION
        "Notification of Event SPF.65

        Message: 'Authentication $1 in the interface $2'

        Parameters list:
              $1: spf65_auth
              $2: spf65_spi_addr

        Set the authentication fields in a packet we are sending."
    ::= { spfNotificationsPrefix 65 }

spfNotification66 NOTIFICATION-TYPE
    OBJECTS { 
              spf66_ptype, 
              spf66_IP_destination,
              spf66_interface_IP_address 
            }
    STATUS current
    DESCRIPTION
        "Notification of Event SPF.66

        Message: 'Allocate buffer type $1 to $2, interface $3'

        Parameters list:
              $1: spf66_ptype
              $2: spf66_IP_destination
              $3: spf66_interface_IP_address

        Allocate a buffer and format the IP and SPF headers"
    ::= { spfNotificationsPrefix 66 }

spfNotification67 NOTIFICATION-TYPE
    OBJECTS { 
              spf67_action, 
              spf67_spi_addr,
              spf67_area_id 
            }
    STATUS current
    DESCRIPTION
        "Notification of Event SPF.67

        Message: '$1 the interface $2 from the area $3'

        Parameters list:
              $1: spf67_action
              $2: spf67_spi_addr
              $3: spf67_area_id

        Add/delete an interface from an area"
    ::= { spfNotificationsPrefix 67 }

spfNotification68 NOTIFICATION-TYPE
    OBJECTS { 
              spf68_area_id 
            }
    STATUS current
    DESCRIPTION
        "Notification of Event SPF.68

        Message: 'Not configured interfaces in the area $1'

        Parameters list:
              $1: spf68_area_id

        Not configured interfaces in an area"
    ::= { spfNotificationsPrefix 68 }

spfNotification69 NOTIFICATION-TYPE
    OBJECTS { 
              spf69_state, 
              spf69_network_address,
              spf69_network_mask,
              spf69_route_type,
              spf69_route_cost 
            }
    STATUS current
    DESCRIPTION
        "Notification of Event SPF.69

        Message: 'Import external route state $1 $2/$3 type $4 cost $5'

        Parameters list:
              $1: spf69_state
              $2: spf69_network_address
              $3: spf69_network_mask
              $4: spf69_route_type
              $5: spf69_route_cost

        Import external routes (Cand - Candidate, Disc - Discard , Redist - Redistribute)."
    ::= { spfNotificationsPrefix 69 }

spfNotification70 NOTIFICATION-TYPE
    OBJECTS { 
              spf70_lsa_type, 
              spf70_area_id 
            }
    STATUS current
    DESCRIPTION
        "Notification of Event SPF.70

        Message: 'Install lsa type $1 in the area $2'

        Parameters list:
              $1: spf70_lsa_type
              $2: spf70_area_id

        Install a link state advertisement into the link state database."
    ::= { spfNotificationsPrefix 70 }

spfNotification71 NOTIFICATION-TYPE
    OBJECTS { 
              spf71_network_address, 
              spf71_network_mask,
              spf71_route_type,
              spf71_route_cost 
            }
    STATUS current
    DESCRIPTION
        "Notification of Event SPF.71

        Message: 'Install a SPF route $1/$2 type $3 cost $4'

        Parameters list:
              $1: spf71_network_address
              $2: spf71_network_mask
              $3: spf71_route_type
              $4: spf71_route_cost

        Install a SPF route."
    ::= { spfNotificationsPrefix 71 }

spfNotification72 NOTIFICATION-TYPE
    STATUS current
    DESCRIPTION
        "Notification of Event SPF.72

        Message: 'AS boundary router'

        AS boundary router."
    ::= { spfNotificationsPrefix 72 }

spfNotification73 NOTIFICATION-TYPE
    OBJECTS { 
              spf73_message, 
              spf73_network_address,
              spf73_network_mask,
              spf73_route_type,
              spf73_route_cost 
            }
    STATUS current
    DESCRIPTION
        "Notification of Event SPF.73

        Message: '$1 $2/$3 type $4 cost $5'

        Parameters list:
              $1: spf73_message
              $2: spf73_network_address
              $3: spf73_network_mask
              $4: spf73_route_type
              $5: spf73_route_cost

        Form a new instantiation of a link state advertisement."
    ::= { spfNotificationsPrefix 73 }

spfNotification74 NOTIFICATION-TYPE
    OBJECTS { 
              spf74_neighbor_IP_address, 
              spf74_neighbor_state,
              spf74_neighbor_event,
              spf74_event_descr 
            }
    STATUS current
    DESCRIPTION
        "Notification of Event SPF.74

        Message: 'State change, neighbor $1, new state $2, event $3($4)'

        Parameters list:
              $1: spf74_neighbor_IP_address
              $2: spf74_neighbor_state
              $3: spf74_neighbor_event
              $4: spf74_event_descr

        The specified event has been generated, causing the specified neighbor
        to transfer to a new state."
    ::= { spfNotificationsPrefix 74 }

spfNotification75 NOTIFICATION-TYPE
    OBJECTS { 
              spf75_OSPF_packet_type, 
              spf75_OSPF_packet_type_str,
              spf75_IP_source 
            }
    STATUS current
    DESCRIPTION
        "Notification of Event SPF.75

        Message: 'Received packet type $1($2) from $3'

        Parameters list:
              $1: spf75_OSPF_packet_type
              $2: spf75_OSPF_packet_type_str
              $3: spf75_IP_source

        An OSPF packet of the specified type was received."
    ::= { spfNotificationsPrefix 75 }

spfNotification76 NOTIFICATION-TYPE
    OBJECTS { 
              spf76_OSPF_packet_type, 
              spf76_OSPF_packet_type_str,
              spf76_IP_destination,
              spf76_interface 
            }
    STATUS current
    DESCRIPTION
        "Notification of Event SPF.76

        Message: 'Sending multicast, type $1($2), destination $3 interface $4'

        Parameters list:
              $1: spf76_OSPF_packet_type
              $2: spf76_OSPF_packet_type_str
              $3: spf76_IP_destination
              $4: spf76_interface

        Multicast OSPF packet of specified type sent out through specified
        interface."
    ::= { spfNotificationsPrefix 76 }


END
