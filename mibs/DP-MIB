DP-MIB DEFINITIONS ::= BEGIN

-- Title:      RADWARE
--             This Private MIB supports the Vgate
-- Version:    2.9
-- Date:       9 Apr 2000
-- By:         RMA (Radware MIB Authority)
-- E-mail:     US:            support@radware.com
--             International: support_int@radware.com
--
IMPORTS
       IpAddress,
       Counter
              FROM RFC1155-SMI
       OBJECT-TYPE
              FROM RFC-1212
       DisplayString,
       PhysAddress
              FROM RFC1213-MIB
       Ipv6Address 
              FROM IPV6-TC
       rdwrDP,
       rndErrorDesc,
       rndErrorSeverity              
              FROM RADWARE-MIB;

    RowStatus ::= INTEGER {
        active(1),
        notInService(2),
        notReady(3),
        createAndGo(4),
        createAndWait(5),
        destroy(6)
        }

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }

rdwrDPPacketReport   OBJECT IDENTIFIER ::= { rdwrDP 1 }

rdwrDPPacketReportAddr OBJECT-TYPE
    SYNTAX  IpAddress
    ACCESS  read-write
    STATUS  mandatory
    DESCRIPTION
      "IP Address of packet reporting destination."
    ::=  { rdwrDPPacketReport 1}

-- obsolete
rdwrDPPacketReportDestPort OBJECT-TYPE
    SYNTAX  INTEGER  (0..65535)
    ACCESS  read-write
    STATUS  mandatory
    DESCRIPTION
      "Packet reporting destination port."
    DEFVAL { 2088 }
 ::= { rdwrDPPacketReport 2}

rdwrDPPacketReportStatus OBJECT-TYPE
    SYNTAX INTEGER {
      enable(1),
      disable(2)
    }
    ACCESS  read-write
    STATUS  mandatory
    DESCRIPTION
      "Enable\Disable packet reporting globally."
    DEFVAL { disable }
 ::=  { rdwrDPPacketReport 3 }  

rdwrDPPassiveSSL  OBJECT IDENTIFIER ::= { rdwrDP 2 }

rdwrDPPassiveSSLPortTable OBJECT-TYPE
    SYNTAX SEQUENCE OF RdwrDPPassiveSSLPortEntry
    ACCESS not-accessible
    STATUS  mandatory
    DESCRIPTION
      "Table containing the passive SSL physical ports relationship."
    ::= { rdwrDPPassiveSSL 1 }

rdwrDPPassiveSSLPortEntry OBJECT-TYPE
    SYNTAX RdwrDPPassiveSSLPortEntry
    ACCESS not-accessible
    STATUS mandatory
    DESCRIPTION
       "The row definition for this table."
    INDEX { rdwrDPPassiveSSLSourcePort }
    ::=  { rdwrDPPassiveSSLPortTable 1 }

RdwrDPPassiveSSLPortEntry ::= SEQUENCE {
    rdwrDPPassiveSSLSourcePort INTEGER,
    rdwrDPPassiveSSLAcceleratorPort INTEGER,
    rdwrDPPassiveSSLPortStatus RowStatus
}

rdwrDPPassiveSSLSourcePort OBJECT-TYPE
    SYNTAX INTEGER
    ACCESS read-only
    STATUS mandatory
    DESCRIPTION
      "The index of the source port."
    ::=  { rdwrDPPassiveSSLPortEntry 1 }

rdwrDPPassiveSSLAcceleratorPort OBJECT-TYPE
    SYNTAX INTEGER
    ACCESS read-write
    STATUS mandatory
    DESCRIPTION
      "The passive SSL Accelerator port."
    ::=  { rdwrDPPassiveSSLPortEntry 2 }

rdwrDPPassiveSSLPortStatus OBJECT-TYPE
    SYNTAX RowStatus
    ACCESS  read-write
    STATUS  mandatory
    DESCRIPTION
       "This variable indicates the administrative status of this entry.
        Used to delete an entry of this table."
    ::=  { rdwrDPPassiveSSLPortEntry 3 }


rdwrDPPassiveSSLTcpPortTable OBJECT-TYPE
    SYNTAX SEQUENCE OF RdwrDPPassiveSSLTcpPortEntry
    ACCESS not-accessible
    STATUS  mandatory
    DESCRIPTION
      "Table containing the passive SSL TCP ports translation."
    ::= { rdwrDPPassiveSSL 2 }

rdwrDPPassiveSSLTcpPortEntry OBJECT-TYPE
    SYNTAX RdwrDPPassiveSSLTcpPortEntry
    ACCESS not-accessible
    STATUS mandatory
    DESCRIPTION
       "The row definition for this table."
    INDEX { rdwrDPPassiveSSLTcpSSLPort }
    ::=  { rdwrDPPassiveSSLTcpPortTable 1 }

RdwrDPPassiveSSLTcpPortEntry::= SEQUENCE {
    rdwrDPPassiveSSLTcpSSLPort INTEGER,
    rdwrDPPassiveSSLTcpDecryptedPort INTEGER,
    rdwrDPPassiveSSLTcpPortStatus RowStatus
}

rdwrDPPassiveSSLTcpSSLPort OBJECT-TYPE
    SYNTAX INTEGER (0..65535)
    ACCESS read-only
    STATUS mandatory
    DESCRIPTION
      "The index of the source port."
    ::=  { rdwrDPPassiveSSLTcpPortEntry 1 }

rdwrDPPassiveSSLTcpDecryptedPort OBJECT-TYPE
    SYNTAX INTEGER (0..1023)
    ACCESS read-write
    STATUS mandatory
    DESCRIPTION
      "The passive SSL Accelerator port."
    ::=  { rdwrDPPassiveSSLTcpPortEntry 2 }

rdwrDPPassiveSSLTcpPortStatus OBJECT-TYPE
    SYNTAX RowStatus
    ACCESS  read-write
    STATUS  mandatory
    DESCRIPTION
       "This variable indicates the administrative status of this entry.
        Used to delete an entry of this table."
    ::=  { rdwrDPPassiveSSLTcpPortEntry 3 }

rdwrDPBypassStatus OBJECT-TYPE
    SYNTAX INTEGER {
        enable(1),
        disable(2)
    }
    ACCESS  read-write
    STATUS  mandatory
    DESCRIPTION
        "Bypass status of all ports."
    DEFVAL { disable }
    ::=  { rdwrDP 3}


rsSmeOverloadMechanism OBJECT-TYPE
    SYNTAX INTEGER {
        enable(1),
        disable(2)
    }
    ACCESS  read-write
    STATUS  mandatory
    DESCRIPTION
        "Sme Overload Mechanism."
    DEFVAL { disable }
    ::=  { rdwrDP 4}


rsOverloadAlerts OBJECT-TYPE
    SYNTAX INTEGER {
        enable(1),
        disable(2)
    }
    ACCESS  read-write
    STATUS  mandatory
    DESCRIPTION
        "Overload Alerts."
    DEFVAL { disable }
    ::=  { rdwrDP 5}

rsGlobalOverloadMechanism OBJECT-TYPE
    SYNTAX INTEGER {
        enable(1),
        disable(2)
    }
    ACCESS  read-write
    STATUS  mandatory
    DESCRIPTION
        "Overload Mechanism."
    DEFVAL { disable }
    ::=  { rdwrDP 6}

rdwrDPBuildID OBJECT-TYPE
    SYNTAX INTEGER (0..65535)
    ACCESS read-only
    STATUS mandatory
    DESCRIPTION
      "Software BuildID."
    ::=  { rdwrDP 7 }
	
rdwrDPNetDrvVersion OBJECT-TYPE
    SYNTAX DisplayString 
    ACCESS  read-only
    STATUS  mandatory
    DESCRIPTION
      "The net Driver version"
    ::=  {rdwrDP 8}
	
rdwrDPAccRamSize OBJECT-TYPE
    SYNTAX INTEGER (0..65535)
    ACCESS read-only
    STATUS mandatory
    DESCRIPTION
      "Accelerator RAM size."
    ::=  { rdwrDP 9 }

rdwrDPHighAvailability OBJECT IDENTIFIER ::= { rdwrDP 10 }
	
rdwrDPHighAvailabilityDevicePriority  OBJECT-TYPE
 SYNTAX INTEGER {
      secondary(0),
      primary(1),
	  standAlone(2)
   }
    ACCESS read-write
    STATUS mandatory
    DESCRIPTION
      "The Priority of the device Primary, Secondary or stand alone"
   DEFVAL  {standAlone}
    ::= {rdwrDPHighAvailability 1}
			
rdwrDPHighAvailabilityKeepAliveTimeout OBJECT-TYPE
	SYNTAX INTEGER (10..30)
    ACCESS read-write
    STATUS mandatory
    DESCRIPTION
      "High Availability retries number"
	DEFVAL  { 10 }
    ::= {rdwrDPHighAvailability 2}
	
rdwrDPHighAvailabilityLinkDownTimeout OBJECT-TYPE
	SYNTAX INTEGER (1..65535)
    ACCESS read-write
    STATUS mandatory
    DESCRIPTION
      "High Availability link down timeout - in sec"
	DEFVAL  { 1 }
    ::= {rdwrDPHighAvailability 3}
	
rdwrDPHighAvailabilityLineDetectStatus OBJECT-TYPE
 SYNTAX INTEGER {
      enable(1),
      disable(2)
   }
    ACCESS read-write
    STATUS mandatory
    DESCRIPTION
      "Idle line detection status"
   DEFVAL  {disable}
    ::= {rdwrDPHighAvailability 4}
	
	
rdwrDPHighAvailabilityBW OBJECT-TYPE
	SYNTAX INTEGER
    ACCESS read-write
    STATUS mandatory
    DESCRIPTION
      "Total BW threshold - in kbits/sec"
	DEFVAL  { 512 }
    ::= {rdwrDPHighAvailability 5}
	
rdwrDPHighAvailabilityIdleLineTimeout OBJECT-TYPE
	SYNTAX INTEGER (3..65535)
    ACCESS read-write
    STATUS mandatory
    DESCRIPTION
      "Idle line timeout - sec"
	DEFVAL  { 65535 }
    ::= {rdwrDPHighAvailability 6}

rdwrDPHighAvailabilitySwitchOverTimeout OBJECT-TYPE
	SYNTAX INTEGER (30..3600)
    ACCESS read-write
    STATUS mandatory
    DESCRIPTION
      "Switch-Over timeout - in sec"
	DEFVAL  { 180 }
    ::= {rdwrDPHighAvailability 7}	

rdwrDPHighAvailabilitySwitchOverAction OBJECT-TYPE
    SYNTAX INTEGER {
        switchOver(1)
    }
    ACCESS  read-write
    STATUS  mandatory
    DESCRIPTION "Switch Over to peer device"
    ::= { rdwrDPHighAvailability 8 }
	
rdwrDPHighAvailabilityCurrentState OBJECT-TYPE
    SYNTAX INTEGER {
		pairNotDefined(0),
        disconnected(1),
		negotiate(2),
		synchronizing(3),
		inSync(4),
		holdOn(5)
    }
    ACCESS  read-only
    STATUS  mandatory
    DESCRIPTION "The current mehanism state "
    ::= { rdwrDPHighAvailability 9 }

rdwrDPHighAvailabilityProtectionState OBJECT-TYPE
    SYNTAX INTEGER {
        active(1),
		passive(2)
    }
    ACCESS  read-only
    STATUS  mandatory
    DESCRIPTION "The current mehanism state "
	DEFVAL  {1}
    ::= { rdwrDPHighAvailability 10 }

rdwrDPHighAvailabilityForceSyncAction OBJECT-TYPE
    SYNTAX INTEGER {
        activateSync(1)
    }
    ACCESS  read-write
    STATUS  mandatory
    DESCRIPTION "Force baseline sync with peer"
    ::= { rdwrDPHighAvailability 11 }	

rdwrDPHighAvailabilityLastSyncTime OBJECT-TYPE
    SYNTAX DisplayString
    ACCESS  read-only
    STATUS  mandatory
    DESCRIPTION "Last successful sync time"
    ::= { rdwrDPHighAvailability 12 }	
	
rdwrDPHighAvailabilityPeerIpAddrMngOne OBJECT-TYPE
	SYNTAX IpAddress
	ACCESS  read-write
	STATUS  mandatory
	DESCRIPTION
		"The peer IP address of managment one."
	::= {rdwrDPHighAvailability 13}
	
	
rdwrDPHighAvailabilityPeerIpAddrMngTwo OBJECT-TYPE
	SYNTAX IpAddress
	ACCESS  read-write
	STATUS  mandatory
	DESCRIPTION
		"The peer IP address of managment two."
	::= {rdwrDPHighAvailability 14}
	
rdwrDPHighAvailabilityPeerUserName OBJECT-TYPE
    SYNTAX DisplayString
    ACCESS  read-write
    STATUS  mandatory
    DESCRIPTION "Peer device user name"
    ::= { rdwrDPHighAvailability 15 }
	
rdwrDPHighAvailabilityPeerPassword OBJECT-TYPE
    SYNTAX DisplayString 
    ACCESS read-write
    STATUS mandatory
    DESCRIPTION
      "Peer device user password."
    ::=  { rdwrDPHighAvailability 16 }

rdwrDPHighAvailabilityBaseLineSyncInterval OBJECT-TYPE
	SYNTAX INTEGER (3600..86400)
    ACCESS read-write
    STATUS mandatory
    DESCRIPTION
      "Base Line sync interval - in sec"
	DEFVAL  { 3600 }
    ::= {rdwrDPHighAvailability 17}
	
rdwrDPHighAvailabilityDevicePriorityDisplay OBJECT-TYPE
    SYNTAX INTEGER {
        secondary(0),
	primary(1),
	standAlone(2)
    }
    ACCESS  read-only
    STATUS  mandatory
    DESCRIPTION "The Priority of the device display string purpose only"
	DEFVAL  {1}
    ::= { rdwrDPHighAvailability 18 }
	
	
rdwrDPHighAvailabilityPairAction OBJECT-TYPE
    SYNTAX INTEGER {
        setPair(1)
    }
    ACCESS  read-write
    STATUS  mandatory
    DESCRIPTION "Set or update high availability pair"
    ::= { rdwrDPHighAvailability 19 }	

rdwrDPHighAvailabilityImmediateSync OBJECT-TYPE
    SYNTAX INTEGER {
      enable(1),
      disable(2)
    }
    ACCESS  read-write
    STATUS  mandatory
    DESCRIPTION
      "Enable\Disable base-line sync immediatly on update."
    DEFVAL { disable }
    ::= { rdwrDPHighAvailability 20 }
	
rdwrDPHighAvailabilityStatus  OBJECT-TYPE
 SYNTAX INTEGER {
      enable(1),
      disable(2)
   }
    ACCESS read-write
    STATUS mandatory
    DESCRIPTION
      "The status of high availability mechanism"
   DEFVAL  {enable}
    ::= {rdwrDPHighAvailability 21}
	
rdwrDPHighAvailabilityFailBack  OBJECT-TYPE
 SYNTAX INTEGER {
      enable(1),
      disable(2)
   }
    ACCESS read-write
    STATUS mandatory
    DESCRIPTION
      "Fail Back to Primary"
   DEFVAL  {disable}
    ::= {rdwrDPHighAvailability 22}

rdwrDPOverload OBJECT IDENTIFIER ::= { rdwrDP 11 }

rsOverloadMechanismCongestionStatus OBJECT-TYPE
    SYNTAX INTEGER {
        noCongestion(0),
        smeCongestion(1),
		acceleratorCongestion(2),
		masterCongestion(3),
		wireBypass(4)		
    }
    ACCESS  read-only
    STATUS  mandatory
    DESCRIPTION
        "Overload Mechanism congestion status"
    DEFVAL { noCongestion }
    ::=  {rdwrDPOverload 1}

rsOverloadThresholdsTable OBJECT-TYPE
    SYNTAX SEQUENCE OF RsOverloadThresholdsEntry
    ACCESS not-accessible
    STATUS  mandatory
    DESCRIPTION
      "Table containing the thresholds for overload mechanism"
    ::=  {rdwrDPOverload 2}
	
rsOverloadThresholdsEntry OBJECT-TYPE
    SYNTAX RsOverloadThresholdsEntry
    ACCESS not-accessible
    STATUS  mandatory
    DESCRIPTION
       "The row definition for overload table."
    INDEX { rsOverloadModuleType, rsOverloadCongestionElement,rsOverloadThresholdType  }
    ::=  { rsOverloadThresholdsTable 1 }

RsOverloadThresholdsEntry ::= SEQUENCE {
	rsOverloadModuleType INTEGER,
    rsOverloadCongestionElement INTEGER,
	rsOverloadThresholdType INTEGER,
    rsOverloadThresholdValue INTEGER,
    rsOverloadThresholdRowStatus RowStatus
}

rsOverloadModuleType OBJECT-TYPE
   SYNTAX INTEGER {
   accelerator(0), 
   master(1), 
   sme(2)
    }
    ACCESS  read-only
    STATUS  mandatory
    DESCRIPTION
       "The module of which its threshold are defined" 
    ::=  { rsOverloadThresholdsEntry 1}

rsOverloadCongestionElement OBJECT-TYPE
   SYNTAX INTEGER {
   buffer(1), 
   cpu(2),
   sendError(3)
   }
    ACCESS  read-only
    STATUS  mandatory
    DESCRIPTION
       "The module of which its threshold are defined" 
    ::=  { rsOverloadThresholdsEntry 2}
	
rsOverloadThresholdType OBJECT-TYPE
   SYNTAX INTEGER {
   low(0), 
   opt(1),
   neg(2),
   maxRegular(3),
   activePeriod(4)
    }
    ACCESS  read-only
    STATUS  mandatory
    DESCRIPTION
       "The type of threshold" 
    ::=  { rsOverloadThresholdsEntry 3}
	
rsOverloadThresholdValue OBJECT-TYPE
   SYNTAX INTEGER (1..100000)
    ACCESS  read-write
    STATUS  mandatory
    DESCRIPTION
       "The value of threshold" 
    ::=  { rsOverloadThresholdsEntry 4}

rsOverloadThresholdRowStatus OBJECT-TYPE
    SYNTAX RowStatus
    ACCESS  read-write
    STATUS  mandatory
    DESCRIPTION
       "This variable indicates the administrative status of this entry.
        Used to delete an entry of this table."
    ::=  { rsOverloadThresholdsEntry 5 }
	
rsOverloadThresholdsDefault OBJECT-TYPE
 SYNTAX INTEGER 
   ACCESS  read-write
   STATUS  mandatory
   DESCRIPTION
       "return to default overload thresholds"
    ::=  {rdwrDPOverload 3}
	
rdwrDPJumboFrames OBJECT IDENTIFIER ::= { rdwrDP 12 }

rdwrDPJumboFramesMaxSwitchSize OBJECT-TYPE
   SYNTAX INTEGER (1550..16000)
    ACCESS  read-write
    STATUS  mandatory
    DESCRIPTION
       "Max Frame Size for switch" 
	DEFVAL { 1550 }
    ::=  { rdwrDPJumboFrames 1}
	
rdwrDPJumboFramesMaxInspectionSize OBJECT-TYPE
   SYNTAX INTEGER (1550..16000)
    ACCESS  read-write
    STATUS  mandatory
    DESCRIPTION
       "Max Frame Size for inspection" 
	DEFVAL { 1550 }
    ::=  { rdwrDPJumboFrames 2}
	
rdwrDPJumboFramesProcessStatus OBJECT-TYPE
   SYNTAX INTEGER {
      enable(1),
      disable(2)
    }
    ACCESS  read-write
    STATUS  mandatory
    DESCRIPTION
       "Jumbo Frames Mechanism status" 
	DEFVAL {2}
    ::=  { rdwrDPJumboFrames 3}
	
	
rdwrDPRouting OBJECT IDENTIFIER ::= { rdwrDP 13 }

rdwrDPRoutingStatus OBJECT-TYPE
    SYNTAX INTEGER {
      routing(1),
      transparent(2)
    }
    ACCESS  read-write
    STATUS  mandatory
    DESCRIPTION
      "Defines the DP working-mode (transparent or routing)."
    DEFVAL { transparent }
 ::=  { rdwrDPRouting 1 }  
	
rdwrDPRoutingVifTable OBJECT-TYPE
    SYNTAX SEQUENCE OF RdwrDPRoutingVifEntry
    ACCESS not-accessible
    STATUS  mandatory
    DESCRIPTION
      "Table containing the DP Virtual-Interface parameters used in Routing-Mode."
    ::= { rdwrDPRouting 2 }

rdwrDPRoutingVifEntry OBJECT-TYPE
    SYNTAX RdwrDPRoutingVifEntry
    ACCESS not-accessible
    STATUS mandatory
    DESCRIPTION
       "The row definition for this table."
    INDEX { rdwrDPRoutingVifIndex }
    ::=  { rdwrDPRoutingVifTable 1 }

RdwrDPRoutingVifEntry ::= SEQUENCE {
    rdwrDPRoutingVifIndex INTEGER,
    rdwrDPRoutingVifInterface INTEGER,
    rdwrDPRoutingVifMac PhysAddress,
    rdwrDPRoutingVifIp Ipv6Address,
    rdwrDPRoutingVifMask DisplayString,
    rdwrDPRoutingVifVlanType INTEGER,
    rdwrDPRoutingVifVlanTag INTEGER,
    rdwrDPRoutingVifAdminStatus INTEGER,
    rdwrDPRoutingVifOperStatus INTEGER,
    rdwrDPRoutingVifRowStatus RowStatus
}

rdwrDPRoutingVifIndex OBJECT-TYPE
    SYNTAX INTEGER
    ACCESS read-only
    STATUS mandatory
    DESCRIPTION
      "The index of the VIF table."
    ::=  { rdwrDPRoutingVifEntry 1 }

rdwrDPRoutingVifInterface OBJECT-TYPE
    SYNTAX INTEGER
    ACCESS read-write
    STATUS mandatory
    DESCRIPTION
      "The physical interface of the VIF."
    ::=  { rdwrDPRoutingVifEntry 2 }

rdwrDPRoutingVifMac OBJECT-TYPE
    SYNTAX PhysAddress
    ACCESS read-only
    STATUS mandatory
    DESCRIPTION
      "The MAC address of the VIF port."
    ::=  { rdwrDPRoutingVifEntry 3 }

rdwrDPRoutingVifIp OBJECT-TYPE
    SYNTAX Ipv6Address
    ACCESS read-write
    STATUS mandatory
    DESCRIPTION
      "The IP address of the VIF port."
    ::=  { rdwrDPRoutingVifEntry 4 }
    
rdwrDPRoutingVifMask OBJECT-TYPE
    SYNTAX DisplayString
    ACCESS read-write
    STATUS mandatory
    DESCRIPTION
      "The subnet mask of the VIF IP address."
    ::=  { rdwrDPRoutingVifEntry 5 }
    
rdwrDPRoutingVifVlanType OBJECT-TYPE
    SYNTAX INTEGER {
      ignore(1),
      none(2),
      all(3),
      specific(4)
	}
    ACCESS read-write
    STATUS mandatory
    DESCRIPTION
      "The VLAN-Tag treatment type of the VIF (may be 'N/A', 'None', 'ALL', or Specific)."
	DEFVAL { specific }
    ::=  { rdwrDPRoutingVifEntry 6 }
    
rdwrDPRoutingVifVlanTag OBJECT-TYPE
    SYNTAX INTEGER
    ACCESS read-write
    STATUS mandatory
    DESCRIPTION
      "The VLAN-Tag of the VIF."
    ::=  { rdwrDPRoutingVifEntry 7 }
    
rdwrDPRoutingVifAdminStatus OBJECT-TYPE
    SYNTAX INTEGER {
      up(1),
      down(2)
    }
    ACCESS read-write
    STATUS mandatory
    DESCRIPTION
      "The desired status of the VIF"
	  DEFVAL { up }
    ::=  { rdwrDPRoutingVifEntry 8 }
    
rdwrDPRoutingVifOperStatus OBJECT-TYPE
    SYNTAX INTEGER {
      up(1),
      down(2)
    }
    ACCESS read-only
    STATUS mandatory
    DESCRIPTION
      "The current Operational status of the VIF"
    ::=  { rdwrDPRoutingVifEntry 9 }
    
rdwrDPRoutingVifRowStatus OBJECT-TYPE
    SYNTAX RowStatus
    ACCESS  read-write
    STATUS  mandatory
    DESCRIPTION
       "This variable indicates the administrative status of this entry.
        Used to delete an entry of this table."
    ::=  { rdwrDPRoutingVifEntry 10 }

rdwrDPRoutingIpForwardingTable OBJECT-TYPE
    SYNTAX SEQUENCE OF RdwrDPRoutingIpForwardingEntry
    ACCESS not-accessible
    STATUS  mandatory
    DESCRIPTION
      "Table containing the DP Virtual-Interface pairs for Routing-Mode."
    ::= { rdwrDPRouting 3 }

rdwrDPRoutingIpForwardingEntry OBJECT-TYPE
    SYNTAX RdwrDPRoutingIpForwardingEntry
    ACCESS not-accessible
    STATUS mandatory
    DESCRIPTION
       "The row definition for this table."
    INDEX { rdwrDPRoutingIpForwardingIngressVif }
    ::=  { rdwrDPRoutingIpForwardingTable 1 }

RdwrDPRoutingIpForwardingEntry ::= SEQUENCE {
    rdwrDPRoutingIpForwardingIngressVif INTEGER,
    rdwrDPRoutingIpForwardingEgressVif INTEGER,
    rdwrDPRoutingIpForwardingNextHop Ipv6Address,
    rdwrDPRoutingIpForwardingNextHopMac PhysAddress,
    rdwrDPRoutingIpForwardingAdminStatus INTEGER,
    rdwrDPRoutingIpForwardingOperStatus INTEGER,
    rdwrDPRoutingIpForwardingRowStatus RowStatus
}

rdwrDPRoutingIpForwardingIngressVif OBJECT-TYPE
    SYNTAX INTEGER
    ACCESS read-only
    STATUS mandatory
    DESCRIPTION
      "The Ingress virtual interface of the ip-forwarding entry."
    ::=  { rdwrDPRoutingIpForwardingEntry 1 }

rdwrDPRoutingIpForwardingEgressVif OBJECT-TYPE
    SYNTAX INTEGER
    ACCESS read-write
    STATUS mandatory
    DESCRIPTION
      "The Egress virtual interface of the ip-forwarding entry."
    ::=  { rdwrDPRoutingIpForwardingEntry 2 }

rdwrDPRoutingIpForwardingNextHop OBJECT-TYPE
    SYNTAX Ipv6Address
    ACCESS read-write
    STATUS mandatory
    DESCRIPTION
      "The next-hop IP address of the ip-forwarding entry."
    ::=  { rdwrDPRoutingIpForwardingEntry 3 }
    
rdwrDPRoutingIpForwardingNextHopMac OBJECT-TYPE
    SYNTAX PhysAddress
    ACCESS read-write
    STATUS mandatory
    DESCRIPTION
      "The MAC of the next-hop IP of the ip-forwarding entry."
    ::=  { rdwrDPRoutingIpForwardingEntry 4 }
    
    
rdwrDPRoutingIpForwardingAdminStatus OBJECT-TYPE
    SYNTAX INTEGER {
      up(1),
      down(2)
    }
    ACCESS read-write
    STATUS mandatory
    DESCRIPTION
      "The desired status of the ip-forwarding entry"
	DEFVAL { up }
    ::=  { rdwrDPRoutingIpForwardingEntry 5 }
    
rdwrDPRoutingIpForwardingOperStatus OBJECT-TYPE
    SYNTAX INTEGER {
      up(1),
      down(2)
    }
    ACCESS read-only
    STATUS mandatory
    DESCRIPTION
      "The current Operational status of the ip-forwarding entry"
    ::=  { rdwrDPRoutingIpForwardingEntry 6 }
    
rdwrDPRoutingIpForwardingRowStatus OBJECT-TYPE
    SYNTAX RowStatus
    ACCESS  read-write
    STATUS  mandatory
    DESCRIPTION
       "This variable indicates the administrative status of this entry.
        Used to delete an entry of this table."
    ::=  { rdwrDPRoutingIpForwardingEntry 7 }
    
rdwrDPVersion OBJECT-TYPE
    SYNTAX DisplayString 
    ACCESS  read-only
    STATUS  mandatory
    DESCRIPTION
      "DefensePro version"
    ::=  {rdwrDP 18}
	
rdwrDPBypassJumboFramesStatus OBJECT-TYPE
    SYNTAX INTEGER {
      enable(1),
      disable(2)
    }
    ACCESS  read-write
    STATUS  mandatory
    DESCRIPTION
      "Enable\Disable jumbo frames bypass."
    DEFVAL { disable }
 ::=  { rdwrDP 19 } 

rdwrDPEZChipEnabled OBJECT-TYPE
    SYNTAX INTEGER {
      false(0),
      true(1)
    }
    ACCESS  read-only
    STATUS  mandatory
    DESCRIPTION
      "Whether the EZChip Hardware accelerator exists or not."
 ::=  { rdwrDP 20 } 

-- Note: There is still a gap between MIBS: 12-18 (ArikC. 09/10/2011)

	
-- Enterprise-specific traps for DEFENSE PRO
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rdwrDP
--       VARIABLES   { rndErrorDesc, rndErrorSeverity }
--       DESCRIPTION
--             ""
--       ::=
-- -------------

rdwrDPAllBypassPortsEnabled TRAP-TYPE
   ENTERPRISE rdwrDP
   VARIABLES { rndErrorDesc, rndErrorSeverity }
   DESCRIPTION
      "This info trap is generated when the status of all bypass ports is set to enable."
   ::= 1
   
rdwrDPAllBypassPortsDisabled TRAP-TYPE
   ENTERPRISE rdwrDP
   VARIABLES { rndErrorDesc, rndErrorSeverity }
   DESCRIPTION
      "This info trap is generated when the status of all bypass ports is set to disable."
   ::= 2

rdwrDPtrafficCapacity90percent TRAP-TYPE
   ENTERPRISE rdwrDP
   VARIABLES { rndErrorDesc, rndErrorSeverity }
   DESCRIPTION
      "This warning trap is generated when the devices reaches 90% of its traffic capacity."
   ::= 3
   
rdwrDPtrafficCapacity100percent TRAP-TYPE
   ENTERPRISE rdwrDP
   VARIABLES { rndErrorDesc, rndErrorSeverity }
   DESCRIPTION
      "This warning trap is generated when the devices reaches 100% of its traffic capacity."
   ::= 4

rdwrDPSmeOverloadActivation TRAP-TYPE
   ENTERPRISE rdwrDP
   VARIABLES { rndErrorDesc, rndErrorSeverity }
   DESCRIPTION
      "This info trap is generated when the SME overload mechanism activated or deactivated."
   ::= 5

rdwrDPOverloadAlertsActivation TRAP-TYPE
   ENTERPRISE rdwrDP
   VARIABLES { rndErrorDesc, rndErrorSeverity }
   DESCRIPTION
      "This info trap is generated when overload alerts activated or deactivated."
   ::= 6

rdwrDPFanStatus TRAP-TYPE
   ENTERPRISE rdwrDP
   VARIABLES { rndErrorDesc, rndErrorSeverity }
   DESCRIPTION
      "This warning trap is generated when a fan stop working."
   ::= 7

rdwrUserConfigurationChange TRAP-TYPE
   ENTERPRISE rdwrDP
   VARIABLES { rndErrorDesc, rndErrorSeverity }
   DESCRIPTION
      "This info trap is generated when on user configuration change."
   ::= 8

rdwrDPHighAvailabilityInfoTrap TRAP-TYPE
   ENTERPRISE rdwrDP
   VARIABLES { rndErrorDesc, rndErrorSeverity }
   DESCRIPTION
      "This info trap is generated upon high availability event"
   ::= 9
   
rdwrDPHighAvailabilityWarningTrap TRAP-TYPE
   ENTERPRISE rdwrDP
   VARIABLES { rndErrorDesc, rndErrorSeverity }
   DESCRIPTION
      "This warning trap is generated upon high availability event"
   ::= 10

rdwrDPHighAvailabilityErrorTrap TRAP-TYPE
   ENTERPRISE rdwrDP
   VARIABLES { rndErrorDesc, rndErrorSeverity }
   DESCRIPTION
      "This error trap is generated upon high availability event"
   ::= 11
   
rdwrDPPacketTraceWarningTrap TRAP-TYPE
   ENTERPRISE rdwrDP
   VARIABLES { rndErrorDesc, rndErrorSeverity }
   DESCRIPTION
      "This error trap is generated upon packet-trace port limit event"
   ::= 12

rdwrIDSLocalOutOfPathWarningTrap  TRAP-TYPE
       ENTERPRISE  rdwrDP
       VARIABLES { rndErrorDesc, rndErrorSeverity }
	   DESCRIPTION
      "This error trap is generated upon Local Out-of-Path Failure event"
   ::= 13 
	   
rdwrIDSLocalOutOfPathInfoTrap  TRAP-TYPE
       ENTERPRISE  rdwrDP
       VARIABLES { rndErrorDesc, rndErrorSeverity }
	   DESCRIPTION
      "This error trap is generated upon Local Out-of-Path Success event"
   ::= 14 
   
rdwrDPPacketTraceInfoTrap TRAP-TYPE
   ENTERPRISE rdwrDP
   VARIABLES { rndErrorDesc, rndErrorSeverity }
   DESCRIPTION
      "This error trap is generated upon packet-trace port limit event"
   ::= 15
   
END
