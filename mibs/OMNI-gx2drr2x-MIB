OMNI-gx2drr2x-MIB DEFINITIONS ::= BEGIN

    IMPORTS
	
	OBJECT-TYPE                     
					      FROM RFC-1212
	DisplayString        
					      FROM RFC1213-MIB
	TRAP-TYPE                       
					      FROM RFC-1215
	gx2Drr2x
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

      -- *********************************************************************
      -- *                                                                   *  
      -- * REVISION history:                                                 *
      -- *	      MIB at Rev 0 to support Firmware at Rev A, July 2, 2003    * 
      -- *                                                                   *
      -- *********************************************************************

	-- OMNISTAR Digital Receiver Return 2X Module MIB MODULE

	-- This MIB module defines information for management of HFC networks
		-- 
		-- The MIB module assumes that all generic (static) network element
		-- information is defined in a different module such as the HFC module
		-- The MIB consists of two groups:
		-- the device type descriptor subgroup and 
		-- gx2drr2x Network Elements subgroup.
		-- The device type descriptor subgroup is used to define 
		-- parameters specific to gx2drr2x device type.
		-- These parameters are common across all network elements
		-- from gx2drr2x device type.
		--
		-- The gx2drr2x Network Elements subgroup is
		-- a list of gx2drr2x type elements in the
		-- current network topology with nominal
		-- and current parameter values for the
		-- individual network elements; the individual
		-- network elements are identified by  
		-- index from hfcCommonTable.
		-- That implies the hfcCommonTableIndex and
		-- gx2drr2xTableIndex are equal for each individual
		-- network element.
		-- This table is an extension of the hfcCommonTable
		-- for all elements of gx2drr2x type.
		--
		-- Both groups are mandatory for management of gx2drr2x devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2drr2x Device Descriptor subgroup.

		-- The device type descriptor subgroup is used to define 
		-- parameters specific to gx2drr2x device type.
		-- These parameters are common across all network elements
		-- from gx2drr2x device type.


		 gx2drr2xDescriptor OBJECT IDENTIFIER ::= {gx2Drr2x 1}



--*****************************************************************************
		--              gx2drr2x Table
		
		--
		-- The individual network elements indentified by  
		-- index from hfcCommonTable.
		-- That implies what hfcCommonTableIndex and
		-- gx2drr2xTableIndex are equal for each individual
		-- nettwork element.
		-- This table should be used as an extension of the hfcCommonTable
		-- for all elements of gx2drr2x type.

	-- ANALOG TABLE:
	-- Analog table hold analog parameters. 
	--    For each analog parameter, there are following alarm limits:
      --       major high, major low, minor high and minor low.
      --    Firmware use these limits to determine alarm related to this parameter. Based on 
	--    individual parameter, certain alarm limit may not be populated.   
      --    For the unused entry, this MIB provides the following comment:
 	--    "This object is not used by this module and always returns invalid float value 
	--	of 0xFFFFFFFF . This object is kept here for persistence." 

	       gx2drr2xAnalogTable                    OBJECT-TYPE
			 SYNTAX             SEQUENCE OF Gx2drr2xAnalogEntry
			 ACCESS             not-accessible
			 STATUS             mandatory
			 DESCRIPTION
			 "This table contains gx2drr2x specific analog parameters with
			  nominal,limits and current values."
			 ::= { gx2Drr2x 2 }


	       gx2drr2xAnalogEntry               OBJECT-TYPE
			 SYNTAX             Gx2drr2xAnalogEntry
			 ACCESS             not-accessible
			 STATUS             mandatory
			 DESCRIPTION
			 "This list contains the analog parameters and descriptions."
			 INDEX { gx2drr2xAnalogTableIndex }
			 ::= { gx2drr2xAnalogTable  1}

--*****************************************************************************
	       gx2drr2xDigitalTable                    OBJECT-TYPE
			 SYNTAX             SEQUENCE OF Gx2drr2xDigitalEntry
			 ACCESS             not-accessible
			 STATUS             mandatory
			 DESCRIPTION
			 "This table contains gx2drr2x specific digital parameters with
			  nominal and current values."
			 ::= { gx2Drr2x 3 }

	       gx2drr2xDigitalEntry               OBJECT-TYPE
			 SYNTAX             Gx2drr2xDigitalEntry
			 ACCESS             not-accessible
			 STATUS             mandatory
			 DESCRIPTION
			 "This list contains individual digital parameters and descriptions."
			 INDEX { gx2drr2xDigitalTableIndex }
			 ::= { gx2drr2xDigitalTable  2}

--*****************************************************************************
	       gx2drr2xStatusTable                    OBJECT-TYPE
			 SYNTAX             SEQUENCE OF Gx2drr2xStatusEntry
			 ACCESS             not-accessible
			 STATUS             mandatory
			 DESCRIPTION
			 "This table contains gx2drr2x specific status parameters with
			  nominal and current values."
			 ::= { gx2Drr2x 4 }

	       gx2drr2xStatusEntry               OBJECT-TYPE
			 SYNTAX             Gx2drr2xStatusEntry
			 ACCESS             not-accessible
			 STATUS             mandatory
			 DESCRIPTION
			 "This list contains Status parameters and descriptions."
			 INDEX { gx2drr2xStatusTableIndex }
			 ::= { gx2drr2xStatusTable  3}

--*****************************************************************************
	       gx2drr2xFactoryTable                    OBJECT-TYPE
			 SYNTAX             SEQUENCE OF Gx2drr2xFactoryEntry
			 ACCESS             not-accessible
			 STATUS             mandatory
			 DESCRIPTION
			 "This table contains gx2drr2x specific factory setting parameters with
			  nominal and current values."
			 ::= { gx2Drr2x 5 }

	       gx2drr2xFactoryEntry               OBJECT-TYPE
			 SYNTAX             Gx2drr2xFactoryEntry
			 ACCESS             not-accessible
			 STATUS             mandatory
			 DESCRIPTION
			 "This list contains Factory setting parameters and descriptions."
			 INDEX { gx2drr2xFactoryTableIndex }
			 ::= { gx2drr2xFactoryTable  4}

--*****************************************************************************


	      Gx2drr2xAnalogEntry    ::= SEQUENCE  
	       {
		gx2drr2xAnalogTableIndex      INTEGER,
 		
		drr2xlabelRFAAttenuation			DisplayString (SIZE (0..80)),
		drr2xuomRFAAttenuation			DisplayString (SIZE (0..80)),
		drr2xmajorHighRFAAttenuation		Float,
		drr2xmajorLowRFAAttenuation		Float, 
		drr2xminorHighRFAAttenuation		Float,
		drr2xminorLowRFAAttenuation		Float, 
		drr2xcurrentValueRFAAttenuation	Float, 
		drr2xstateFlagRFAAttenuation		INTEGER,
		drr2xminValueRFAAttenuation		Float,
		drr2xmaxValueRFAAttenuation 		Float,
		drr2xalarmStateRFAAttenuation		INTEGER,
		
		drr2xlabelRFBAttenuation			DisplayString (SIZE (0..80)),
		drr2xuomRFBAttenuation			DisplayString (SIZE (0..80)),
		drr2xmajorHighRFBAttenuation		Float, 
		drr2xmajorLowRFBAttenuation		Float, 
		drr2xminorHighRFBAttenuation		Float,
		drr2xminorLowRFBAttenuation		Float, 
		drr2xcurrentValueRFBAttenuation	Float, 
		drr2xstateFlagRFBAttenuation		INTEGER,
		drr2xminValueRFBAttenuation		Float,
		drr2xmaxValueRFBAttenuation 		Float,
		drr2xalarmStateRFBAttenuation		INTEGER,
  
		drr2xlabelTrippointLevel			DisplayString (SIZE (0..80)),
		drr2xuomTrippointLevel			DisplayString (SIZE (0..80)),
		drr2xmajorHighTrippointLevel		Float, 
		drr2xmajorLowTrippointLevel		Float, 
		drr2xminorHighTrippointLevel		Float,
		drr2xminorLowTrippointLevel		Float, 
		drr2xcurrentValueTrippointLevel	Float, 
		drr2xstateFlagTrippointLevel		INTEGER,
		drr2xminValueTrippointLevel		Float,
		drr2xmaxValueTrippointLevel 		Float,
		drr2xalarmStateTrippointLevel  	INTEGER,	
		                   
            drr2xlabelOptCurrent				DisplayString (SIZE (0..80)),
		drr2xuomOptCurrent				DisplayString (SIZE (0..80)),
		drr2xmajorHighOptCurrent			Float, 
		drr2xmajorLowOptCurrent			Float, 
		drr2xminorHighOptCurrent			Float,
		drr2xminorLowOptCurrent			Float, 
		drr2xcurrentValueOptCurrent		Float, 
		drr2xstateFlagOptCurrent			INTEGER,
		drr2xminValueOptCurrent			Float,
		drr2xmaxValueOptCurrent 			Float,
		drr2xalarmStateOptCurrent			INTEGER,
                 
		drr2xlabel12VCurrent				DisplayString (SIZE (0..80)),
		drr2xuom12VCurrent				DisplayString (SIZE (0..80)),
		drr2xmajorHigh12VCurrent			Float, 
		drr2xmajorLow12VCurrent			Float, 
		drr2xminorHigh12VCurrent			Float,
		drr2xminorLow12VCurrent			Float, 
		drr2xcurrentValue12VCurrent		Float, 
		drr2xstateFlag12VCurrent			INTEGER,
		drr2xminValue12VCurrent			Float,
		drr2xmaxValue12VCurrent 			Float,
		drr2xalarmState12VCurrent			INTEGER, 
		
		drr2xlabelModTemp			    	DisplayString (SIZE (0..80)),
		drr2xuomModTemp					DisplayString (SIZE (0..80)),
		drr2xmajorHighModTemp				Float, 
		drr2xmajorLowModTemp				Float, 
		drr2xminorHighModTemp				Float,
		drr2xminorLowModTemp				Float, 
		drr2xcurrentValueModTemp			Float, 
		drr2xstateFlagModTemp				INTEGER,
		drr2xminValueModTemp				Float,
		drr2xmaxValueModTemp				Float,
		drr2xalarmStateModTemp			INTEGER,    
			
		drr2xlabelFanCurrent			DisplayString (SIZE (0..80)),
		drr2xuomFanCurrent			DisplayString (SIZE (0..80)),
		drr2xmajorHighFanCurrent		Float, 
		drr2xmajorLowFanCurrent		Float, 
		drr2xminorHighFanCurrent		Float,
		drr2xminorLowFanCurrent		Float, 
		drr2xcurrentValueFanCurrent	Float, 
		drr2xstateFlagFanCurrent		INTEGER,
		drr2xminValueFanCurrent		Float,
		drr2xmaxValueFanCurrent 		Float,
		drr2xalarmStateFanCurrent		INTEGER
				
		}

		-- ****************  Digital Parameters ***********************
	     Gx2drr2xDigitalEntry    ::= SEQUENCE  
	     {
		gx2drr2xDigitalTableIndex         INTEGER,    
		               
            drr2xlabelTrippointMode   	    DisplayString (SIZE (0..80)),
		drr2xenumTrippointMode		    DisplayString (SIZE (0..80)),
		drr2xvalueTrippointMode		    INTEGER,
		drr2xstateflagTrippointMode       INTEGER,
		    							         
		drr2xlabelFactoryDefaultReset	    DisplayString (SIZE (0..80)),
		drr2xenumFactoryDefaultReset		DisplayString (SIZE (0..80)),
		drr2xvalueFactoryDefaultReset		INTEGER,
		drr2xstateflagFactoryDefaultReset INTEGER                             
	    }

		-- ****************  Status Parameters ************************************
	     Gx2drr2xStatusEntry    ::= SEQUENCE  
	     {
		gx2drr2xStatusTableIndex      INTEGER,

		drr2xlabelBoot				DisplayString (SIZE (0..80)),
		drr2xvalueBoot				INTEGER,
		drr2xstateflagBoot			INTEGER,
		
		drr2xlabelFlash				DisplayString (SIZE (0..80)),
		drr2xvalueFlash				INTEGER,
		drr2xstateflagFlash			INTEGER,

		drr2xlabelFactoryDataCRC 		DisplayString (SIZE (0..80)),
		drr2xvalueFactoryDataCRC		INTEGER,
		drr2xstateflagFactoryDataCRC	INTEGER,

		drr2xlabelAlarmDataCrc		DisplayString (SIZE (0..80)),
		drr2xvalueAlarmDataCrc		INTEGER,
		drr2xstateflagAlarmDataCrc	INTEGER,

		drr2xlabelCalibrationDataCrc		DisplayString (SIZE (0..80)),
		drr2xvalueCalibrationDataCrc		INTEGER,
		drr2xstateflagCalibrationDataCrc	INTEGER,

		drr2xlabelHardwareStatus		DisplayString (SIZE (0..80)),
		drr2xvalueHardwareStatus		INTEGER,
		drr2xstateflagHardwareStatus	INTEGER, 
	
		drr2xlabelOpticTripPointStatus		 DisplayString (SIZE (0..80)),
		drr2xvalueOpticTripPointStatus		 INTEGER,
		drr2xstateflagOpticTripPointStatus	 INTEGER,
			
		drr2xlabelLinkStatus	                 DisplayString (SIZE (0..80)),
		drr2xvalueLinkStatus		             INTEGER,
		drr2xstateflagLinkStatus	             INTEGER     
		}


		-- ****************  Factory Parameters *************************************
       Gx2drr2xFactoryEntry    ::= SEQUENCE  
       {
		gx2drr2xFactoryTableIndex       INTEGER,
		drr2xbootControlByte  			INTEGER,
		drr2xbootStatusByte   			INTEGER,
		drr2xbank1CRC    			        INTEGER,
		drr2xbank2CRC    			        INTEGER,
		drr2xprgEEPROMByte    			INTEGER,
		drr2xfactoryCRC    			    INTEGER,
		drr2xcalculateCRC    				INTEGER,
		drr2xhourMeter    				INTEGER,
		drr2xflashPrgCntA    				INTEGER,
		drr2xflashPrgCntB    				INTEGER,
		drr2xflashBankARev    			DisplayString (SIZE (0..80)),
		drr2xflashBankBRev    			DisplayString (SIZE (0..80)),
		drr2xSubAgentRev					DisplayString (SIZE (0..80))
		}
            -- ************** Analog Parameters ****************************
		gx2drr2xAnalogTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2drr2xAnalogEntry 1}
			   
 -- RFAAttenuation         
        drr2xlabelRFAAttenuation           OBJECT-TYPE
			   SYNTAX           DisplayString (SIZE (0..80))
			   ACCESS           read-only
			   STATUS           optional
			   DESCRIPTION
			   "The value of this object provides the label of the
			    RF Channel A Attenuation Analog parameter."
			   ::= { gx2drr2xAnalogEntry 2}

		drr2xuomRFAAttenuation             OBJECT-TYPE
			   SYNTAX           DisplayString (SIZE (0..80))
			   ACCESS           read-only
			   STATUS           optional
			   DESCRIPTION
			   "The value of this object provides the Unit of Measure of the
			     RF Channel A Attenuation Analog parameter. The unit is in dB"
			   ::= { gx2drr2xAnalogEntry 3}

		drr2xmajorHighRFAAttenuation       OBJECT-TYPE
			   SYNTAX           Float 
			   ACCESS           read-only
			   STATUS           obsolete
			   DESCRIPTION
			   "This object is not used by this module and always returns invalid float value
			    of 0xFFFFFFFF . It is kept here for persistence."
			   ::= { gx2drr2xAnalogEntry 4}

		drr2xmajorLowRFAAttenuation        OBJECT-TYPE
			   SYNTAX           Float 
			   ACCESS           read-only
			   STATUS           obsolete
			   DESCRIPTION
			    "This object is not used by this module and always returns invalid float value
			    of 0xFFFFFFFF . It is kept here for persistence."
			   ::= { gx2drr2xAnalogEntry 5}

		drr2xminorHighRFAAttenuation       OBJECT-TYPE
			   SYNTAX           Float
			   ACCESS           read-only
			   STATUS           obsolete
			   DESCRIPTION
			    "This object is not used by this module and always returns invalid float value
			    of 0xFFFFFFFF . It is kept here for persistence."
			   ::= { gx2drr2xAnalogEntry 6}

		drr2xminorLowRFAAttenuation        OBJECT-TYPE
			   SYNTAX           Float 
			   ACCESS           read-only
			   STATUS           obsolete
			   DESCRIPTION
			    "This object is not used by this module and always returns invalid float value
			    of 0xFFFFFFFF . It is kept here for persistence."
			   ::= { gx2drr2xAnalogEntry 7}

		drr2xcurrentValueRFAAttenuation    OBJECT-TYPE
			   SYNTAX           Float 
			   ACCESS           read-write
			   STATUS           mandatory
			   DESCRIPTION
			   "The value of this object provides the Current value
			    of the RF Channel A Attenuation Analog parameter." 
			   ::= { gx2drr2xAnalogEntry 8}

		drr2xstateFlagRFAAttenuation       OBJECT-TYPE
			   SYNTAX           INTEGER
								{
								hidden(1),
								read-only(2),
								updateable(3)
								}
			   ACCESS           read-only
			   STATUS           mandatory
			   DESCRIPTION
			   "The value of this object provides the state
			    of the RF Channel A Attenuation Analog parameter. (1-hidden	
			          2-read-only, 3-updateable)."
			   ::= { gx2drr2xAnalogEntry 9}

		drr2xminValueRFAAttenuation        OBJECT-TYPE
			   SYNTAX           Float
			   ACCESS           read-only
			   STATUS           mandatory
			   DESCRIPTION
			   "The value of this object provides the minimum value
			    the RF Channel A Attenuation Analog parameter can achive."
			    ::= { gx2drr2xAnalogEntry 10}

		drr2xmaxValueRFAAttenuation        OBJECT-TYPE
			   SYNTAX           Float
			   ACCESS           read-only
			   STATUS           mandatory
			   DESCRIPTION
			   "The value of this object provides the maximum value
			    the RF Channel A Attenuation Analog parameter can achive."
			   ::= { gx2drr2xAnalogEntry 11}

        drr2xalarmStateRFAAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel A Attenuation Analog parameter."
			   ::= { gx2drr2xAnalogEntry 12}
			   
			   
-- 	RFBAttenuation		         
       
          		drr2xlabelRFBAttenuation           OBJECT-TYPE
			   SYNTAX           DisplayString (SIZE (0..80))
			   ACCESS           read-only
			   STATUS           optional
			   DESCRIPTION
			   "The value of this object provides the label of the
			    RF Channel B Attenuation Analog parameter."
			   ::= { gx2drr2xAnalogEntry 13}

		drr2xuomRFBAttenuation             OBJECT-TYPE
			   SYNTAX           DisplayString (SIZE (0..80))
			   ACCESS           read-only
			   STATUS           optional
			   DESCRIPTION
			   "The value of this object provides the Unit of Measure of the
			     RF Channel B Attenuation Analog parameter."
			   ::= { gx2drr2xAnalogEntry 14}

		drr2xmajorHighRFBAttenuation       OBJECT-TYPE
			   SYNTAX           Float 
			   ACCESS           read-only
			   STATUS           obsolete
			   DESCRIPTION
			 "This object is not used by this module and always returns invalid float value
			    of 0xFFFFFFFF . It is kept here for persistence."
			   ::= { gx2drr2xAnalogEntry 15}

		drr2xmajorLowRFBAttenuation        OBJECT-TYPE
			   SYNTAX           Float 
			   ACCESS           read-only
			   STATUS           obsolete
			   DESCRIPTION
			   "This object is not used by this module and always returns invalid float value
			    of 0xFFFFFFFF . It is kept here for persistence."

			   ::= { gx2drr2xAnalogEntry 16}

		drr2xminorHighRFBAttenuation       OBJECT-TYPE
			   SYNTAX           Float
			   ACCESS           read-only
			   STATUS           obsolete
			   DESCRIPTION
			   "This object is not used by this module and always returns invalid float value
			    of 0xFFFFFFFF . It is kept here for persistence."
			   ::= { gx2drr2xAnalogEntry 17}

		drr2xminorLowRFBAttenuation        OBJECT-TYPE
			   SYNTAX           Float 
			   ACCESS           read-only
			   STATUS           obsolete
			   DESCRIPTION
			    "This object is not used by this module and always returns invalid float value
			    of 0xFFFFFFFF. It is kept here for persistence."
			   ::= { gx2drr2xAnalogEntry 18}

		drr2xcurrentValueRFBAttenuation    OBJECT-TYPE
			   SYNTAX           Float 
			   ACCESS           read-write
			   STATUS           mandatory
			   DESCRIPTION
			   "The value of this object provides the Current value
			    of the RF Channel B Attenuation Analog parameter. The unit is dB "              
			   ::= { gx2drr2xAnalogEntry 19}

		drr2xstateFlagRFBAttenuation       OBJECT-TYPE
			   SYNTAX           INTEGER
								{
								hidden(1),
								read-only(2),
								updateable(3)
								}
			   ACCESS           read-only
			   STATUS           mandatory
			   DESCRIPTION
			   "The value of this object provides the state
			    of the RF Channel B Attenuation Analog parameter. (1-hidden	
			          2-read-only, 3-updateable)."
			   ::= { gx2drr2xAnalogEntry 20}

		drr2xminValueRFBAttenuation        OBJECT-TYPE
			   SYNTAX           Float
			   ACCESS           read-only
			   STATUS           mandatory
			   DESCRIPTION
			   "The value of this object provides the minimum value
			    the RF Channel B Attenuation Analog parameter can achive."
			   ::= { gx2drr2xAnalogEntry 21}

		drr2xmaxValueRFBAttenuation        OBJECT-TYPE
			   SYNTAX           Float
			   ACCESS           read-only
			   STATUS           mandatory
			   DESCRIPTION
			   "The value of this object provides the maximum value
			    the RF Channel B Attenuation Analog parameter can achive."
			   ::= { gx2drr2xAnalogEntry 22}

        drr2xalarmStateRFBAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel B Attenuation Analog parameter."
			   ::= { gx2drr2xAnalogEntry 23}
                            			   
-- 	TrippointLevel	          
        drr2xlabelTrippointLevel           OBJECT-TYPE
			   SYNTAX           DisplayString (SIZE (0..80))
			   ACCESS           read-only
			   STATUS           optional
			   DESCRIPTION
			   "The value of this object provides the label of the
			    trip point level Analog parameter."
			   ::= { gx2drr2xAnalogEntry 24}

		drr2xuomTrippointLevel             OBJECT-TYPE
			   SYNTAX           DisplayString (SIZE (0..80))
			   ACCESS           read-only
			   STATUS           optional
			   DESCRIPTION
			   "The value of this object provides the Unit of Measure of the
			     trip point level Analog parameter."
			   ::= { gx2drr2xAnalogEntry 25}

		drr2xmajorHighTrippointLevel       OBJECT-TYPE
			   SYNTAX           Float 
			   ACCESS           read-only
			   STATUS           obsolete
			   DESCRIPTION
			      "This object is not used by this module and always returns invalid float value
			    of 0xFFFFFFFF . It is kept here for persistence."
			   ::= { gx2drr2xAnalogEntry 26}

		drr2xmajorLowTrippointLevel        OBJECT-TYPE
			   SYNTAX           Float 
			   ACCESS           read-only
			   STATUS           obsolete
			   DESCRIPTION
			      "This object is not used by this module and always returns invalid float value
			    of 0xFFFFFFFF . It is kept here for persistence."
			   ::= { gx2drr2xAnalogEntry 27}

		drr2xminorHighTrippointLevel       OBJECT-TYPE
			   SYNTAX           Float
			   ACCESS           read-only
			   STATUS           obsolete
			   DESCRIPTION
			      "This object is not used by this module and always returns invalid float value
			    of 0xFFFFFFFF . It is kept here for persistence."
			   ::= { gx2drr2xAnalogEntry 28}

		drr2xminorLowTrippointLevel        OBJECT-TYPE
			   SYNTAX           Float 
			   ACCESS           read-only
			   STATUS           obsolete
			   DESCRIPTION
			      "This object is not used by this module and always returns invalid float value
			    of 0xFFFFFFFF . It is kept here for persistence."
			   ::= { gx2drr2xAnalogEntry 29}

		drr2xcurrentValueTrippointLevel    OBJECT-TYPE
			   SYNTAX           Float 
			   ACCESS           read-write
			   STATUS           mandatory
			   DESCRIPTION
			   "The value of this object provides the Current value of the trip point level Analog parameter. The trip point level set the custumer preferred 
                      optical input level.
                This parameter combined with trippoint mode decides the trippoint alarm and RF channel output impedance.
                      
                when optical power level is lower than trip point level(Set by this parameter)
                    1) When trip point mode is ALARM_SWITCH,  trip point alarm will be generated and RF output 
                      impedance will be changed to high impedance.
                    2) When trippoint mode is ALARM_ONLY, trippoint alarm will be generated but RF output inpedance 
                      remains to be low impedance.    
			   This trip point level value is a floating point number that is represented as an IEEE 32 bit number."
			   ::= { gx2drr2xAnalogEntry 30}

		drr2xstateFlagTrippointLevel       OBJECT-TYPE
			   SYNTAX           INTEGER
								{
								hidden(1),
								read-only(2),
								updateable(3)
								}
			   ACCESS           read-only
			   STATUS           mandatory
			   DESCRIPTION
			   "The value of this object provides the state
			    of the trip point level Analog parameter. (1-hidden
			          2-read-only, 3-updateable)."
			   ::= { gx2drr2xAnalogEntry 31}

		drr2xminValueTrippointLevel        OBJECT-TYPE
			   SYNTAX           Float
			   ACCESS           read-only
			   STATUS           mandatory
			   DESCRIPTION
			   "The value of this object provides the minimum value
			    the trip point level Analog parameter can achive." 
			   ::= { gx2drr2xAnalogEntry 32}

		drr2xmaxValueTrippointLevel        OBJECT-TYPE
			   SYNTAX           Float
			   ACCESS           read-only
			   STATUS           mandatory
			   DESCRIPTION
			   "The value of this object provides the maximum value
			    the trip point level Analog parameter can achive."
			   ::= { gx2drr2xAnalogEntry 33}

        drr2xalarmStateTrippointLevel      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the trip point level Analog parameter."
			   ::= { gx2drr2xAnalogEntry 34}
			               
-- Optical power 
	    drr2xlabelOptCurrent           OBJECT-TYPE
			   SYNTAX           DisplayString (SIZE (0..80))
			   ACCESS           read-only
			   STATUS           optional
			   DESCRIPTION
			   "The value of this object provides the label of the
			    Optical Power Current Analog parameter."
			   ::= { gx2drr2xAnalogEntry 35}

		drr2xuomOptCurrent             OBJECT-TYPE
			   SYNTAX           DisplayString (SIZE (0..80))
			   ACCESS           read-only
			   STATUS           optional
			   DESCRIPTION
			   "The value of this object provides the Unit of Measure of the
			    Optical Power Current Analog parameter."
			   ::= { gx2drr2xAnalogEntry 36}

		drr2xmajorHighOptCurrent       OBJECT-TYPE
			   SYNTAX           Float 
			   ACCESS           read-only
			   STATUS           mandatory
			   DESCRIPTION
			   "The value of this object provides the Major High alarm value
			    of the Optical Power Current Analog parameter."
			   ::= { gx2drr2xAnalogEntry 37}


		drr2xmajorLowOptCurrent        OBJECT-TYPE
			   SYNTAX           Float 
			   ACCESS           read-only
			   STATUS           mandatory
			   DESCRIPTION
			   "The value of this object provides the Major Low alarm value
			    of the Optical Power Current Analog parameter."
			   ::= { gx2drr2xAnalogEntry 38}

		drr2xminorHighOptCurrent       OBJECT-TYPE
			   SYNTAX           Float
			   ACCESS           read-only
			   STATUS           obsolete
			   DESCRIPTION
			    "This object is not used by this module and always returns invalid float value
			    of 0xFFFFFFFF . It is kept here for persistence."
			   ::= { gx2drr2xAnalogEntry 39}

		drr2xminorLowOptCurrent        OBJECT-TYPE
			   SYNTAX           Float 
			   ACCESS           read-only
			   STATUS           obsolete
			   DESCRIPTION
			   "This object is not used by this module and always returns invalid float value
			    of 0xFFFFFFFF . It is kept here for persistence."
			   ::= { gx2drr2xAnalogEntry 40}

		drr2xcurrentValueOptCurrent    OBJECT-TYPE
			   SYNTAX           Float 
			   ACCESS           read-only
			   STATUS           mandatory
			   DESCRIPTION
			   "The value of this object provides the Current value
			    of the Optical Power Current Analog parameter.

			   The input optical power in lower than min value, 
			   drr2xcurrentValueOptCurrent will report -99dBm

 			   The input optical power in higher than this value, 
			   drr2xcurrentValueOptCurrent will report 99dBm"
			   ::= { gx2drr2xAnalogEntry 41}

		drr2xstateFlagOptCurrent       OBJECT-TYPE
			   SYNTAX           INTEGER
								{
								hidden(1),
								read-only(2),
								updateable(3)
								}
			   ACCESS           read-only
			   STATUS           mandatory
			   DESCRIPTION
			   "The value of this object provides the state
			    of the Optical Power Current Analog parameter. (1-hidden	
			          2-read-only, 3-updateable)."
			   ::= { gx2drr2xAnalogEntry 42}

		drr2xminValueOptCurrent        OBJECT-TYPE
			   SYNTAX           Float
			   ACCESS           read-only
			   STATUS           mandatory
			   DESCRIPTION
			   "This is recommended min range for display gauge"			 
			   ::= { gx2drr2xAnalogEntry 43}

		drr2xmaxValueOptCurrent        OBJECT-TYPE
			   SYNTAX           Float
			   ACCESS           read-only
			   STATUS           mandatory
			   DESCRIPTION
			   "This is recommended max range for display gauge"			  
			   ::= { gx2drr2xAnalogEntry 44}

        drr2xalarmStateOptCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Current Analog parameter."
			   ::= { gx2drr2xAnalogEntry 45}
			   
-- 12V current 
    	drr2xlabel12VCurrent           OBJECT-TYPE
			   SYNTAX           DisplayString (SIZE (0..80))
			   ACCESS           read-only
			   STATUS           optional
			   DESCRIPTION
			   "The value of this object provides the label of the
			    12v power supply Current Analog parameter."
			   ::= { gx2drr2xAnalogEntry 46}

		drr2xuom12VCurrent             OBJECT-TYPE
			   SYNTAX           DisplayString (SIZE (0..80))
			   ACCESS           read-only
			   STATUS           optional
			   DESCRIPTION
			   "The value of this object provides the Unit of Measure of the
			    12v power supply Current Analog parameter."
			   ::= { gx2drr2xAnalogEntry 47}

		drr2xmajorHigh12VCurrent       OBJECT-TYPE
			   SYNTAX           Float 
			   ACCESS           read-only
			   STATUS           mandatory
			   DESCRIPTION
			   "The value of this object provides the Major High alarm value
			    of the 12v power supply Current Analog parameter."
			   ::= { gx2drr2xAnalogEntry 48}


		drr2xmajorLow12VCurrent        OBJECT-TYPE
			   SYNTAX           Float 
			   ACCESS           read-only
			   STATUS           mandatory
			   DESCRIPTION
			   "The value of this object provides the Major Low alarm value
			    of the 12v power supply Current Analog parameter."
			   ::= { gx2drr2xAnalogEntry 49}

		drr2xminorHigh12VCurrent       OBJECT-TYPE
			   SYNTAX           Float
			   ACCESS           read-only
			   STATUS           mandatory
			   DESCRIPTION
			   "The value of this object provides the Minor High alarm value
			    of the 12v power supply Current Analog parameter."
			   ::= { gx2drr2xAnalogEntry 50}

		drr2xminorLow12VCurrent        OBJECT-TYPE
			   SYNTAX           Float 
			   ACCESS           read-only
			   STATUS           mandatory
			   DESCRIPTION
			   "The value of this object provides the Minor Low alarm value
			    of the 12v power supply Current Analog parameter."
			   ::= { gx2drr2xAnalogEntry 51}

		drr2xcurrentValue12VCurrent    OBJECT-TYPE
			   SYNTAX           Float 
			   ACCESS           read-only
			   STATUS           mandatory
			   DESCRIPTION
			   "The value of this object provides the Current value
			    of the 12v power supply Current parameter."
			   ::= { gx2drr2xAnalogEntry 52}

		drr2xstateFlag12VCurrent       OBJECT-TYPE
			   SYNTAX           INTEGER
								{
								hidden(1),
								read-only(2),
								updateable(3)
								}
			   ACCESS           read-only
			   STATUS           mandatory
			   DESCRIPTION
			   "The value of this object provides the state
			    of the 12v power supply Current Analog parameter. (1-hidden	
			          2-read-only, 3-updateable)."
			   ::= { gx2drr2xAnalogEntry 53}

		drr2xminValue12VCurrent        OBJECT-TYPE
			   SYNTAX           Float
			   ACCESS           read-only
			   STATUS           mandatory
			   DESCRIPTION
			   "The value of this object provides the minimum value
			    the 12v power supply Current Analog parameter can achive."
			   ::= { gx2drr2xAnalogEntry 54}

		drr2xmaxValue12VCurrent        OBJECT-TYPE
			   SYNTAX           Float
			   ACCESS           read-only
			   STATUS           mandatory
			   DESCRIPTION
			   "The value of this object provides the maximum value
			    the 12v power supply Current Analog parameter can achive."
			   ::= { gx2drr2xAnalogEntry 55}

        drr2xalarmState12VCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v power supply Current Analog parameter."
			   ::= { gx2drr2xAnalogEntry 56}
			   
-- Module Temperature 

		drr2xlabelModTemp              OBJECT-TYPE
			   SYNTAX           DisplayString (SIZE (0..80))
			   ACCESS           read-only
			   STATUS           optional
			   DESCRIPTION
			   "The value of this object provides the label of the
			    Module Temperature Analog parameter."
			   ::= { gx2drr2xAnalogEntry 57}

		drr2xuomModTemp                OBJECT-TYPE
			   SYNTAX           DisplayString (SIZE (0..80))
			   ACCESS           read-only
			   STATUS           optional
			   DESCRIPTION
			   "The value of this object provides the Unit of Measure of the
			    Module Temperature Analog parameter."
			   ::= { gx2drr2xAnalogEntry 58}

		drr2xmajorHighModTemp          OBJECT-TYPE
			   SYNTAX           Float 
			   ACCESS           read-only
			   STATUS           mandatory
			   DESCRIPTION
			   "The value of this object provides the Major High alarm value
			    of the Module Temperature Analog parameter."
			   ::= { gx2drr2xAnalogEntry 59}


		drr2xmajorLowModTemp           OBJECT-TYPE
			   SYNTAX           Float 
			   ACCESS           read-only
			   STATUS           mandatory
			   DESCRIPTION
			   "The value of this object provides the Major Low alarm value
			    of the Module Temperature Analog parameter."
			     ::= { gx2drr2xAnalogEntry 60}

		drr2xminorHighModTemp          OBJECT-TYPE
			   SYNTAX           Float
			   ACCESS           read-only
			   STATUS           mandatory
			   DESCRIPTION
			   "The value of this object provides the Minor High alarm value
			    of the Module Temperature Analog parameter."
			    ::= { gx2drr2xAnalogEntry 61}

		drr2xminorLowModTemp           OBJECT-TYPE
			   SYNTAX           Float 
			   ACCESS           read-only
			   STATUS           mandatory
			   DESCRIPTION
			   "The value of this object provides the Minor Low alarm value
			    of the Module Temperature Analog parameter."
			    ::= { gx2drr2xAnalogEntry 62}

		drr2xcurrentValueModTemp       OBJECT-TYPE
			   SYNTAX           Float 
			   ACCESS           read-only
			   STATUS           mandatory
			   DESCRIPTION
			   "The value of this object provides the Current value
			    of the Module Temperature Analog parameter."
			   ::= { gx2drr2xAnalogEntry 63}

		drr2xstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (1-hidden	
			          2-read-only, 3-updateable)."
			   ::= { gx2drr2xAnalogEntry 64}

		drr2xminValueModTemp           OBJECT-TYPE
			   SYNTAX           Float
			   ACCESS           read-only
			   STATUS           mandatory
			   DESCRIPTION
			   "The value of this object provides the minimum value
			    the Module Temperature Analog parameter can achive."
			    ::= { gx2drr2xAnalogEntry 65}

		drr2xmaxValueModTemp           OBJECT-TYPE
			   SYNTAX           Float
			   ACCESS           read-only
			   STATUS           mandatory
			   DESCRIPTION
			   "The value of this object provides the maximum value
			    the Module Temperature Analog parameter can achive."
			   ::= { gx2drr2xAnalogEntry 66}

		drr2xalarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2drr2xAnalogEntry 67}
			     
			   
-- Fan current 
		drr2xlabelFanCurrent           OBJECT-TYPE
			   SYNTAX           DisplayString (SIZE (0..80))
			   ACCESS           read-only
			   STATUS           optional
			   DESCRIPTION
			   "The value of this object provides the label of the
			    Fan Current Analog parameter."
			   ::= { gx2drr2xAnalogEntry 68}

		drr2xuomFanCurrent             OBJECT-TYPE
			   SYNTAX           DisplayString (SIZE (0..80))
			   ACCESS           read-only
			   STATUS           optional
			   DESCRIPTION
			   "The value of this object provides the Unit of Measure of the
			    Fan Current Analog parameter."
			   ::= { gx2drr2xAnalogEntry 69}

		drr2xmajorHighFanCurrent       OBJECT-TYPE
			   SYNTAX           Float 
			   ACCESS           read-only
			   STATUS           mandatory
			   DESCRIPTION
			   "The value of this object provides the Major High alarm value
			    of the Fan Current Analog parameter."
			   ::= { gx2drr2xAnalogEntry 70}


		drr2xmajorLowFanCurrent        OBJECT-TYPE
			   SYNTAX           Float 
			   ACCESS           read-only
			   STATUS           mandatory
			   DESCRIPTION
			   "The value of this object provides the Major Low alarm value
			    of the Fan Current Analog parameter."
			   ::= { gx2drr2xAnalogEntry 71}

		drr2xminorHighFanCurrent       OBJECT-TYPE
			   SYNTAX           Float
			   ACCESS           read-only
			   STATUS           obsolete
			   DESCRIPTION
			   "This object is not used by this module and always returns invalid float value
			    of 0xFFFFFFFF . It is kept here for persistence."
			   ::= { gx2drr2xAnalogEntry 72}

		drr2xminorLowFanCurrent        OBJECT-TYPE
			   SYNTAX           Float 
			   ACCESS           read-only
			   STATUS           obsolete
			   DESCRIPTION
			   "This object is not used by this module and always returns invalid float value
			    of 0xFFFFFFFF . It is kept here for persistence."
			   ::= { gx2drr2xAnalogEntry 73}

		drr2xcurrentValueFanCurrent    OBJECT-TYPE
			   SYNTAX           Float 
			   ACCESS           read-only
			   STATUS           mandatory
			   DESCRIPTION
			   "The value of this object provides the Current value
			    of the Fan Current Analog parameter."
			   ::= { gx2drr2xAnalogEntry 74}

		drr2xstateFlagFanCurrent       OBJECT-TYPE
			   SYNTAX           INTEGER
								{
								hidden(1),
								read-only(2),
								updateable(3)
								}
			   ACCESS           read-only
			   STATUS           mandatory
			   DESCRIPTION
			   "The value of this object provides the state
			    of the Module Temperature Analog parameter. (1-hidden	
			          2-read-only, 3-updateable)."
			   ::= { gx2drr2xAnalogEntry 75}

		drr2xminValueFanCurrent        OBJECT-TYPE
			   SYNTAX           Float
			   ACCESS           read-only
			   STATUS           mandatory
			   DESCRIPTION
			   "The value of this object provides the minimum value
			    the Fan Current Analog parameter can achive."
			   ::= { gx2drr2xAnalogEntry 76}

		drr2xmaxValueFanCurrent        OBJECT-TYPE
			   SYNTAX           Float
			   ACCESS           read-only
			   STATUS           mandatory
			   DESCRIPTION
			   "The value of this object provides the maximum value
			    the Fan Current Analog parameter can achive."
			   ::= { gx2drr2xAnalogEntry 77}

        drr2xalarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2drr2xAnalogEntry 78}  
			   
    			   
-- ************************ Digital parameters **********************************
		gx2drr2xDigitalTableIndex              OBJECT-TYPE
			   SYNTAX           INTEGER (1..2147483647)
			   ACCESS           read-only
			   STATUS           mandatory
			   DESCRIPTION
			   "The value of this object identifies the network
			    element. This index is equal to the
			    hfcCommonTableIndex for the same element."
               ::= { gx2drr2xDigitalEntry 1}
               
   -- Trip point mode   
         drr2xlabelTrippointMode          OBJECT-TYPE
			   SYNTAX       		DisplayString (SIZE (0..80))         
			   ACCESS           	read-only
			   STATUS           	optional
			   DESCRIPTION
			   "The value of this object provides the label of the
			    Trip point mode Digital parameter. The trip point mode defines the RF switch 
                      action based on the optical power input to the DRR"
			   ::= { gx2drr2xDigitalEntry 2}

		drr2xenumTrippointMode               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2drr2xDigitalEntry 3}


		drr2xvalueTrippointMode         	OBJECT-TYPE
			   SYNTAX					INTEGER{
			   							off(1),
			   							alarmOnly(2),
			   							alarm-and-Switch(3)
			   							}			   					    	
			   ACCESS           	read-write
			   STATUS           	mandatory
			   DESCRIPTION
			   "The value of this object is the current value of trip point mode.
			   There are three possible value: 1-off, 2-alarm_only, 3-alarm&switch.
			   			   
			   If module input optical power is higher than the preset trippoint value,
			        no operational difference for these three modes. 
			   
			   If module input optical power is less than the preset trippoint value, 
                     1) When trippoint mode is OFF, no trippoint alarm will be generated and RF output impedance 
                     will stay normal as low.
                     2) When tripoint mode is ALARM_ONLY, trip_point alarm will be generated when the input optical power 
                     lower than the preset trippoint level but RF output impedance will stay normal as low. 
                     3) When trippoint mode is ALARM_SWITCH, trip point alarm will be generated and RF output impedance 
                     will switch to abnorml"
			   ::= { gx2drr2xDigitalEntry 4}

		drr2xstateflagTrippointMode     	OBJECT-TYPE
			   SYNTAX       		INTEGER
								{
								hidden(1),
								readOnly(2),
								updateable(3)
								}
			   ACCESS           	read-only
			   STATUS           	mandatory
			   DESCRIPTION
			   "The value of this object provides the state
			    of the the parameter. (1-Hidden 2-Read-Only, 3-Updateable)."
			   ::= { gx2drr2xDigitalEntry 5}
			   		   		   		   
-- Factory default reset 
         drr2xlabelFactoryDefaultReset           OBJECT-TYPE
			   SYNTAX       		DisplayString (SIZE (0..80))         
			   ACCESS           	read-only
			   STATUS           	optional
			   DESCRIPTION
			   "The value of this object provides the label of the
			    Factory Default Reset  Digital parameter."
			   ::= { gx2drr2xDigitalEntry 6}

		drr2xenumFactoryDefaultReset               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2drr2xDigitalEntry 7}


		drr2xvalueFactoryDefaultReset         	OBJECT-TYPE
			   SYNTAX       		INTEGER
					    		{
							off(1),
							on(2)
					    		}
			   ACCESS           	read-write
			   STATUS           	mandatory
			   DESCRIPTION
			   "The read of this value will return a invalid value.
			    The read will not reflect the actual setting value for this parameter
			   "
			   ::= { gx2drr2xDigitalEntry 8}

		drr2xstateflagFactoryDefaultReset     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr2xDigitalEntry 9} 
			   
   
 	--*********** STATUS *****************
		gx2drr2xStatusTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2drr2xStatusEntry 1}

--Boot status 
		drr2xlabelBoot               	OBJECT-TYPE
			   SYNTAX       		DisplayString (SIZE (0..80))         
			   ACCESS           	read-only
			   STATUS           	optional
			   DESCRIPTION
			   "The value of this object provides the label of the
			    Boot Status  parameter."
			   ::= { gx2drr2xStatusEntry 2}

		drr2xvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr2xStatusEntry 3}

		drr2xstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr2xStatusEntry  4}

--Flash program status 
		drr2xlabelFlash               	OBJECT-TYPE
			   SYNTAX       		DisplayString (SIZE (0..80))         
			   ACCESS           	read-only
			   STATUS           	optional
			   DESCRIPTION
			   "The value of this object provides the label of the
			    Flash Status  parameter."
			   ::= { gx2drr2xStatusEntry 5}

		drr2xvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr2xStatusEntry 6}

		drr2xstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr2xStatusEntry  7}

--Factory data crc 
		drr2xlabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2drr2xStatusEntry 8}

		drr2xvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr2xStatusEntry 9}

		drr2xstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr2xStatusEntry  10}

--Alarm data status CRC
		drr2xlabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2drr2xStatusEntry 11}

		drr2xvalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr2xStatusEntry 12}

		drr2xstateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr2xStatusEntry  13}

--Calibration data status CRC
		drr2xlabelCalibrationDataCrc               	      OBJECT-TYPE
			   SYNTAX       		DisplayString (SIZE (0..80))         
			   ACCESS           	read-only
			   STATUS           	optional
			   DESCRIPTION
			   "The value of this object provides the label of the
			    Calibration Data Crc parameter."
			   ::= { gx2drr2xStatusEntry 14}

		drr2xvalueCalibrationDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr2xStatusEntry 15}

		drr2xstateflagCalibrationDataCrc     	OBJECT-TYPE
			   SYNTAX       		INTEGER
								{
								hidden(1),
								read-only(2),
								updateable(3)
								}
			   ACCESS           	read-only
			   STATUS           	mandatory
			   DESCRIPTION
			   "The value of this object provides the state
			    of the the parameter. (1-Hidden 2-Read-Only, 3-Updateable)."
			   ::= { gx2drr2xStatusEntry  16}



--Module hardware status
		drr2xlabelHardwareStatus              OBJECT-TYPE
			   SYNTAX       		DisplayString (SIZE (0..80))         
			   ACCESS           	read-only
			   STATUS           	optional
			   DESCRIPTION
			   "The value of this object provides the label of the
			   Module Hardware Status parameter."
			   ::= { gx2drr2xStatusEntry 17}

		drr2xvalueHardwareStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr2xStatusEntry 18}

		drr2xstateflagHardwareStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2drr2xStatusEntry  19}
                            
  --Optical signal trip point status 
		drr2xlabelOpticTripPointStatus              OBJECT-TYPE
			   SYNTAX       		DisplayString (SIZE (0..80))         
			   ACCESS           	read-only
			   STATUS           	optional
			   DESCRIPTION
			   "The value of this object provides the label of the
			    Optical Trip Point Status parameter.It indicates whether 
			    the optical power is above(0) or below(1) trip point value"
			   ::= { gx2drr2xStatusEntry 20}

		drr2xvalueOpticTripPointStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr2xStatusEntry 21}

		drr2xstateflagOpticTripPointStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2drr2xStatusEntry  22}
    
                                        
         --Link Status 
		drr2xlabelLinkStatus              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2drr2xStatusEntry 23}

		drr2xvalueLinkStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (1-Ok, 2-Undetermined
			    3-Warning, 4-Minor, 5-Major, 6-Critical)."
			   ::= { gx2drr2xStatusEntry 24}

		drr2xstateflagLinkStatus     	OBJECT-TYPE
			   SYNTAX       		INTEGER
								{
								hidden(1),
								read-only(2),
								updateable(3)
								}
			   ACCESS           	read-only
			   STATUS           	mandatory
			   DESCRIPTION
			   "The value of this object provides the state
			    of the parameter. (1-Hidden 2-Read-Only, 3-Updateable)."
			   ::= { gx2drr2xStatusEntry  25}
                          
                                       
-- ************ FACTORY DATA ****************
		gx2drr2xFactoryTableIndex              OBJECT-TYPE
			   SYNTAX           INTEGER (1..2147483647)
			   ACCESS           read-only
			   STATUS           mandatory
			   DESCRIPTION
			   "The value of this object identifies the network
			    element. This index is equal to the
			    hfcCommonTableIndex for the same element."
			   ::= { gx2drr2xFactoryEntry 1}

		drr2xbootControlByte          	OBJECT-TYPE
			   SYNTAX       		INTEGER
			   ACCESS           	read-only
			   STATUS           	mandatory
			   DESCRIPTION
			   "The value of this object indicates which bank the firmware
			    is currently being boot from."
			   ::= { gx2drr2xFactoryEntry 2}

		drr2xbootStatusByte          	OBJECT-TYPE
			   SYNTAX       		INTEGER
			   ACCESS           	read-only
			   STATUS           	mandatory
			   DESCRIPTION
			   "This object indicates the status of the last boot"
			   ::= { gx2drr2xFactoryEntry 3}

		drr2xbank1CRC          		OBJECT-TYPE
			   SYNTAX       		INTEGER
			   ACCESS           	read-only
			   STATUS           	mandatory
			   DESCRIPTION
			   "This object provides the CRC code of bank 0."
			   ::= { gx2drr2xFactoryEntry 4}

		drr2xbank2CRC          		OBJECT-TYPE
			   SYNTAX       		INTEGER
			   ACCESS           	read-only
			   STATUS           	mandatory
			   DESCRIPTION
			   "This object provides the CRC code of bank 1."
			   ::= { gx2drr2xFactoryEntry 5}

		drr2xprgEEPROMByte          		OBJECT-TYPE
			   SYNTAX       		INTEGER
			   ACCESS           	read-only
			   STATUS           	mandatory
			   DESCRIPTION
			   "This object indicates if the EEPROM has been programmed"
			   ::= { gx2drr2xFactoryEntry 6}

		drr2xfactoryCRC          		OBJECT-TYPE
			   SYNTAX       		INTEGER
			   ACCESS           	read-only
			   STATUS           	mandatory
			   DESCRIPTION
			   "This object provides the CRC code for the Factory data."
			   ::= { gx2drr2xFactoryEntry 7}

		drr2xcalculateCRC          		OBJECT-TYPE
			   SYNTAX       		INTEGER
					    		{
							factory(1),
							alarm(2),
							calibration(3)
					    		}
			   ACCESS           	read-only
			   STATUS           	mandatory
			   DESCRIPTION
			   "This object indicates which of the Emnums will have the
                      CRC calculated (1-factory, 2-alarm, 3-calibration)."
			   ::= { gx2drr2xFactoryEntry 8}

		drr2xhourMeter          		OBJECT-TYPE
			   SYNTAX       		INTEGER
			   ACCESS           	read-only
			   STATUS           	mandatory
			   DESCRIPTION
			   "This object provides the hour meter reading of the module."
			   ::= { gx2drr2xFactoryEntry 9}

		drr2xflashPrgCntA          		OBJECT-TYPE
			   SYNTAX       		INTEGER
			   ACCESS           	read-only
			   STATUS           	mandatory
			   DESCRIPTION
			   "This object provides the number of times Bank 0 flash has been 
                      programmed."
			   ::= { gx2drr2xFactoryEntry 10}

		drr2xflashPrgCntB          		OBJECT-TYPE
			   SYNTAX       		INTEGER
			   ACCESS           	read-only
			   STATUS           	mandatory
			   DESCRIPTION
			   "This object provides the number of times Bank 1 flash has been 
                      programmed."
			   ::= { gx2drr2xFactoryEntry 11}

		drr2xflashBankARev          		OBJECT-TYPE
			   SYNTAX       		DisplayString (SIZE (0..80))
			   ACCESS           	read-only
			   STATUS           	mandatory
			   DESCRIPTION
			   "This object provides the revision of flash bank 0."
			   ::= { gx2drr2xFactoryEntry 12}

		drr2xflashBankBRev          		OBJECT-TYPE
			   SYNTAX       		DisplayString (SIZE (0..80))
			   ACCESS           	read-only
			   STATUS           	mandatory
			   DESCRIPTION
			   "This object provides the revision of flash bank 1."
			   ::= { gx2drr2xFactoryEntry 13}
                  
		drr2xSubAgentRev          		OBJECT-TYPE
			   SYNTAX       		DisplayString (SIZE (0..80))
			   ACCESS           	read-only
			   STATUS           	mandatory
			   DESCRIPTION
			   "This object provides the subagent revision of receiver module."
			   ::= { gx2drr2xFactoryEntry 14}

-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

-- **************************************************************************
--                              Digital Receiver Return Module traps
-- **************************************************************************
   trapdrrConfigChangeInteger TRAP-TYPE
       ENTERPRISE gx2Drr2x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapdrrConfigChangeDisplayString TRAP-TYPE
       ENTERPRISE gx2Drr2x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
        
   trapdrr12VCurrentAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the 12V power supply Current 
	 parameter goes out of range.
	 trapAdditionalInfoInteger variable contains current reading of 
	 the this parameter."
     ::= 3       
          
  trapdrrModuleTempAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Internal Module Temperature goes out of range.
	 trapAdditionalInfoInteger variable contains current reading of 
	 the this parameter."
    ::= 4
  
    trapdrrFanCurrentAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 5

  trapdrrFlashAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error during
	Flash memory operations."
  ::= 6
  
  trapdrrBankBootAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the module detects an error while booting
	from bank 0 or bank 1."
  ::= 7

	trapdrrAlarmDataCRCAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 8

	trapdrrHardwareErrAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when hardware is abnormal."
  ::= 9

 	trapdrrOpticalSignalAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the optical signal is beyond the preset range."  
  ::= 10
 
	trapdrrFactoryDataCRCAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 11

	trapdrrResetFactoryDefaultAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs."
  ::= 12

	trapdrrTripPointAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Input optical power is lower than the custumer set 
	trip point and trippoint mode as ALARM_ONLY or SWITCH & ALARM."
  ::= 13       
  
    trapdrrLinkAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when receiver is out of SYN with transmitter"
  ::= 14 
    trapdrrCalibrationDataCRCAlarm TRAP-TYPE
	ENTERPRISE gx2Drr2x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Calibration Data CRC is incorrect"
  ::= 15 

  END
