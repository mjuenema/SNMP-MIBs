--
-- EXTREME-SUMMIT-WM-DOT11-EXTNS-MIB.my
-- MIB generated by MG-SOFT Visual MIB Builder Version 4.0 Build 349
-- Friday, October 28, 2005 at 15:09:43
--

	EXTREME-SUMMIT-WM-DOT11-EXTNS-MIB DEFINITIONS ::= BEGIN
 
		IMPORTS
			summitWMMgmt, summitWMModules			
				FROM EXTREME-SUMMIT-WM-SMI			
			dot11WEPDefaultKeyIndex			
				FROM IEEE802dot11-MIB			
			ifIndex, InterfaceIndex			
				FROM IF-MIB			
			OBJECT-GROUP, MODULE-COMPLIANCE			
				FROM SNMPv2-CONF			
			Integer32, Unsigned32, Counter64, OBJECT-TYPE, MODULE-IDENTITY			
				FROM SNMPv2-SMI			
			MacAddress, TruthValue, RowStatus, DisplayString			
				FROM SNMPv2-TC;
	
	
--  September 01, 2005 at 02:37 GMT
-- September 01, 2005 at 02:37 GMT
		-- 1.3.6.1.4.1.1916.5.5.3
		summitWMDot11ExtnsMIB MODULE-IDENTITY 
			LAST-UPDATED "200510280310Z"		-- October 28, 2005 at 03:10 GMT
			ORGANIZATION 
				"Extreme Networks, Inc."
			CONTACT-INFO 
				"www.extremenetworks.com"
			DESCRIPTION 
				"Summit WM Dot11 extensions MIB. This module provides extension
				objects to the ieee80211 MIB."
			REVISION "200510280310Z"		-- October 28, 2005 at 03:10 GMT
			DESCRIPTION 
				"Initial version."
			::= { summitWMModules 3 }

		
	
--
-- Type definitions
--
	
		WEPKeytype ::= OCTET STRING (SIZE (0 | 14 | 38))

	
	
--
-- Node definitions
--
	
		-- 1.3.6.1.4.1.1916.5.3.1
		dot11ExtnsMib OBJECT IDENTIFIER ::= { summitWMMgmt 1 }

		
		-- 1.3.6.1.4.1.1916.5.3.1.1
		dot11Extsmt OBJECT IDENTIFIER ::= { dot11ExtnsMib 1 }

		
		-- 1.3.6.1.4.1.1916.5.3.1.1.1
		dot11ExtBSSIDTable OBJECT-TYPE
			SYNTAX SEQUENCE OF Dot11ExtBSSIDEntry
			MAX-ACCESS not-accessible
			STATUS current
			DESCRIPTION
				"The dot11ExtBSSIDTable contains a list of the BSS (Basic Service Set) 
				Identifiers supported by each radio, and associates an 
				SSID with with each BSS."
			::= { dot11Extsmt 1 }

		
		-- 1.3.6.1.4.1.1916.5.3.1.1.1.1
		dot11ExtBSSIDEntry OBJECT-TYPE
			SYNTAX Dot11ExtBSSIDEntry
			MAX-ACCESS not-accessible
			STATUS current
			DESCRIPTION
				"An entry in the BSSID table."
			INDEX { ifIndex, dot11ExtBSSIndex }
			::= { dot11ExtBSSIDTable 1 }

		
		Dot11ExtBSSIDEntry ::=
			SEQUENCE { 
				dot11ExtBSSIndex
					Integer32,
				dot11ExtBSSID
					MacAddress,
				dot11ExtSSIDID
					Integer32,
				dot11ExtSSID
					OCTET STRING,
				dot11ExtBSSIDWEPKeyIndex
					Integer32,
				dot11ExtSSIDSuppress
					TruthValue,
				dot11ExtPriorityTrafficHandling
					TruthValue
			 }

		-- 1.3.6.1.4.1.1916.5.3.1.1.1.1.1
		dot11ExtBSSIndex OBJECT-TYPE
			SYNTAX Integer32 (1..2147483647)
			MAX-ACCESS read-only
			STATUS current
			DESCRIPTION
				"A unique value, greater than zero, that identifies
				each Basic Service Set Identifier (BSSID) supported by a radio."
			::= { dot11ExtBSSIDEntry 1 }

		
		-- 1.3.6.1.4.1.1916.5.3.1.1.1.1.2
		dot11ExtBSSID OBJECT-TYPE
			SYNTAX MacAddress
			MAX-ACCESS read-only
			STATUS current
			DESCRIPTION
				"The Basic Service Set Identifier (BSSID) uniquely identifies a 
				wireless network adapter.  In the case of the altitue350, 
				a radio can support up to 8 distinct BSSIDs."
			::= { dot11ExtBSSIDEntry 2 }

		
		-- 1.3.6.1.4.1.1916.5.3.1.1.1.1.3
		dot11ExtSSIDID OBJECT-TYPE
			SYNTAX Integer32 (0..2147483647)
			MAX-ACCESS read-write
			STATUS current
			DESCRIPTION
				"SSIDID is a Extreme Summit WM internal numeric identifier for the SSID.  
				This number is meaningless external to the product."
			::= { dot11ExtBSSIDEntry 3 }

		
		-- 1.3.6.1.4.1.1916.5.3.1.1.1.1.4
		dot11ExtSSID OBJECT-TYPE
			SYNTAX OCTET STRING (SIZE (0..32))
			MAX-ACCESS read-write
			STATUS current
			DESCRIPTION
				"The Service Set Identifier (SSID) is the network name identifying 
				the wireless network to which this adapter belongs."
			::= { dot11ExtBSSIDEntry 4 }

		
		-- 1.3.6.1.4.1.1916.5.3.1.1.1.1.5
		dot11ExtBSSIDWEPKeyIndex OBJECT-TYPE
			SYNTAX Integer32
			MAX-ACCESS read-write
			STATUS current
			DESCRIPTION
				"Specifies the WEP default key associated with this BSS
				from the ieee802dot11 dot11WEPDefaultKeysTable."
			::= { dot11ExtBSSIDEntry 5 }

		
		-- 1.3.6.1.4.1.1916.5.3.1.1.1.1.6
		dot11ExtSSIDSuppress OBJECT-TYPE
			SYNTAX TruthValue
			MAX-ACCESS read-write
			STATUS current
			DESCRIPTION
				"When True, the radio will not broadcast the SSID associated 
				with this BSSID in the beacons."
			::= { dot11ExtBSSIDEntry 6 }

		
		-- 1.3.6.1.4.1.1916.5.3.1.1.1.1.7
		dot11ExtPriorityTrafficHandling OBJECT-TYPE
			SYNTAX TruthValue
			MAX-ACCESS read-write
			STATUS current
			DESCRIPTION
				"When True, priority traffic handling is enabled for this BSSID."
			::= { dot11ExtBSSIDEntry 7 }

		
		-- 1.3.6.1.4.1.1916.5.3.1.1.2
		dot11ExtWEPKeyMappingsTable OBJECT-TYPE
			SYNTAX SEQUENCE OF Dot11ExtWEPKeyMappingsEntry
			MAX-ACCESS not-accessible
			STATUS current
			DESCRIPTION
				"The dot11ExtWEPKeyMappingsTable supports the ability to 
				configure a separate WEP key for each BSS/Station pairing.
				
				The WEPKeyMappingValues in this table are logically WRITE-ONLY. 
				Any attempt to read these values will return null or 0."
			::= { dot11Extsmt 2 }

		
		-- 1.3.6.1.4.1.1916.5.3.1.1.2.1
		dot11ExtWEPKeyMappingsEntry OBJECT-TYPE
			SYNTAX Dot11ExtWEPKeyMappingsEntry
			MAX-ACCESS not-accessible
			STATUS current
			DESCRIPTION
				"An entry in the dot11ExtWEPKeyMappingsTable."
			INDEX { ifIndex, dot11ExtBSSIndex, dot11ExtWEPKeyMappingIndex }
			::= { dot11ExtWEPKeyMappingsTable 1 }

		
		Dot11ExtWEPKeyMappingsEntry ::=
			SEQUENCE { 
				dot11ExtWEPKeyMappingIndex
					Integer32,
				dot11ExtWEPKeyMappingAddress
					MacAddress,
				dot11ExtWEPKeyMappingWEPOn
					TruthValue,
				dot11ExtWEPKeyMappingValue
					WEPKeytype,
				dot11ExtWEPKeyMappingStatus
					RowStatus
			 }

		-- 1.3.6.1.4.1.1916.5.3.1.1.2.1.1
		dot11ExtWEPKeyMappingIndex OBJECT-TYPE
			SYNTAX Integer32 (1..2147483647)
			MAX-ACCESS read-only
			STATUS current
			DESCRIPTION
				"The auxiliary variable used to identify instances
				of the columnar objects in the WEP Key Mappings Table."
			::= { dot11ExtWEPKeyMappingsEntry 1 }

		
		-- 1.3.6.1.4.1.1916.5.3.1.1.2.1.2
		dot11ExtWEPKeyMappingAddress OBJECT-TYPE
			SYNTAX MacAddress
			MAX-ACCESS read-create
			STATUS current
			DESCRIPTION
				"The MAC address of the STA for which the values from this
				key mapping entry are to be used."
			::= { dot11ExtWEPKeyMappingsEntry 2 }

		
		-- 1.3.6.1.4.1.1916.5.3.1.1.2.1.3
		dot11ExtWEPKeyMappingWEPOn OBJECT-TYPE
			SYNTAX TruthValue
			MAX-ACCESS read-create
			STATUS current
			DESCRIPTION
				"Boolean as to whether WEP is to be used when communicating
				with the dot11WEPKeyMappingAddress STA."
			::= { dot11ExtWEPKeyMappingsEntry 3 }

		
		-- 1.3.6.1.4.1.1916.5.3.1.1.2.1.4
		dot11ExtWEPKeyMappingValue OBJECT-TYPE
			SYNTAX WEPKeytype
			MAX-ACCESS read-create
			STATUS current
			DESCRIPTION
				"A WEP secret key value."
			::= { dot11ExtWEPKeyMappingsEntry 4 }

		
		-- 1.3.6.1.4.1.1916.5.3.1.1.2.1.5
		dot11ExtWEPKeyMappingStatus OBJECT-TYPE
			SYNTAX RowStatus
			MAX-ACCESS read-create
			STATUS current
			DESCRIPTION
				"The status column used for creating, modifying, and
				deleting instances of the columnar objects in the WEP key
				mapping Table."
			::= { dot11ExtWEPKeyMappingsEntry 5 }

		
		-- 1.3.6.1.4.1.1916.5.3.1.1.3
		dot11CapabilitiesTable OBJECT-TYPE
			SYNTAX SEQUENCE OF Dot11CapabilitiesEntry
			MAX-ACCESS not-accessible
			STATUS current
			DESCRIPTION
				"The dot11CapabilitiesTable contains the 802.11 protocols 
				that each radio in the accessPoint are capable of supporting."
			::= { dot11Extsmt 3 }

		
		-- 1.3.6.1.4.1.1916.5.3.1.1.3.1
		dot11CapabilitiesEntry OBJECT-TYPE
			SYNTAX Dot11CapabilitiesEntry
			MAX-ACCESS not-accessible
			STATUS current
			DESCRIPTION
				"An entry in the dot11CapabilitiesTable."
			INDEX { ifIndex }
			::= { dot11CapabilitiesTable 1 }

		
		Dot11CapabilitiesEntry ::=
			SEQUENCE { 
				dot11Capabilities
					BITS
			 }

		-- 1.3.6.1.4.1.1916.5.3.1.1.3.1.1
		dot11Capabilities OBJECT-TYPE
			SYNTAX BITS
				{
				dot11g(0),
				dot11a(1)
				}
			MAX-ACCESS read-write
			STATUS current
			DESCRIPTION
				"Describes the capabilities of a radio, for example the protocol supported."
			::= { dot11CapabilitiesEntry 1 }

		
		-- 1.3.6.1.4.1.1916.5.3.1.1.4
		dot11bConfigTable OBJECT-TYPE
			SYNTAX SEQUENCE OF Dot11bConfigEntry
			MAX-ACCESS not-accessible
			STATUS current
			DESCRIPTION
				"The table contains configuration elements specific to the 802.11b protocol."
			::= { dot11Extsmt 4 }

		
		-- 1.3.6.1.4.1.1916.5.3.1.1.4.1
		dot11bConfigEntry OBJECT-TYPE
			SYNTAX Dot11bConfigEntry
			MAX-ACCESS not-accessible
			STATUS current
			DESCRIPTION
				"The dot11bConfigTable contains configuration elements 
				specific to the 802.11b protocol.  If an attempt to 
				read the elements is made for a radio which does not 
				support 802.11b, null or 0 will be returned."
			INDEX { ifIndex }
			::= { dot11bConfigTable 1 }

		
		Dot11bConfigEntry ::=
			SEQUENCE { 
				dot11bEnabled
					TruthValue,
				dot11BasicB
					INTEGER
			 }

		-- 1.3.6.1.4.1.1916.5.3.1.1.4.1.1
		dot11bEnabled OBJECT-TYPE
			SYNTAX TruthValue
			MAX-ACCESS read-write
			STATUS current
			DESCRIPTION
				"When true, 802.1b protocol support is active on this radio."
			::= { dot11bConfigEntry 1 }

		
		-- 1.3.6.1.4.1.1916.5.3.1.1.4.1.2
		dot11BasicB OBJECT-TYPE
			SYNTAX INTEGER
				{
				basic11b(1),
				basic11(2)
				}
			MAX-ACCESS read-write
			STATUS current
			DESCRIPTION
				"Specifies the basic rate set for a 11b or 11b+g radio. When set to 
				basic11b, the radio uses all four 11b rates (1, 2, 5.5 and 11 Mbps)  
				as basic rates. When when set to basic11 the radio uses
				only the two 11 rates (1 and 2 Mbps) as basic rates."
			::= { dot11bConfigEntry 2 }

		
		-- 1.3.6.1.4.1.1916.5.3.1.1.5
		dot11gConfigTable OBJECT-TYPE
			SYNTAX SEQUENCE OF Dot11gConfigEntry
			MAX-ACCESS not-accessible
			STATUS current
			DESCRIPTION
				"The dot11gConfigTable contains configuration elements 
				specific to the 802.11g protocol.  If an attempt to 
				read the elements is made for a radio which does not 
				support 802.11g, null or 0 will be returned."
			::= { dot11Extsmt 5 }

		
		-- 1.3.6.1.4.1.1916.5.3.1.1.5.1
		dot11gConfigEntry OBJECT-TYPE
			SYNTAX Dot11gConfigEntry
			MAX-ACCESS not-accessible
			STATUS current
			DESCRIPTION
				"An entry in the dot11gConfigTable."
			INDEX { ifIndex }
			::= { dot11gConfigTable 1 }

		
		Dot11gConfigEntry ::=
			SEQUENCE { 
				dot11gEnabled
					TruthValue,
				dot11gProtectionMode
					INTEGER,
				dot11gProtectionType
					INTEGER,
				dot11gProtectionRate
					INTEGER,
				dot11gBasicG
					INTEGER
			 }

		-- 1.3.6.1.4.1.1916.5.3.1.1.5.1.1
		dot11gEnabled OBJECT-TYPE
			SYNTAX TruthValue
			MAX-ACCESS read-write
			STATUS current
			DESCRIPTION
				"When true, 802.1g protocol support is active on this radio."
			::= { dot11gConfigEntry 1 }

		
		-- 1.3.6.1.4.1.1916.5.3.1.1.5.1.3
		dot11gProtectionMode OBJECT-TYPE
			SYNTAX INTEGER
				{
				none(1),
				auto(2),
				always(3)
				}
			MAX-ACCESS read-write
			STATUS current
			DESCRIPTION
				"Configures whether and when to use Protection Mode for the 802.11g 
				transmissions. Protection Mode helps reduce collisions with legacy
				802.11b stations at the expense of additional overhead. None specifies 
				that no protection is to be used. Auto specifies that 
				radio will enable protection mode when it detects 
				an 802.11b station.  Always specifies that protection
				mode is always enabled."
			::= { dot11gConfigEntry 3 }

		
		-- 1.3.6.1.4.1.1916.5.3.1.1.5.1.4
		dot11gProtectionType OBJECT-TYPE
			SYNTAX INTEGER
				{
				ctsOnly(1),
				rtsCts(2)
				}
			MAX-ACCESS read-write
			STATUS current
			DESCRIPTION
				"Determines whether 802.11g Protection Mode uses a RTS-CTS sequence
				or a CTS-only protection mechanism when Protection Mode is enabled."
			::= { dot11gConfigEntry 4 }

		
		-- 1.3.6.1.4.1.1916.5.3.1.1.5.1.5
		dot11gProtectionRate OBJECT-TYPE
			SYNTAX INTEGER
				{
				rate1Mbps(0),
				rate2Mbps(1),
				rate5Mbps(2),
				rate11Mbps(3)
				}
			MAX-ACCESS read-write
			STATUS current
			DESCRIPTION
				"Specifies the rate to be used by RTS or CTS in protection mode."
			::= { dot11gConfigEntry 5 }

		
		-- 1.3.6.1.4.1.1916.5.3.1.1.5.1.6
		dot11gBasicG OBJECT-TYPE
			SYNTAX INTEGER
				{
				default(1),
				basic11(2),
				basic11b(3),
				ofdm(4)
				}
			MAX-ACCESS read-write
			STATUS current
			DESCRIPTION
				"Specifies the set of basic rates in 11-g-only mode. Default 
				allows all possible basic rates (1, 2, 5.5, 11, 6, 12 and 24 Mbps).
				Basic11 specifies only 11 rates (1 nad 2 Mbps) as basic. Basic11b 
				specifies all four 11b rates (1, 2, 5.5 and 11 Mbps) as basic.
				OFDM specifies only OFDM rates (6, 12 and 24 Mbps) as basic."
			::= { dot11gConfigEntry 6 }

		
		-- 1.3.6.1.4.1.1916.5.3.1.1.7
		dot11ExtSmtTable OBJECT-TYPE
			SYNTAX SEQUENCE OF Dot11ExtSmtEntry
			MAX-ACCESS not-accessible
			STATUS current
			DESCRIPTION
				"Extended settings table."
			::= { dot11Extsmt 7 }

		
		-- 1.3.6.1.4.1.1916.5.3.1.1.7.1
		dot11ExtSmtEntry OBJECT-TYPE
			SYNTAX Dot11ExtSmtEntry
			MAX-ACCESS not-accessible
			STATUS current
			DESCRIPTION
				"An entry in the Extended settings table dot11ExtSmtTable."
			INDEX { ifIndex }
			::= { dot11ExtSmtTable 1 }

		
		Dot11ExtSmtEntry ::=
			SEQUENCE { 
				smtShortPreambleInvoked
					INTEGER,
				dot11ExtSmtCurrentChannel
					Integer32,
				dot11ExtSmtMaxBasicRate
					OCTET STRING,
				dot11ExtSmtMinBasicRate
					OCTET STRING,
				dot11ExtSmtMaxOperationalRate
					OCTET STRING
			 }

		-- 1.3.6.1.4.1.1916.5.3.1.1.7.1.1
		smtShortPreambleInvoked OBJECT-TYPE
			SYNTAX INTEGER
				{
				shortPreamble(1),
				longPreamble(2),
				autoSelectPreamble(3)
				}
			MAX-ACCESS read-write
			STATUS current
			DESCRIPTION
				"Specifies the type of preamble used in an 11b/g radio: 
				always short, always long or automatically selected."
			::= { dot11ExtSmtEntry 1 }

		
		-- 1.3.6.1.4.1.1916.5.3.1.1.7.1.2
		dot11ExtSmtCurrentChannel OBJECT-TYPE
			SYNTAX Integer32 (0..2147483647)
			MAX-ACCESS read-write
			STATUS current
			DESCRIPTION
				"Specfies the current rdio channel."
			::= { dot11ExtSmtEntry 2 }

		
		-- 1.3.6.1.4.1.1916.5.3.1.1.7.1.3
		dot11ExtSmtMaxBasicRate OBJECT-TYPE
			SYNTAX OCTET STRING (SIZE (1..126))
			MAX-ACCESS read-write
			STATUS current
			DESCRIPTION
				"Specifies the maximum basic rate."
			::= { dot11ExtSmtEntry 3 }

		
		-- 1.3.6.1.4.1.1916.5.3.1.1.7.1.4
		dot11ExtSmtMinBasicRate OBJECT-TYPE
			SYNTAX OCTET STRING (SIZE (1..126))
			MAX-ACCESS read-write
			STATUS current
			DESCRIPTION
				"Specifies the minimum basic rate which is 
				also the minimum operational rate."
			::= { dot11ExtSmtEntry 4 }

		
		-- 1.3.6.1.4.1.1916.5.3.1.1.7.1.5
		dot11ExtSmtMaxOperationalRate OBJECT-TYPE
			SYNTAX OCTET STRING (SIZE (1..126))
			MAX-ACCESS read-write
			STATUS current
			DESCRIPTION
				"Specifies the maximum operational rate."
			::= { dot11ExtSmtEntry 5 }

		
		-- 1.3.6.1.4.1.1916.5.3.1.1.8
		dot11ExtVlanSmtTable OBJECT-TYPE
			SYNTAX SEQUENCE OF Dot11ExtVlanSmtEntry
			MAX-ACCESS not-accessible
			STATUS current
			DESCRIPTION
				"This table contains configuration about bridging mode for the radio."
			::= { dot11Extsmt 8 }

		
		-- 1.3.6.1.4.1.1916.5.3.1.1.8.1
		dot11ExtVlanSmtEntry OBJECT-TYPE
			SYNTAX Dot11ExtVlanSmtEntry
			MAX-ACCESS not-accessible
			STATUS current
			DESCRIPTION
				"An entry in dot11ExtVlanSmtTable table."
			INDEX { ifIndex, dot11ExtBSSIndex }
			::= { dot11ExtVlanSmtTable 1 }

		
		Dot11ExtVlanSmtEntry ::=
			SEQUENCE { 
				vlanBridgeMode
					TruthValue,
				vlanTag
					Integer32
			 }

		-- 1.3.6.1.4.1.1916.5.3.1.1.8.1.1
		vlanBridgeMode OBJECT-TYPE
			SYNTAX TruthValue
			MAX-ACCESS read-write
			STATUS current
			DESCRIPTION
				"When true, bridging mode is enabled on this radio."
			::= { dot11ExtVlanSmtEntry 1 }

		
		-- 1.3.6.1.4.1.1916.5.3.1.1.8.1.2
		vlanTag OBJECT-TYPE
			SYNTAX Integer32
			MAX-ACCESS read-write
			STATUS current
			DESCRIPTION
				"Integer specifying the VLAN tag.  If untagged, returns -1."
			::= { dot11ExtVlanSmtEntry 2 }

		
		-- 1.3.6.1.4.1.1916.5.3.1.2
		dot11ExtAPObjs OBJECT IDENTIFIER ::= { dot11ExtnsMib 2 }

		
		-- 1.3.6.1.4.1.1916.5.3.1.2.2
		dot1XConfigTable OBJECT-TYPE
			SYNTAX SEQUENCE OF Dot1XConfigEntry
			MAX-ACCESS not-accessible
			STATUS current
			DESCRIPTION
				"Conceptual table for 802.1X settings required for wireless
				security."
			::= { dot11ExtAPObjs 2 }

		
		-- 1.3.6.1.4.1.1916.5.3.1.2.2.1
		dot1XConfigEntry OBJECT-TYPE
			SYNTAX Dot1XConfigEntry
			MAX-ACCESS not-accessible
			STATUS current
			DESCRIPTION
				"An entry in dot1XConfigTable table."
			INDEX { ifIndex, dot11ExtBSSIndex }
			::= { dot1XConfigTable 1 }

		
		Dot1XConfigEntry ::=
			SEQUENCE { 
				dot1XEnabled
					TruthValue,
				dot1XDynamicRekeyingInterval
					Unsigned32,
				dot1XWPA1Enabled
					TruthValue,
				dot1XWPAPassphrase
					DisplayString,
				dot1XWPACipherType
					INTEGER,
				dot1XWPA2Enabled
					TruthValue
			 }

		-- 1.3.6.1.4.1.1916.5.3.1.2.2.1.1
		dot1XEnabled OBJECT-TYPE
			SYNTAX TruthValue
			MAX-ACCESS read-write
			STATUS current
			DESCRIPTION
				"Enable 802.1X authentication for this BSSID."
			::= { dot1XConfigEntry 1 }

		
		-- 1.3.6.1.4.1.1916.5.3.1.2.2.1.2
		dot1XDynamicRekeyingInterval OBJECT-TYPE
			SYNTAX Unsigned32
			UNITS "seconds"
			MAX-ACCESS read-write
			STATUS current
			DESCRIPTION
				"This object defines the time period, in seconds, after which
				the key value must be updated."
			::= { dot1XConfigEntry 2 }

		
		-- 1.3.6.1.4.1.1916.5.3.1.2.2.1.3
		dot1XWPA1Enabled OBJECT-TYPE
			SYNTAX TruthValue
			MAX-ACCESS read-write
			STATUS current
			DESCRIPTION
				"Enables WPA.1 (Wi-Fi Protected Access) on this BSSID"
			::= { dot1XConfigEntry 3 }

		
		-- 1.3.6.1.4.1.1916.5.3.1.2.2.1.4
		dot1XWPAPassphrase OBJECT-TYPE
			SYNTAX DisplayString
			MAX-ACCESS read-write
			STATUS current
			DESCRIPTION
				"Specifies the WPA passphrase for the BSSID.  This element is logically 
				write only.  Any attempt to read this element will result in null or 0."
			::= { dot1XConfigEntry 4 }

		
		-- 1.3.6.1.4.1.1916.5.3.1.2.2.1.5
		dot1XWPACipherType OBJECT-TYPE
			SYNTAX INTEGER
				{
				tkipOnly(1),
				auto(2)
				}
			MAX-ACCESS read-write
			STATUS current
			DESCRIPTION
				"Defines the encryption algoritms allowed with WPA: 
				only TKIP if tkipOnly or both AES and TKIP if auto."
			::= { dot1XConfigEntry 5 }

		
		-- 1.3.6.1.4.1.1916.5.3.1.2.2.1.6
		dot1XWPA2Enabled OBJECT-TYPE
			SYNTAX TruthValue
			MAX-ACCESS read-write
			STATUS current
			DESCRIPTION
				"When true, WPA v.2 support is enabled."
			::= { dot1XConfigEntry 6 }

		
		-- 1.3.6.1.4.1.1916.5.3.1.4
		dot11ExtCounters OBJECT IDENTIFIER ::= { dot11ExtnsMib 4 }

		
		-- 1.3.6.1.4.1.1916.5.3.1.4.1
		assocGroupTable OBJECT-TYPE
			SYNTAX SEQUENCE OF AssocGroupEntry
			MAX-ACCESS not-accessible
			STATUS current
			DESCRIPTION
				"STA statistics table."
			::= { dot11ExtCounters 1 }

		
		-- 1.3.6.1.4.1.1916.5.3.1.4.1.1
		assocGroupEntry OBJECT-TYPE
			SYNTAX AssocGroupEntry
			MAX-ACCESS not-accessible
			STATUS current
			DESCRIPTION
				"Entry in the STA statistics table."
			INDEX { assocAddress }
			::= { assocGroupTable 1 }

		
		AssocGroupEntry ::=
			SEQUENCE { 
				assocAddress
					MacAddress,
				assocIfIndex
					InterfaceIndex,
				assocReceivedRSSI
					Integer32,
				assocTransmittedRSSI
					Integer32,
				assocReceivedRate
					Unsigned32,
				assocTransmittedRate
					Unsigned32,
				assocReceivedFrameCount
					Counter64,
				assocTransmittedFrameCount
					Counter64,
				assocReceiveErrors
					Counter64,
				assocTransmitErrors
					Counter64,
				assocTransmitBytes
					Counter64,
				assocReceiveBytes
					Counter64
			 }

		-- 1.3.6.1.4.1.1916.5.3.1.4.1.1.1
		assocAddress OBJECT-TYPE
			SYNTAX MacAddress
			MAX-ACCESS read-only
			STATUS current
			DESCRIPTION
				"MAC address associated with the client."
			::= { assocGroupEntry 1 }

		
		-- 1.3.6.1.4.1.1916.5.3.1.4.1.1.2
		assocIfIndex OBJECT-TYPE
			SYNTAX InterfaceIndex
			MAX-ACCESS read-only
			STATUS current
			DESCRIPTION
				"Interface index of the radio to which the client is associated."
			::= { assocGroupEntry 2 }

		
		-- 1.3.6.1.4.1.1916.5.3.1.4.1.1.3
		assocReceivedRSSI OBJECT-TYPE
			SYNTAX Integer32
			MAX-ACCESS read-only
			STATUS current
			DESCRIPTION
				"Received signal strength for the packets received from this client."
			::= { assocGroupEntry 3 }

		
		-- 1.3.6.1.4.1.1916.5.3.1.4.1.1.4
		assocTransmittedRSSI OBJECT-TYPE
			SYNTAX Integer32
			MAX-ACCESS read-only
			STATUS current
			DESCRIPTION
				"Received signal strength averaged for the ACK packets received in response 
				to transmitted packets for this client."
			::= { assocGroupEntry 4 }

		
		-- 1.3.6.1.4.1.1916.5.3.1.4.1.1.5
		assocReceivedRate OBJECT-TYPE
			SYNTAX Unsigned32
			MAX-ACCESS read-only
			STATUS current
			DESCRIPTION
				"PHY rate for the packets received from this client."
			::= { assocGroupEntry 5 }

		
		-- 1.3.6.1.4.1.1916.5.3.1.4.1.1.6
		assocTransmittedRate OBJECT-TYPE
			SYNTAX Unsigned32
			MAX-ACCESS read-only
			STATUS current
			DESCRIPTION
				"PHY rate used to transmit packets for this client."
			::= { assocGroupEntry 6 }

		
		-- 1.3.6.1.4.1.1916.5.3.1.4.1.1.7
		assocReceivedFrameCount OBJECT-TYPE
			SYNTAX Counter64
			MAX-ACCESS read-only
			STATUS current
			DESCRIPTION
				"Frames received from this client."
			::= { assocGroupEntry 7 }

		
		-- 1.3.6.1.4.1.1916.5.3.1.4.1.1.8
		assocTransmittedFrameCount OBJECT-TYPE
			SYNTAX Counter64
			MAX-ACCESS read-only
			STATUS current
			DESCRIPTION
				"Frames transmitted for this client."
			::= { assocGroupEntry 8 }

		
		-- 1.3.6.1.4.1.1916.5.3.1.4.1.1.9
		assocReceiveErrors OBJECT-TYPE
			SYNTAX Counter64
			MAX-ACCESS read-only
			STATUS current
			DESCRIPTION
				"Frames received with errors from this client."
			::= { assocGroupEntry 9 }

		
		-- 1.3.6.1.4.1.1916.5.3.1.4.1.1.10
		assocTransmitErrors OBJECT-TYPE
			SYNTAX Counter64
			MAX-ACCESS read-only
			STATUS current
			DESCRIPTION
				"Frames transmitted with errors (not acknowledged) 
				for this cleint."
			::= { assocGroupEntry 10 }

		
		-- 1.3.6.1.4.1.1916.5.3.1.4.1.1.11
		assocTransmitBytes OBJECT-TYPE
			SYNTAX Counter64
			MAX-ACCESS read-only
			STATUS current
			DESCRIPTION
				"Bytes transmitted for this client."
			::= { assocGroupEntry 11 }

		
		-- 1.3.6.1.4.1.1916.5.3.1.4.1.1.12
		assocReceiveBytes OBJECT-TYPE
			SYNTAX Counter64
			MAX-ACCESS read-only
			STATUS current
			DESCRIPTION
				"Bytes received from this client."
			::= { assocGroupEntry 12 }

		
		-- 1.3.6.1.4.1.1916.5.3.1.4.2
		assocCountersTable OBJECT-TYPE
			SYNTAX SEQUENCE OF AssocCountersEntry
			MAX-ACCESS not-accessible
			STATUS current
			DESCRIPTION
				"STA association statistics table."
			::= { dot11ExtCounters 2 }

		
		-- 1.3.6.1.4.1.1916.5.3.1.4.2.1
		assocCountersEntry OBJECT-TYPE
			SYNTAX AssocCountersEntry
			MAX-ACCESS not-accessible
			STATUS current
			DESCRIPTION
				"Entry in the STA association statistics table."
			INDEX { assocAddress }
			::= { assocCountersTable 1 }

		
		AssocCountersEntry ::=
			SEQUENCE { 
				assocAuthenticationCount
					Counter64,
				assocDeauthenticationCount
					Counter64,
				assocAssociationCount
					Counter64,
				assocDeassociationCount
					Counter64,
				assocReassociationCount
					Counter64
			 }

		-- 1.3.6.1.4.1.1916.5.3.1.4.2.1.1
		assocAuthenticationCount OBJECT-TYPE
			SYNTAX Counter64
			MAX-ACCESS read-only
			STATUS current
			DESCRIPTION
				"Number of authentications for this client."
			::= { assocCountersEntry 1 }

		
		-- 1.3.6.1.4.1.1916.5.3.1.4.2.1.2
		assocDeauthenticationCount OBJECT-TYPE
			SYNTAX Counter64
			MAX-ACCESS read-only
			STATUS current
			DESCRIPTION
				"Number of deauthentications for this client."
			::= { assocCountersEntry 2 }

		
		-- 1.3.6.1.4.1.1916.5.3.1.4.2.1.3
		assocAssociationCount OBJECT-TYPE
			SYNTAX Counter64
			MAX-ACCESS read-only
			STATUS current
			DESCRIPTION
				"Number of associations for this client."
			::= { assocCountersEntry 3 }

		
		-- 1.3.6.1.4.1.1916.5.3.1.4.2.1.4
		assocDeassociationCount OBJECT-TYPE
			SYNTAX Counter64
			MAX-ACCESS read-only
			STATUS current
			DESCRIPTION
				"Number of deassociations for this client."
			::= { assocCountersEntry 4 }

		
		-- 1.3.6.1.4.1.1916.5.3.1.4.2.1.5
		assocReassociationCount OBJECT-TYPE
			SYNTAX Counter64
			MAX-ACCESS read-only
			STATUS current
			DESCRIPTION
				"Number of reassociations for this client."
			::= { assocCountersEntry 5 }

		
		-- 1.3.6.1.4.1.1916.5.3.1.5
		dot11ExtConformance OBJECT IDENTIFIER ::= { dot11ExtnsMib 5 }

		
--  this module
		-- 1.3.6.1.4.1.1916.5.3.1.5.1
		summitWMDot11ExtModule MODULE-COMPLIANCE
			STATUS current
			DESCRIPTION 
				"EXTREME-SUMMIT-WM-DOT11-EXTNS module compliance."
			MODULE -- this module
				MANDATORY-GROUPS { summitWMDot11ExtGroups }
			::= { dot11ExtConformance 1 }

		
		-- 1.3.6.1.4.1.1916.5.3.1.5.2
		summitWMDot11ExtGroups OBJECT-GROUP
			OBJECTS { dot11ExtSSIDID, dot11ExtSSID, assocAddress, assocIfIndex, assocReceivedRSSI, 
				assocTransmittedRSSI, assocReceivedRate, assocTransmittedRate, assocReceivedFrameCount, assocTransmittedFrameCount, 
				assocReceiveErrors, assocTransmitErrors, assocAuthenticationCount, assocDeauthenticationCount, assocAssociationCount, 
				assocDeassociationCount, assocReassociationCount, dot11ExtWEPKeyMappingIndex, dot11ExtWEPKeyMappingAddress, dot11ExtWEPKeyMappingWEPOn, 
				dot11ExtWEPKeyMappingValue, dot11ExtWEPKeyMappingStatus, dot11gEnabled, dot11gProtectionMode, dot11gProtectionType, 
				smtShortPreambleInvoked, dot11ExtBSSID, dot11ExtBSSIDWEPKeyIndex, dot11bEnabled, dot11Capabilities, 
				dot11ExtBSSIndex, dot11ExtSSIDSuppress, dot11ExtPriorityTrafficHandling, dot11BasicB, dot11gProtectionRate, 
				vlanBridgeMode, assocReceiveBytes, assocTransmitBytes, dot1XWPA2Enabled, dot1XEnabled, 
				dot1XDynamicRekeyingInterval, dot1XWPA1Enabled, dot1XWPAPassphrase, dot1XWPACipherType, dot11ExtSmtMinBasicRate, 
				dot11ExtSmtMaxBasicRate, vlanTag, dot11ExtSmtMaxOperationalRate, dot11ExtSmtCurrentChannel, dot11gBasicG
				 }
			STATUS current
			DESCRIPTION 
				"Extreme summit WM Dot11-Extns object-group."
			::= { dot11ExtConformance 2 }

		
	
	END
