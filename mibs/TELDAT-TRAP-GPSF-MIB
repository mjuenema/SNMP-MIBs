-- file automatically created


TELDAT-TRAP-GPSF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


gpsfTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the GPSF event subsystem."
    REVISION "201401200930Z"
    DESCRIPTION "Initial implementation"
        ::= { telEventTraps 256 }


gpsfEventsGroup	OBJECT IDENTIFIER	::= { gpsfTrapsMIB 1 }

gpsfNotifications	OBJECT IDENTIFIER	::= { gpsfTrapsMIB 2 }
gpsfNotificationsPrefix	OBJECT IDENTIFIER	::= { gpsfNotifications 0 }

gpsfEventObjects1 OBJECT-IDENTITY
    STATUS current
    DESCRIPTION
        "Event GPSF.1
        Shows last position obtained fron GPS fix data."
    ::= { gpsfEventsGroup 1 }

gpsf1_h OBJECT-TYPE
    SYNTAX Integer32
    MAX-ACCESS accessible-for-notify
    STATUS current
    DESCRIPTION
        "Parameter 'h' in event GPSF.1"
    ::= { gpsfEventObjects1 1 }

gpsf1_m OBJECT-TYPE
    SYNTAX Integer32
    MAX-ACCESS accessible-for-notify
    STATUS current
    DESCRIPTION
        "Parameter 'm' in event GPSF.1"
    ::= { gpsfEventObjects1 2 }

gpsf1_s OBJECT-TYPE
    SYNTAX Integer32
    MAX-ACCESS accessible-for-notify
    STATUS current
    DESCRIPTION
        "Parameter 's' in event GPSF.1"
    ::= { gpsfEventObjects1 3 }

gpsf1_la_deg OBJECT-TYPE
    SYNTAX Integer32
    MAX-ACCESS accessible-for-notify
    STATUS current
    DESCRIPTION
        "Parameter 'la_deg' in event GPSF.1"
    ::= { gpsfEventObjects1 4 }

gpsf1_la_min OBJECT-TYPE
    SYNTAX Integer32
    MAX-ACCESS accessible-for-notify
    STATUS current
    DESCRIPTION
        "Parameter 'la_min' in event GPSF.1"
    ::= { gpsfEventObjects1 5 }

gpsf1_la_minfrac OBJECT-TYPE
    SYNTAX Integer32
    MAX-ACCESS accessible-for-notify
    STATUS current
    DESCRIPTION
        "Parameter 'la_minfrac' in event GPSF.1"
    ::= { gpsfEventObjects1 6 }

gpsf1_la_area OBJECT-TYPE
    SYNTAX DisplayString
    MAX-ACCESS accessible-for-notify
    STATUS current
    DESCRIPTION
        "Parameter 'la_area' in event GPSF.1"
    ::= { gpsfEventObjects1 7 }

gpsf1_lo_deg OBJECT-TYPE
    SYNTAX Integer32
    MAX-ACCESS accessible-for-notify
    STATUS current
    DESCRIPTION
        "Parameter 'lo_deg' in event GPSF.1"
    ::= { gpsfEventObjects1 8 }

gpsf1_lo_min OBJECT-TYPE
    SYNTAX Integer32
    MAX-ACCESS accessible-for-notify
    STATUS current
    DESCRIPTION
        "Parameter 'lo_min' in event GPSF.1"
    ::= { gpsfEventObjects1 9 }

gpsf1_lo_minfrac OBJECT-TYPE
    SYNTAX Integer32
    MAX-ACCESS accessible-for-notify
    STATUS current
    DESCRIPTION
        "Parameter 'lo_minfrac' in event GPSF.1"
    ::= { gpsfEventObjects1 10 }

gpsf1_lo_area OBJECT-TYPE
    SYNTAX DisplayString
    MAX-ACCESS accessible-for-notify
    STATUS current
    DESCRIPTION
        "Parameter 'lo_area' in event GPSF.1"
    ::= { gpsfEventObjects1 11 }

gpsf1_altint OBJECT-TYPE
    SYNTAX Integer32
    MAX-ACCESS accessible-for-notify
    STATUS current
    DESCRIPTION
        "Parameter 'altint' in event GPSF.1"
    ::= { gpsfEventObjects1 12 }

gpsf1_altfrac OBJECT-TYPE
    SYNTAX Integer32
    MAX-ACCESS accessible-for-notify
    STATUS current
    DESCRIPTION
        "Parameter 'altfrac' in event GPSF.1"
    ::= { gpsfEventObjects1 13 }

gpsf1_nsat OBJECT-TYPE
    SYNTAX Integer32
    MAX-ACCESS accessible-for-notify
    STATUS current
    DESCRIPTION
        "Parameter 'nsat' in event GPSF.1"
    ::= { gpsfEventObjects1 14 }


gpsfNotification1 NOTIFICATION-TYPE
    OBJECTS { 
              gpsf1_h, 
              gpsf1_m,
              gpsf1_s,
              gpsf1_la_deg,
              gpsf1_la_min,
              gpsf1_la_minfrac,
              gpsf1_la_area,
              gpsf1_lo_deg,
              gpsf1_lo_min,
              gpsf1_lo_minfrac,
              gpsf1_lo_area,
              gpsf1_altint,
              gpsf1_altfrac,
              gpsf1_nsat 
            }
    STATUS current
    DESCRIPTION
        "Notification of Event GPSF.1

        Message: 'Last GPS Fix . Time: $1:$2:$3, Latitude: $4— $5.$6' $7, Longitude: $8— $9.$10' $11, Alt: $12.$13 m, N—sat: $14'

        Parameters list:
              $1: gpsf1_h
              $2: gpsf1_m
              $3: gpsf1_s
              $4: gpsf1_la_deg
              $5: gpsf1_la_min
              $6: gpsf1_la_minfrac
              $7: gpsf1_la_area
              $8: gpsf1_lo_deg
              $9: gpsf1_lo_min
              $10: gpsf1_lo_minfrac
              $11: gpsf1_lo_area
              $12: gpsf1_altint
              $13: gpsf1_altfrac
              $14: gpsf1_nsat

        Shows last position obtained fron GPS fix data."
    ::= { gpsfNotificationsPrefix 1 }


END
