-- file automatically created


TELDAT-TRAP-BFD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


bfdTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BFD event subsystem."
    REVISION "201401200930Z"
    DESCRIPTION "Initial implementation"
        ::= { telEventTraps 203 }


bfdEventsGroup	OBJECT IDENTIFIER	::= { bfdTrapsMIB 1 }

bfdNotifications	OBJECT IDENTIFIER	::= { bfdTrapsMIB 2 }
bfdNotificationsPrefix	OBJECT IDENTIFIER	::= { bfdNotifications 0 }

bfdEventObjects2 OBJECT-IDENTITY
    STATUS current
    DESCRIPTION
        "Event BFD.2
        A BFD packet with invalid TTL value has been received."
    ::= { bfdEventsGroup 2 }

bfd2_ttl_received OBJECT-TYPE
    SYNTAX Integer32
    MAX-ACCESS accessible-for-notify
    STATUS current
    DESCRIPTION
        "Parameter 'ttl_received' in event BFD.2"
    ::= { bfdEventObjects2 1 }

bfd2_peer_address OBJECT-TYPE
    SYNTAX DisplayString
    MAX-ACCESS accessible-for-notify
    STATUS current
    DESCRIPTION
        "Parameter 'peer_address' in event BFD.2"
    ::= { bfdEventObjects2 2 }

bfdEventObjects3 OBJECT-IDENTITY
    STATUS current
    DESCRIPTION
        "Event BFD.3
        A BFD packet with invalid size has been received."
    ::= { bfdEventsGroup 3 }

bfd3_peer_address OBJECT-TYPE
    SYNTAX DisplayString
    MAX-ACCESS accessible-for-notify
    STATUS current
    DESCRIPTION
        "Parameter 'peer_address' in event BFD.3"
    ::= { bfdEventObjects3 1 }

bfdEventObjects4 OBJECT-IDENTITY
    STATUS current
    DESCRIPTION
        "Event BFD.4
        A BFD packet with invalid BFD version has been received."
    ::= { bfdEventsGroup 4 }

bfd4_protocol_version OBJECT-TYPE
    SYNTAX Integer32
    MAX-ACCESS accessible-for-notify
    STATUS current
    DESCRIPTION
        "Parameter 'protocol_version' in event BFD.4"
    ::= { bfdEventObjects4 1 }

bfd4_peer_address OBJECT-TYPE
    SYNTAX DisplayString
    MAX-ACCESS accessible-for-notify
    STATUS current
    DESCRIPTION
        "Parameter 'peer_address' in event BFD.4"
    ::= { bfdEventObjects4 2 }

bfdEventObjects5 OBJECT-IDENTITY
    STATUS current
    DESCRIPTION
        "Event BFD.5
        A BFD packet with invalid length has been received."
    ::= { bfdEventsGroup 5 }

bfd5_packet_legth OBJECT-TYPE
    SYNTAX Integer32
    MAX-ACCESS accessible-for-notify
    STATUS current
    DESCRIPTION
        "Parameter 'packet_legth' in event BFD.5"
    ::= { bfdEventObjects5 1 }

bfd5_peer_address OBJECT-TYPE
    SYNTAX DisplayString
    MAX-ACCESS accessible-for-notify
    STATUS current
    DESCRIPTION
        "Parameter 'peer_address' in event BFD.5"
    ::= { bfdEventObjects5 2 }

bfdEventObjects6 OBJECT-IDENTITY
    STATUS current
    DESCRIPTION
        "Event BFD.6
        A BFD packet with zero detect time multiplier has been received."
    ::= { bfdEventsGroup 6 }

bfd6_peer_address OBJECT-TYPE
    SYNTAX DisplayString
    MAX-ACCESS accessible-for-notify
    STATUS current
    DESCRIPTION
        "Parameter 'peer_address' in event BFD.6"
    ::= { bfdEventObjects6 1 }

bfdEventObjects7 OBJECT-IDENTITY
    STATUS current
    DESCRIPTION
        "Event BFD.7
        A BFD packet with zero in the My Discriminator field has been received."
    ::= { bfdEventsGroup 7 }

bfd7_peer_address OBJECT-TYPE
    SYNTAX DisplayString
    MAX-ACCESS accessible-for-notify
    STATUS current
    DESCRIPTION
        "Parameter 'peer_address' in event BFD.7"
    ::= { bfdEventObjects7 1 }

bfdEventObjects8 OBJECT-IDENTITY
    STATUS current
    DESCRIPTION
        "Event BFD.8
        A BFD packet with zero in the Your Duscriminator field and non-zero
        in the I Hear You flag has been received."
    ::= { bfdEventsGroup 8 }

bfd8_peer_address OBJECT-TYPE
    SYNTAX DisplayString
    MAX-ACCESS accessible-for-notify
    STATUS current
    DESCRIPTION
        "Parameter 'peer_address' in event BFD.8"
    ::= { bfdEventObjects8 1 }

bfdEventObjects9 OBJECT-IDENTITY
    STATUS current
    DESCRIPTION
        "Event BFD.9
        The system could not find a valid session for the BFD packet received."
    ::= { bfdEventsGroup 9 }

bfd9_peer_address OBJECT-TYPE
    SYNTAX DisplayString
    MAX-ACCESS accessible-for-notify
    STATUS current
    DESCRIPTION
        "Parameter 'peer_address' in event BFD.9"
    ::= { bfdEventObjects9 1 }

bfdEventObjects10 OBJECT-IDENTITY
    STATUS current
    DESCRIPTION
        "Event BFD.10
        Some of the BFD definition parameters has changed and timers must be
        renegotiated."
    ::= { bfdEventsGroup 10 }

bfd10_session_disc OBJECT-TYPE
    SYNTAX Integer32
    MAX-ACCESS accessible-for-notify
    STATUS current
    DESCRIPTION
        "Parameter 'session_disc' in event BFD.10"
    ::= { bfdEventObjects10 1 }

bfd10_peer_address OBJECT-TYPE
    SYNTAX DisplayString
    MAX-ACCESS accessible-for-notify
    STATUS current
    DESCRIPTION
        "Parameter 'peer_address' in event BFD.10"
    ::= { bfdEventObjects10 2 }

bfdEventObjects11 OBJECT-IDENTITY
    STATUS current
    DESCRIPTION
        "Event BFD.11
        A BFD poll sequence has been finished."
    ::= { bfdEventsGroup 11 }

bfd11_session_disc OBJECT-TYPE
    SYNTAX Integer32
    MAX-ACCESS accessible-for-notify
    STATUS current
    DESCRIPTION
        "Parameter 'session_disc' in event BFD.11"
    ::= { bfdEventObjects11 1 }

bfd11_peer_address OBJECT-TYPE
    SYNTAX DisplayString
    MAX-ACCESS accessible-for-notify
    STATUS current
    DESCRIPTION
        "Parameter 'peer_address' in event BFD.11"
    ::= { bfdEventObjects11 2 }

bfdEventObjects12 OBJECT-IDENTITY
    STATUS current
    DESCRIPTION
        "Event BFD.12
        A BFD session is coming to DOWN state because remote peer is 
        administratively down."
    ::= { bfdEventsGroup 12 }

bfd12_session_disc OBJECT-TYPE
    SYNTAX Integer32
    MAX-ACCESS accessible-for-notify
    STATUS current
    DESCRIPTION
        "Parameter 'session_disc' in event BFD.12"
    ::= { bfdEventObjects12 1 }

bfd12_peer_address OBJECT-TYPE
    SYNTAX DisplayString
    MAX-ACCESS accessible-for-notify
    STATUS current
    DESCRIPTION
        "Parameter 'peer_address' in event BFD.12"
    ::= { bfdEventObjects12 2 }

bfdEventObjects13 OBJECT-IDENTITY
    STATUS current
    DESCRIPTION
        "Event BFD.13
        The detection period has been finished without receiving packets from
        the remote peer. Session will come down."
    ::= { bfdEventsGroup 13 }

bfd13_session_disc OBJECT-TYPE
    SYNTAX Integer32
    MAX-ACCESS accessible-for-notify
    STATUS current
    DESCRIPTION
        "Parameter 'session_disc' in event BFD.13"
    ::= { bfdEventObjects13 1 }

bfd13_peer_address OBJECT-TYPE
    SYNTAX DisplayString
    MAX-ACCESS accessible-for-notify
    STATUS current
    DESCRIPTION
        "Parameter 'peer_address' in event BFD.13"
    ::= { bfdEventObjects13 2 }

bfd13_bfd_state OBJECT-TYPE
    SYNTAX DisplayString
    MAX-ACCESS accessible-for-notify
    STATUS current
    DESCRIPTION
        "Parameter 'bfd_state' in event BFD.13"
    ::= { bfdEventObjects13 3 }

bfdEventObjects14 OBJECT-IDENTITY
    STATUS current
    DESCRIPTION
        "Event BFD.14
        A BFD session is coming to DOWN state."
    ::= { bfdEventsGroup 14 }

bfd14_session_disc OBJECT-TYPE
    SYNTAX Integer32
    MAX-ACCESS accessible-for-notify
    STATUS current
    DESCRIPTION
        "Parameter 'session_disc' in event BFD.14"
    ::= { bfdEventObjects14 1 }

bfd14_peer_address OBJECT-TYPE
    SYNTAX DisplayString
    MAX-ACCESS accessible-for-notify
    STATUS current
    DESCRIPTION
        "Parameter 'peer_address' in event BFD.14"
    ::= { bfdEventObjects14 2 }

bfdEventObjects15 OBJECT-IDENTITY
    STATUS current
    DESCRIPTION
        "Event BFD.15
        A BFD session is coming to UP state."
    ::= { bfdEventsGroup 15 }

bfd15_session_disc OBJECT-TYPE
    SYNTAX Integer32
    MAX-ACCESS accessible-for-notify
    STATUS current
    DESCRIPTION
        "Parameter 'session_disc' in event BFD.15"
    ::= { bfdEventObjects15 1 }

bfd15_peer_address OBJECT-TYPE
    SYNTAX DisplayString
    MAX-ACCESS accessible-for-notify
    STATUS current
    DESCRIPTION
        "Parameter 'peer_address' in event BFD.15"
    ::= { bfdEventObjects15 2 }

bfdEventObjects16 OBJECT-IDENTITY
    STATUS current
    DESCRIPTION
        "Event BFD.16
        A BFD session with this value of Your Discriminator does not exist in
        the system."
    ::= { bfdEventsGroup 16 }

bfd16_session_disc OBJECT-TYPE
    SYNTAX Integer32
    MAX-ACCESS accessible-for-notify
    STATUS current
    DESCRIPTION
        "Parameter 'session_disc' in event BFD.16"
    ::= { bfdEventObjects16 1 }

bfd16_peer_address OBJECT-TYPE
    SYNTAX DisplayString
    MAX-ACCESS accessible-for-notify
    STATUS current
    DESCRIPTION
        "Parameter 'peer_address' in event BFD.16"
    ::= { bfdEventObjects16 2 }

bfdEventObjects17 OBJECT-IDENTITY
    STATUS current
    DESCRIPTION
        "Event BFD.17
        A BFD session with this peer does not exist in the system."
    ::= { bfdEventsGroup 17 }

bfd17_peer_address OBJECT-TYPE
    SYNTAX DisplayString
    MAX-ACCESS accessible-for-notify
    STATUS current
    DESCRIPTION
        "Parameter 'peer_address' in event BFD.17"
    ::= { bfdEventObjects17 1 }

bfdEventObjects18 OBJECT-IDENTITY
    STATUS current
    DESCRIPTION
        "Event BFD.18
        The BFD protocol sending function has failed."
    ::= { bfdEventsGroup 18 }

bfd18_peer_address OBJECT-TYPE
    SYNTAX DisplayString
    MAX-ACCESS accessible-for-notify
    STATUS current
    DESCRIPTION
        "Parameter 'peer_address' in event BFD.18"
    ::= { bfdEventObjects18 1 }

bfdEventObjects19 OBJECT-IDENTITY
    STATUS current
    DESCRIPTION
        "Event BFD.19
        The system has not enough memory to allocate a new BFD session."
    ::= { bfdEventsGroup 19 }

bfd19_peer_address OBJECT-TYPE
    SYNTAX DisplayString
    MAX-ACCESS accessible-for-notify
    STATUS current
    DESCRIPTION
        "Parameter 'peer_address' in event BFD.19"
    ::= { bfdEventObjects19 1 }

bfdEventObjects20 OBJECT-IDENTITY
    STATUS current
    DESCRIPTION
        "Event BFD.20
        The system can not get a free socket for a new BFD session."
    ::= { bfdEventsGroup 20 }

bfd20_peer_address OBJECT-TYPE
    SYNTAX DisplayString
    MAX-ACCESS accessible-for-notify
    STATUS current
    DESCRIPTION
        "Parameter 'peer_address' in event BFD.20"
    ::= { bfdEventObjects20 1 }

bfdEventObjects21 OBJECT-IDENTITY
    STATUS current
    DESCRIPTION
        "Event BFD.21
        The system can not set TTL value for a new BFD session."
    ::= { bfdEventsGroup 21 }

bfd21_peer_address OBJECT-TYPE
    SYNTAX DisplayString
    MAX-ACCESS accessible-for-notify
    STATUS current
    DESCRIPTION
        "Parameter 'peer_address' in event BFD.21"
    ::= { bfdEventObjects21 1 }

bfdEventObjects22 OBJECT-IDENTITY
    STATUS current
    DESCRIPTION
        "Event BFD.22
        The system can not find a free source port for a new BFD session."
    ::= { bfdEventsGroup 22 }

bfd22_peer_address OBJECT-TYPE
    SYNTAX DisplayString
    MAX-ACCESS accessible-for-notify
    STATUS current
    DESCRIPTION
        "Parameter 'peer_address' in event BFD.22"
    ::= { bfdEventObjects22 1 }

bfdEventObjects23 OBJECT-IDENTITY
    STATUS current
    DESCRIPTION
        "Event BFD.23
        A new BFD session has been successfully created."
    ::= { bfdEventsGroup 23 }

bfd23_session_disc OBJECT-TYPE
    SYNTAX Integer32
    MAX-ACCESS accessible-for-notify
    STATUS current
    DESCRIPTION
        "Parameter 'session_disc' in event BFD.23"
    ::= { bfdEventObjects23 1 }

bfd23_local_address OBJECT-TYPE
    SYNTAX DisplayString
    MAX-ACCESS accessible-for-notify
    STATUS current
    DESCRIPTION
        "Parameter 'local_address' in event BFD.23"
    ::= { bfdEventObjects23 2 }

bfd23_peer_address OBJECT-TYPE
    SYNTAX DisplayString
    MAX-ACCESS accessible-for-notify
    STATUS current
    DESCRIPTION
        "Parameter 'peer_address' in event BFD.23"
    ::= { bfdEventObjects23 3 }

bfdEventObjects24 OBJECT-IDENTITY
    STATUS current
    DESCRIPTION
        "Event BFD.24
        The session that is been deleted does not exsist in the session hash."
    ::= { bfdEventsGroup 24 }

bfd24_session_disc OBJECT-TYPE
    SYNTAX Integer32
    MAX-ACCESS accessible-for-notify
    STATUS current
    DESCRIPTION
        "Parameter 'session_disc' in event BFD.24"
    ::= { bfdEventObjects24 1 }

bfdEventObjects25 OBJECT-IDENTITY
    STATUS current
    DESCRIPTION
        "Event BFD.25
        The session that is been deleted does not exsist in the peer hash."
    ::= { bfdEventsGroup 25 }

bfd25_session_disc OBJECT-TYPE
    SYNTAX Integer32
    MAX-ACCESS accessible-for-notify
    STATUS current
    DESCRIPTION
        "Parameter 'session_disc' in event BFD.25"
    ::= { bfdEventObjects25 1 }

bfdEventObjects26 OBJECT-IDENTITY
    STATUS current
    DESCRIPTION
        "Event BFD.26
        The session that is been deleted does not exsist in the session list."
    ::= { bfdEventsGroup 26 }

bfd26_session_disc OBJECT-TYPE
    SYNTAX Integer32
    MAX-ACCESS accessible-for-notify
    STATUS current
    DESCRIPTION
        "Parameter 'session_disc' in event BFD.26"
    ::= { bfdEventObjects26 1 }

bfdEventObjects27 OBJECT-IDENTITY
    STATUS current
    DESCRIPTION
        "Event BFD.27
        A BFD poll sequence has been started."
    ::= { bfdEventsGroup 27 }

bfd27_session_disc OBJECT-TYPE
    SYNTAX Integer32
    MAX-ACCESS accessible-for-notify
    STATUS current
    DESCRIPTION
        "Parameter 'session_disc' in event BFD.27"
    ::= { bfdEventObjects27 1 }

bfd27_peer_address OBJECT-TYPE
    SYNTAX DisplayString
    MAX-ACCESS accessible-for-notify
    STATUS current
    DESCRIPTION
        "Parameter 'peer_address' in event BFD.27"
    ::= { bfdEventObjects27 2 }

bfd27_detect_timer OBJECT-TYPE
    SYNTAX Integer32
    MAX-ACCESS accessible-for-notify
    STATUS current
    DESCRIPTION
        "Parameter 'detect_timer' in event BFD.27"
    ::= { bfdEventObjects27 3 }

bfdEventObjects28 OBJECT-IDENTITY
    STATUS current
    DESCRIPTION
        "Event BFD.28
        The session is administratively enabled."
    ::= { bfdEventsGroup 28 }

bfd28_session_disc OBJECT-TYPE
    SYNTAX Integer32
    MAX-ACCESS accessible-for-notify
    STATUS current
    DESCRIPTION
        "Parameter 'session_disc' in event BFD.28"
    ::= { bfdEventObjects28 1 }

bfd28_peer_address OBJECT-TYPE
    SYNTAX DisplayString
    MAX-ACCESS accessible-for-notify
    STATUS current
    DESCRIPTION
        "Parameter 'peer_address' in event BFD.28"
    ::= { bfdEventObjects28 2 }

bfdEventObjects29 OBJECT-IDENTITY
    STATUS current
    DESCRIPTION
        "Event BFD.29
        The session is administratively disabled."
    ::= { bfdEventsGroup 29 }

bfd29_session_disc OBJECT-TYPE
    SYNTAX Integer32
    MAX-ACCESS accessible-for-notify
    STATUS current
    DESCRIPTION
        "Parameter 'session_disc' in event BFD.29"
    ::= { bfdEventObjects29 1 }

bfd29_peer_address OBJECT-TYPE
    SYNTAX DisplayString
    MAX-ACCESS accessible-for-notify
    STATUS current
    DESCRIPTION
        "Parameter 'peer_address' in event BFD.29"
    ::= { bfdEventObjects29 2 }

bfdEventObjects33 OBJECT-IDENTITY
    STATUS current
    DESCRIPTION
        "Event BFD.33
        The system can not bind a socket to the BFD destination port."
    ::= { bfdEventsGroup 33 }

bfd33_port_number OBJECT-TYPE
    SYNTAX Integer32
    MAX-ACCESS accessible-for-notify
    STATUS current
    DESCRIPTION
        "Parameter 'port_number' in event BFD.33"
    ::= { bfdEventObjects33 1 }

bfdEventObjects34 OBJECT-IDENTITY
    STATUS current
    DESCRIPTION
        "Event BFD.34
        A routing protocol has been succesfully registered in a BFD session."
    ::= { bfdEventsGroup 34 }

bfd34_protocol_name OBJECT-TYPE
    SYNTAX DisplayString
    MAX-ACCESS accessible-for-notify
    STATUS current
    DESCRIPTION
        "Parameter 'protocol_name' in event BFD.34"
    ::= { bfdEventObjects34 1 }

bfd34_session_disc OBJECT-TYPE
    SYNTAX Integer32
    MAX-ACCESS accessible-for-notify
    STATUS current
    DESCRIPTION
        "Parameter 'session_disc' in event BFD.34"
    ::= { bfdEventObjects34 2 }

bfd34_local_address OBJECT-TYPE
    SYNTAX DisplayString
    MAX-ACCESS accessible-for-notify
    STATUS current
    DESCRIPTION
        "Parameter 'local_address' in event BFD.34"
    ::= { bfdEventObjects34 3 }

bfd34_peer_address OBJECT-TYPE
    SYNTAX DisplayString
    MAX-ACCESS accessible-for-notify
    STATUS current
    DESCRIPTION
        "Parameter 'peer_address' in event BFD.34"
    ::= { bfdEventObjects34 4 }

bfdEventObjects35 OBJECT-IDENTITY
    STATUS current
    DESCRIPTION
        "Event BFD.35
        The session can not be created."
    ::= { bfdEventsGroup 35 }

bfd35_local_address OBJECT-TYPE
    SYNTAX DisplayString
    MAX-ACCESS accessible-for-notify
    STATUS current
    DESCRIPTION
        "Parameter 'local_address' in event BFD.35"
    ::= { bfdEventObjects35 1 }

bfd35_peer_address OBJECT-TYPE
    SYNTAX DisplayString
    MAX-ACCESS accessible-for-notify
    STATUS current
    DESCRIPTION
        "Parameter 'peer_address' in event BFD.35"
    ::= { bfdEventObjects35 2 }

bfdEventObjects36 OBJECT-IDENTITY
    STATUS current
    DESCRIPTION
        "Event BFD.36
        There is no need to create a new BFD session with the peer, a session
        already exists."
    ::= { bfdEventsGroup 36 }

bfd36_peer_address OBJECT-TYPE
    SYNTAX DisplayString
    MAX-ACCESS accessible-for-notify
    STATUS current
    DESCRIPTION
        "Parameter 'peer_address' in event BFD.36"
    ::= { bfdEventObjects36 1 }

bfd36_session_disc OBJECT-TYPE
    SYNTAX Integer32
    MAX-ACCESS accessible-for-notify
    STATUS current
    DESCRIPTION
        "Parameter 'session_disc' in event BFD.36"
    ::= { bfdEventObjects36 2 }

bfd36_bfd_state OBJECT-TYPE
    SYNTAX DisplayString
    MAX-ACCESS accessible-for-notify
    STATUS current
    DESCRIPTION
        "Parameter 'bfd_state' in event BFD.36"
    ::= { bfdEventObjects36 3 }

bfdEventObjects37 OBJECT-IDENTITY
    STATUS current
    DESCRIPTION
        "Event BFD.37
        A change in the BFD state machine has happened."
    ::= { bfdEventsGroup 37 }

bfd37_session_disc OBJECT-TYPE
    SYNTAX Integer32
    MAX-ACCESS accessible-for-notify
    STATUS current
    DESCRIPTION
        "Parameter 'session_disc' in event BFD.37"
    ::= { bfdEventObjects37 1 }

bfd37_bfd_prev_state OBJECT-TYPE
    SYNTAX DisplayString
    MAX-ACCESS accessible-for-notify
    STATUS current
    DESCRIPTION
        "Parameter 'bfd_prev_state' in event BFD.37"
    ::= { bfdEventObjects37 2 }

bfd37_bfd_new_state OBJECT-TYPE
    SYNTAX DisplayString
    MAX-ACCESS accessible-for-notify
    STATUS current
    DESCRIPTION
        "Parameter 'bfd_new_state' in event BFD.37"
    ::= { bfdEventObjects37 3 }

bfdEventObjects38 OBJECT-IDENTITY
    STATUS current
    DESCRIPTION
        "Event BFD.38
        A packet has been sent to a neighbour."
    ::= { bfdEventsGroup 38 }

bfd38_local_address OBJECT-TYPE
    SYNTAX DisplayString
    MAX-ACCESS accessible-for-notify
    STATUS current
    DESCRIPTION
        "Parameter 'local_address' in event BFD.38"
    ::= { bfdEventObjects38 1 }

bfd38_peer_address OBJECT-TYPE
    SYNTAX DisplayString
    MAX-ACCESS accessible-for-notify
    STATUS current
    DESCRIPTION
        "Parameter 'peer_address' in event BFD.38"
    ::= { bfdEventObjects38 2 }

bfd38_bfdversion OBJECT-TYPE
    SYNTAX Integer32
    MAX-ACCESS accessible-for-notify
    STATUS current
    DESCRIPTION
        "Parameter 'bfdversion' in event BFD.38"
    ::= { bfdEventObjects38 3 }

bfd38_diag_code OBJECT-TYPE
    SYNTAX Integer32
    MAX-ACCESS accessible-for-notify
    STATUS current
    DESCRIPTION
        "Parameter 'diag_code' in event BFD.38"
    ::= { bfdEventObjects38 4 }

bfd38_flags OBJECT-TYPE
    SYNTAX DisplayString
    MAX-ACCESS accessible-for-notify
    STATUS current
    DESCRIPTION
        "Parameter 'flags' in event BFD.38"
    ::= { bfdEventObjects38 5 }

bfd38_detetct_mult OBJECT-TYPE
    SYNTAX Integer32
    MAX-ACCESS accessible-for-notify
    STATUS current
    DESCRIPTION
        "Parameter 'detetct_mult' in event BFD.38"
    ::= { bfdEventObjects38 6 }

bfd38_pkt_len OBJECT-TYPE
    SYNTAX Integer32
    MAX-ACCESS accessible-for-notify
    STATUS current
    DESCRIPTION
        "Parameter 'pkt_len' in event BFD.38"
    ::= { bfdEventObjects38 7 }

bfdEventObjects39 OBJECT-IDENTITY
    STATUS current
    DESCRIPTION
        "Event BFD.39
        A packet has been received from a neighbour."
    ::= { bfdEventsGroup 39 }

bfd39_peer_address OBJECT-TYPE
    SYNTAX DisplayString
    MAX-ACCESS accessible-for-notify
    STATUS current
    DESCRIPTION
        "Parameter 'peer_address' in event BFD.39"
    ::= { bfdEventObjects39 1 }

bfd39_local_address OBJECT-TYPE
    SYNTAX DisplayString
    MAX-ACCESS accessible-for-notify
    STATUS current
    DESCRIPTION
        "Parameter 'local_address' in event BFD.39"
    ::= { bfdEventObjects39 2 }

bfd39_bfdversion OBJECT-TYPE
    SYNTAX Integer32
    MAX-ACCESS accessible-for-notify
    STATUS current
    DESCRIPTION
        "Parameter 'bfdversion' in event BFD.39"
    ::= { bfdEventObjects39 3 }

bfd39_diag_code OBJECT-TYPE
    SYNTAX Integer32
    MAX-ACCESS accessible-for-notify
    STATUS current
    DESCRIPTION
        "Parameter 'diag_code' in event BFD.39"
    ::= { bfdEventObjects39 4 }

bfd39_flags OBJECT-TYPE
    SYNTAX DisplayString
    MAX-ACCESS accessible-for-notify
    STATUS current
    DESCRIPTION
        "Parameter 'flags' in event BFD.39"
    ::= { bfdEventObjects39 5 }

bfd39_detetct_mult OBJECT-TYPE
    SYNTAX Integer32
    MAX-ACCESS accessible-for-notify
    STATUS current
    DESCRIPTION
        "Parameter 'detetct_mult' in event BFD.39"
    ::= { bfdEventObjects39 6 }

bfd39_pkt_len OBJECT-TYPE
    SYNTAX Integer32
    MAX-ACCESS accessible-for-notify
    STATUS current
    DESCRIPTION
        "Parameter 'pkt_len' in event BFD.39"
    ::= { bfdEventObjects39 7 }

bfdEventObjects40 OBJECT-IDENTITY
    STATUS current
    DESCRIPTION
        "Event BFD.40
        This event shows the BFD packet body contents."
    ::= { bfdEventsGroup 40 }

bfd40_mydisc OBJECT-TYPE
    SYNTAX Integer32
    MAX-ACCESS accessible-for-notify
    STATUS current
    DESCRIPTION
        "Parameter 'mydisc' in event BFD.40"
    ::= { bfdEventObjects40 1 }

bfd40_yourdisc OBJECT-TYPE
    SYNTAX Integer32
    MAX-ACCESS accessible-for-notify
    STATUS current
    DESCRIPTION
        "Parameter 'yourdisc' in event BFD.40"
    ::= { bfdEventObjects40 2 }

bfd40_des_mintx OBJECT-TYPE
    SYNTAX Integer32
    MAX-ACCESS accessible-for-notify
    STATUS current
    DESCRIPTION
        "Parameter 'des_mintx' in event BFD.40"
    ::= { bfdEventObjects40 3 }

bfd40_req_minrx OBJECT-TYPE
    SYNTAX Integer32
    MAX-ACCESS accessible-for-notify
    STATUS current
    DESCRIPTION
        "Parameter 'req_minrx' in event BFD.40"
    ::= { bfdEventObjects40 4 }

bfd40_req_minechorx OBJECT-TYPE
    SYNTAX Integer32
    MAX-ACCESS accessible-for-notify
    STATUS current
    DESCRIPTION
        "Parameter 'req_minechorx' in event BFD.40"
    ::= { bfdEventObjects40 5 }

bfdEventObjects42 OBJECT-IDENTITY
    STATUS current
    DESCRIPTION
        "Event BFD.42
        The BFD parameter configuration does not exist or an interface with
        this IP address does not exist. Protocol can not be registered. "
    ::= { bfdEventsGroup 42 }

bfd42_intfc_addr OBJECT-TYPE
    SYNTAX DisplayString
    MAX-ACCESS accessible-for-notify
    STATUS current
    DESCRIPTION
        "Parameter 'intfc_addr' in event BFD.42"
    ::= { bfdEventObjects42 1 }

bfd42_protocol OBJECT-TYPE
    SYNTAX DisplayString
    MAX-ACCESS accessible-for-notify
    STATUS current
    DESCRIPTION
        "Parameter 'protocol' in event BFD.42"
    ::= { bfdEventObjects42 2 }

bfdEventObjects43 OBJECT-IDENTITY
    STATUS current
    DESCRIPTION
        "Event BFD.43
        A BFD packet with zero in the Your Duscriminator field and with not Down
        or Admindown in the state field has been received."
    ::= { bfdEventsGroup 43 }

bfd43_peer_address OBJECT-TYPE
    SYNTAX DisplayString
    MAX-ACCESS accessible-for-notify
    STATUS current
    DESCRIPTION
        "Parameter 'peer_address' in event BFD.43"
    ::= { bfdEventObjects43 1 }

bfdEventObjects44 OBJECT-IDENTITY
    STATUS current
    DESCRIPTION
        "Event BFD.44
        A routing protocol registered in a BFD session is being deleted."
    ::= { bfdEventsGroup 44 }

bfd44_protocol_name OBJECT-TYPE
    SYNTAX DisplayString
    MAX-ACCESS accessible-for-notify
    STATUS current
    DESCRIPTION
        "Parameter 'protocol_name' in event BFD.44"
    ::= { bfdEventObjects44 1 }

bfd44_session_disc OBJECT-TYPE
    SYNTAX Integer32
    MAX-ACCESS accessible-for-notify
    STATUS current
    DESCRIPTION
        "Parameter 'session_disc' in event BFD.44"
    ::= { bfdEventObjects44 2 }

bfd44_local_address OBJECT-TYPE
    SYNTAX DisplayString
    MAX-ACCESS accessible-for-notify
    STATUS current
    DESCRIPTION
        "Parameter 'local_address' in event BFD.44"
    ::= { bfdEventObjects44 3 }

bfd44_peer_address OBJECT-TYPE
    SYNTAX DisplayString
    MAX-ACCESS accessible-for-notify
    STATUS current
    DESCRIPTION
        "Parameter 'peer_address' in event BFD.44"
    ::= { bfdEventObjects44 4 }

bfdEventObjects45 OBJECT-IDENTITY
    STATUS current
    DESCRIPTION
        "Event BFD.45
        The Key Chain is probably not configured, so the protocol is not able to
        find it."
    ::= { bfdEventsGroup 45 }

bfd45_keychain_name OBJECT-TYPE
    SYNTAX DisplayString
    MAX-ACCESS accessible-for-notify
    STATUS current
    DESCRIPTION
        "Parameter 'keychain_name' in event BFD.45"
    ::= { bfdEventObjects45 1 }

bfdEventObjects46 OBJECT-IDENTITY
    STATUS current
    DESCRIPTION
        "Event BFD.46
        The protocol is not able to find a valid Key inside the Key Chain, maybe
        it is not configured."
    ::= { bfdEventsGroup 46 }

bfd46_keychain_name OBJECT-TYPE
    SYNTAX DisplayString
    MAX-ACCESS accessible-for-notify
    STATUS current
    DESCRIPTION
        "Parameter 'keychain_name' in event BFD.46"
    ::= { bfdEventObjects46 1 }

bfdEventObjects47 OBJECT-IDENTITY
    STATUS current
    DESCRIPTION
        "Event BFD.47
        A packet without authentication has been received but session requires
        authentication. The packet will be discarded and ignored."
    ::= { bfdEventsGroup 47 }

bfd47_peer_address OBJECT-TYPE
    SYNTAX DisplayString
    MAX-ACCESS accessible-for-notify
    STATUS current
    DESCRIPTION
        "Parameter 'peer_address' in event BFD.47"
    ::= { bfdEventObjects47 1 }

bfd47_authentication_type OBJECT-TYPE
    SYNTAX DisplayString
    MAX-ACCESS accessible-for-notify
    STATUS current
    DESCRIPTION
        "Parameter 'authentication_type' in event BFD.47"
    ::= { bfdEventObjects47 2 }

bfdEventObjects48 OBJECT-IDENTITY
    STATUS current
    DESCRIPTION
        "Event BFD.48
        A packet with authentication has been received but authentication type
        is not correct for the configured session. The packet will be discarded
        and ignored."
    ::= { bfdEventsGroup 48 }

bfd48_authentication_type OBJECT-TYPE
    SYNTAX DisplayString
    MAX-ACCESS accessible-for-notify
    STATUS current
    DESCRIPTION
        "Parameter 'authentication_type' in event BFD.48"
    ::= { bfdEventObjects48 1 }

bfd48_peer_address OBJECT-TYPE
    SYNTAX DisplayString
    MAX-ACCESS accessible-for-notify
    STATUS current
    DESCRIPTION
        "Parameter 'peer_address' in event BFD.48"
    ::= { bfdEventObjects48 2 }

bfdEventObjects49 OBJECT-IDENTITY
    STATUS current
    DESCRIPTION
        "Event BFD.49
        A packet with authentication has been received but the Key ID is invalid
        for the configured session. Check both remote and local configurations."
    ::= { bfdEventsGroup 49 }

bfd49_key_identifier OBJECT-TYPE
    SYNTAX Integer32
    MAX-ACCESS accessible-for-notify
    STATUS current
    DESCRIPTION
        "Parameter 'key_identifier' in event BFD.49"
    ::= { bfdEventObjects49 1 }

bfd49_peer_address OBJECT-TYPE
    SYNTAX DisplayString
    MAX-ACCESS accessible-for-notify
    STATUS current
    DESCRIPTION
        "Parameter 'peer_address' in event BFD.49"
    ::= { bfdEventObjects49 2 }

bfdEventObjects50 OBJECT-IDENTITY
    STATUS current
    DESCRIPTION
        "Event BFD.50
        A packet with authentication has been received but authentication
        length is invalid for Authentication Type."
    ::= { bfdEventsGroup 50 }

bfd50_authentication_length OBJECT-TYPE
    SYNTAX Integer32
    MAX-ACCESS accessible-for-notify
    STATUS current
    DESCRIPTION
        "Parameter 'authentication_length' in event BFD.50"
    ::= { bfdEventObjects50 1 }

bfd50_peer_address OBJECT-TYPE
    SYNTAX DisplayString
    MAX-ACCESS accessible-for-notify
    STATUS current
    DESCRIPTION
        "Parameter 'peer_address' in event BFD.50"
    ::= { bfdEventObjects50 2 }

bfdEventObjects51 OBJECT-IDENTITY
    STATUS current
    DESCRIPTION
        "Event BFD.51
        The protocol is not able to find received Key ID inside Key Chain, maybe
        it is not configured."
    ::= { bfdEventsGroup 51 }

bfd51_key_identifier OBJECT-TYPE
    SYNTAX Integer32
    MAX-ACCESS accessible-for-notify
    STATUS current
    DESCRIPTION
        "Parameter 'key_identifier' in event BFD.51"
    ::= { bfdEventObjects51 1 }

bfd51_keychain_name OBJECT-TYPE
    SYNTAX DisplayString
    MAX-ACCESS accessible-for-notify
    STATUS current
    DESCRIPTION
        "Parameter 'keychain_name' in event BFD.51"
    ::= { bfdEventObjects51 2 }

bfd51_peer_address OBJECT-TYPE
    SYNTAX DisplayString
    MAX-ACCESS accessible-for-notify
    STATUS current
    DESCRIPTION
        "Parameter 'peer_address' in event BFD.51"
    ::= { bfdEventObjects51 3 }

bfdEventObjects52 OBJECT-IDENTITY
    STATUS current
    DESCRIPTION
        "Event BFD.52
        A packet with authentication has been received but authentication
        sequence number is invalid."
    ::= { bfdEventsGroup 52 }

bfd52_authentication_seqnum OBJECT-TYPE
    SYNTAX Integer32
    MAX-ACCESS accessible-for-notify
    STATUS current
    DESCRIPTION
        "Parameter 'authentication_seqnum' in event BFD.52"
    ::= { bfdEventObjects52 1 }

bfd52_peer_address OBJECT-TYPE
    SYNTAX DisplayString
    MAX-ACCESS accessible-for-notify
    STATUS current
    DESCRIPTION
        "Parameter 'peer_address' in event BFD.52"
    ::= { bfdEventObjects52 2 }

bfd52_last_authentication_seqnum OBJECT-TYPE
    SYNTAX Integer32
    MAX-ACCESS accessible-for-notify
    STATUS current
    DESCRIPTION
        "Parameter 'last_authentication_seqnum' in event BFD.52"
    ::= { bfdEventObjects52 3 }

bfdEventObjects53 OBJECT-IDENTITY
    STATUS current
    DESCRIPTION
        "Event BFD.53
        A packet with authentication has been received but authentication
        digest is invalid."
    ::= { bfdEventsGroup 53 }

bfd53_peer_address OBJECT-TYPE
    SYNTAX DisplayString
    MAX-ACCESS accessible-for-notify
    STATUS current
    DESCRIPTION
        "Parameter 'peer_address' in event BFD.53"
    ::= { bfdEventObjects53 1 }


bfdNotification1 NOTIFICATION-TYPE
    STATUS current
    DESCRIPTION
        "Notification of Event BFD.1

        Message: 'Error receiving from BFD socket'

        The BFD protocol receive function has failed."
    ::= { bfdNotificationsPrefix 1 }

bfdNotification2 NOTIFICATION-TYPE
    OBJECTS { 
              bfd2_ttl_received, 
              bfd2_peer_address 
            }
    STATUS current
    DESCRIPTION
        "Notification of Event BFD.2

        Message: 'Received pkt with invalid TTL $1 from $2'

        Parameters list:
              $1: bfd2_ttl_received
              $2: bfd2_peer_address

        A BFD packet with invalid TTL value has been received."
    ::= { bfdNotificationsPrefix 2 }

bfdNotification3 NOTIFICATION-TYPE
    OBJECTS { 
              bfd3_peer_address 
            }
    STATUS current
    DESCRIPTION
        "Notification of Event BFD.3

        Message: 'Received short packet from $1'

        Parameters list:
              $1: bfd3_peer_address

        A BFD packet with invalid size has been received."
    ::= { bfdNotificationsPrefix 3 }

bfdNotification4 NOTIFICATION-TYPE
    OBJECTS { 
              bfd4_protocol_version, 
              bfd4_peer_address 
            }
    STATUS current
    DESCRIPTION
        "Notification of Event BFD.4

        Message: 'Received bad version $1 from $2'

        Parameters list:
              $1: bfd4_protocol_version
              $2: bfd4_peer_address

        A BFD packet with invalid BFD version has been received."
    ::= { bfdNotificationsPrefix 4 }

bfdNotification5 NOTIFICATION-TYPE
    OBJECTS { 
              bfd5_packet_legth, 
              bfd5_peer_address 
            }
    STATUS current
    DESCRIPTION
        "Notification of Event BFD.5

        Message: 'Invalid length $1 in control pkt from $2'

        Parameters list:
              $1: bfd5_packet_legth
              $2: bfd5_peer_address

        A BFD packet with invalid length has been received."
    ::= { bfdNotificationsPrefix 5 }

bfdNotification6 NOTIFICATION-TYPE
    OBJECTS { 
              bfd6_peer_address 
            }
    STATUS current
    DESCRIPTION
        "Notification of Event BFD.6

        Message: 'Detect Mult is zero in pkt from $1'

        Parameters list:
              $1: bfd6_peer_address

        A BFD packet with zero detect time multiplier has been received."
    ::= { bfdNotificationsPrefix 6 }

bfdNotification7 NOTIFICATION-TYPE
    OBJECTS { 
              bfd7_peer_address 
            }
    STATUS current
    DESCRIPTION
        "Notification of Event BFD.7

        Message: 'My discriminator is zero in pkt from $1'

        Parameters list:
              $1: bfd7_peer_address

        A BFD packet with zero in the My Discriminator field has been received."
    ::= { bfdNotificationsPrefix 7 }

bfdNotification8 NOTIFICATION-TYPE
    OBJECTS { 
              bfd8_peer_address 
            }
    STATUS current
    DESCRIPTION
        "Notification of Event BFD.8

        Message: 'Zero Your Discriminator and non-zero I Hear You in pkt from $1'

        Parameters list:
              $1: bfd8_peer_address

        A BFD packet with zero in the Your Duscriminator field and non-zero
        in the I Hear You flag has been received."
    ::= { bfdNotificationsPrefix 8 }

bfdNotification9 NOTIFICATION-TYPE
    OBJECTS { 
              bfd9_peer_address 
            }
    STATUS current
    DESCRIPTION
        "Notification of Event BFD.9

        Message: 'Can not find session for ctl pkt from $1'

        Parameters list:
              $1: bfd9_peer_address

        The system could not find a valid session for the BFD packet received."
    ::= { bfdNotificationsPrefix 9 }

bfdNotification10 NOTIFICATION-TYPE
    OBJECTS { 
              bfd10_session_disc, 
              bfd10_peer_address 
            }
    STATUS current
    DESCRIPTION
        "Notification of Event BFD.10

        Message: 'Timer renegotiation started for session 0x$1 to peer $2'

        Parameters list:
              $1: bfd10_session_disc
              $2: bfd10_peer_address

        Some of the BFD definition parameters has changed and timers must be
        renegotiated."
    ::= { bfdNotificationsPrefix 10 }

bfdNotification11 NOTIFICATION-TYPE
    OBJECTS { 
              bfd11_session_disc, 
              bfd11_peer_address 
            }
    STATUS current
    DESCRIPTION
        "Notification of Event BFD.11

        Message: 'Poll sequence concluded for session 0x$1 to peer $2'

        Parameters list:
              $1: bfd11_session_disc
              $2: bfd11_peer_address

        A BFD poll sequence has been finished."
    ::= { bfdNotificationsPrefix 11 }

bfdNotification12 NOTIFICATION-TYPE
    OBJECTS { 
              bfd12_session_disc, 
              bfd12_peer_address 
            }
    STATUS current
    DESCRIPTION
        "Notification of Event BFD.12

        Message: 'Neigbor down on session 0x$1 with peer $2'

        Parameters list:
              $1: bfd12_session_disc
              $2: bfd12_peer_address

        A BFD session is coming to DOWN state because remote peer is 
        administratively down."
    ::= { bfdNotificationsPrefix 12 }

bfdNotification13 NOTIFICATION-TYPE
    OBJECTS { 
              bfd13_session_disc, 
              bfd13_peer_address,
              bfd13_bfd_state 
            }
    STATUS current
    DESCRIPTION
        "Notification of Event BFD.13

        Message: 'Detect timeout on session 0x$1 with peer $2, in state $3'

        Parameters list:
              $1: bfd13_session_disc
              $2: bfd13_peer_address
              $3: bfd13_bfd_state

        The detection period has been finished without receiving packets from
        the remote peer. Session will come down."
    ::= { bfdNotificationsPrefix 13 }

bfdNotification14 NOTIFICATION-TYPE
    OBJECTS { 
              bfd14_session_disc, 
              bfd14_peer_address 
            }
    STATUS current
    DESCRIPTION
        "Notification of Event BFD.14

        Message: 'Session 0x$1 down to peer $2'

        Parameters list:
              $1: bfd14_session_disc
              $2: bfd14_peer_address

        A BFD session is coming to DOWN state."
    ::= { bfdNotificationsPrefix 14 }

bfdNotification15 NOTIFICATION-TYPE
    OBJECTS { 
              bfd15_session_disc, 
              bfd15_peer_address 
            }
    STATUS current
    DESCRIPTION
        "Notification of Event BFD.15

        Message: 'Session 0x$1 up to peer $2'

        Parameters list:
              $1: bfd15_session_disc
              $2: bfd15_peer_address

        A BFD session is coming to UP state."
    ::= { bfdNotificationsPrefix 15 }

bfdNotification16 NOTIFICATION-TYPE
    OBJECTS { 
              bfd16_session_disc, 
              bfd16_peer_address 
            }
    STATUS current
    DESCRIPTION
        "Notification of Event BFD.16

        Message: 'Can not find session for yourDisc 0x$1 from $2'

        Parameters list:
              $1: bfd16_session_disc
              $2: bfd16_peer_address

        A BFD session with this value of Your Discriminator does not exist in
        the system."
    ::= { bfdNotificationsPrefix 16 }

bfdNotification17 NOTIFICATION-TYPE
    OBJECTS { 
              bfd17_peer_address 
            }
    STATUS current
    DESCRIPTION
        "Notification of Event BFD.17

        Message: 'Can not find session for peer $1'

        Parameters list:
              $1: bfd17_peer_address

        A BFD session with this peer does not exist in the system."
    ::= { bfdNotificationsPrefix 17 }

bfdNotification18 NOTIFICATION-TYPE
    OBJECTS { 
              bfd18_peer_address 
            }
    STATUS current
    DESCRIPTION
        "Notification of Event BFD.18

        Message: 'Error sending control pkt to peer $1'

        Parameters list:
              $1: bfd18_peer_address

        The BFD protocol sending function has failed."
    ::= { bfdNotificationsPrefix 18 }

bfdNotification19 NOTIFICATION-TYPE
    OBJECTS { 
              bfd19_peer_address 
            }
    STATUS current
    DESCRIPTION
        "Notification of Event BFD.19

        Message: 'Can not malloc memory for new session for peer $1'

        Parameters list:
              $1: bfd19_peer_address

        The system has not enough memory to allocate a new BFD session."
    ::= { bfdNotificationsPrefix 19 }

bfdNotification20 NOTIFICATION-TYPE
    OBJECTS { 
              bfd20_peer_address 
            }
    STATUS current
    DESCRIPTION
        "Notification of Event BFD.20

        Message: 'Can not get socket for new session for peer $1'

        Parameters list:
              $1: bfd20_peer_address

        The system can not get a free socket for a new BFD session."
    ::= { bfdNotificationsPrefix 20 }

bfdNotification21 NOTIFICATION-TYPE
    OBJECTS { 
              bfd21_peer_address 
            }
    STATUS current
    DESCRIPTION
        "Notification of Event BFD.21

        Message: 'Can not set TTL for new session for peer $1'

        Parameters list:
              $1: bfd21_peer_address

        The system can not set TTL value for a new BFD session."
    ::= { bfdNotificationsPrefix 21 }

bfdNotification22 NOTIFICATION-TYPE
    OBJECTS { 
              bfd22_peer_address 
            }
    STATUS current
    DESCRIPTION
        "Notification of Event BFD.22

        Message: 'Can not find source port for new session for peer $1'

        Parameters list:
              $1: bfd22_peer_address

        The system can not find a free source port for a new BFD session."
    ::= { bfdNotificationsPrefix 22 }

bfdNotification23 NOTIFICATION-TYPE
    OBJECTS { 
              bfd23_session_disc, 
              bfd23_local_address,
              bfd23_peer_address 
            }
    STATUS current
    DESCRIPTION
        "Notification of Event BFD.23

        Message: 'Created new session 0x$1 from $2 to peer $3'

        Parameters list:
              $1: bfd23_session_disc
              $2: bfd23_local_address
              $3: bfd23_peer_address

        A new BFD session has been successfully created."
    ::= { bfdNotificationsPrefix 23 }

bfdNotification24 NOTIFICATION-TYPE
    OBJECTS { 
              bfd24_session_disc 
            }
    STATUS current
    DESCRIPTION
        "Notification of Event BFD.24

        Message: 'Can not find session 0x$1 in session hash'

        Parameters list:
              $1: bfd24_session_disc

        The session that is been deleted does not exsist in the session hash."
    ::= { bfdNotificationsPrefix 24 }

bfdNotification25 NOTIFICATION-TYPE
    OBJECTS { 
              bfd25_session_disc 
            }
    STATUS current
    DESCRIPTION
        "Notification of Event BFD.25

        Message: 'Can not find session 0x$1 in peer hash'

        Parameters list:
              $1: bfd25_session_disc

        The session that is been deleted does not exsist in the peer hash."
    ::= { bfdNotificationsPrefix 25 }

bfdNotification26 NOTIFICATION-TYPE
    OBJECTS { 
              bfd26_session_disc 
            }
    STATUS current
    DESCRIPTION
        "Notification of Event BFD.26

        Message: 'Can not find session 0x$1 in session list'

        Parameters list:
              $1: bfd26_session_disc

        The session that is been deleted does not exsist in the session list."
    ::= { bfdNotificationsPrefix 26 }

bfdNotification27 NOTIFICATION-TYPE
    OBJECTS { 
              bfd27_session_disc, 
              bfd27_peer_address,
              bfd27_detect_timer 
            }
    STATUS current
    DESCRIPTION
        "Notification of Event BFD.27

        Message: 'Poll sequence started for session 0x$1 to peer $2, timer $3'

        Parameters list:
              $1: bfd27_session_disc
              $2: bfd27_peer_address
              $3: bfd27_detect_timer

        A BFD poll sequence has been started."
    ::= { bfdNotificationsPrefix 27 }

bfdNotification28 NOTIFICATION-TYPE
    OBJECTS { 
              bfd28_session_disc, 
              bfd28_peer_address 
            }
    STATUS current
    DESCRIPTION
        "Notification of Event BFD.28

        Message: 'Session 0x$1 to peer $2 enabled'

        Parameters list:
              $1: bfd28_session_disc
              $2: bfd28_peer_address

        The session is administratively enabled."
    ::= { bfdNotificationsPrefix 28 }

bfdNotification29 NOTIFICATION-TYPE
    OBJECTS { 
              bfd29_session_disc, 
              bfd29_peer_address 
            }
    STATUS current
    DESCRIPTION
        "Notification of Event BFD.29

        Message: 'Session 0x$1 to peer $2 disabled'

        Parameters list:
              $1: bfd29_session_disc
              $2: bfd29_peer_address

        The session is administratively disabled."
    ::= { bfdNotificationsPrefix 29 }

bfdNotification30 NOTIFICATION-TYPE
    STATUS current
    DESCRIPTION
        "Notification of Event BFD.30

        Message: 'Can not get receive socket'

        The system can not get a free socket for the BFD packet reception."
    ::= { bfdNotificationsPrefix 30 }

bfdNotification31 NOTIFICATION-TYPE
    STATUS current
    DESCRIPTION
        "Notification of Event BFD.31

        Message: 'Can not set TTL for outgoing packets'

        The system can not set TTL value for outgoing BFD packets."
    ::= { bfdNotificationsPrefix 31 }

bfdNotification32 NOTIFICATION-TYPE
    STATUS current
    DESCRIPTION
        "Notification of Event BFD.32

        Message: 'Can not set receive TTL for incoming packets'

        The system can not set TTL value for incoming BFD packets."
    ::= { bfdNotificationsPrefix 32 }

bfdNotification33 NOTIFICATION-TYPE
    OBJECTS { 
              bfd33_port_number 
            }
    STATUS current
    DESCRIPTION
        "Notification of Event BFD.33

        Message: 'Can not bind socket to default port $1'

        Parameters list:
              $1: bfd33_port_number

        The system can not bind a socket to the BFD destination port."
    ::= { bfdNotificationsPrefix 33 }

bfdNotification34 NOTIFICATION-TYPE
    OBJECTS { 
              bfd34_protocol_name, 
              bfd34_session_disc,
              bfd34_local_address,
              bfd34_peer_address 
            }
    STATUS current
    DESCRIPTION
        "Notification of Event BFD.34

        Message: 'Routing protocol $1 registered in session 0x$2 from $3 to peer $4'

        Parameters list:
              $1: bfd34_protocol_name
              $2: bfd34_session_disc
              $3: bfd34_local_address
              $4: bfd34_peer_address

        A routing protocol has been succesfully registered in a BFD session."
    ::= { bfdNotificationsPrefix 34 }

bfdNotification35 NOTIFICATION-TYPE
    OBJECTS { 
              bfd35_local_address, 
              bfd35_peer_address 
            }
    STATUS current
    DESCRIPTION
        "Notification of Event BFD.35

        Message: 'Can not create session from $1 to peer $2'

        Parameters list:
              $1: bfd35_local_address
              $2: bfd35_peer_address

        The session can not be created."
    ::= { bfdNotificationsPrefix 35 }

bfdNotification36 NOTIFICATION-TYPE
    OBJECTS { 
              bfd36_peer_address, 
              bfd36_session_disc,
              bfd36_bfd_state 
            }
    STATUS current
    DESCRIPTION
        "Notification of Event BFD.36

        Message: 'A session already exists with peer $1, session: 0x$2, state: $3'

        Parameters list:
              $1: bfd36_peer_address
              $2: bfd36_session_disc
              $3: bfd36_bfd_state

        There is no need to create a new BFD session with the peer, a session
        already exists."
    ::= { bfdNotificationsPrefix 36 }

bfdNotification37 NOTIFICATION-TYPE
    OBJECTS { 
              bfd37_session_disc, 
              bfd37_bfd_prev_state,
              bfd37_bfd_new_state 
            }
    STATUS current
    DESCRIPTION
        "Notification of Event BFD.37

        Message: 'BFD session 0x$1 state change $2 -> $3'

        Parameters list:
              $1: bfd37_session_disc
              $2: bfd37_bfd_prev_state
              $3: bfd37_bfd_new_state

        A change in the BFD state machine has happened."
    ::= { bfdNotificationsPrefix 37 }

bfdNotification38 NOTIFICATION-TYPE
    OBJECTS { 
              bfd38_local_address, 
              bfd38_peer_address,
              bfd38_bfdversion,
              bfd38_diag_code,
              bfd38_flags,
              bfd38_detetct_mult,
              bfd38_pkt_len 
            }
    STATUS current
    DESCRIPTION
        "Notification of Event BFD.38

        Message: 'TxPkt src:$1 dst:$2 ver:$3 diag:$4 $5 mult:$6 len:$7'

        Parameters list:
              $1: bfd38_local_address
              $2: bfd38_peer_address
              $3: bfd38_bfdversion
              $4: bfd38_diag_code
              $5: bfd38_flags
              $6: bfd38_detetct_mult
              $7: bfd38_pkt_len

        A packet has been sent to a neighbour."
    ::= { bfdNotificationsPrefix 38 }

bfdNotification39 NOTIFICATION-TYPE
    OBJECTS { 
              bfd39_peer_address, 
              bfd39_local_address,
              bfd39_bfdversion,
              bfd39_diag_code,
              bfd39_flags,
              bfd39_detetct_mult,
              bfd39_pkt_len 
            }
    STATUS current
    DESCRIPTION
        "Notification of Event BFD.39

        Message: 'RxPkt src:$1 dst:$2 ver:$3 diag:$4 $5 mult:$6 len:$7'

        Parameters list:
              $1: bfd39_peer_address
              $2: bfd39_local_address
              $3: bfd39_bfdversion
              $4: bfd39_diag_code
              $5: bfd39_flags
              $6: bfd39_detetct_mult
              $7: bfd39_pkt_len

        A packet has been received from a neighbour."
    ::= { bfdNotificationsPrefix 39 }

bfdNotification40 NOTIFICATION-TYPE
    OBJECTS { 
              bfd40_mydisc, 
              bfd40_yourdisc,
              bfd40_des_mintx,
              bfd40_req_minrx,
              bfd40_req_minechorx 
            }
    STATUS current
    DESCRIPTION
        "Notification of Event BFD.40

        Message: 'mydisc:0x$1 ydisc:0x$2 Dmtx:$3 Rmtx:$4 Rmerx:$5'

        Parameters list:
              $1: bfd40_mydisc
              $2: bfd40_yourdisc
              $3: bfd40_des_mintx
              $4: bfd40_req_minrx
              $5: bfd40_req_minechorx

        This event shows the BFD packet body contents."
    ::= { bfdNotificationsPrefix 40 }

bfdNotification41 NOTIFICATION-TYPE
    STATUS current
    DESCRIPTION
        "Notification of Event BFD.41

        Message: 'Disable this event to disable event packet sampling'

        By disabling this event all received and sent packets will display
        an event. "
    ::= { bfdNotificationsPrefix 41 }

bfdNotification42 NOTIFICATION-TYPE
    OBJECTS { 
              bfd42_intfc_addr, 
              bfd42_protocol 
            }
    STATUS current
    DESCRIPTION
        "Notification of Event BFD.42

        Message: 'Could not find BFD configuration for interface with addr: $1, protocol $2 registration failed'

        Parameters list:
              $1: bfd42_intfc_addr
              $2: bfd42_protocol

        The BFD parameter configuration does not exist or an interface with
        this IP address does not exist. Protocol can not be registered. "
    ::= { bfdNotificationsPrefix 42 }

bfdNotification43 NOTIFICATION-TYPE
    OBJECTS { 
              bfd43_peer_address 
            }
    STATUS current
    DESCRIPTION
        "Notification of Event BFD.43

        Message: 'Zero Your Discriminator and peer state not DOWN in pkt from $1'

        Parameters list:
              $1: bfd43_peer_address

        A BFD packet with zero in the Your Duscriminator field and with not Down
        or Admindown in the state field has been received."
    ::= { bfdNotificationsPrefix 43 }

bfdNotification44 NOTIFICATION-TYPE
    OBJECTS { 
              bfd44_protocol_name, 
              bfd44_session_disc,
              bfd44_local_address,
              bfd44_peer_address 
            }
    STATUS current
    DESCRIPTION
        "Notification of Event BFD.44

        Message: 'Routing protocol $1 registered in session 0x$2 from $3 to peer $4 is being deleted'

        Parameters list:
              $1: bfd44_protocol_name
              $2: bfd44_session_disc
              $3: bfd44_local_address
              $4: bfd44_peer_address

        A routing protocol registered in a BFD session is being deleted."
    ::= { bfdNotificationsPrefix 44 }

bfdNotification45 NOTIFICATION-TYPE
    OBJECTS { 
              bfd45_keychain_name 
            }
    STATUS current
    DESCRIPTION
        "Notification of Event BFD.45

        Message: 'Can not find Key Chain $1, check configuration to resolve the problem'

        Parameters list:
              $1: bfd45_keychain_name

        The Key Chain is probably not configured, so the protocol is not able to
        find it."
    ::= { bfdNotificationsPrefix 45 }

bfdNotification46 NOTIFICATION-TYPE
    OBJECTS { 
              bfd46_keychain_name 
            }
    STATUS current
    DESCRIPTION
        "Notification of Event BFD.46

        Message: 'Can not find a valid Key inside Key Chain $1, check configuration to resolve the problem'

        Parameters list:
              $1: bfd46_keychain_name

        The protocol is not able to find a valid Key inside the Key Chain, maybe
        it is not configured."
    ::= { bfdNotificationsPrefix 46 }

bfdNotification47 NOTIFICATION-TYPE
    OBJECTS { 
              bfd47_peer_address, 
              bfd47_authentication_type 
            }
    STATUS current
    DESCRIPTION
        "Notification of Event BFD.47

        Message: 'Received packet from peer $1 without authentication, $2 authentication required for this session'

        Parameters list:
              $1: bfd47_peer_address
              $2: bfd47_authentication_type

        A packet without authentication has been received but session requires
        authentication. The packet will be discarded and ignored."
    ::= { bfdNotificationsPrefix 47 }

bfdNotification48 NOTIFICATION-TYPE
    OBJECTS { 
              bfd48_authentication_type, 
              bfd48_peer_address 
            }
    STATUS current
    DESCRIPTION
        "Notification of Event BFD.48

        Message: 'Received wrong $1 authentication type from peer $2'

        Parameters list:
              $1: bfd48_authentication_type
              $2: bfd48_peer_address

        A packet with authentication has been received but authentication type
        is not correct for the configured session. The packet will be discarded
        and ignored."
    ::= { bfdNotificationsPrefix 48 }

bfdNotification49 NOTIFICATION-TYPE
    OBJECTS { 
              bfd49_key_identifier, 
              bfd49_peer_address 
            }
    STATUS current
    DESCRIPTION
        "Notification of Event BFD.49

        Message: 'Invalid Key ID $1 received from peer $2'

        Parameters list:
              $1: bfd49_key_identifier
              $2: bfd49_peer_address

        A packet with authentication has been received but the Key ID is invalid
        for the configured session. Check both remote and local configurations."
    ::= { bfdNotificationsPrefix 49 }

bfdNotification50 NOTIFICATION-TYPE
    OBJECTS { 
              bfd50_authentication_length, 
              bfd50_peer_address 
            }
    STATUS current
    DESCRIPTION
        "Notification of Event BFD.50

        Message: 'Received invalid authentication length $1 from peer $2'

        Parameters list:
              $1: bfd50_authentication_length
              $2: bfd50_peer_address

        A packet with authentication has been received but authentication
        length is invalid for Authentication Type."
    ::= { bfdNotificationsPrefix 50 }

bfdNotification51 NOTIFICATION-TYPE
    OBJECTS { 
              bfd51_key_identifier, 
              bfd51_keychain_name,
              bfd51_peer_address 
            }
    STATUS current
    DESCRIPTION
        "Notification of Event BFD.51

        Message: 'Can not find Key ID $1 inside Key Chain $2, for peer $3'

        Parameters list:
              $1: bfd51_key_identifier
              $2: bfd51_keychain_name
              $3: bfd51_peer_address

        The protocol is not able to find received Key ID inside Key Chain, maybe
        it is not configured."
    ::= { bfdNotificationsPrefix 51 }

bfdNotification52 NOTIFICATION-TYPE
    OBJECTS { 
              bfd52_authentication_seqnum, 
              bfd52_peer_address,
              bfd52_last_authentication_seqnum 
            }
    STATUS current
    DESCRIPTION
        "Notification of Event BFD.52

        Message: 'Received invalid authentication sequence number $1 from peer $2, last was $3'

        Parameters list:
              $1: bfd52_authentication_seqnum
              $2: bfd52_peer_address
              $3: bfd52_last_authentication_seqnum

        A packet with authentication has been received but authentication
        sequence number is invalid."
    ::= { bfdNotificationsPrefix 52 }

bfdNotification53 NOTIFICATION-TYPE
    OBJECTS { 
              bfd53_peer_address 
            }
    STATUS current
    DESCRIPTION
        "Notification of Event BFD.53

        Message: 'Authentication fail in packet received from peer $1'

        Parameters list:
              $1: bfd53_peer_address

        A packet with authentication has been received but authentication
        digest is invalid."
    ::= { bfdNotificationsPrefix 53 }


END
