CCK-MIB DEFINITIONS ::= BEGIN

-- Title:      RADWARE
--             This Private MIB supports the Vgate
-- Version:    2.9
-- Date:       27 Oct 1995
-- By:         RMA (Radware MIB Authority)
-- E-mail:     US:            support@radware.com
--             International: support_int@radware.com
--
IMPORTS
       NetworkAddress,
       IpAddress,
       Counter,
       Gauge,
       enterprises
              FROM RFC1155-SMI
       Unsigned32
              FROM SNMPv2-SMI
       OBJECT-TYPE
              FROM RFC-1212
       DisplayString,
       PhysAddress,
       ipAddrEntry
              FROM RFC1213-MIB
       TRAP-TYPE
                    FROM RFC1215
       rsCCK,
       rndErrorDesc,
       rndErrorSeverity,
       TruthValue,
       RowStatus
                    FROM RADWARE-MIB;

    NetNumber ::=  OCTET STRING (SIZE(4))
  

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }




rsCCKElementTable OBJECT-TYPE
    SYNTAX SEQUENCE OF RsCCKElementEntry
    ACCESS not-accessible
    STATUS  mandatory
    DESCRIPTION
      "Table for the device's connectivity checks checked elements"
    ::=  {rsCCK 1}

rsCCKElementEntry OBJECT-TYPE
    SYNTAX RsCCKElementEntry
    ACCESS not-accessible
    STATUS  mandatory
    DESCRIPTION
       "the row definition for this table"
   INDEX { rsCCKElementId }
    ::=  {rsCCKElementTable 1}

RsCCKElementEntry ::= SEQUENCE {
  rsCCKElementId           INTEGER,
  rsCCKElementDescription  DisplayString,
  rsCCKElementGroup        DisplayString,
  rsCCKElementIsActive     INTEGER,
  rsCCKElementIsAvailable  INTEGER,
  rsCCKElementDftAddr      IpAddress,
  rsCCKElementRowStatus    RowStatus,
  rsCCKElementLoadFactor   INTEGER,
  rsCCKElementUptimePct    INTEGER,
  rsCCKElementSuccessCnt   INTEGER,
  rsCCKElementFailCnt      INTEGER
  }

rsCCKElementId OBJECT-TYPE
    SYNTAX INTEGER
    ACCESS  read-only
    STATUS  mandatory
    DESCRIPTION
      "connectivity check's checked element ID"
    ::=  {rsCCKElementEntry 1}

rsCCKElementDescription OBJECT-TYPE
    SYNTAX  DisplayString (SIZE(0..80))
    ACCESS  read-only
    STATUS  mandatory
    DESCRIPTION
      "connectivity check's checked element description"
    ::=  {rsCCKElementEntry 2}

rsCCKElementGroup OBJECT-TYPE
    SYNTAX  DisplayString (SIZE(0..80))
    ACCESS  read-only
    STATUS  mandatory
    DESCRIPTION
      "connectivity check's checked element description"
    ::=  {rsCCKElementEntry 3}

rsCCKElementIsActive OBJECT-TYPE
    SYNTAX  INTEGER {
       active(1),
       inactive(2)
    }
    ACCESS  read-only
    STATUS  mandatory
    DESCRIPTION
      "connectivity check's checked element active status"
    ::=  {rsCCKElementEntry 4}

rsCCKElementIsAvailable OBJECT-TYPE
    SYNTAX  INTEGER {
       available(1),
       unavailable(2),
       nonewsessions(3)
    }
    ACCESS  read-only
    STATUS  mandatory
    DESCRIPTION
      "connectivity check's checked element available status"
    ::=  {rsCCKElementEntry 5}

rsCCKElementDftAddr OBJECT-TYPE
    SYNTAX  IpAddress
    ACCESS read-only
    STATUS  mandatory
    DESCRIPTION
      "connectivity check's checked element's default ip address"
    ::=  {rsCCKElementEntry 6}

rsCCKElementRowStatus OBJECT-TYPE
    SYNTAX  RowStatus
    ACCESS  read-only
    STATUS  mandatory
    DESCRIPTION
      "connectivity check's checked element row status"
    ::=  {rsCCKElementEntry 7}


rsCCKElementLoadFactor OBJECT-TYPE
    SYNTAX  INTEGER
    ACCESS read-only
    STATUS  mandatory
    DESCRIPTION
      "connectivity check's checked element load factor"
    ::=  {rsCCKElementEntry 8}

rsCCKElementUptimePct OBJECT-TYPE
    SYNTAX  INTEGER
    ACCESS read-only
    STATUS  mandatory
    DESCRIPTION
      "connectivity check's checked element uptime percentage"
    ::=  {rsCCKElementEntry 9}

rsCCKElementSuccessCnt OBJECT-TYPE
    SYNTAX  INTEGER
    ACCESS read-only
    STATUS  mandatory
    DESCRIPTION
      "connectivity check's checked element success count"
    ::=  {rsCCKElementEntry 10}

rsCCKElementFailCnt OBJECT-TYPE
    SYNTAX  INTEGER
    ACCESS read-only
    STATUS  mandatory
    DESCRIPTION
      "connectivity check's checked element failure count"
    ::=  {rsCCKElementEntry 11}


--------------------------
rsCCKHealthChkTable OBJECT-TYPE
    SYNTAX SEQUENCE OF RsCCKHealthChkEntry
    ACCESS not-accessible
    STATUS  mandatory
    DESCRIPTION
      "Table for the device's connectivity checks health checks"
    ::=  {rsCCK 2}

rsCCKHealthChkEntry OBJECT-TYPE
    SYNTAX RsCCKHealthChkEntry
    ACCESS not-accessible
    STATUS  mandatory
    DESCRIPTION
       "The row definition for this table"
   INDEX { rsCCKHealthChkName }
    ::=  {rsCCKHealthChkTable 1}

RsCCKHealthChkEntry ::= SEQUENCE {
  rsCCKHealthChkName        DisplayString,
  rsCCKHealthChkId          INTEGER,
  rsCCKHealthChkMethod      INTEGER,
  rsCCKHealthChkStatus      INTEGER,
  rsCCKHealthChkDstAddr     IpAddress,
  rsCCKHealthChkNextHop     IpAddress,
  rsCCKHealthChkDstPort     INTEGER,
  rsCCKHealthChkArguments   DisplayString,
  rsCCKHealthChkInterval    INTEGER,
  rsCCKHealthChkRetries     INTEGER,
  rsCCKHealthChkTimeout     INTEGER,
  rsCCKHealthChkRowStatus   RowStatus,
  rsCCKHealthChkNNSTimeout  INTEGER,
  rsCCKHealthChkTrckLoad    INTEGER,
  rsCCKHealthChkLoadFactor  INTEGER,
  rsCCKHealthChkRevResult   INTEGER,
  rsCCKHealthChkUptimePct   INTEGER,
  rsCCKHealthChkSuccessCnt  INTEGER,
  rsCCKHealthChkFailCnt     INTEGER,
  rsCCKHealthChkDuration    INTEGER,
  rsCCKHealthChkServerSpoof INTEGER,
  rsCCKHealthChkDstHost     DisplayString
  }

rsCCKHealthChkName OBJECT-TYPE
    SYNTAX  DisplayString (SIZE(0..80))
    ACCESS read-only
    STATUS  mandatory
    DESCRIPTION
      "connectivity check's health check name"
    ::=  {rsCCKHealthChkEntry 1}

rsCCKHealthChkId OBJECT-TYPE
    SYNTAX  INTEGER
    ACCESS read-write
    STATUS  mandatory
    DESCRIPTION
      "connectivity check's health check identifier"
    ::=  {rsCCKHealthChkEntry 2}

rsCCKHealthChkMethod OBJECT-TYPE
    SYNTAX  INTEGER
    ACCESS read-write
    STATUS  mandatory
    DESCRIPTION
      "connectivity check's health check method"
    ::=  {rsCCKHealthChkEntry 3}

rsCCKHealthChkStatus OBJECT-TYPE
    SYNTAX  INTEGER {
	unknown(1),
	failed(2),
	passed(3),
	nonewsessions(4)
    }
    ACCESS read-only
    STATUS  mandatory
    DESCRIPTION
      "connectivity check's health check status"
    DEFVAL { 1 }
    ::=  {rsCCKHealthChkEntry 4}

rsCCKHealthChkDstAddr OBJECT-TYPE
    SYNTAX  IpAddress
    ACCESS read-write
    STATUS  mandatory
    DESCRIPTION
      "connectivity check's health check destination address"
    ::=  {rsCCKHealthChkEntry 5}

rsCCKHealthChkNextHop OBJECT-TYPE
    SYNTAX  IpAddress
    ACCESS read-write
    STATUS  mandatory
    DESCRIPTION
      "connectivity check's health check next hop"
    ::=  {rsCCKHealthChkEntry 6}

rsCCKHealthChkDstPort OBJECT-TYPE
    SYNTAX  INTEGER
    ACCESS read-write
    STATUS  mandatory
    DESCRIPTION
      "connectivity check's health check destination port"
    ::=  {rsCCKHealthChkEntry 7}

rsCCKHealthChkArguments OBJECT-TYPE
    SYNTAX  DisplayString (SIZE(0..255))
    ACCESS read-write
    STATUS  mandatory
    DESCRIPTION
      "connectivity check's health check argument list"
    ::=  {rsCCKHealthChkEntry 8}

rsCCKHealthChkInterval OBJECT-TYPE
    SYNTAX  INTEGER
    ACCESS read-write
    STATUS  mandatory
    DESCRIPTION
      "connectivity check's health check interval in seconds"
    DEFVAL { 10 }
    ::=  {rsCCKHealthChkEntry 9}

rsCCKHealthChkRetries OBJECT-TYPE
    SYNTAX  INTEGER
    ACCESS read-write
    STATUS  mandatory
    DESCRIPTION
      "connectivity check's health check number of retries before failing"
    DEFVAL { 5 }
    ::=  {rsCCKHealthChkEntry 10}

rsCCKHealthChkTimeout OBJECT-TYPE
    SYNTAX  INTEGER
    ACCESS read-write
    STATUS  mandatory
    DESCRIPTION
      "connectivity check's health check timeout in seconds"
    DEFVAL { 5 }
    ::=  {rsCCKHealthChkEntry 11}

rsCCKHealthChkRowStatus OBJECT-TYPE
    SYNTAX  RowStatus
    ACCESS  read-write
    STATUS  mandatory
    DESCRIPTION
      "connectivity check's health check row status"
    ::=  {rsCCKHealthChkEntry 12}

rsCCKHealthChkNNSTimeout OBJECT-TYPE
    SYNTAX  INTEGER
    ACCESS read-write
    STATUS  mandatory
    DESCRIPTION
      "connectivity check's no new session timeout, in seconds"
    ::=  {rsCCKHealthChkEntry 13}

rsCCKHealthChkTrckLoad OBJECT-TYPE
     SYNTAX INTEGER {
       enable(1),
       disable(2)
     }
     ACCESS read-write
     STATUS mandatory
     DESCRIPTION
      "connectivity check's health check - use this check for load evaluation"
     DEFVAL { 2 }
    ::=  {rsCCKHealthChkEntry 14}

rsCCKHealthChkLoadFactor OBJECT-TYPE
    SYNTAX  INTEGER
    ACCESS read-only
    STATUS  mandatory
    DESCRIPTION
      "connectivity check's health check load factor"
    ::=  {rsCCKHealthChkEntry 15}

rsCCKHealthChkRevResult OBJECT-TYPE
     SYNTAX INTEGER {
       enable(1),
       disable(2)
     }
     ACCESS read-write
     STATUS mandatory
     DESCRIPTION
      "connectivity check's health check - reverse check's result"
     DEFVAL { 2 }
    ::=  {rsCCKHealthChkEntry 16}

rsCCKHealthChkUptimePct OBJECT-TYPE
    SYNTAX  INTEGER
    ACCESS read-only
    STATUS  mandatory
    DESCRIPTION
      "connectivity check's health check uptime percentage"
    ::=  {rsCCKHealthChkEntry 17}

rsCCKHealthChkSuccessCnt OBJECT-TYPE
    SYNTAX  INTEGER
    ACCESS read-only
    STATUS  mandatory
    DESCRIPTION
      "connectivity check's health check success count"
    ::=  {rsCCKHealthChkEntry 18}

rsCCKHealthChkFailCnt OBJECT-TYPE
    SYNTAX  INTEGER
    ACCESS read-only
    STATUS  mandatory
    DESCRIPTION
      "connectivity check's health check failure count"
    ::=  {rsCCKHealthChkEntry 19}

rsCCKHealthChkDuration OBJECT-TYPE
    SYNTAX  INTEGER
    ACCESS read-only
    STATUS  mandatory
    DESCRIPTION
      "connectivity check's health check average duration"
    ::=  {rsCCKHealthChkEntry 20}


rsCCKHealthChkServerSpoof OBJECT-TYPE
     SYNTAX INTEGER {
       enable(1),
       disable(2)
     }
     ACCESS read-write
     STATUS mandatory
     DESCRIPTION
      "connectivity check's health check - server spoofing"
     DEFVAL { 2 }
    ::=  {rsCCKHealthChkEntry 21}

rsCCKHealthChkDstHost OBJECT-TYPE
     SYNTAX DisplayString (SIZE(0..64))
     ACCESS read-write
     STATUS mandatory
     DESCRIPTION
      "connectivity check's destination host name"
    ::=  {rsCCKHealthChkEntry 22}

--------------------------
rsCCKChkBindingTable OBJECT-TYPE
    SYNTAX SEQUENCE OF RsCCKChkBindingEntry
    ACCESS not-accessible
    STATUS  mandatory
    DESCRIPTION
      "Table for health check - element bindings"
    ::=  {rsCCK 3}

rsCCKChkBindingEntry OBJECT-TYPE
    SYNTAX RsCCKChkBindingEntry
    ACCESS not-accessible
    STATUS  mandatory
    DESCRIPTION
       "The row definition for this table"
   INDEX { rsCCKChkBindingHealthChk, rsCCKChkBindingElement }
    ::=  {rsCCKChkBindingTable 1}

RsCCKChkBindingEntry ::= SEQUENCE {
  rsCCKChkBindingHealthChk   INTEGER,
  rsCCKChkBindingElement     INTEGER,
  rsCCKChkBindingGroup       INTEGER,
  rsCCKChkBindingMandatory   INTEGER,
  rsCCKChkBindingRowStatus   RowStatus
  }

rsCCKChkBindingHealthChk OBJECT-TYPE
    SYNTAX  INTEGER
    ACCESS read-only
    STATUS  mandatory
    DESCRIPTION
      "the bound health check id"
    ::=  {rsCCKChkBindingEntry 1}

rsCCKChkBindingElement OBJECT-TYPE
    SYNTAX  INTEGER
    ACCESS read-only
    STATUS  mandatory
    DESCRIPTION
      "the bound element id"
    ::=  {rsCCKChkBindingEntry 2}

rsCCKChkBindingGroup OBJECT-TYPE
    SYNTAX  INTEGER
    ACCESS read-write
    STATUS  mandatory
    DESCRIPTION
      "the bound element group"
    ::=  {rsCCKChkBindingEntry 3}

rsCCKChkBindingMandatory OBJECT-TYPE
     SYNTAX INTEGER {
       ismandatory(1),
       isnon-mandatory(2)
     }
     ACCESS read-write
     STATUS mandatory
     DESCRIPTION
      "connectivity check's binding relation - mandatory or not"
     DEFVAL { 1 }
    ::=  {rsCCKChkBindingEntry 4}

rsCCKChkBindingRowStatus OBJECT-TYPE
    SYNTAX  RowStatus
    ACCESS  read-write
    STATUS  mandatory
    DESCRIPTION
      "health cehck's binding check row status"
    ::=  {rsCCKChkBindingEntry 5}

--------------------------
rsCCKChkMethodTable OBJECT-TYPE
    SYNTAX SEQUENCE OF RsCCKChkMethodEntry
    ACCESS not-accessible
    STATUS  mandatory
    DESCRIPTION
      "connectivity check's check methods table"
    ::=  {rsCCK 4}

rsCCKChkMethodEntry OBJECT-TYPE
    SYNTAX RsCCKChkMethodEntry
    ACCESS not-accessible
    STATUS  mandatory
    DESCRIPTION
       "The row definition for this table"
   INDEX { rsCCKChkMethodId }
    ::=  {rsCCKChkMethodTable 1}

RsCCKChkMethodEntry ::= SEQUENCE {
  rsCCKChkMethodId          INTEGER,
  rsCCKChkMethodDescription DisplayString,
  rsCCKChkMethodRowStatus   RowStatus
  }

rsCCKChkMethodId OBJECT-TYPE
    SYNTAX  INTEGER
    ACCESS read-only
    STATUS  mandatory
    DESCRIPTION
      "connectivity check's check method's id"
    ::=  {rsCCKChkMethodEntry 1}

rsCCKChkMethodDescription OBJECT-TYPE
    SYNTAX  DisplayString (SIZE(0..80))
    ACCESS read-only
    STATUS  mandatory
    DESCRIPTION
      "connectivity check's check method's description"
    ::=  {rsCCKChkMethodEntry 2}

rsCCKChkMethodRowStatus OBJECT-TYPE
    SYNTAX  RowStatus
    ACCESS  read-only
    STATUS  mandatory
    DESCRIPTION
      "connectivity check's check method's row status"
    ::=  {rsCCKChkMethodEntry 3}


--------------------------
rsCCKPktSequenceTable OBJECT-TYPE
    SYNTAX SEQUENCE OF RsCCKPktSequenceEntry
    ACCESS not-accessible
    STATUS  mandatory
    DESCRIPTION
      "connectivity check's packet sequence table"
    ::=  {rsCCK 5}

rsCCKPktSequenceEntry OBJECT-TYPE
    SYNTAX RsCCKPktSequenceEntry
    ACCESS not-accessible
    STATUS  mandatory
    DESCRIPTION
       "The row definition for this table"
   INDEX { rsCCKPktSequenceSeqId, rsCCKPktSequencePktId }
    ::=  {rsCCKPktSequenceTable 1}

RsCCKPktSequenceEntry ::= SEQUENCE {
  rsCCKPktSequenceSeqId       INTEGER,
  rsCCKPktSequencePktId       INTEGER,
  rsCCKPktSequenceType        INTEGER,
  rsCCKPktSequenceString      DisplayString,
  rsCCKPktSequenceDescription DisplayString,
  rsCCKPktSequenceRowStatus   RowStatus,
  rsCCKPktSequenceCompareMtd  INTEGER
  }

rsCCKPktSequenceSeqId OBJECT-TYPE
    SYNTAX  INTEGER
    ACCESS read-only
    STATUS  mandatory
    DESCRIPTION
      "packet sequence id"
    ::=  {rsCCKPktSequenceEntry 1}

rsCCKPktSequencePktId OBJECT-TYPE
    SYNTAX  INTEGER
    ACCESS read-only
    STATUS  mandatory
    DESCRIPTION
      "packet's sequence number within the packet sequence"
    ::=  {rsCCKPktSequenceEntry 2}

rsCCKPktSequenceType OBJECT-TYPE
    SYNTAX  INTEGER {
       send (1),
       recieve(2)
    }
    ACCESS read-write
    STATUS  mandatory
    DESCRIPTION
      "packet type (send/recieve)"
    DEFVAL { 1 }
    ::=  {rsCCKPktSequenceEntry 3}

rsCCKPktSequenceString OBJECT-TYPE
    SYNTAX  DisplayString (SIZE(0..255))
    ACCESS read-write
    STATUS  mandatory
    DESCRIPTION
      "packet data (for send)/match pattern (for recieve)"
    ::=  {rsCCKPktSequenceEntry 4}

rsCCKPktSequenceDescription OBJECT-TYPE
    SYNTAX  DisplayString (SIZE(0..80))
    ACCESS read-write
    STATUS  mandatory
    DESCRIPTION
      "packet description"
    ::=  {rsCCKPktSequenceEntry 5}

rsCCKPktSequenceRowStatus OBJECT-TYPE
    SYNTAX  RowStatus
    ACCESS  read-write
    STATUS  mandatory
    DESCRIPTION
      "connectivity check's packet sequence's row status"
    ::=  {rsCCKPktSequenceEntry 6}

rsCCKPktSequenceCompareMtd OBJECT-TYPE
    SYNTAX  INTEGER {
       regex (1),
       binary(2)
    }
    ACCESS read-write
    STATUS  mandatory
    DESCRIPTION
      "receive packet comparison method (regex/binary)"
    DEFVAL { 1 }
    ::=  {rsCCKPktSequenceEntry 7}

--------------------------
rsCCKArgDelimiter  OBJECT-TYPE
    SYNTAX  DisplayString (SIZE(0..1))
    ACCESS  read-write
    STATUS  mandatory
    DESCRIPTION
      "Connectivity checks additional argument delimiter character"
    ::=  {rsCCK 6}


--------------------------
rsCCKNextElementId  OBJECT-TYPE
    SYNTAX  INTEGER
    ACCESS  read-write
    STATUS  mandatory
    DESCRIPTION
      "Connectivity checks next element id"
    ::=  {rsCCK 7}

--------------------------
rsCCKNextCheckId  OBJECT-TYPE
    SYNTAX  INTEGER
    ACCESS  read-write
    STATUS  mandatory
    DESCRIPTION
      "Connectivity checks next health check id"
    ::=  {rsCCK 8}

--------------------------
rsCCKStatus  OBJECT-TYPE
    SYNTAX  INTEGER {
       enable(1),
       disable(2)
    }
    ACCESS  read-write
    STATUS  mandatory
    DESCRIPTION
      "Connectivity checks enable switch"
    ::=  {rsCCK 9}

--------------------------
rsCCKLoadSamples  OBJECT-TYPE
    SYNTAX  INTEGER (0..10)
    ACCESS  read-write
    STATUS  mandatory
    DESCRIPTION
      "Connectivity checks load tracking samples used"
    ::=  {rsCCK 10}

--------------------------
rsCCKCertFile  OBJECT-TYPE
    SYNTAX  DisplayString(SIZE(1..80))
    ACCESS  read-write
    STATUS  mandatory
    DESCRIPTION
      "SSL Connectivity checks certificate file"
    ::=  {rsCCK 11}

--------------------------
rsCCKKeyFile  OBJECT-TYPE
    SYNTAX  DisplayString(SIZE(1..80))
    ACCESS  read-write
    STATUS  mandatory
    DESCRIPTION
      "SSL Connectivity checks key file"
    ::=  {rsCCK 12}

------------------------------------
-- Diameter check arguments table --
------------------------------------
rsCCKDiameterArgsTable OBJECT-TYPE
    SYNTAX SEQUENCE OF RsCCKDiameterArgsEntry
    ACCESS not-accessible
    STATUS  mandatory
    DESCRIPTION
      "Diameter connectivity check's arguments table"
    ::=  {rsCCK 13}

rsCCKDiameterArgsEntry OBJECT-TYPE
    SYNTAX RsCCKDiameterArgsEntry
    ACCESS not-accessible
    STATUS  mandatory
    DESCRIPTION
       "The row definition for the Diameter args table"
   INDEX { rsCCKDiameterArgsName }
    ::=  {rsCCKDiameterArgsTable 1}

RsCCKDiameterArgsEntry ::= SEQUENCE {
  rsCCKDiameterArgsName            DisplayString,
  rsCCKDiameterArgsOriginHost      DisplayString,
  rsCCKDiameterArgsOriginRealm     DisplayString,
  rsCCKDiameterArgsProductName     DisplayString,
  rsCCKDiameterArgsAuthAppID       Unsigned32,
  rsCCKDiameterArgsAuthSessState   INTEGER,
  rsCCKDiameterArgsDestRealm       DisplayString,
  rsCCKDiameterArgsDestHost        DisplayString,
  rsCCKDiameterArgsPublicID        DisplayString,
  rsCCKDiameterArgsDisconnectCause INTEGER,
  rsCCKDiameterArgsAppMessType     INTEGER,
  rsCCKDiameterArgsAppMessPresent  INTEGER,
  rsCCKDiameterArgsDescription     DisplayString,
  rsCCKDiameterArgsResultCodes     DisplayString,
  rsCCKDiameterArgsVendorID        Unsigned32,
  rsCCKDiameterArgsRowStatus       RowStatus
  }

rsCCKDiameterArgsName OBJECT-TYPE
    SYNTAX  DisplayString
    ACCESS read-write
    STATUS  mandatory
    DESCRIPTION
      "Diameter arguments name"
    ::=  {rsCCKDiameterArgsEntry 1}

rsCCKDiameterArgsOriginHost OBJECT-TYPE
    SYNTAX  DisplayString
    ACCESS read-write
    STATUS  mandatory
    DESCRIPTION
      "Diameter arguments Origin-Host AVP"
    ::=  {rsCCKDiameterArgsEntry 2}

rsCCKDiameterArgsOriginRealm OBJECT-TYPE
    SYNTAX  DisplayString
    ACCESS read-write
    STATUS  mandatory
    DESCRIPTION
      "Diameter arguments Origin-Realm AVP"
    ::=  {rsCCKDiameterArgsEntry 3}

rsCCKDiameterArgsProductName OBJECT-TYPE
    SYNTAX  DisplayString
    ACCESS read-write
    STATUS  mandatory
    DESCRIPTION
      "Diameter arguments Product-Name AVP"
    ::=  {rsCCKDiameterArgsEntry 4}

rsCCKDiameterArgsAuthAppID OBJECT-TYPE
    SYNTAX  Unsigned32
    ACCESS read-write
    STATUS  optional
    DESCRIPTION
      "Diameter arguments Auth-Application-ID AVP"
    DEFVAL { 0 }
    ::=  {rsCCKDiameterArgsEntry 5}

rsCCKDiameterArgsAuthSessState OBJECT-TYPE
    SYNTAX INTEGER {
      state-maintained(0),
      no-state-maintained(1)  
    }
    ACCESS read-write
    STATUS  optional
    DESCRIPTION
      "Diameter arguments Auth-Session-State AVP"
    DEFVAL { 1 }
    ::=  {rsCCKDiameterArgsEntry 6}

rsCCKDiameterArgsDestRealm OBJECT-TYPE
    SYNTAX  DisplayString
    ACCESS read-write
    STATUS  optional
    DESCRIPTION
      "Diameter arguments Destination-Realm AVP"
    DEFVAL { "" }
    ::=  {rsCCKDiameterArgsEntry 7}

rsCCKDiameterArgsDestHost OBJECT-TYPE
    SYNTAX  DisplayString
    ACCESS read-write
    STATUS  optional
    DESCRIPTION
      "Diameter arguments Destination-Host AVP"
    DEFVAL { "" }
    ::=  {rsCCKDiameterArgsEntry 8}

rsCCKDiameterArgsPublicID OBJECT-TYPE
    SYNTAX  DisplayString
    ACCESS read-write
    STATUS  optional
    DESCRIPTION
      "Diameter arguments Public Identity AVP"
    DEFVAL { "" }
    ::=  {rsCCKDiameterArgsEntry 9}

rsCCKDiameterArgsDisconnectCause  OBJECT-TYPE
    SYNTAX INTEGER {
      rebooting(0),
      busy(1),
      do-not-want-to-talk-to-you(2)
    }    
    ACCESS read-write
    STATUS  mandatory
    DESCRIPTION
      "Diameter arguments Origin-Host AVP"
    ::=  {rsCCKDiameterArgsEntry 10}

rsCCKDiameterArgsAppMessType OBJECT-TYPE
    SYNTAX INTEGER {
      lir(0),
      user-defined(1),
      none(2)
    }    
    ACCESS read-write
    STATUS  mandatory
    DESCRIPTION
      "Diameter arguments field - defines type of the application message (either LIR or user defined)"
    ::=  {rsCCKDiameterArgsEntry 11}

rsCCKDiameterArgsAppMessPresent OBJECT-TYPE
    SYNTAX INTEGER {
        yes (1),
        no (2),
        na (3)
    }    
    ACCESS read-only
    STATUS  mandatory
    DESCRIPTION
      "Diameter arguments field - defines whether a user-defined message has been provided"
    DEFVAL  { 2 }
    ::=  {rsCCKDiameterArgsEntry 12}

rsCCKDiameterArgsDescription OBJECT-TYPE
    SYNTAX  DisplayString (SIZE(0..80))
    ACCESS read-write
    STATUS  mandatory
    DESCRIPTION
      "diameter argument set description"
    ::=  {rsCCKDiameterArgsEntry 13}

rsCCKDiameterArgsResultCodes OBJECT-TYPE
    SYNTAX  DisplayString (SIZE(0..80))
    ACCESS read-write
    STATUS  mandatory
    DESCRIPTION
      "Comma separated list of acceptable result codes"
    ::=  {rsCCKDiameterArgsEntry 14}

rsCCKDiameterArgsVendorID OBJECT-TYPE
    SYNTAX  Unsigned32
    ACCESS read-write
    STATUS  mandatory
    DESCRIPTION
      "Vendor-ID value"
    ::=  {rsCCKDiameterArgsEntry 15}

rsCCKDiameterArgsRowStatus OBJECT-TYPE
    SYNTAX  RowStatus
    ACCESS read-write
    STATUS  mandatory
    DESCRIPTION
      "Diameter arguments row status"
    ::=  {rsCCKDiameterArgsEntry 16}

--------------------------------------
-- Diameter check Binary File table --
--------------------------------------

rsCCKDiameterBinaryFileTable OBJECT-TYPE
    SYNTAX SEQUENCE OF RsCCKDiameterBinaryFileEntry
    ACCESS not-accessible
    STATUS  mandatory
    DESCRIPTION
      "Diameter connectivity check's binary file"
    ::=  {rsCCK 14}

rsCCKDiameterBinaryFileEntry OBJECT-TYPE
    SYNTAX RsCCKDiameterBinaryFileEntry
    ACCESS not-accessible
    STATUS  mandatory
    DESCRIPTION
       "The row definition for the Diameter binary file's table"
   INDEX { rsCCKDiameterBinaryFileArgsSetName }
    ::=  {rsCCKDiameterBinaryFileTable 1}

RsCCKDiameterBinaryFileEntry ::= SEQUENCE {
  rsCCKDiameterBinaryFileArgsSetName DisplayString,
  rsCCKDiameterBinaryFileData1       DisplayString,
  rsCCKDiameterBinaryFileData2       DisplayString,
  rsCCKDiameterBinaryFileData3       DisplayString,
  rsCCKDiameterBinaryFileData4       DisplayString,
  rsCCKDiameterBinaryFileTotalLength Unsigned32,
  rsCCKDiameterBinaryFileRowStatus   RowStatus
  }


rsCCKDiameterBinaryFileArgsSetName OBJECT-TYPE
    SYNTAX  DisplayString
    ACCESS read-write
    STATUS  mandatory
    DESCRIPTION
      "Diameter arguments name"
    ::=  {rsCCKDiameterBinaryFileEntry 1}

rsCCKDiameterBinaryFileData1 OBJECT-TYPE
    SYNTAX  DisplayString
    ACCESS read-write
    STATUS  mandatory
    DESCRIPTION
      "Diameter file data part 1"
    ::=  {rsCCKDiameterBinaryFileEntry 2}

rsCCKDiameterBinaryFileData2 OBJECT-TYPE
    SYNTAX  DisplayString
    ACCESS read-write
    STATUS  mandatory
    DESCRIPTION
      "Diameter file data part 2"
    ::=  {rsCCKDiameterBinaryFileEntry 3}

rsCCKDiameterBinaryFileData3 OBJECT-TYPE
    SYNTAX  DisplayString
    ACCESS read-write
    STATUS  mandatory
    DESCRIPTION
      "Diameter file data part 3"
    ::=  {rsCCKDiameterBinaryFileEntry 4}

rsCCKDiameterBinaryFileData4 OBJECT-TYPE
    SYNTAX  DisplayString
    ACCESS read-write
    STATUS  mandatory
    DESCRIPTION
      "Diameter file data part 4"
    ::=  {rsCCKDiameterBinaryFileEntry 5}

rsCCKDiameterBinaryFileTotalLength OBJECT-TYPE
    SYNTAX  Unsigned32
    ACCESS read-write
    STATUS  mandatory
    DESCRIPTION
      "Diameter binary file total length"
    ::=  {rsCCKDiameterBinaryFileEntry 6}

rsCCKDiameterBinaryFileRowStatus OBJECT-TYPE
    SYNTAX  RowStatus
    ACCESS read-write
    STATUS  mandatory
    DESCRIPTION
      "Diameter binary file row status"
    ::=  {rsCCKDiameterBinaryFileEntry 7}

--------------------------

-- Application-specific traps for CCK
-- Each enterprise-specific trap has two bound variables describing the exact nature of
-- the trap. rndErrorDesc provides a detailed description of the problem, including the
-- related interface number, board number or any other applicable variable.
-- rndErrorSeverity describes the severity of this problem.

-- Trap template
-- -------------
--    TRAP-TYPE
--       ENTERPRISE  rsServerDispatcher
--       VARIABLES   { rndErrorDesc, rndErrorSeverity }
--       DESCRIPTION
--             ""
--       ::=

-- -------------
rsCCKElemIsUp TRAP-TYPE
        ENTERPRISE rsCCK
        VARIABLES  { rndErrorDesc, rndErrorSeverity }
        DESCRIPTION
             "This trap is sent to inform that an element is up."
		::=  1

rsCCKElemIsDown TRAP-TYPE
        ENTERPRISE rsCCK
        VARIABLES  { rndErrorDesc, rndErrorSeverity }
        DESCRIPTION
             "This trap is sent to warn that an element is down."
		::=  2

rsCCKElemIsNNS TRAP-TYPE
        ENTERPRISE rsCCK
        VARIABLES  { rndErrorDesc, rndErrorSeverity }
        DESCRIPTION
             "This trap is sent to inform that an element is set to no new
	     sessions."
		::=  3

END
