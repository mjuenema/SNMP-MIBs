SARIAN-MONITOR-MIB DEFINITIONS ::= BEGIN
--
-- Copyright (c) 2011 Digi International Inc. All rights reserved.
--
-- Sarian Monitor MIB
--

IMPORTS
	enterprises							FROM RFC1155-SMI
	Counter32, Counter64, IpAddress		FROM SNMPv2-SMI
	DisplayString						FROM SNMPv2-TC;


sarian			OBJECT IDENTIFIER ::= { enterprises 16378 }
sarian-monitor	OBJECT IDENTIFIER ::= { sarian 10000 }

sarian-ppp		OBJECT IDENTIFIER ::= { sarian-monitor 1 }
sarian-gprs		OBJECT IDENTIFIER ::= { sarian-monitor 2 }
sarian-system	OBJECT IDENTIFIER ::= { sarian-monitor 3 }
sarian-config	OBJECT IDENTIFIER ::= { sarian-monitor 4 }


--
-- Sarian PPP
--
numPPPInterfaces	OBJECT-TYPE
	SYNTAX	INTEGER
	ACCESS	read-only
	STATUS	mandatory
	DESCRIPTION
		"The number of PPP interfaces."
	::= { sarian-ppp 1 }

sarianPPPTable	OBJECT-TYPE
	SYNTAX	SEQUENCE OF SarianPPPEntry
	ACCESS	not-accessible
	STATUS	mandatory
	DESCRIPTION
		"A list of entries containing status information for all
		PPP entities on this system."
	::= { sarian-ppp 2 }

sarianPPPEntry	OBJECT-TYPE
	SYNTAX	SarianPPPEntry
	ACCESS	not-accessible
	STATUS	mandatory
	DESCRIPTION
		"An entry containing status information for a particular
		PPP entity."
	INDEX { ifIndex }
	::= { sarianPPPTable 1 }

SarianPPPEntry ::=
	SEQUENCE {
		ifIndex
		  INTEGER,
		pppDLTotalData
		  Counter64,
		pppDLWarn
		  Counter64,
		pppDLStop
		  Counter64,
		pppDLDayReset
		  INTEGER
	}

ifIndex 		OBJECT-TYPE
	SYNTAX	INTEGER
	ACCESS	read-only
	STATUS	mandatory
	DESCRIPTION
		"A unique value assigned to each interface."
	::= { sarianPPPEntry 1 }

pppDLTotalData	OBJECT-TYPE
	SYNTAX	Counter64
	ACCESS	read-only
	STATUS	mandatory
	DESCRIPTION
		"Total amount of data (in bytes) transferred in this PPP
		entity during the data limit period."
	::= { sarianPPPEntry 2 }

pppDLWarn	OBJECT-TYPE
	SYNTAX	Counter64
	ACCESS	read-only
	STATUS	mandatory
	DESCRIPTION
		"The PPP data limit (in bytes) at which point a warning
		event is generated."
	::= { sarianPPPEntry 3 }

pppDLStop	OBJECT-TYPE
	SYNTAX	Counter64
	ACCESS	read-only
	STATUS	mandatory
	DESCRIPTION
		"The PPP data limit (in bytes) at which point no more
		traffic is transferred."
	::= { sarianPPPEntry 4 }

pppDLDayReset	OBJECT-TYPE
	SYNTAX	INTEGER (0..31)
	ACCESS	read-only
	STATUS	mandatory
	DESCRIPTION
		"The day of the month on which the total data transferred 
		is reset. If this object is zero, the total data 
		transferred needs to be manually reset."
	::= { sarianPPPEntry 5 }



--
-- Sarian GPRS
--
gprsSignalStrength	OBJECT-TYPE
	SYNTAX	INTEGER
	ACCESS	read-only
	STATUS	mandatory
	DESCRIPTION
		"The GPRS signal strength."
	::= { sarian-gprs 1 }

gprsRegistered	OBJECT-TYPE
	SYNTAX	INTEGER {
				notRegisteredNotSearching(0),
				registeredHomeNetwork(1),
				notRegisteredSearching(2),
				registerationDenied(3),
				unknown(4),
				registeredRoaming(5),
				unrecognised(6)
			}
	ACCESS	read-only
	STATUS	mandatory
	DESCRIPTION
		"The GPRS Registeration Status."
	::= { sarian-gprs 2 }

gprsAttached	OBJECT-TYPE
	SYNTAX	INTEGER {
				notAttached(0),
				attached(1)
			}
	ACCESS	read-only
	STATUS	mandatory
	DESCRIPTION
		"The GPRS Attachment Status."
	::= { sarian-gprs 3 }

gprsPPPIP		OBJECT-TYPE
	SYNTAX	IpAddress
	ACCESS	read-only
	STATUS	mandatory
	DESCRIPTION
		"The IP address of the PPP interface using GPRS."
	::= { sarian-gprs 4 }

gprsAreaID		OBJECT-TYPE
	SYNTAX	INTEGER
	ACCESS	read-only
	STATUS	mandatory
	DESCRIPTION
		"The GPRS Location Area Code."
	::= { sarian-gprs 5 }

gprsCellID		OBJECT-TYPE
	SYNTAX	INTEGER
	ACCESS	read-only
	STATUS	mandatory
	DESCRIPTION
		"The GPRS Cell ID."
	::= { sarian-gprs 6 }

gprsNetworkTechnology	OBJECT-TYPE
	SYNTAX	INTEGER {
				unknown(1),
				gprs(2),
				edge(3),
				umts(4),
				hsdpa(5)
			}
	ACCESS	read-only
	STATUS	mandatory
	DESCRIPTION
		"The GPRS Network Technology in use."
	::= { sarian-gprs 7 }

cdmaEcio	OBJECT-TYPE
	SYNTAX	DisplayString
	ACCESS	read-only
	STATUS	mandatory
	DESCRIPTION
		"The CDMA ECIO."
	::= { sarian-gprs 8 }

cdmaPilotPN	OBJECT-TYPE
	SYNTAX	INTEGER
	ACCESS	read-only
	STATUS	mandatory
	DESCRIPTION
		"The CDMA Pilot PN."
	::= { sarian-gprs 9 }

cdmaDRC		OBJECT-TYPE
	SYNTAX	DisplayString
	ACCESS	read-only
	STATUS	mandatory
	DESCRIPTION
		"The CDMA DRC."
	::= { sarian-gprs 10 }

cdmaESN OBJECT-TYPE
	SYNTAX	DisplayString
	ACCESS	read-only
	STATUS	mandatory
	DESCRIPTION
		"The CMDA Electronic Serial Number."
	::= { sarian-gprs 11 }

cdmaMEID OBJECT-TYPE
	SYNTAX	DisplayString
	ACCESS	read-only
	STATUS	mandatory
	DESCRIPTION
		"The CMDA Mobile Equipment Manufacturer ID."
	::= { sarian-gprs 12 }

cdmaMDN OBJECT-TYPE
	SYNTAX	DisplayString
	ACCESS	read-only
	STATUS	mandatory
	DESCRIPTION
		"The CMDA Mobile Directory Number."
	::= { sarian-gprs 13 }

cdmaMIN OBJECT-TYPE
	SYNTAX	DisplayString
	ACCESS	read-only
	STATUS	mandatory
	DESCRIPTION
		"The CMDA Mobile Identification Number."
	::= { sarian-gprs 14 }


--
-- Sarian System
--
cpuUtil		OBJECT-TYPE
	SYNTAX	INTEGER (0..100)
	ACCESS	read-only
	STATUS	mandatory
	DESCRIPTION
		"The current CPU utilization."
	::= { sarian-system 1 }

cpuMin		OBJECT-TYPE
	SYNTAX	INTEGER (0..100)
	ACCESS	read-only
	STATUS	mandatory
	DESCRIPTION
		"The minimum CPU utilization recorded."
	::= { sarian-system 2 }

cpuMax		OBJECT-TYPE
	SYNTAX	INTEGER (0..100)
	ACCESS	read-only
	STATUS	mandatory
	DESCRIPTION
		"The maximum CPU utilization recorded."
	::= { sarian-system 3 }

cpuAvg		OBJECT-TYPE
	SYNTAX	INTEGER (0..100)
	ACCESS	read-only
	STATUS	mandatory
	DESCRIPTION
		"The average CPU utilization recorded."
	::= { sarian-system 4 }

msgsFree	OBJECT-TYPE
	SYNTAX  INTEGER
	ACCESS  read-only
	STATUS  mandatory
	DESCRIPTION
		"The number of free messages."
	::= { sarian-system 5 }

msgsMin		OBJECT-TYPE
	SYNTAX  INTEGER
	ACCESS  read-only
	STATUS  mandatory
	DESCRIPTION
		"The minimum number of free messages that has been 
		recorded."
	::= { sarian-system 6 }

bufsFree	OBJECT-TYPE
	SYNTAX  INTEGER
	ACCESS  read-only
	STATUS  mandatory
	DESCRIPTION
		"The number of free buffers."
	::= { sarian-system 7 }

bufsMin		OBJECT-TYPE
	SYNTAX  INTEGER
	ACCESS  read-only
	STATUS  mandatory
	DESCRIPTION
		"The minimum number of free buffers that has been 
		recorded."
	::= { sarian-system 8 }

bigBufsFree		OBJECT-TYPE
	SYNTAX  INTEGER
	ACCESS  read-only
	STATUS  mandatory
	DESCRIPTION
		"The number of free big buffers."
	::= { sarian-system 9 }

bigBufsMin		OBJECT-TYPE
	SYNTAX  INTEGER
	ACCESS  read-only
	STATUS  mandatory
	DESCRIPTION
		"The minimum number of free big buffers that has been 
		recorded."
	::= { sarian-system 10 }

temperature		OBJECT-TYPE
	SYNTAX	INTEGER
	ACCESS	read-only
	STATUS	mandatory
	DESCRIPTION
		"The internal temperature of the device in Celsius."
	::= { sarian-system 11 }
	

--
-- Sarian Config
--
changesSincePowerUp		OBJECT-TYPE
	SYNTAX	INTEGER
	ACCESS	read-only
	STATUS	mandatory
	DESCRIPTION
		"The number of changes made to the configuration since
		the unit was powered up."
	::= { sarian-config 1 }

unsavedChanges			OBJECT-TYPE
	SYNTAX	INTEGER
	ACCESS	read-only
	STATUS	mandatory
	DESCRIPTION
		"The number of unsaved configuration changes."
	::= { sarian-config 2 }

lastSavedConfigUser		OBJECT-TYPE
	SYNTAX	DisplayString
	ACCESS	read-only
	STATUS	mandatory
	DESCRIPTION
		"The user who last saved the configuration."
	::= { sarian-config 3 }

lastSavedConfigTime		OBJECT-TYPE
	SYNTAX	DisplayString
	ACCESS	read-only
	STATUS	mandatory
	DESCRIPTION
		"The time the configuration was last saved."
	::= { sarian-config 4 }

lastSavedConfigNumber	OBJECT-TYPE
	SYNTAX	INTEGER
	ACCESS	read-only
	STATUS	mandatory
	DESCRIPTION
		"The number of changes that had been made when the 
		configuration was last saved."
	::= { sarian-config 5 }

pwdChangesSincePowerUp	OBJECT-TYPE
	SYNTAX	INTEGER
	ACCESS	read-only
	STATUS	mandatory
	DESCRIPTION
		"The number of changes made to the password 
		configuration since the unit was powered up."
	::= { sarian-config 6 }

unsavedPwdChanges		OBJECT-TYPE
	SYNTAX	INTEGER
	ACCESS	read-only
	STATUS	mandatory
	DESCRIPTION
		"The number of unsaved password configuration 
		changes."
	::= { sarian-config 7 }

lastSavedPwdConfigUser	OBJECT-TYPE
	SYNTAX	DisplayString
	ACCESS	read-only
	STATUS	mandatory
	DESCRIPTION
		"The user who last saved the password configuration."
	::= { sarian-config 8 }

lastSavedPwdConfigTime	OBJECT-TYPE
	SYNTAX	DisplayString
	ACCESS	read-only
	STATUS	mandatory
	DESCRIPTION
		"The time the password configuration was last saved."
	::= { sarian-config 9 }

lastSavedPwdConfigNumber	OBJECT-TYPE
	SYNTAX	INTEGER
	ACCESS	read-only
	STATUS	mandatory
	DESCRIPTION
		"The number of changes that had been made when the 
		password configuration was last saved."
	::= { sarian-config 10 }

END
