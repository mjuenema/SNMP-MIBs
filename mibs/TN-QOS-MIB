TN-QOS-MIB DEFINITIONS ::= BEGIN

-- (c) Copyright 2016 Nokia.  All rights reserved.
-- This software is the confidential and proprietary property of
-- Nokia and may only be used in accordance with the
-- terms of the license agreement provided with this software.

IMPORTS
    MODULE-IDENTITY, OBJECT-TYPE,
    Unsigned32, IpAddress, Integer32
                                                     FROM SNMPv2-SMI
    RowStatus, MacAddress, TruthValue, 
    TimeStamp, TEXTUAL-CONVENTION
                                                     FROM SNMPv2-TC
    InetAddressIPv6, InetAddressPrefixLength
                                                     FROM INET-ADDRESS-MIB

    tnSRMIBModules, tnSRObjs
                                                     FROM TROPIC-GLOBAL-REG

    
    Dot1PPriority, IpAddressPrefixLength,
    ServiceAccessPoint,TItemDescription,
    TNamedItem, TNamedItemOrEmpty,
    TDSCPNameOrEmpty,
    TIpProtocol, TTcpUdpPort,
    TTcpUdpPortOperator, TFrameType, TFCName,
    TLspExpValue, TQueueId, TIngressQueueId,
    TEgressQueueId, TIngressHsmdaQueueId,
    TPortSchedulerPIR, 
    TPortSchedulerCIR,
    TWeight, 
    TSapIngressPolicyID, 
    TIngressHsmdaPerPacketOffset,
    TIngressHsmdaCounterIdOrZero,
    TNetworkPolicyID, TItemScope, TItemMatch,
    TPriority, TPriorityOrDefault,
    TProfile, TDEProfile, TProfileOrNone,
    TRemarkType,
    TPrecValueOrNone,
    TBurstHundredthsOfPercent, TBurstPercentOrDefault,
    TRatePercent, TPIRRatePercent,
    TLevel, TLevelOrDefault,
    TEntryId, TMatchCriteria,
    TDEValue, TMacFilterType, TLNamedItemOrEmpty, TAdaptationRule
                                                     FROM TN-TC-MIB

    tnSysSwitchId                                    FROM TROPIC-SYSTEM-MIB
    ;

tnQosMIBModule   MODULE-IDENTITY
        LAST-UPDATED    "1511020000Z"
        ORGANIZATION    "Nokia"
        CONTACT-INFO
            "Nokia 7x50 Support
             Web: http://www.nokia.com/comps/pages/carrier_support.jhtml"
        DESCRIPTION
            "This document is the SNMP MIB module to manage and provision
             Quality of Service features on Nokia 7x50 systems.

             Copyright 2003-2011 Nokia. All rights reserved.
             Reproduction of this document is authorized on the condition that
             the foregoing copyright notice is included.

             This SNMP MIB module (Specification) embodies Nokia's
             proprietary intellectual property.  Nokia retains
             all title and ownership in the Specification, including any
             revisions.

             Nokia grants all interested parties a non-exclusive
             license to use and distribute an unmodified copy of this
             Specification in connection with management of Nokia 
             products, and without fee, provided this copyright notice and
             license appear on all copies.

             This Specification is supplied 'as is', and Nokia 
             makes no warranty, either express or implied, as to the use,
             operation, condition, or performance of the Specification."

--
--  Revision History
--
        REVISION        "1308220000Z"
        DESCRIPTION     "Added the following to tnSapIngressTable:
                         tnSapIngressMacCritType 
                         tnSapIngressPolicyName."

        REVISION        "1212050000Z"
        DESCRIPTION     "Commented out unsupported MIB tables and
                         attributes for 1830."

        REVISION        "0902280000Z"
        DESCRIPTION     "Rev 7.0                28 Feb 2009 00:00
                         7.0 release of the TIMETRA-QOS-MIB."

        REVISION        "0807010000Z"
        DESCRIPTION     "Rev 6.1                01 Jul 2008 00:00
                         6.1 release of the TIMETRA-QOS-MIB."

        REVISION        "0801010000Z"
        DESCRIPTION     "Rev 6.0                01 Jan 2008 00:00
                         6.0 release of the TIMETRA-QOS-MIB."

        REVISION        "0701010000Z"
        DESCRIPTION     "Rev 5.0                01 Jan 2007 00:00
                         5.0 release of the TIMETRA-QOS-MIB."

        REVISION        "0602280000Z"
        DESCRIPTION     "Rev 4.0                28 Feb 2006 00:00
                         4.0 release of the TIMETRA-QOS-MIB."

        REVISION        "0508310000Z"
        DESCRIPTION     "Rev 3.0                31 Aug 2005 00:00
                         3.0 release of the TIMETRA-QOS-MIB."

        REVISION        "0501240000Z"
        DESCRIPTION     "Rev 2.1                24 Jan 2005 00:00
                         2.1 release of the TIMETRA-QOS-MIB."

        REVISION        "0401150000Z"
        DESCRIPTION     "Rev 2.0                    15 Jan 2004 00:00
                         2.0 release of the TIMETRA-QOS-MIB."

        REVISION        "0308150000Z"
        DESCRIPTION     "Rev 1.2                    15 Aug 2003 00:00
                         1.2 release of the TIMETRA-QOS-MIB."

        REVISION        "0301200000Z"
        DESCRIPTION     "Rev 1.0                    20 Jan 2003 00:00
                         1.0 Release of the TIMETRA-QOS-MIB."

        REVISION        "0105290000Z"
        DESCRIPTION     "Rev 0.1                    29 May 2001 00:00
                         Initial version of the TIMETRA-QOS-MIB."
       
        REVISION        "1511020000Z"
        DESCRIPTION     "Added the following MIB table:
                         tnNetworkIngressLSPEXPTable."

        ::= { tnSRMIBModules 16 }

tnQosObjects                    OBJECT IDENTIFIER ::= { tnSRObjs 16 }
-- tnQosNotifyPrefix              OBJECT IDENTIFIER ::= { tnSRNotifyPrefix 16}
--     tnQosNotifications           OBJECT IDENTIFIER ::= { tnQosNotifyPrefix 0}
-- tnQosConformance             OBJECT IDENTIFIER ::= { tnSRConfs 16 }

-- tnDSCPObjects                   OBJECT IDENTIFIER ::= { tnQosObjects 1 }
-- tnFCObjects                     OBJECT IDENTIFIER ::= { tnQosObjects 2 }
tnSapIngressObjects             OBJECT IDENTIFIER ::= { tnQosObjects 3 }
-- tnSapEgressObjects              OBJECT IDENTIFIER ::= { tnQosObjects 4 }
tnNetworkObjects                OBJECT IDENTIFIER ::= { tnQosObjects 5 }
tnNetworkQueueObjects           OBJECT IDENTIFIER ::= { tnQosObjects 6 }
-- tnSharedQueueObjects            OBJECT IDENTIFIER ::= { tnQosObjects 7 }
tnSlopeObjects                  OBJECT IDENTIFIER ::= { tnQosObjects 10 }
tnSchedulerObjects              OBJECT IDENTIFIER ::= { tnQosObjects 12 }
-- tnQosTimeStampObjects           OBJECT IDENTIFIER ::= { tnQosObjects 20 }
-- tnAtmTdpObjects                 OBJECT IDENTIFIER ::= { tnQosObjects 21 }
-- tnPoolObjects                   OBJECT IDENTIFIER ::= { tnQosObjects 22 }
-- tnMcMlpppIngressObjects         OBJECT IDENTIFIER ::= { tnQosObjects 23 } 
-- tnMcMlpppEgressObjects          OBJECT IDENTIFIER ::= { tnQosObjects 24 }
-- tnMcFrIngressObjects            OBJECT IDENTIFIER ::= { tnQosObjects 25 } 
-- tnMcFrEgressObjects             OBJECT IDENTIFIER ::= { tnQosObjects 26 }

--
-- mib objects
--

--
--      TmnxMcFrClassIndex
--
TmnxMcFrClassIndex ::= TEXTUAL-CONVENTION
    STATUS      current
    DESCRIPTION
        "The TmnxMcFrClassIndex indicates the class
         of a Multiclass Fr bundle.
         For example, a 4-class Fr link has 4 classes with 
         indices 0, 1, 2, and 3."
    SYNTAX      INTEGER (0..15)
    
--
-- DSCP Name -> DSCP value mapping table
--

-- tnDSCPNameTable OBJECT-TYPE
--     SYNTAX       SEQUENCE OF TnDSCPNameEntry
--     MAX-ACCESS   not-accessible
--     STATUS       current
--     DESCRIPTION
--         "A list of all DSCP Names.  DSCP Name entries must
--          exist here and be active before they can be referenced
--          elsewhere (e.g. IP filter)."
--     ::= { tnDSCPObjects 1 }
-- 
-- tnDSCPNameEntry OBJECT-TYPE
--     SYNTAX       TnDSCPNameEntry
--     MAX-ACCESS   not-accessible
--     STATUS       current
--     DESCRIPTION
--         "Information about a particular DSCP Name, particularly
--          the DSCP value. It maps a DSCP Name into a DSCP value.
-- 
--          Some default entries are created by the agent.
--          Default entries have tnDSCPNameStorageType permanent,
--          and can not be deleted.
-- 
--          Entries cannot be created by user but may be supported later.
-- 
--          An attempt to create a row in this table would return no creation."
--     INDEX { tnSysSwitchId, tnDSCPName }
--     ::= { tnDSCPNameTable 1 }
-- 
-- TnDSCPNameEntry ::= SEQUENCE
--     {
--         tnDSCPName            TDSCPName,
--         tnDSCPNameRowStatus   RowStatus,
--         tnDSCPNameStorageType StorageType,
--         tnDSCPNameDscpValue   TDSCPValue,
--         tnDSCPNameLastChanged TimeStamp
--     }
-- 
-- tnDSCPName OBJECT-TYPE
--     SYNTAX       TDSCPName
--     MAX-ACCESS   not-accessible
--     STATUS       current
--     DESCRIPTION
--         "The name assigned to the DSCP Value."
--     REFERENCE
--         ""
--     ::= { tnDSCPNameEntry 1 }
-- 
-- tnDSCPNameRowStatus OBJECT-TYPE
--     SYNTAX       RowStatus
--     MAX-ACCESS   read-create
--     STATUS       current
--     DESCRIPTION
--         "Row Status of the entry."
--     ::= { tnDSCPNameEntry 2 }
-- 
-- tnDSCPNameStorageType OBJECT-TYPE
--     SYNTAX       StorageType
--     MAX-ACCESS   read-create
--     STATUS       current
--     DESCRIPTION
--         "The storage type of this row in the table."
--     DEFVAL { nonVolatile }
--     ::= { tnDSCPNameEntry 3 }
-- 
-- tnDSCPNameDscpValue OBJECT-TYPE
--     SYNTAX       TDSCPValue
--     MAX-ACCESS   read-create
--     STATUS       current
--     DESCRIPTION
--         "The DSCP Value."
--     REFERENCE
--         ""
--     DEFVAL { 0 }
--     ::= { tnDSCPNameEntry 4 }
-- 
-- tnDSCPNameLastChanged OBJECT-TYPE
--     SYNTAX       TimeStamp
--     MAX-ACCESS   read-only
--     STATUS       current
--     DESCRIPTION
--         "timestamp of last change to this row in tnDSCPNameTable."
--     ::= { tnDSCPNameEntry 5 }

--
-- Forwarding Class name table
--

-- tnFCNameTable OBJECT-TYPE
--     SYNTAX       SEQUENCE OF TFCNameEntry
--     MAX-ACCESS   not-accessible
--     STATUS       current
--     DESCRIPTION
--         "A list of all Forwarding Class Names.  Forwarding Class Name entries
--         must exist here and be active before they can be referenced
--         elsewhere (e.g. qos queue)."
--     ::= { tnFCObjects 1 }
-- 
-- tnFCNameEntry OBJECT-TYPE
--     SYNTAX       TFCNameEntry
--     MAX-ACCESS   not-accessible
--     STATUS       current
--     DESCRIPTION
--         "Information about a particular Forwarding Class Name, particularly
--          the Forwarding Class value.
-- 
--          Some default entries are created by the agent.
--          Default entries have tnFCStorageType permanent,
--          and can not be deleted.
-- 
--          Entries cannot be created by user but maybe supported in future.
-- 
--          An attempt to create a row in this table would return no creation."
--     INDEX { tnSysSwitchId, tnFCName }
--     ::= { tnFCNameTable 1 }
-- 
-- TFCNameEntry ::= SEQUENCE
--     {
--         tnFCName               TFCName,
--         tnFCRowStatus          RowStatus,
--         tnFCStorageType        StorageType,
--         tnFCValue              Integer32,
--         tnFCNameLastChanged    TimeStamp
--     }
-- 
-- tnFCName OBJECT-TYPE
--     SYNTAX       TFCName
--     MAX-ACCESS   not-accessible
--     STATUS       current
--     DESCRIPTION "Forwarding class name."
--     REFERENCE ""
--     ::= { tnFCNameEntry 1 }
-- 
-- tnFCRowStatus OBJECT-TYPE
--     SYNTAX       RowStatus
--     MAX-ACCESS   read-create
--     STATUS       current
--     DESCRIPTION "Row Status of the entry."
--     ::= { tnFCNameEntry 2 }
-- 
-- tnFCStorageType OBJECT-TYPE
--     SYNTAX       StorageType
--     MAX-ACCESS   read-create
--     STATUS       current
--     DESCRIPTION "The storage type of this row in the table."
--     DEFVAL { nonVolatile }
--     ::= { tnFCNameEntry 3 }
-- 
-- tnFCValue OBJECT-TYPE
--     SYNTAX       Integer32 (0..7)
--     MAX-ACCESS   read-create
--     STATUS       current
--     DESCRIPTION "FC Value."
--     REFERENCE ""
--     DEFVAL { 0 }
--     ::= { tnFCNameEntry 4 }
-- 
-- tnFCNameLastChanged OBJECT-TYPE
--     SYNTAX       TimeStamp
--     MAX-ACCESS   read-only
--     STATUS       current
--     DESCRIPTION
--         "timestamp of last change to this row in tnFCNameTable."
--     ::= { tnFCNameEntry 5 }

--
-- sap-ingress policy table
--

tnSapIngressTable OBJECT-TYPE
    SYNTAX       SEQUENCE OF TSapIngressEntry
    MAX-ACCESS   not-accessible
    STATUS       current
    DESCRIPTION  "  "
    ::= { tnSapIngressObjects 1 }

tnSapIngressEntry OBJECT-TYPE
    SYNTAX       TSapIngressEntry
    MAX-ACCESS   not-accessible
    STATUS       current
    DESCRIPTION
        "Information about a particular Sap Ingress Policy.

         sap-ingress policy (1) is the default entry.

         Default Entry is created by the agent, other entries are
         created by user.

         Default Entry cannot be modified/deleted. The other
         entries are deleted by user.

         There is no StorageType object, entries have a presumed
         StorageType of nonVolatile.
        "
    INDEX { tnSysSwitchId, tnSapIngressIndex }
    ::= { tnSapIngressTable 1 }

TSapIngressEntry ::= SEQUENCE
    {
        tnSapIngressIndex                        TSapIngressPolicyID,
        tnSapIngressRowStatus                    RowStatus,
        tnSapIngressScope                        TItemScope,
        tnSapIngressDescription                  TItemDescription,
        tnSapIngressDefaultFC                    TNamedItem,
        tnSapIngressDefaultFCPriority            TPriority,
        tnSapIngressMatchCriteria                TMatchCriteria,
        tnSapIngressLastChanged                  TimeStamp,
        tnSapIngressHsmdaPacketOffset            TIngressHsmdaPerPacketOffset,
        tnSapIngressDefFCHsmdaCntrOvr            TIngressHsmdaCounterIdOrZero,
        tnSapIngressMacCritType                  TMacFilterType,
        tnSapIngressPolicyName                   TLNamedItemOrEmpty
    }

tnSapIngressIndex OBJECT-TYPE
    SYNTAX       TSapIngressPolicyID (1..65535)
    MAX-ACCESS   not-accessible
    STATUS       current
    DESCRIPTION
        "the policy ID is the index to this table."
    ::= { tnSapIngressEntry 1 }

tnSapIngressRowStatus OBJECT-TYPE
    SYNTAX       RowStatus
    MAX-ACCESS   read-create
    STATUS       current
    DESCRIPTION
        "Row Status for the policy. The deletion of this row has
         an action of removing the dependent rows in the following
         tables :
           - tnSapIngressQueueTable
           - tnSapIngressDSCPTable
           - tnSapIngressDot1pTable
        "
    ::= { tnSapIngressEntry 2 }

tnSapIngressScope OBJECT-TYPE
    SYNTAX       TItemScope
    MAX-ACCESS   read-create
    STATUS       current
    DESCRIPTION
        "Scope of the policy. If the scope is 'exclusive', it can only be
         instantiated once whereas it could have multiple instances if defined
         as 'exclusive'."
    DEFVAL { template }
    ::= { tnSapIngressEntry 3 }

tnSapIngressDescription OBJECT-TYPE
    SYNTAX       TItemDescription
    MAX-ACCESS   read-create
    STATUS       current
    DESCRIPTION
        "user-provided description of the policy."
    DEFVAL { ''H }
    ::= { tnSapIngressEntry 4 }

tnSapIngressDefaultFC OBJECT-TYPE
    SYNTAX       TNamedItem
    MAX-ACCESS   read-create
    STATUS       current
    DESCRIPTION
        "tnSapIngressDefaultFC specifies the forwarding class or the
         sub forwarding class which should be used for all traffic that
         does not match a specific classification specified in this
         SAP ingress QoS policy.

         Specification of a sub forwarding class is also allowed. The
         format of a sub forwarding class is the concatenation of the
         base forwarding class and a sub class identifier in the form

             base-fc-name[.sub-fc-name]

         To reference a sub forwarding class, the mapping of the sub
         forwarding class should be existing in this QoS policy.

         If not specified explicitly, all traffic will be classified
         as best-effort 'be'."
    DEFVAL { 'be'H }
    ::= { tnSapIngressEntry 5 }

tnSapIngressDefaultFCPriority OBJECT-TYPE
    SYNTAX       TPriority
    MAX-ACCESS   read-create
    STATUS       current
    DESCRIPTION
        "the priority to assign to traffic ingressing as the default
         action queue."
    DEFVAL { low }
    ::= { tnSapIngressEntry 6 }

tnSapIngressMatchCriteria OBJECT-TYPE
    SYNTAX       TMatchCriteria
    MAX-ACCESS   read-only
    STATUS       current
    DESCRIPTION
        "indicates which type of match criteria the policy should use.
         when set to ip(1), the policy looks for match entries in
         tnSapIngressIPCriteriaTable or tnSapIngressIPv6CriteriaTable.
         When set to mac(2), the policy looks for match entries in 
         tnSapIngressMacCriteriaTable.

         the value of tnSapIngressMatchCriteria is set when the first
         match criteria table entry is created.  the value is set to
         none(3) when the last criteria table entry is removed.

         when tnSapIngressMatchCriteria is set to ip(1), no
         tnSapIngressMacCriteriaTable entries can be created.
         when set to mac(2), no tnSapIngressIPCriteriaTable or 
         tnSapIngressIPv6CriteriaTable entries can be created.
        "
    ::= { tnSapIngressEntry 7 }

tnSapIngressLastChanged OBJECT-TYPE
    SYNTAX       TimeStamp
    MAX-ACCESS   read-only
    STATUS       current
    DESCRIPTION
        "timestamp of last change to this row in tnSapIngressTable."
    ::= { tnSapIngressEntry 8 }

tnSapIngressHsmdaPacketOffset    OBJECT-TYPE
    SYNTAX      TIngressHsmdaPerPacketOffset
    UNITS       "bytes"
    MAX-ACCESS  read-create
    STATUS      current
    DESCRIPTION
        "The value of tnSapIngressHsmdaPacketOffset specifies the
         value, in bytes, of the adjustment to make to the size of each
         packet for HSMDA queue accounting."
    DEFVAL { 0 }
    ::= { tnSapIngressEntry 9 }

tnSapIngressDefFCHsmdaCntrOvr OBJECT-TYPE
    SYNTAX       TIngressHsmdaCounterIdOrZero
    MAX-ACCESS   read-create
    STATUS       current
    DESCRIPTION
        "The value of the object tnSapIngressDefFCHsmdaCntrOvr specifies
         the counter to use for all traffic that does not match a specific 
         classification specified in this SAP ingress QoS policy.

         A value of zero implies that the default counters should be used."
    DEFVAL { 0 }
    ::= { tnSapIngressEntry 10 }

tnSapIngressMacCritType OBJECT-TYPE
    SYNTAX       TMacFilterType       
    MAX-ACCESS   read-create
    STATUS       current
    DESCRIPTION
        "tnSapIngressMacCritType specifies which type of entries this mac filter
         can contain.
 
         If tnSapIngressMacCritType is set to 'normal(1)', all match criteria
         are accepted except the criteria mentioned below that belong to type
         vid(3) or isid(2). 
         
         tnSapIngressMacCritType 'isid(2)' is not supported here. 
 
         If tnSapIngressMacCritType is set to vid(3) the only accepted match
         criteria for the filter entries are:
         - tSapIngressMacCritInnerTagValue
         - tSapIngressMacCritInnerTagMask 
         - tSapIngressMacCritOuterTagValue
         - tSapIngressMacCritOuterTagMask 
         
         tnSapIngressMacCritType can only be changed if the filter
         has no entries.
         
         The value will be set to  'normal(1)' if IP or IPV6 criteria are added
         to the this SAP ingress QoS policy. Any change attempt in this case 
         will be silently discarded.
         "
    DEFVAL { normal }
    ::= { tnSapIngressEntry 11 }
 
tnSapIngressPolicyName OBJECT-TYPE
    SYNTAX       TLNamedItemOrEmpty
    MAX-ACCESS   read-create
    STATUS       current
    DESCRIPTION
        "The value of tnSapIngressPolicyName specifies the name to associate
        with this policy."
    DEFVAL { ''H }
    ::= { tnSapIngressEntry 12 }

--
-- sap-ingress policy queue table
--

-- tnSapIngressQueueTable OBJECT-TYPE
--     SYNTAX       SEQUENCE OF TSapIngressQueueEntry
--     MAX-ACCESS   not-accessible
--     STATUS       current
--     DESCRIPTION
--         "information about all sap-ingress policies' queues."
--     ::= { tnSapIngressObjects 2 }
-- 
-- tnSapIngressQueueEntry OBJECT-TYPE
--     SYNTAX       TSapIngressQueueEntry
--     MAX-ACCESS   not-accessible
--     STATUS       current
--     DESCRIPTION
--         "Information about a particular queue for a sap-ingress policy.
-- 
--          Queue (1) is the used as a default for unicast and queue (11) is
--          used as a default for multicast. Both these are created by the
--          agent and can be edited but not removed from the system.
-- 
--          Other entries are created by user."
--     INDEX { tnSysSwitchId, tnSapIngressIndex, tnSapIngressQueue }
--     ::= { tnSapIngressQueueTable 1 }
-- 
-- TSapIngressQueueEntry ::= SEQUENCE
--     {
--         tnSapIngressQueue                 TIngressQueueId,
--         tnSapIngressQueueRowStatus        RowStatus,
--         tnSapIngressQueueParent           TNamedItemOrEmpty,
--         tnSapIngressQueueLevel            TLevel,
--         tnSapIngressQueueWeight           TWeight,
--         tnSapIngressQueueCIRLevel         TLevelOrDefault,
--         tnSapIngressQueueCIRWeight        TWeight,
--         tnSapIngressQueueMCast            TruthValue,
--         tnSapIngressQueueExpedite         INTEGER,
--         tnSapIngressQueueCBS              TBurstSize,
--         tnSapIngressQueueMBS              TBurstSize,
--         tnSapIngressQueueHiPrioOnly       TBurstPercentOrDefault,
--         tnSapIngressQueuePIRAdaptation    TAdaptationRule,
--         tnSapIngressQueueCIRAdaptation    TAdaptationRule,
--         tnSapIngressQueueAdminPIR         TPIRRate,
--         tnSapIngressQueueAdminCIR         TCIRRate,
-- ==        tnSapIngressQueueOperPIR          TPIRRate,
-- ==        tnSapIngressQueueOperCIR          TCIRRate,
--         tnSapIngressQueueLastChanged      TimeStamp,
--         tnSapIngressQueuePoliced          TruthValue,
--         tnSapIngressQueueMode             TQueueMode,
--         tnSapIngressQueuePoolName         TNamedItemOrEmpty
--     }
-- 
-- tnSapIngressQueue OBJECT-TYPE
--     SYNTAX       TIngressQueueId (1..32)
--     MAX-ACCESS   not-accessible
--     STATUS       current
--     DESCRIPTION
--         "The queue ID is used as the secondary index to the table entry."
--     ::= { tnSapIngressQueueEntry 1 }
-- 
-- tnSapIngressQueueRowStatus OBJECT-TYPE
--     SYNTAX       RowStatus
--     MAX-ACCESS   read-create
--     STATUS       current
--     DESCRIPTION
--         "Row Status of the entry. This allows creation/deletion of rows in this
--          table."
--     ::= { tnSapIngressQueueEntry 2 }
-- 
-- tnSapIngressQueueParent OBJECT-TYPE
--     SYNTAX       TNamedItemOrEmpty
--     MAX-ACCESS   read-create
--     STATUS       current
--     DESCRIPTION
--         "The scheduler to which this queue would be feeding to."
--     DEFVAL { ''H }
--     ::= { tnSapIngressQueueEntry 3 }
-- 
-- tnSapIngressQueueLevel OBJECT-TYPE
--     SYNTAX       TLevel
--     MAX-ACCESS   read-create
--     STATUS       current
--     DESCRIPTION
--         "This specifies the level of priority while feeding to the parent."
--     DEFVAL { 1 }
--     ::= { tnSapIngressQueueEntry 4 }
-- 
-- tnSapIngressQueueWeight OBJECT-TYPE
--     SYNTAX       TWeight
--     MAX-ACCESS   read-create
--     STATUS       current
--     DESCRIPTION
--         "The weight that needs to be used by the scheduler to which this queue
--          would be feeding to."
--     DEFVAL { 1 }
--     ::= { tnSapIngressQueueEntry 5 }
-- 
-- tnSapIngressQueueCIRLevel OBJECT-TYPE
--     SYNTAX       TLevelOrDefault
--     MAX-ACCESS   read-create
--     STATUS       current
--     DESCRIPTION
--         "This specifies the level of priority while feeding to the parent.
--          The level '0' means treat all offered load for this queue as for
--          the above CIR traffic."
--     DEFVAL { 0 }
--     ::= { tnSapIngressQueueEntry 6 }
-- 
-- tnSapIngressQueueCIRWeight OBJECT-TYPE
--     SYNTAX       TWeight
--     MAX-ACCESS   read-create
--     STATUS       current
--     DESCRIPTION
--         "The weight that needs to be used until the committed rate by the
--          scheduler to which this queue would be feeding to."
--     DEFVAL { 1 }
--     ::= { tnSapIngressQueueEntry 7 }
-- 
-- tnSapIngressQueueMCast OBJECT-TYPE
--     SYNTAX       TruthValue
--     MAX-ACCESS   read-create
--     STATUS       current
--     DESCRIPTION
--         "This object specifies if this is a multicast queue or not."
--     DEFVAL { false }
--     ::= { tnSapIngressQueueEntry 8 }
-- 
-- tnSapIngressQueueExpedite OBJECT-TYPE
--     SYNTAX       INTEGER {
--                     expedited     (1),
--                     auto-expedited(2),
--                     non-expedited (3)
--                  }
--     MAX-ACCESS   read-create
--     STATUS       current
--     DESCRIPTION
--         "tnSapIngressQueueExpedite specifies the priority that this queue should
--          be assigned by the hardware level schedulers.
-- 
--          The value 'auto-expedited' implies that this attribute should be
--          dynamically updated by looking at the forwarding classes mapping
--          into this queue. In such a case the queue is treated as
--          'non-expedited' if there is even a single non-expedited forwarding
--          class using this queue.
-- 
--          This attribute is associated with the queue at the time of creation and
--          cannot be modified thereafter."
--     DEFVAL { auto-expedited }
--     ::= { tnSapIngressQueueEntry 9 }
-- 
-- tnSapIngressQueueCBS OBJECT-TYPE
--     SYNTAX       TBurstSize
--     MAX-ACCESS   read-create
--     STATUS       current
--     DESCRIPTION
--         "The amount of reserved buffer space (in kilo bytes) for the queue."
--     DEFVAL { -1 }
--     ::= { tnSapIngressQueueEntry 10 }
-- 
-- tnSapIngressQueueMBS OBJECT-TYPE
--     SYNTAX       TBurstSize
--     MAX-ACCESS   read-create
--     STATUS       current
--     DESCRIPTION
--         "The maximum amount of buffer space (in kilo bytes) allowed for the
--          queue."
--     DEFVAL { -1 }
--     ::= { tnSapIngressQueueEntry 11 }
-- 
-- tnSapIngressQueueHiPrioOnly OBJECT-TYPE
--     SYNTAX       TBurstPercentOrDefault
--     MAX-ACCESS   read-create
--     STATUS       current
--     DESCRIPTION
--         "The percentage of buffer space for the queue, used
--          exclusively by high priority packets."
--     DEFVAL { -1 }
--     ::= { tnSapIngressQueueEntry 12 }
-- 
-- tnSapIngressQueuePIRAdaptation OBJECT-TYPE
--     SYNTAX       TAdaptationRule
--     MAX-ACCESS   read-create
--     STATUS       current
--     DESCRIPTION
--         "The adaptation rule to be used while computing the operational PIR
--          value. The adaptation rule specifies the rules to compute the
--          operational values while maintaining minimum offset."
--     DEFVAL { closest }
--     ::= { tnSapIngressQueueEntry 13 }
-- 
-- tnSapIngressQueueCIRAdaptation OBJECT-TYPE
--     SYNTAX       TAdaptationRule
--     MAX-ACCESS   read-create
--     STATUS       current
--     DESCRIPTION
--         "The adaptation rule to be used while computing the operational CIR
--          value. The adaptation rule specifies the rules to compute the
--          operational values while maintaining minimum offset."
--     DEFVAL { closest }
--     ::= { tnSapIngressQueueEntry 14 }
-- 
-- tnSapIngressQueueAdminPIR OBJECT-TYPE
--     SYNTAX       TPIRRate
--     UNITS        "kbps"
--     MAX-ACCESS   read-create
--     STATUS       current
--     DESCRIPTION
--         "The administrative PIR specified by the user."
--     DEFVAL { -1 }
--     ::= { tnSapIngressQueueEntry 15 }
-- 
-- tnSapIngressQueueAdminCIR OBJECT-TYPE
--     SYNTAX       TCIRRate
--     UNITS        "kbps"
--     MAX-ACCESS   read-create
--     STATUS       current
--     DESCRIPTION
--         "The administrative CIR specified by the user."
--     DEFVAL { 0 }
--     ::= { tnSapIngressQueueEntry 16 }
-- 
-- == tnSapIngressQueueOperPIR OBJECT-TYPE
-- ==     SYNTAX       TPIRRate
-- ==     UNITS        "kbps"
-- ==     MAX-ACCESS   read-only
-- ==     STATUS       obsolete
-- ==     DESCRIPTION
-- ==         "The operating PIR."
-- ==     ::= { tnSapIngressQueueEntry 17 }
-- == 
-- == tnSapIngressQueueOperCIR OBJECT-TYPE
-- ==     SYNTAX       TCIRRate
-- ==     UNITS        "kbps"
-- ==     MAX-ACCESS   read-only
-- ==     STATUS       obsolete
-- ==     DESCRIPTION
-- ==         "The operational value derived by computing the CIR value from
-- ==          the administrative CIR and PIR values and their corresponding
-- ==          adaptation rules."
-- ==     ::= { tnSapIngressQueueEntry 18 }
-- 
-- tnSapIngressQueueLastChanged OBJECT-TYPE
--     SYNTAX       TimeStamp
--     MAX-ACCESS   read-only
--     STATUS       current
--     DESCRIPTION
--         "timestamp of last change to this row in tnSapIngressQueueTable."
--     ::= { tnSapIngressQueueEntry 19 }
-- 
-- tnSapIngressQueuePoliced OBJECT-TYPE
--     SYNTAX       TruthValue
--     MAX-ACCESS   read-create
--     STATUS       current
--     DESCRIPTION
--         "tnSapIngressQueuePoliced specifies that the out of profile
--          traffic feeding into the physical queue instance should be
--          dropped. tnSapIngressQueuePoliced overrides the bandwidth
--          specified by the object tnSapIngressQueueAdminCIR."
--     DEFVAL { false }
--     ::= { tnSapIngressQueueEntry 20 }
-- 
-- tnSapIngressQueueMode OBJECT-TYPE
--     SYNTAX       TQueueMode
--     MAX-ACCESS   read-create
--     STATUS       current
--     DESCRIPTION
--         "tnSapIngressQueueMode specifies the mode in which the queue
--          is operating. This attribute is associated with the queue
--          at the time of creation and cannot be modified thereafter."
--     DEFVAL { priority }
--     ::= { tnSapIngressQueueEntry 21 }
-- 
-- tnSapIngressQueuePoolName OBJECT-TYPE   
--     SYNTAX      TNamedItemOrEmpty
--     MAX-ACCESS  read-create
--     STATUS      current
--     DESCRIPTION
--         "The value of tnSapIngressQueuePoolName specifies the name of 
--          the pool to be applied for SAP ingress queue."
--     DEFVAL { ''H }    
--     ::= { tnSapIngressQueueEntry 22 }

--
-- sap-ingress policy dscp table
--

-- tnSapIngressDSCPTable OBJECT-TYPE
--     SYNTAX       SEQUENCE OF TSapIngressDSCPEntry
--     MAX-ACCESS   not-accessible
--     STATUS       current
--     DESCRIPTION
--         "a list of all DSCP entries for all sap-ingress policies."
--     ::= { tnSapIngressObjects 3 }
-- 
-- tnSapIngressDSCPEntry OBJECT-TYPE
--     SYNTAX       TSapIngressDSCPEntry
--     MAX-ACCESS   not-accessible
--     STATUS       current
--     DESCRIPTION
--         "Information about a particular DSCP entry for a sap-ingress policy.
-- 
--         Entries are created by user.
--         Entries are deleted by user.
-- 
--         There is no StorageType object, entries have a presumed
--         StorageType of nonVolatile.
-- 
--         in the event that one policy has multiple entries, and
--         the tnSapIngressDSCP values are the same, only one queue
--         will be created (the queue for the lexicographically
--         first tnSapIngressDSCP).
--         "
--     INDEX { tnSysSwitchId, tnSapIngressIndex, tnSapIngressDSCP }
--     ::= { tnSapIngressDSCPTable 1 }
-- 
-- TSapIngressDSCPEntry ::= SEQUENCE
--     {
--         tnSapIngressDSCP                    TDSCPName,
--         tnSapIngressDSCPRowStatus           RowStatus,
--         tnSapIngressDSCPFC                  TNamedItemOrEmpty,
--         tnSapIngressDSCPPriority            TPriorityOrDefault,
--         tnSapIngressDSCPLastChanged         TimeStamp,
--         tnSapIngressDSCPHsmdaCntrOvr    TIngressHsmdaCounterIdOrZero
--     }
-- 
-- tnSapIngressDSCP OBJECT-TYPE
--     SYNTAX       TDSCPName
--     MAX-ACCESS   not-accessible
--     STATUS       current
--     DESCRIPTION
--         ""
--     ::= { tnSapIngressDSCPEntry 1 }
-- 
-- tnSapIngressDSCPRowStatus OBJECT-TYPE
--     SYNTAX       RowStatus
--     MAX-ACCESS   read-create
--     STATUS       current
--     DESCRIPTION
--         "This object allows creation/deletion of rows in this table."
--     ::= { tnSapIngressDSCPEntry 2 }
-- 
-- tnSapIngressDSCPFC OBJECT-TYPE
--     SYNTAX       TNamedItemOrEmpty
--     MAX-ACCESS   read-create
--     STATUS       current
--     DESCRIPTION
--         "tnSapIngressDSCPFC specifies the forwarding class or the sub
--          forwarding class to be used to classify all the traffic that
--          matches the specific DSCP i.e. tnSapIngressDSCP.
-- 
--          Specification of a sub forwarding class is also allowed. The
--          format of a sub forwarding class is the concatenation of the
--          base forwarding class and a sub class identifier in the form
-- 
--              base-fc-name[.sub-fc-name]
-- 
--          To reference a sub forwarding class, the mapping of the sub
--          forwarding class should be existing in this QoS policy.
-- 
--          Unless tnSapIngressDSCPFC is specified explicitly, this match
--          will be ignored for classification purposes."
--     DEFVAL { ''H }
--     ::= { tnSapIngressDSCPEntry 3 }
-- 
-- tnSapIngressDSCPPriority OBJECT-TYPE
--     SYNTAX       TPriorityOrDefault
--     MAX-ACCESS   read-create
--     STATUS       current
--     DESCRIPTION
--         ""
--     DEFVAL { default }
--     ::= { tnSapIngressDSCPEntry 4 }
-- 
-- tnSapIngressDSCPLastChanged OBJECT-TYPE
--     SYNTAX       TimeStamp
--     MAX-ACCESS   read-only
--     STATUS       current
--     DESCRIPTION
--         "timestamp of last change to this row in tnSapIngressDSCPTable."
--     ::= { tnSapIngressDSCPEntry 5 }
-- 
-- tnSapIngressDSCPHsmdaCntrOvr OBJECT-TYPE
--     SYNTAX       TIngressHsmdaCounterIdOrZero
--     MAX-ACCESS   read-create
--     STATUS       current
--     DESCRIPTION
--         "The value of the object tnSapIngressDSCPHsmdaCntrOvr 
--          specifies the counter to use for all the traffic that
--          matches the specific DSCP i.e. tnSapIngressDSCP.
-- 
--          A value of zero implies that the default counters should be used."
--     DEFVAL { 0 }
--     ::= { tnSapIngressDSCPEntry 6 }

--
-- sap-ingress policy dot1p table
--

-- tnSapIngressDot1pTable OBJECT-TYPE
--     SYNTAX       SEQUENCE OF TSapIngressDot1pEntry
--     MAX-ACCESS   not-accessible
--     STATUS       current
--     DESCRIPTION
--         "a list of all dot1p entries for all sap-ingress policies."
--     ::= { tnSapIngressObjects 4 }
-- 
-- tnSapIngressDot1pEntry OBJECT-TYPE
--     SYNTAX       TSapIngressDot1pEntry
--     MAX-ACCESS   not-accessible
--     STATUS       current
--     DESCRIPTION
--         "Information about a particular dot1p match for a sap-ingress policy.
--          Entries are created by user.
--          Entries are deleted by user.
-- 
--          There is no StorageType object, entries have a presumed
--          StorageType of nonVolatile.
--         "
--     INDEX { tnSysSwitchId, tnSapIngressIndex, tnSapIngressDot1pValue }
--     ::= { tnSapIngressDot1pTable 1 }
-- 
-- TSapIngressDot1pEntry ::= SEQUENCE
--     {
--         tnSapIngressDot1pValue               Dot1PPriority,
--         tnSapIngressDot1pRowStatus           RowStatus,
--         tnSapIngressDot1pFC                  TNamedItemOrEmpty,
--         tnSapIngressDot1pPriority            TPriorityOrDefault,
--         tnSapIngressDot1pLastChanged         TimeStamp,
--         tnSapIngressDot1pHsmdaCntrOvr    TIngressHsmdaCounterIdOrZero
--     }
-- 
-- tnSapIngressDot1pValue OBJECT-TYPE
--     SYNTAX       Dot1PPriority (0..7)
--     MAX-ACCESS   not-accessible
--     STATUS       current
--     DESCRIPTION
--         "dot1p value to match in the packet.  this value is
--         also used as an index so that for any dot1p value there
--         is only one possible disposition queue and priority.
--         "
--     ::= { tnSapIngressDot1pEntry 1 }
-- 
-- tnSapIngressDot1pRowStatus OBJECT-TYPE
--     SYNTAX       RowStatus
--     MAX-ACCESS   read-create
--     STATUS       current
--     DESCRIPTION
--         "Row Status for this sap-ingress policy's dot1p entry."
--     ::= { tnSapIngressDot1pEntry 2 }
-- 
-- tnSapIngressDot1pFC OBJECT-TYPE
--     SYNTAX       TNamedItemOrEmpty
--     MAX-ACCESS   read-create
--     STATUS       current
--     DESCRIPTION
--         "tnSapIngressDot1pFC specifies the forwarding class or the sub
--          forwarding class to be used to classify all the traffic that
--          matches the specific Dot1p i.e. tnSapIngressDot1pValue.
-- 
--          Specification of a sub forwarding class is also allowed. The
--          format of a sub forwarding class is the concatenation of the
--          base forwarding class and a sub class identifier in the form
-- 
--              base-fc-name[.sub-fc-name]
-- 
--          To reference a sub forwarding class, the mapping of the sub
--          forwarding class should be existing in this QoS policy.
-- 
--          Unless tnSapIngressDot1pFC is specified explicitly, this match
--          will be ignored for classification purposes."
--     DEFVAL { ''H }
--     ::= { tnSapIngressDot1pEntry 3 }
-- 
-- tnSapIngressDot1pPriority OBJECT-TYPE
--     SYNTAX       TPriorityOrDefault
--     MAX-ACCESS   read-create
--     STATUS       current
--     DESCRIPTION
--         "priority to use for packets that match the dot1p value
--         tnSapIngressDot1pValue."
--     DEFVAL { default }
--     ::= { tnSapIngressDot1pEntry 4 }
-- 
-- tnSapIngressDot1pLastChanged OBJECT-TYPE
--     SYNTAX       TimeStamp
--     MAX-ACCESS   read-only
--     STATUS       current
--     DESCRIPTION
--         "timestamp of last change to this row in tnSapIngressDot1pTable."
--     ::= { tnSapIngressDot1pEntry 5 }
-- 
-- tnSapIngressDot1pHsmdaCntrOvr OBJECT-TYPE
--     SYNTAX       TIngressHsmdaCounterIdOrZero
--     MAX-ACCESS   read-create
--     STATUS       current
--     DESCRIPTION
--         "The value of the object tnSapIngressDot1pHsmdaCntrOvr 
--          specifies the counter to use for all the traffic that
--          matches the specific Dot1p i.e. tnSapIngressDot1pValue.
-- 
--          A value of zero implies that the default counters should be used."
--     DEFVAL { 0 }
--     ::= { tnSapIngressDot1pEntry 6 }

--
-- sap-ingress policy ip criteria table
--

tnSapIngressIPCriteriaTable OBJECT-TYPE
    SYNTAX       SEQUENCE OF TSapIngressIPCriteriaEntry
    MAX-ACCESS   not-accessible
    STATUS       current
    DESCRIPTION
        "information about all sap-ingress policies' ip-criteria entries."
    ::= { tnSapIngressObjects 5 }

tnSapIngressIPCriteriaEntry OBJECT-TYPE
    SYNTAX       TSapIngressIPCriteriaEntry
    MAX-ACCESS   not-accessible
    STATUS       current
    DESCRIPTION
        "Information about a particular ip-criteria entry for a sap-ingress
         policy.
         Entries are created by user.
         Entries are deleted by user.
         There is no StorageType object, entries have a presumed
         StorageType of nonVolatile.
        "
    INDEX { tnSysSwitchId, tnSapIngressIndex, tnSapIngressIPCriteriaIndex }
    ::= { tnSapIngressIPCriteriaTable 1 }

TSapIngressIPCriteriaEntry ::= SEQUENCE
    {
        tnSapIngressIPCriteriaIndex               TEntryId,
        tnSapIngressIPCriteriaRowStatus           RowStatus,
        tnSapIngressIPCriteriaDescription         TItemDescription,
        tnSapIngressIPCriteriaActionFC            TNamedItemOrEmpty,
        tnSapIngressIPCriteriaActionPriority      TPriorityOrDefault,
        tnSapIngressIPCriteriaSourceIpAddr        IpAddress,
        tnSapIngressIPCriteriaSourceIpMask        IpAddressPrefixLength,
        tnSapIngressIPCriteriaDestIpAddr          IpAddress,
        tnSapIngressIPCriteriaDestIpMask          IpAddressPrefixLength,
        tnSapIngressIPCriteriaProtocol            TIpProtocol,
        tnSapIngressIPCriteriaSourcePortValue1    TTcpUdpPort,
        tnSapIngressIPCriteriaSourcePortValue2    TTcpUdpPort,
        tnSapIngressIPCriteriaSourcePortOperator  TTcpUdpPortOperator,
        tnSapIngressIPCriteriaDestPortValue1      TTcpUdpPort,
        tnSapIngressIPCriteriaDestPortValue2      TTcpUdpPort,
        tnSapIngressIPCriteriaDestPortOperator    TTcpUdpPortOperator,
        tnSapIngressIPCriteriaDSCP                TDSCPNameOrEmpty,
        tnSapIngressIPCriteriaFragment            TItemMatch,
        tnSapIngressIPCriteriaLastChanged         TimeStamp,
        tnSapIngressIPCritHsmdaCntrOvr         TIngressHsmdaCounterIdOrZero
    }

tnSapIngressIPCriteriaIndex OBJECT-TYPE
    SYNTAX       TEntryId
    MAX-ACCESS   not-accessible
    STATUS       current
    DESCRIPTION
        "unique identifier separates this entry from others in this
         policy."
    ::= { tnSapIngressIPCriteriaEntry 1 }

tnSapIngressIPCriteriaRowStatus OBJECT-TYPE
    SYNTAX       RowStatus
    MAX-ACCESS   read-create
    STATUS       current
    DESCRIPTION
        "Row Status for the IP Criteria entry."
    ::= { tnSapIngressIPCriteriaEntry 2 }

tnSapIngressIPCriteriaDescription OBJECT-TYPE
    SYNTAX       TItemDescription
    MAX-ACCESS   read-create
    STATUS       current
    DESCRIPTION
        "description of this IP criteria entry."
    DEFVAL { ''H }
    ::= { tnSapIngressIPCriteriaEntry 3 }

tnSapIngressIPCriteriaActionFC OBJECT-TYPE
    SYNTAX       TNamedItemOrEmpty
    MAX-ACCESS   read-create
    STATUS       current
    DESCRIPTION
        "tnSapIngressIPCriteriaActionFC specifies the forwarding class
         or the sub forwarding class to be used to classify all the
         traffic that matches the specific IP criteria.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tnSapIngressIPCriteriaActionFC is specified explicitly,
         this match will be ignored for classification purposes."
    DEFVAL { ''H }
    ::= { tnSapIngressIPCriteriaEntry 4 }

tnSapIngressIPCriteriaActionPriority OBJECT-TYPE
    SYNTAX       TPriorityOrDefault
    MAX-ACCESS   read-create
    STATUS       current
    DESCRIPTION
       "priority for packets which match this entry's criteria.

        when set to default, the packet is sent to the queue
        from DSCP/dot1p/FC which matched the packet, using the
        priority from the DSCP/dot1p/FC which matched the packet."
    DEFVAL { default }
    ::= { tnSapIngressIPCriteriaEntry 5 }

tnSapIngressIPCriteriaSourceIpAddr OBJECT-TYPE
    SYNTAX       IpAddress
    MAX-ACCESS   read-create
    STATUS       current
    DESCRIPTION
        "IP address to match with source-IP of the packet."
    DEFVAL { '00000000'H }
    ::= { tnSapIngressIPCriteriaEntry 6 }

tnSapIngressIPCriteriaSourceIpMask OBJECT-TYPE
    SYNTAX       IpAddressPrefixLength
    MAX-ACCESS   read-create
    STATUS       current
    DESCRIPTION
        "the prefix is the number of bits of the source IP address to match."
    DEFVAL { 0 }
    ::= { tnSapIngressIPCriteriaEntry 7 }

tnSapIngressIPCriteriaDestIpAddr OBJECT-TYPE
    SYNTAX       IpAddress
    MAX-ACCESS   read-create
    STATUS       current
    DESCRIPTION
        "IP address to match with destination-IP of the packet."
    DEFVAL { '00000000'H }
    ::= { tnSapIngressIPCriteriaEntry 8 }

tnSapIngressIPCriteriaDestIpMask OBJECT-TYPE
    SYNTAX       IpAddressPrefixLength
    MAX-ACCESS   read-create
    STATUS       current
    DESCRIPTION
        "the prefix is the number of bits of the destination IP address to
         match."
    DEFVAL { 0 }
    ::= { tnSapIngressIPCriteriaEntry 9 }

tnSapIngressIPCriteriaProtocol OBJECT-TYPE
    SYNTAX       TIpProtocol
    MAX-ACCESS   read-create
    STATUS       current
    DESCRIPTION
        "IP protocol to match.  use -1 to disable matching by IP protocol."
    DEFVAL { -1 }
    ::= { tnSapIngressIPCriteriaEntry 10 }

tnSapIngressIPCriteriaSourcePortValue1 OBJECT-TYPE
    SYNTAX       TTcpUdpPort
    MAX-ACCESS   read-create
    STATUS       current
    DESCRIPTION
        "TCP/UDP port value1. The value of this object is used according
         to the description for tnSapIngressIPCriteriaSourcePortOperator."
    DEFVAL { 0 }
    ::= { tnSapIngressIPCriteriaEntry 11 }

tnSapIngressIPCriteriaSourcePortValue2 OBJECT-TYPE
    SYNTAX       TTcpUdpPort
    MAX-ACCESS   read-create
    STATUS       current
    DESCRIPTION
        "TCP/UDP port value2. The value of this object is used according
         to the description for tnSapIngressIPCriteriaSourcePortOperator."
    DEFVAL { 0 }
    ::= { tnSapIngressIPCriteriaEntry 12 }

tnSapIngressIPCriteriaSourcePortOperator OBJECT-TYPE
    SYNTAX       TTcpUdpPortOperator
    MAX-ACCESS   read-create
    STATUS       current
    DESCRIPTION
        "The operator specifies the manner in which
         tnSapIngressIPCriteriaSourcePortValue1 and 
         tnSapIngressIPCriteriaSourcePortValue2 are to be used. The value 
         of these latter 2 objects and 
         tnSapIngressIPCriteriaSourcePortOperator is used as described in 
         TTcpUdpPortOperator."
    DEFVAL { none }
    ::= { tnSapIngressIPCriteriaEntry 13 }

tnSapIngressIPCriteriaDestPortValue1 OBJECT-TYPE
    SYNTAX       TTcpUdpPort
    MAX-ACCESS   read-create
    STATUS       current
    DESCRIPTION
        "TCP/UDP port value1. The value of this object is used according
         to the description for tnSapIngressIPCriteriaDestPortOperator."
    DEFVAL { 0 }
    ::= { tnSapIngressIPCriteriaEntry 14 }

tnSapIngressIPCriteriaDestPortValue2 OBJECT-TYPE
    SYNTAX       TTcpUdpPort
    MAX-ACCESS   read-create
    STATUS       current
    DESCRIPTION
        "TCP/UDP port value2. The value of this object is used according
         to the description for tnSapIngressIPCriteriaDestPortOperator."
    DEFVAL { 0 }
    ::= { tnSapIngressIPCriteriaEntry 15 }

tnSapIngressIPCriteriaDestPortOperator OBJECT-TYPE
    SYNTAX       TTcpUdpPortOperator
    MAX-ACCESS   read-create
    STATUS       current
    DESCRIPTION
        "The operator specifies the manner in which
         tnSapIngressIPCriteriaDestPortValue1 and 
         tnSapIngressIPCriteriaDestPortValue2 are to be used. The value 
         of these latter 2 objects and 
         tnSapIngressIPCriteriaDestPortOperator is used as described in 
         TTcpUdpPortOperator."
    DEFVAL { none }
    ::= { tnSapIngressIPCriteriaEntry 16 }

tnSapIngressIPCriteriaDSCP OBJECT-TYPE
    SYNTAX       TDSCPNameOrEmpty
    MAX-ACCESS   read-create
    STATUS       current
    DESCRIPTION
        "DSCP value to match in the packet"
    DEFVAL { ''H }
    ::= { tnSapIngressIPCriteriaEntry 17 }

tnSapIngressIPCriteriaFragment OBJECT-TYPE
    SYNTAX       TItemMatch
    MAX-ACCESS   read-create
    STATUS       current
    DESCRIPTION
        "matches when the packet is a fragment (true)
         or when the packet is not a fragment (false)
         or matches all packets fragmented or not (off)."
    DEFVAL { off }
    ::= { tnSapIngressIPCriteriaEntry 19 }

tnSapIngressIPCriteriaLastChanged OBJECT-TYPE
    SYNTAX       TimeStamp
    MAX-ACCESS   read-only
    STATUS       current
    DESCRIPTION
        "timestamp of last change to this row in tnSapIngressIPCriteriaTable."
    ::= { tnSapIngressIPCriteriaEntry 20 }

tnSapIngressIPCritHsmdaCntrOvr OBJECT-TYPE
    SYNTAX       TIngressHsmdaCounterIdOrZero
    MAX-ACCESS   read-create
    STATUS       current
    DESCRIPTION
        "The value of the object tnSapIngressIPCritHsmdaCntrOvr specifies
         the Hsmda counter to use for matching packets. This value will be
         ignored when the sap-ingress policy specified by tnSapIngressIndex,
         is applied to a SAP on a non-Hsmda MDA type. 

         A value of zero implies that the default counters should be used."
    DEFVAL { 0 }
    ::= { tnSapIngressIPCriteriaEntry 21 }

--
-- sap-ingress policy mac criteria table
--

tnSapIngressMacCriteriaTable OBJECT-TYPE
    SYNTAX       SEQUENCE OF TSapIngressMacCriteriaEntry
    MAX-ACCESS   not-accessible
    STATUS       current
    DESCRIPTION
        "information about all sap-ingress policies' mac-criteria entries."
    ::= { tnSapIngressObjects 6 }

tnSapIngressMacCriteriaEntry OBJECT-TYPE
    SYNTAX       TSapIngressMacCriteriaEntry
    MAX-ACCESS   not-accessible
    STATUS       current
    DESCRIPTION
        "Information about a particular mac-criteria entry
         for a sap-ingress policy.
         Entries are created by user.
         Entries are deleted by user.
         There is no StorageType object, entries have a presumed
         StorageType of nonVolatile."
    INDEX { tnSysSwitchId, tnSapIngressIndex, tnSapIngressMacCriteriaIndex }
    ::= { tnSapIngressMacCriteriaTable 1 }

TSapIngressMacCriteriaEntry ::= SEQUENCE
    {
        tnSapIngressMacCriteriaIndex          TEntryId,
        tnSapIngressMacCriteriaRowStatus      RowStatus,
        tnSapIngressMacCriteriaDescription    TItemDescription,
        tnSapIngressMacCriteriaActionFC       TNamedItemOrEmpty,
        tnSapIngressMacCriteriaActionPriority TPriorityOrDefault,
        tnSapIngressMacCriteriaFrameType      TFrameType,
        tnSapIngressMacCriteriaSrcMacAddr     MacAddress,
        tnSapIngressMacCriteriaSrcMacMask     MacAddress,
        tnSapIngressMacCriteriaDstMacAddr     MacAddress,
        tnSapIngressMacCriteriaDstMacMask     MacAddress,
        tnSapIngressMacCriteriaDot1PValue     Dot1PPriority,
        tnSapIngressMacCriteriaDot1PMask      Dot1PPriority,
        tnSapIngressMacCriteriaEthernetType   Integer32,
        tnSapIngressMacCriteriaDSAP           ServiceAccessPoint,
        tnSapIngressMacCriteriaDSAPMask       ServiceAccessPoint,
        tnSapIngressMacCriteriaSSAP           ServiceAccessPoint,
        tnSapIngressMacCriteriaSSAPMask       ServiceAccessPoint,
        tnSapIngressMacCriteriaSnapPid        Integer32,
        tnSapIngressMacCriteriaSnapOui        INTEGER,
        tnSapIngressMacCriteriaLastChanged    TimeStamp  -- ,
--         tnSapIngressMacCriteriaAtmVci         AtmVcIdentifier
    }

tnSapIngressMacCriteriaIndex OBJECT-TYPE
    SYNTAX       TEntryId
    MAX-ACCESS   not-accessible
    STATUS       current
    DESCRIPTION ""
    ::= { tnSapIngressMacCriteriaEntry 1 }

tnSapIngressMacCriteriaRowStatus OBJECT-TYPE
    SYNTAX       RowStatus
    MAX-ACCESS   read-create
    STATUS       current
    DESCRIPTION ""
    ::= { tnSapIngressMacCriteriaEntry 2 }

tnSapIngressMacCriteriaDescription OBJECT-TYPE
    SYNTAX       TItemDescription
    MAX-ACCESS   read-create
    STATUS       current
    DESCRIPTION ""
    DEFVAL { ''H }
    ::= { tnSapIngressMacCriteriaEntry 3 }

tnSapIngressMacCriteriaActionFC OBJECT-TYPE
    SYNTAX       TNamedItemOrEmpty
    MAX-ACCESS   read-create
    STATUS       current
    DESCRIPTION
        "tnSapIngressMacCriteriaActionFC specifies the forwarding class
         or the sub forwarding class to be used to classify all the
         traffic that matches the specific Mac criteria.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tnSapIngressMacCriteriaActionFC is specified explicitly,
         this match will be ignored for classification purposes."
    ::= { tnSapIngressMacCriteriaEntry 4 }

tnSapIngressMacCriteriaActionPriority OBJECT-TYPE
    SYNTAX       TPriorityOrDefault
    MAX-ACCESS   read-create
    STATUS       current
    DESCRIPTION ""
    DEFVAL { default }
    ::= { tnSapIngressMacCriteriaEntry 5 }

tnSapIngressMacCriteriaFrameType OBJECT-TYPE
    SYNTAX       TFrameType
    MAX-ACCESS   read-create
    STATUS       current
    DESCRIPTION
        "The type of mac frame for which we are defining this match criteria."
    DEFVAL { e802dot3 }
    ::= { tnSapIngressMacCriteriaEntry 6 }

tnSapIngressMacCriteriaSrcMacAddr OBJECT-TYPE
    SYNTAX       MacAddress
    MAX-ACCESS   read-create
    STATUS       current
    DESCRIPTION ""
    DEFVAL { '000000000000'H }
    ::= { tnSapIngressMacCriteriaEntry 8 }

tnSapIngressMacCriteriaSrcMacMask OBJECT-TYPE
    SYNTAX       MacAddress
    MAX-ACCESS   read-create
    STATUS       current
    DESCRIPTION ""
    DEFVAL { '000000000000'H }
    ::= { tnSapIngressMacCriteriaEntry 9 }

tnSapIngressMacCriteriaDstMacAddr OBJECT-TYPE
    SYNTAX       MacAddress
    MAX-ACCESS   read-create
    STATUS       current
    DESCRIPTION ""
    DEFVAL { '000000000000'H }
    ::= { tnSapIngressMacCriteriaEntry 10 }

tnSapIngressMacCriteriaDstMacMask OBJECT-TYPE
    SYNTAX       MacAddress
    MAX-ACCESS   read-create
    STATUS       current
    DESCRIPTION ""
    DEFVAL { '000000000000'H }
    ::= { tnSapIngressMacCriteriaEntry 11 }

tnSapIngressMacCriteriaDot1PValue OBJECT-TYPE
    SYNTAX       Dot1PPriority
    MAX-ACCESS   read-create
    STATUS       current
    DESCRIPTION ""
    DEFVAL { -1 }
    ::= { tnSapIngressMacCriteriaEntry 12 }

tnSapIngressMacCriteriaDot1PMask OBJECT-TYPE
    SYNTAX       Dot1PPriority (0..7)
    MAX-ACCESS   read-create
    STATUS       current
    DESCRIPTION ""
    DEFVAL { 0 }
    ::= { tnSapIngressMacCriteriaEntry 13 }

tnSapIngressMacCriteriaEthernetType OBJECT-TYPE
    SYNTAX       Integer32 (-1 | 1536..65535)
    MAX-ACCESS   read-create
    STATUS       current
    DESCRIPTION
        "the ethernet type, ssap/dsap, and snap-pid match criteria
         are mutually exclusive and only one can be set per entry."
    DEFVAL { -1 }
    ::= { tnSapIngressMacCriteriaEntry 14 }

tnSapIngressMacCriteriaDSAP OBJECT-TYPE
    SYNTAX       ServiceAccessPoint
    MAX-ACCESS   read-create
    STATUS       current
    DESCRIPTION
        "the ethernet type, ssap/dsap, and snap-pid match criteria
         are mutually exclusive and only one can be set per entry."
    DEFVAL { -1 }
    ::= { tnSapIngressMacCriteriaEntry 15 }

tnSapIngressMacCriteriaDSAPMask OBJECT-TYPE
    SYNTAX       ServiceAccessPoint
    MAX-ACCESS   read-create
    STATUS       current
    DESCRIPTION
        "the ethernet type, ssap/dsap, and snap-pid match criteria
         are mutually exclusive and only one can be set per entry."
    DEFVAL { -1 }
    ::= { tnSapIngressMacCriteriaEntry 16 }

tnSapIngressMacCriteriaSSAP OBJECT-TYPE
    SYNTAX       ServiceAccessPoint
    MAX-ACCESS   read-create
    STATUS       current
    DESCRIPTION
        "the ethernet type, ssap/dsap, and snap-pid match criteria
         are mutually exclusive and only one can be set per entry."
    DEFVAL { -1 }
    ::= { tnSapIngressMacCriteriaEntry 17 }

tnSapIngressMacCriteriaSSAPMask OBJECT-TYPE
    SYNTAX       ServiceAccessPoint
    MAX-ACCESS   read-create
    STATUS       current
    DESCRIPTION
        "the ethernet type, ssap/dsap, and snap-pid match criteria
         are mutually exclusive and only one can be set per entry."
    DEFVAL { -1 }
    ::= { tnSapIngressMacCriteriaEntry 18 }

tnSapIngressMacCriteriaSnapPid OBJECT-TYPE
    SYNTAX       Integer32 (-1 | 0..65535)
    MAX-ACCESS   read-create
    STATUS       current
    DESCRIPTION
        "the ethernet type, ssap/dsap, and snap-pid match criteria
         are mutually exclusive and only one can be set per entry."
    DEFVAL { -1 }
    ::= { tnSapIngressMacCriteriaEntry 19 }

tnSapIngressMacCriteriaSnapOui OBJECT-TYPE
    SYNTAX          INTEGER { off(1), zero(2), nonZero(3) }
    MAX-ACCESS      read-create
    STATUS          current
    DESCRIPTION     "whether to match snap-oui, and what to match."
    DEFVAL { off }
    ::= { tnSapIngressMacCriteriaEntry 20 }

tnSapIngressMacCriteriaLastChanged OBJECT-TYPE
    SYNTAX       TimeStamp
    MAX-ACCESS   read-only
    STATUS       current
    DESCRIPTION
        "timestamp of last change to this row in tnSapIngressMacCriteriaTable."
    ::= { tnSapIngressMacCriteriaEntry 21 }

-- tnSapIngressMacCriteriaAtmVci OBJECT-TYPE
--     SYNTAX          AtmVcIdentifier
--     MAX-ACCESS      read-create
--     STATUS          current
--     DESCRIPTION
--         "The value of tnSapIngressMacCriteriaAtmVci specifies ATM VC Identifier
--          to match as part of the MAC criteria for this SAP on the ingress.

--          An inconsistentValue error is returned if this object is set when
--          tnSapIngressMacCriteriaFrameType is not set to 'atm'."
--     DEFVAL { 0 }
--     ::= { tnSapIngressMacCriteriaEntry 22 }

--
-- sap-ingress policy fc table
--

tnSapIngressFCTable OBJECT-TYPE
    SYNTAX       SEQUENCE OF TSapIngressFCEntry
    MAX-ACCESS   not-accessible
    STATUS       current
    DESCRIPTION
        "This table maintains the mapping of a particular
         forwarding class traffic into the specified queue."
    ::= { tnSapIngressObjects 7 }

tnSapIngressFCEntry OBJECT-TYPE
    SYNTAX       TSapIngressFCEntry
    MAX-ACCESS   not-accessible
    STATUS       current
    DESCRIPTION
        "Information about a particular sap-ingress policy's
         forwarding class mappings to queues.

         Entries are created and deleted by user. They have
         a presumed StorageType of nonVolatile."
    INDEX { tnSysSwitchId, tnSapIngressIndex, tnSapIngressFCName }
    ::= { tnSapIngressFCTable 1 }

TSapIngressFCEntry ::= SEQUENCE
    {
        tnSapIngressFCName              TNamedItem,
        tnSapIngressFCRowStatus         RowStatus,
        tnSapIngressFCQueue             TIngressQueueId,
        tnSapIngressFCMCastQueue        TIngressQueueId,
        tnSapIngressFCBCastQueue        TIngressQueueId,
        tnSapIngressFCUnknownQueue      TIngressQueueId,
        tnSapIngressFCLastChanged       TimeStamp,
        tnSapIngressFCInProfRemark      TRemarkType,
        tnSapIngressFCInProfDscp        TNamedItemOrEmpty,
        tnSapIngressFCInProfPrec        TPrecValueOrNone,
        tnSapIngressFCOutProfRemark     TRemarkType,
        tnSapIngressFCOutProfDscp       TNamedItemOrEmpty,
        tnSapIngressFCOutProfPrec       TPrecValueOrNone,
        tnSapIngressFCProfile           TProfileOrNone,
        tnSapIngressFCHsmdaQueue        TIngressHsmdaQueueId,
        tnSapIngressFCHsmdaMCastQueue   TIngressHsmdaQueueId,
        tnSapIngressFCHsmdaBCastQueue   TIngressHsmdaQueueId,
        tnSapIngressFCDE1OutOfProfile   TruthValue,
        tnSapIngressFCQGrp              TNamedItemOrEmpty,
        tnSapIngressFCQGrpMCast         TNamedItemOrEmpty,
        tnSapIngressFCQGrpBCast         TNamedItemOrEmpty,
        tnSapIngressFCQGrpUnknown       TNamedItemOrEmpty
    }

tnSapIngressFCName OBJECT-TYPE
    SYNTAX       TNamedItem
    MAX-ACCESS   not-accessible
    STATUS       current
    DESCRIPTION
        "tnSapIngressFCName specifies the forwarding class or the sub
         forwarding class for which this mapping is defined.

         A sub forwarding class mapping can also be configured. The
         format of a sub forwarding class is the concatenation of the
         base forwarding class and a sub class identifier in the form

             base-fc-name[.sub-fc-name]

         A sub forwarding class mapping should exist in this table if
         any explicit match criteria in this SAP ingress QoS policy
         try to use it. However, it is not the same for the base
         forwarding classes."
    ::= { tnSapIngressFCEntry 1 }

tnSapIngressFCRowStatus OBJECT-TYPE
    SYNTAX       RowStatus
    MAX-ACCESS   read-create
    STATUS       current
    DESCRIPTION
        "Row Status for this queue."
    ::= { tnSapIngressFCEntry 2 }

tnSapIngressFCQueue OBJECT-TYPE
    SYNTAX       TIngressQueueId
    MAX-ACCESS   read-create
    STATUS       current
    DESCRIPTION
        "The specific queue to be used for packets in this forwarding class.

         Default value for this object along with default value for
         tnSapIngressFCQGrp implies that the default queues should be used."
    DEFVAL { 0 }
    ::= { tnSapIngressFCEntry 3 }

tnSapIngressFCMCastQueue OBJECT-TYPE
    SYNTAX       TIngressQueueId
    MAX-ACCESS   read-create
    STATUS       current
    DESCRIPTION
        "The specific multicast queue to be used for packets in this forwarding
         class. The queue is used only for specific entities and will be
         ignored wherever it is irrelevant.

         Default value for this object along with default value for
         tnSapIngressFCQGrpMCast implies that the default queues should be used."
    DEFVAL { 0 }
    ::= { tnSapIngressFCEntry 4 }

tnSapIngressFCBCastQueue OBJECT-TYPE
    SYNTAX       TIngressQueueId
    MAX-ACCESS   read-create
    STATUS       current
    DESCRIPTION
        "The specific broadcast queue to be used for packets in this forwarding
         class. The queue is used only for specific entities and will be
         ignored wherever it is irrelevant.

         Default value for this object along with default value for
         tnSapIngressFCQGrpBCast implies that the default queues should be used."
    DEFVAL { 0 }
    ::= { tnSapIngressFCEntry 5 }

tnSapIngressFCUnknownQueue OBJECT-TYPE
    SYNTAX       TIngressQueueId
    MAX-ACCESS   read-create
    STATUS       current
    DESCRIPTION
        "The specific unknown destination queue to be used for packets in this
         forwarding class. The queue is used only for specific entities and
         will be ignored wherever it is irrelevant.

         Default value for this object along with default value for
         tnSapIngressFCQGrpUnknown implies that the default queues should be used."
    DEFVAL { 0 }
    ::= { tnSapIngressFCEntry 6 }

tnSapIngressFCLastChanged OBJECT-TYPE
    SYNTAX       TimeStamp
    MAX-ACCESS   read-only
    STATUS       current
    DESCRIPTION
        "tnSapIngressFCLastChanged indicates the value of sysUpTime
         when the forwarding class entry was last modified."
    ::= { tnSapIngressFCEntry 7 }

tnSapIngressFCInProfRemark OBJECT-TYPE
    SYNTAX       TRemarkType
    MAX-ACCESS   read-create
    STATUS       current
    DESCRIPTION
        "tnSapIngressFCInProfRemark specifies the remarking type to
         be used for the in profile packets feeding into the queues."
    DEFVAL { none }
    ::= { tnSapIngressFCEntry 8 }

tnSapIngressFCInProfDscp OBJECT-TYPE
    SYNTAX       TNamedItemOrEmpty
    MAX-ACCESS   read-create
    STATUS       current
    DESCRIPTION
        "tnSapIngressFCInProfDscp specifies the DSCP to be used while
         remarking the in profile packets when the in-profile
         remarking type, tnSapIngressFCInProfRemark is specified to be
         'dscp'."
    DEFVAL { ''H }
    ::= { tnSapIngressFCEntry 9 }

tnSapIngressFCInProfPrec OBJECT-TYPE
    SYNTAX       TPrecValueOrNone
    MAX-ACCESS   read-create
    STATUS       current
    DESCRIPTION
        "tnSapIngressFCInProfPrec specifies the precedence value to be used
         while remarking the in profile packets when the in-profile
         remarking type, tnSapIngressFCInProfRemark is specified to be
         'precedence'."
    DEFVAL { -1 }
    ::= { tnSapIngressFCEntry 10 }

tnSapIngressFCOutProfRemark OBJECT-TYPE
    SYNTAX       TRemarkType
    MAX-ACCESS   read-create
    STATUS       current
    DESCRIPTION
        "tnSapIngressFCOutProfRemark specifies the remarking type to
         be used for the in profile packets feeding into the queues."
    DEFVAL { none }
    ::= { tnSapIngressFCEntry 11 }

tnSapIngressFCOutProfDscp OBJECT-TYPE
    SYNTAX       TNamedItemOrEmpty
    MAX-ACCESS   read-create
    STATUS       current
    DESCRIPTION
        "tnSapIngressFCOutProfDscp specifies the DSCP to be used while
         remarking the in profile packets when the in-profile
         remarking type, tnSapIngressFCOutProfRemark is specified to be
         'dscp'."
    DEFVAL { ''H }
    ::= { tnSapIngressFCEntry 12 }

tnSapIngressFCOutProfPrec OBJECT-TYPE
    SYNTAX       TPrecValueOrNone
    MAX-ACCESS   read-create
    STATUS       current
    DESCRIPTION
        "tnSapIngressFCOutProfPrec specifies the precedence value to be used
         while remarking the in profile packets when the in-profile
         remarking type, tnSapIngressFCOutProfRemark is specified to be
         'precedence'."
    DEFVAL { -1 }
    ::= { tnSapIngressFCEntry 13 }

tnSapIngressFCProfile OBJECT-TYPE
    SYNTAX       TProfileOrNone
    MAX-ACCESS   read-create
    STATUS       current
    DESCRIPTION
        "tnSapIngressFCProfile specifies the profile of the packets
         associated with this forwarding class.

         This object can not be set to anything but 'none' if the
         queues being used by this mapping do not have their modes,
         tnSapIngressQueueMode set to 'profile'."
    DEFVAL { none }
    ::= { tnSapIngressFCEntry 14 }

tnSapIngressFCHsmdaQueue OBJECT-TYPE
    SYNTAX       TIngressHsmdaQueueId
    MAX-ACCESS   read-create
    STATUS       current
    DESCRIPTION
        "The value of the object tnSapIngressFCHsmdaQueue specifies the 
         HSMDA queue to use for packets in this forwarding class. This 
         mapping will be used when the SAP is on a HSMDA MDA.
         A value of zero implies that the default queues should be used."
    DEFVAL { 0 }
    ::= { tnSapIngressFCEntry 15 }

tnSapIngressFCHsmdaMCastQueue OBJECT-TYPE
    SYNTAX       TIngressHsmdaQueueId
    MAX-ACCESS   read-create
    STATUS       current
    DESCRIPTION
        "The value of the object tnSapIngressFCHsmdaMCastQueue specifies the 
         multicast queue to use for packets in this forwarding class. This 
         mapping will be used when the SAP is on a HSMDA MDA. 
         A value of zero implies that the default queues should be used."
    DEFVAL { 0 }
    ::= { tnSapIngressFCEntry 16 }

tnSapIngressFCHsmdaBCastQueue OBJECT-TYPE
    SYNTAX       TIngressHsmdaQueueId
    MAX-ACCESS   read-create
    STATUS       current
    DESCRIPTION
        "The value of the object tnSapIngressFCHsmdaBCastQueue specifies the 
         broadcast queue to use for packets in this forwarding class. This 
         mapping will be used when the SAP is on a HSMDA MDA. 
         A value of zero implies that the default queues should be used."
    DEFVAL { 0 }
    ::= { tnSapIngressFCEntry 17 }

tnSapIngressFCDE1OutOfProfile OBJECT-TYPE
    SYNTAX       TruthValue
    MAX-ACCESS   read-create
    STATUS       current
    DESCRIPTION
        "The value of tnSapIngressFCDE1OutOfProfile specifies whether frames
        with DE value of '1' are to be treated as out-of-profile (as if
        tnSapIngressFCProfile was set to 'out'). 
        
        When tnSapIngressFCDE1OutOfProfile is set to 'true', frames with DE value
        of '1' are autmatically classified as out-of-profile.

        Frames with DE value of '0' will continue to be policed based on the
        value of tnSapIngressQueueAdminCIR.  That is, if the dynamic rate of
        ingress queue is within CIR, frames with DE=0 will be treated as
        in-profile (as if tnSapIngressFCProfile was set to 'in') otherwise these
        frames are treated as out-of-profile.
        
        When tnSapIngressFCDE1OutOfProfile is set to 'true', it supercedes action
        specified by the value of tnSapIngressFCProfile."
    DEFVAL { false }
    ::= { tnSapIngressFCEntry 18 }

tnSapIngressFCQGrp OBJECT-TYPE
    SYNTAX       TNamedItemOrEmpty
    MAX-ACCESS   read-create
    STATUS       current
    DESCRIPTION
        "tnSapIngressFCQGrp specifies the tnQosIngQGroupName.

        This object must be set along with tnSapIngressFCQueue object.
        An 'inconsistentValue' error is returned if this object is set to the
        default and other is set to a non-default value."
    DEFVAL { ''H }
    ::= { tnSapIngressFCEntry 19 }

tnSapIngressFCQGrpMCast OBJECT-TYPE
    SYNTAX       TNamedItemOrEmpty
    MAX-ACCESS   read-create
    STATUS       current
    DESCRIPTION
        "tnSapIngressFCQGrpMCast specifies the tnQosIngQGroupName.

        This object must be set along with tnSapIngressFCMCastQueue object.
        An 'inconsistentValue' error is returned if this object is set to the
        default and other is set to a non-default value."
    DEFVAL { ''H }
    ::= { tnSapIngressFCEntry 20 }

tnSapIngressFCQGrpBCast OBJECT-TYPE
    SYNTAX       TNamedItemOrEmpty
    MAX-ACCESS   read-create
    STATUS       current
    DESCRIPTION
        "tnSapIngressFCQGrpBCast specifies the tnQosIngQGroupName.

        This object must be set along with tnSapIngressFCBCastQueue object.
        An 'inconsistentValue' error is returned if this object is set to the
        default and other is set to a non-default value."
    DEFVAL { ''H }
    ::= { tnSapIngressFCEntry 21 }

tnSapIngressFCQGrpUnknown OBJECT-TYPE
    SYNTAX       TNamedItemOrEmpty
    MAX-ACCESS   read-create
    STATUS       current
    DESCRIPTION
        "tnSapIngressFCQGrpUnknown specifies the tnQosIngQGroupName.

        This object must be set along with tnSapIngressFCUnknownQueue object.
        An 'inconsistentValue' error is returned if this object is set to the
        default and other is set to a non-default value."
    DEFVAL { ''H }
    ::= { tnSapIngressFCEntry 22 }

--
-- sap-ingress policy precedence table
--

-- tnSapIngressPrecTable OBJECT-TYPE
--     SYNTAX       SEQUENCE OF TSapIngressPrecEntry
--     MAX-ACCESS   not-accessible
--     STATUS       current
--     DESCRIPTION  "This table maintains the mapping of a particular
--                   precedence value into a forwarding class"
--     ::= { tnSapIngressObjects 8 }
-- 
-- tnSapIngressPrecEntry OBJECT-TYPE
--     SYNTAX       TSapIngressPrecEntry
--     MAX-ACCESS   not-accessible
--     STATUS       current
--     DESCRIPTION
--         "Information about a particular sap-ingress policy's
--          IP precedence values to forwarding class mappings.
-- 
--          Entries are created and deleted by user. They have
--          a presumed StorageType of nonVolatile."
--     INDEX { tnSysSwitchId, tnSapIngressIndex, tnSapIngressPrecValue }
--     ::= { tnSapIngressPrecTable 1 }
-- 
-- TSapIngressPrecEntry ::= SEQUENCE
--     {
--         tnSapIngressPrecValue               TPrecValue,
--         tnSapIngressPrecRowStatus           RowStatus,
--         tnSapIngressPrecFC                  TNamedItemOrEmpty,
--         tnSapIngressPrecFCPriority          TPriorityOrDefault,
--         tnSapIngressPrecLastChanged         TimeStamp,
--         tnSapIngressPrecHsmdaCntrOvr    TIngressHsmdaCounterIdOrZero
--     }
-- 
-- tnSapIngressPrecValue OBJECT-TYPE
--     SYNTAX       TPrecValue
--     MAX-ACCESS   not-accessible
--     STATUS       current
--     DESCRIPTION
--         "Precedence value for which the mapping is done."
--     ::= { tnSapIngressPrecEntry 1 }
-- 
-- tnSapIngressPrecRowStatus OBJECT-TYPE
--     SYNTAX       RowStatus
--     MAX-ACCESS   read-create
--     STATUS       current
--     DESCRIPTION
--         "Row Status for this mapping."
--     ::= { tnSapIngressPrecEntry 2 }
-- 
-- tnSapIngressPrecFC OBJECT-TYPE
--     SYNTAX       TNamedItemOrEmpty
--     MAX-ACCESS   read-create
--     STATUS       current
--     DESCRIPTION
--         "tnSapIngressPrecFC specifies the forwarding class or the sub
--          forwarding class to be used to classify all the traffic that
--          matches the specific precedence value i.e. tnSapIngressPrecValue.
-- 
--          Specification of a sub forwarding class is also allowed. The
--          format of a sub forwarding class is the concatenation of the
--          base forwarding class and a sub class identifier in the form
-- 
--              base-fc-name[.sub-fc-name]
-- 
--          To reference a sub forwarding class, the mapping of the sub
--          forwarding class should be existing in this QoS policy.
-- 
--          Unless tnSapIngressPrecFC is specified explicitly, this match
--          will be ignored for classification purposes."
--     DEFVAL { ''H }
--     ::= { tnSapIngressPrecEntry 3 }
-- 
-- tnSapIngressPrecFCPriority OBJECT-TYPE
--     SYNTAX       TPriorityOrDefault
--     MAX-ACCESS   read-create
--     STATUS       current
--     DESCRIPTION
--         "The priority to be assigned to the matching traffic."
--     DEFVAL { default }
--     ::= { tnSapIngressPrecEntry 4 }
-- 
-- tnSapIngressPrecLastChanged OBJECT-TYPE
--     SYNTAX       TimeStamp
--     MAX-ACCESS   read-only
--     STATUS       current
--     DESCRIPTION
--         "timestamp of last change to this row in tnSapIngressPrecTable."
--     ::= { tnSapIngressPrecEntry 5 }
-- 
-- tnSapIngressPrecHsmdaCntrOvr OBJECT-TYPE
--     SYNTAX       TIngressHsmdaCounterIdOrZero
--     MAX-ACCESS   read-create
--     STATUS       current
--     DESCRIPTION
--         "The value of the object tnSapIngressPrecHsmdaCntrOvr 
--          specifies the counter to use for all the traffic that
--          matches the specific precedence value i.e. tnSapIngressPrecValue.
-- 
--          A value of zero implies that the default counters should be used."
--     DEFVAL { 0 }
--     ::= { tnSapIngressPrecEntry 6 }

--
-- sap-ingress policy ipv6 criteria table
--

tnSapIngressIPv6CriteriaTable OBJECT-TYPE
    SYNTAX       SEQUENCE OF TSapIngressIPv6CriteriaEntry
    MAX-ACCESS   not-accessible
    STATUS       current
    DESCRIPTION
        "Information about all sap-ingress policies' ipv6-criteria entries."
    ::= { tnSapIngressObjects 9 }

tnSapIngressIPv6CriteriaEntry OBJECT-TYPE
    SYNTAX       TSapIngressIPv6CriteriaEntry
    MAX-ACCESS   not-accessible
    STATUS       current
    DESCRIPTION
        "Information about a particular ipv6-criteria entry for a sap-ingress
         policy.
         Entries are created/deleted by user.
         There is no StorageType object, entries have a presumed
         StorageType of nonVolatile."
    INDEX { tnSysSwitchId, tnSapIngressIndex, tnSapIngressIPv6CriteriaIndex }
    ::= { tnSapIngressIPv6CriteriaTable 1 }

TSapIngressIPv6CriteriaEntry ::= SEQUENCE
    {
        tnSapIngressIPv6CriteriaIndex               TEntryId,
        tnSapIngressIPv6CriteriaRowStatus           RowStatus,
        tnSapIngressIPv6CriteriaDescription         TItemDescription,
        tnSapIngressIPv6CriteriaActionFC            TNamedItemOrEmpty,
        tnSapIngressIPv6CriteriaActionPriority      TPriorityOrDefault,
        tnSapIngressIPv6CriteriaSourceIpAddr        InetAddressIPv6,
        tnSapIngressIPv6CriteriaSourceIpMask        InetAddressPrefixLength,
        tnSapIngressIPv6CriteriaDestIpAddr          InetAddressIPv6,
        tnSapIngressIPv6CriteriaDestIpMask          InetAddressPrefixLength,
        tnSapIngressIPv6CriteriaNextHeader          TIpProtocol,
        tnSapIngressIPv6CriteriaSourcePortValue1    TTcpUdpPort,
        tnSapIngressIPv6CriteriaSourcePortValue2    TTcpUdpPort,
        tnSapIngressIPv6CriteriaSourcePortOperator  TTcpUdpPortOperator,
        tnSapIngressIPv6CriteriaDestPortValue1      TTcpUdpPort,
        tnSapIngressIPv6CriteriaDestPortValue2      TTcpUdpPort,
        tnSapIngressIPv6CriteriaDestPortOperator    TTcpUdpPortOperator,
        tnSapIngressIPv6CriteriaDSCP                TDSCPNameOrEmpty,
        tnSapIngressIPv6CriteriaLastChanged         TimeStamp
    }

tnSapIngressIPv6CriteriaIndex OBJECT-TYPE
    SYNTAX       TEntryId
    MAX-ACCESS   not-accessible
    STATUS       current
    DESCRIPTION
        "The value of the object tnSapIngressIPv6CriteriaIndex specifies
         uniquely each entry in the policy."
    ::= { tnSapIngressIPv6CriteriaEntry 1 }

tnSapIngressIPv6CriteriaRowStatus OBJECT-TYPE
    SYNTAX       RowStatus
    MAX-ACCESS   read-create
    STATUS       current
    DESCRIPTION
        "The value of the object tnSapIngressIPv6CriteriaRowStatus specifies the
         Row Status for the IPv6 Criteria entry."
    ::= { tnSapIngressIPv6CriteriaEntry 2 }

tnSapIngressIPv6CriteriaDescription OBJECT-TYPE
    SYNTAX       TItemDescription
    MAX-ACCESS   read-create
    STATUS       current
    DESCRIPTION
        "The value of the object tnSapIngressIPv6CriteriaDescription specifies
         an optional user provided description of this IPv6 criteria entry."
    DEFVAL { ''H }
    ::= { tnSapIngressIPv6CriteriaEntry 3 }

tnSapIngressIPv6CriteriaActionFC OBJECT-TYPE
    SYNTAX       TNamedItemOrEmpty
    MAX-ACCESS   read-create
    STATUS       current
    DESCRIPTION
        "The value of the object tnSapIngressIPv6CriteriaActionFC specifies the
         forwarding class or the sub forwarding class to be used to classify
         all the traffic that matches the specific IPv6 criteria.

         Specification of a sub forwarding class is also allowed. The
         format of a sub forwarding class is the concatenation of the
         base forwarding class and a sub class identifier in the form

             base-fc-name[.sub-fc-name]

         To reference a sub forwarding class, the mapping of the sub
         forwarding class should be existing in this QoS policy.

         Unless tnSapIngressIPv6CriteriaActionFC is specified explicitly,
         this match will be ignored for classification purposes."
    DEFVAL { ''H }
    ::= { tnSapIngressIPv6CriteriaEntry 4 }

tnSapIngressIPv6CriteriaActionPriority OBJECT-TYPE
    SYNTAX       TPriorityOrDefault
    MAX-ACCESS   read-create
    STATUS       current
    DESCRIPTION
       "The value of the object tnSapIngressIPv6CriteriaActionPriority specifies
        the priority for packets which match this entry's criteria.
        When set to 'default', the packet is sent to the queue
        from DSCP/dot1p/FC which matched the packet, using the
        priority from the DSCP/dot1p/FC which matched the packet."
    DEFVAL { default }
    ::= { tnSapIngressIPv6CriteriaEntry 5 }

tnSapIngressIPv6CriteriaSourceIpAddr OBJECT-TYPE
    SYNTAX       InetAddressIPv6
    MAX-ACCESS   read-create
    STATUS       current
    DESCRIPTION
        "The value of the object tnSapIngressIPv6CriteriaSourceIpAddr specifies
         the IPv6 address to match with source-IPv6 of the packet."
    DEFVAL { '00000000000000000000000000000000'H }
    ::= { tnSapIngressIPv6CriteriaEntry 6 }

tnSapIngressIPv6CriteriaSourceIpMask OBJECT-TYPE
    SYNTAX       InetAddressPrefixLength (0..128)
    MAX-ACCESS   read-create
    STATUS       current
    DESCRIPTION
        "The value of the object tnSapIngressIPv6CriteriaSourceIpMask specifies
         the prefix is the number of bits of the source IPv6 address to match."
    DEFVAL { 0 }
    ::= { tnSapIngressIPv6CriteriaEntry 7 }

tnSapIngressIPv6CriteriaDestIpAddr OBJECT-TYPE
    SYNTAX       InetAddressIPv6
    MAX-ACCESS   read-create
    STATUS       current
    DESCRIPTION
        "The value of the object tnSapIngressIPv6CriteriaDestIpAddr specifies
         the IPv6 address to match with destination-IPv6 of the packet."
    DEFVAL { '00000000000000000000000000000000'H }
    ::= { tnSapIngressIPv6CriteriaEntry 8 }

tnSapIngressIPv6CriteriaDestIpMask OBJECT-TYPE
    SYNTAX       InetAddressPrefixLength (0..128)
    MAX-ACCESS   read-create
    STATUS       current
    DESCRIPTION
        "The value of the object tnSapIngressIPv6CriteriaDestIpMask specifies
         the prefix is the number of bits of the destination IPv6 address to
         match."
    DEFVAL { 0 }
    ::= { tnSapIngressIPv6CriteriaEntry 9 }

tnSapIngressIPv6CriteriaNextHeader OBJECT-TYPE
    SYNTAX       TIpProtocol
    MAX-ACCESS   read-create
    STATUS       current
    DESCRIPTION
        "The value of the object tnSapIngressIPv6CriteriaNextHeader specifies
         the Next Header to match.  use -1 to disable matching by Next Header.
         Because the match criteria only pertains to the last next-header, the
         following values are not accepted: 0, 43, 44, 50, 51, and 60."
    DEFVAL { -1 }
    ::= { tnSapIngressIPv6CriteriaEntry 10 }

tnSapIngressIPv6CriteriaSourcePortValue1 OBJECT-TYPE
    SYNTAX       TTcpUdpPort
    MAX-ACCESS   read-create
    STATUS       current
    DESCRIPTION
        "The value of the object tnSapIngressIPv6CriteriaSourcePortValue1
         specifies the TCP/UDP port value1. The value of this object is used
         according to the description for
         tnSapIngressIPv6CriteriaSourcePortOperator."
    DEFVAL { 0 }
    ::= { tnSapIngressIPv6CriteriaEntry 11 }

tnSapIngressIPv6CriteriaSourcePortValue2 OBJECT-TYPE
    SYNTAX       TTcpUdpPort
    MAX-ACCESS   read-create
    STATUS       current
    DESCRIPTION
        "The value of the object tnSapIngressIPv6CriteriaSourcePortValue2
         specifies TCP/UDP port value2. The value of this object is used
         according to the description for
         tnSapIngressIPv6CriteriaSourcePortOperator."
    DEFVAL { 0 }
    ::= { tnSapIngressIPv6CriteriaEntry 12 }

tnSapIngressIPv6CriteriaSourcePortOperator OBJECT-TYPE
    SYNTAX       TTcpUdpPortOperator
    MAX-ACCESS   read-create
    STATUS       current
    DESCRIPTION
        "The value of the object tnSapIngressIPv6CriteriaSourcePortOperator
         specifies The operator specifies the manner in which
         tnSapIngressIPv6CriteriaSourcePortValue1 and
         tnSapIngressIPv6CriteriaSourcePortValue2 are to be used."
    DEFVAL { none }
    ::= { tnSapIngressIPv6CriteriaEntry 13 }

tnSapIngressIPv6CriteriaDestPortValue1 OBJECT-TYPE
    SYNTAX       TTcpUdpPort
    MAX-ACCESS   read-create
    STATUS       current
    DESCRIPTION
        "The value of the object tnSapIngressIPv6CriteriaDestPortValue1
         specifies the TCP/UDP port value1. The value of this object is used
         according to the description for
         tnSapIngressIPv6CriteriaDestPortOperator."
    DEFVAL { 0 }
    ::= { tnSapIngressIPv6CriteriaEntry 14 }

tnSapIngressIPv6CriteriaDestPortValue2 OBJECT-TYPE
    SYNTAX       TTcpUdpPort
    MAX-ACCESS   read-create
    STATUS       current
    DESCRIPTION
        "The value of the object tnSapIngressIPv6CriteriaDestPortValue2
         specifies the TCP/UDP port value2. The value of this object is used
         according to the description for
         tnSapIngressIPv6CriteriaDestPortOperator."
    DEFVAL { 0 }
    ::= { tnSapIngressIPv6CriteriaEntry 15 }

tnSapIngressIPv6CriteriaDestPortOperator OBJECT-TYPE
    SYNTAX       TTcpUdpPortOperator
    MAX-ACCESS   read-create
    STATUS       current
    DESCRIPTION
        "The value of the object tnSapIngressIPv6CriteriaDestPortOperator
         specifies the manner in which
         tnSapIngressIPv6CriteriaDestPortValue1 and
         tnSapIngressIPv6CriteriaDestPortValue2 are to be used."
    DEFVAL { none }
    ::= { tnSapIngressIPv6CriteriaEntry 16 }

tnSapIngressIPv6CriteriaDSCP OBJECT-TYPE
    SYNTAX       TDSCPNameOrEmpty
    MAX-ACCESS   read-create
    STATUS       current
    DESCRIPTION
        "The value of the object tnSapIngressIPv6CriteriaDSCP specifies the
         DSCP value to match in the packet"
    DEFVAL { ''H }
    ::= { tnSapIngressIPv6CriteriaEntry 17 }

tnSapIngressIPv6CriteriaLastChanged OBJECT-TYPE
    SYNTAX       TimeStamp
    MAX-ACCESS   read-only
    STATUS       current
    DESCRIPTION
        "The value of the object indicates timestamp of last change to this
         row in tnSapIngressIPv6CriteriaTable."
    ::= { tnSapIngressIPv6CriteriaEntry 20 }

--
-- sap-ingress hsmda queue table
--

-- tnSapIngressHsmdaQueueTable OBJECT-TYPE
--     SYNTAX      SEQUENCE OF TSapIngressHsmdaQueueEntry
--     MAX-ACCESS  not-accessible
--     STATUS      current
--     DESCRIPTION
--         "Information about all sap-ingress policies' HSMDA queues."
--     ::= { tnSapIngressObjects 10 }
-- 
-- tnSapIngressHsmdaQueueEntry    OBJECT-TYPE
--     SYNTAX      TSapIngressHsmdaQueueEntry
--     MAX-ACCESS  not-accessible
--     STATUS      current
--     DESCRIPTION
--         "Information about a particular HSMDA queue for a sap-ingress policy.
--          Entries are created by user."
--     INDEX { tnSysSwitchId, tnSapIngressIndex, tnSapIngressHsmdaQueue }
--     ::= { tnSapIngressHsmdaQueueTable 1}
-- 
-- TSapIngressHsmdaQueueEntry ::= SEQUENCE
--     {
--         tnSapIngressHsmdaQueue                 TIngressHsmdaQueueId,
--         tnSapIngressHsmdaQueueRowStatus        RowStatus,
--         tnSapIngressHsmdaQueueLastChanged      TimeStamp,
--         tnSapIngressHsmdaQueueCIRAdaptn        TAdaptationRule,
--         tnSapIngressHsmdaQueuePIRAdaptn        TAdaptationRule,
--         tnSapIngressHsmdaQueueAdminPIR         THsmdaPIRKRate,
--         tnSapIngressHsmdaQueueAdminCIR         THsmdaCIRKRate,
--         tnSapIngressHsmdaQueueSlopePolicy      TNamedItem,
--         tnSapIngressHsmdaQueuePoliced          TruthValue
--     }
-- 
-- tnSapIngressHsmdaQueue        OBJECT-TYPE
--     SYNTAX      TIngressHsmdaQueueId (1..8)
--     MAX-ACCESS  not-accessible
--     STATUS      current
--     DESCRIPTION
--         "The HSMDA queue ID is used as the secondary index to the table entry."
--     ::= { tnSapIngressHsmdaQueueEntry 1 }
-- 
-- tnSapIngressHsmdaQueueRowStatus        OBJECT-TYPE
--     SYNTAX      RowStatus
--     MAX-ACCESS  read-create
--     STATUS      current
--     DESCRIPTION
--         "The value of tnSapIngressHsmdaQueueRowStatus is used for the creation
--         and deletion of entries in the tnSapIngressHsmdaQueueTable."
--     ::= { tnSapIngressHsmdaQueueEntry 2 }
-- 
-- tnSapIngressHsmdaQueueLastChanged        OBJECT-TYPE
--     SYNTAX      TimeStamp
--     MAX-ACCESS  read-only
--     STATUS      current
--     DESCRIPTION
--         "The value of tnSapIngressHsmdaQueueLastChanged indicates the timestamp 
--          of last change to this row in tnSapIngressHsmdaQueueTable."
--     ::= { tnSapIngressHsmdaQueueEntry 3 }
-- 
-- tnSapIngressHsmdaQueueCIRAdaptn        OBJECT-TYPE
--     SYNTAX      TAdaptationRule
--     MAX-ACCESS  read-create
--     STATUS      current
--     DESCRIPTION
--         "The value of tnSapIngressHsmdaQueueCIRAdaptn specifies the 
--          adaptation rule to be used while computing the operational CIR
--          value. The adaptation rule specifies the rules to compute the
--          operational values while maintaining minimum offset."
--     DEFVAL { closest }
--     ::= { tnSapIngressHsmdaQueueEntry 4 }
-- 
-- tnSapIngressHsmdaQueuePIRAdaptn        OBJECT-TYPE
--     SYNTAX      TAdaptationRule
--     MAX-ACCESS  read-create
--     STATUS      current
--     DESCRIPTION
--         "The value of tnSapIngressHsmdaQueuePIRAdaptn specifies the 
--          adaptation rule to be used while computing the operational PIR
--          value. The adaptation rule specifies the rules to compute the
--          operational values while maintaining minimum offset."
--     DEFVAL { closest }
--     ::= { tnSapIngressHsmdaQueueEntry 5 }
-- 
-- tnSapIngressHsmdaQueueAdminPIR        OBJECT-TYPE
--     SYNTAX      THsmdaPIRKRate
--     UNITS       "kbps"
--     MAX-ACCESS  read-create
--     STATUS      current
--     DESCRIPTION
--         "The value of tnSapIngressHsmdaQueueAdminPIR specifies the 
--          administrative PIR specified by the user."
--     DEFVAL { -1 }
--     ::= { tnSapIngressHsmdaQueueEntry 6 }
-- 
-- tnSapIngressHsmdaQueueAdminCIR        OBJECT-TYPE
--     SYNTAX      THsmdaCIRKRate
--     UNITS       "kbps"
--     MAX-ACCESS  read-create
--     STATUS      current
--     DESCRIPTION
--         "The value of tnSapIngressHsmdaQueueAdminCIR specifies the 
--          administrative CIR specified by the user."
--     DEFVAL { 0 }
--     ::= { tnSapIngressHsmdaQueueEntry 7 }
-- 
-- tnSapIngressHsmdaQueueSlopePolicy        OBJECT-TYPE
--     SYNTAX      TNamedItem
--     MAX-ACCESS  read-create
--     STATUS      current
--     DESCRIPTION
--         "The value of tnSapIngressHsmdaQueueSlopePolicy specifies the slope
--          policy specified by the user."
--     DEFVAL { "default" }
--     ::= { tnSapIngressHsmdaQueueEntry 8 }
-- 
-- tnSapIngressHsmdaQueuePoliced OBJECT-TYPE
--     SYNTAX       TruthValue
--     MAX-ACCESS   read-create
--     STATUS       current
--     DESCRIPTION
--         "The value of tnSapIngressHsmdaQueuePoliced specifies whether
--          the out of profile traffic feeding into the physical queue 
--          instance should be dropped. When the value is 'true', 
--          out-of-profile packets are discarded.
-- 
--          This policing function is different than the shaping function
--          normally performed by the queues defined rate in that scheduling
--          is not stopped for the queue when the rate is exceeded.
-- 
--          Accordingly, tnSapIngressHsmdaQueuePoliced overrides the bandwidth
--          specified by the object tnSapIngressHsmdaQueueAdminCIR."
--     DEFVAL { false }
--     ::= { tnSapIngressHsmdaQueueEntry 9 }

--
-- Dummy Scalars
--
tnSapIngressScalar1 OBJECT-TYPE
    SYNTAX      Unsigned32
    MAX-ACCESS  read-only
    STATUS      current
    DESCRIPTION
        "A dummy scalar that satisfies a SNMP get request quickly when
         there is no 11QPE24 card provisioned.  Otherwise, it has to
         traverse the remaining 11QPE24 MIB to get to the next applicable
         item."
    ::= { tnSapIngressObjects 101 }

tnSapIngressScalar2 OBJECT-TYPE
    SYNTAX      Unsigned32
    MAX-ACCESS  read-only
    STATUS      current
    DESCRIPTION
        "A dummy scalar that satisfies a SNMP get request quickly when
         there is no 11QPE24 card provisioned.  Otherwise, it has to
         traverse the remaining 11QPE24 MIB to get to the next applicable
         item."
    ::= { tnSapIngressObjects 102 }

--
-- sap-egress policy table
--
-- tnSapEgressTable OBJECT-TYPE
--     SYNTAX       SEQUENCE OF TSapEgressEntry
--     MAX-ACCESS   not-accessible
--     STATUS       current
--     DESCRIPTION
--         "information about all sap-egress policies."
--     ::= { tnSapEgressObjects 1 }
-- 
-- tnSapEgressEntry OBJECT-TYPE
--     SYNTAX       TSapEgressEntry
--     MAX-ACCESS   not-accessible
--     STATUS       current
--     DESCRIPTION
--         "Information about a particular sap-egress policy.
--          Entries are created by user.
--          Entries are deleted by user.
--          There is no StorageType object, entries have a presumed
--          StorageType of nonVolatile.
-- 
--          the default sap-egress policy (1) cannot be changed or
--          destroyed.
--         "
--     INDEX { tnSysSwitchId, tnSapEgressIndex }
--     ::= { tnSapEgressTable 1 }
-- 
-- TSapEgressEntry ::= SEQUENCE
--     {
--         tnSapEgressIndex               TSapEgressPolicyID,
--         tnSapEgressRowStatus           RowStatus,
--         tnSapEgressScope               TItemScope,
--         tnSapEgressDescription         TItemDescription,
--         tnSapEgressLastChanged         TimeStamp,
--         tnSapEgressHsmdaPacketOffset   TEgressHsmdaPerPacketOffset,
--         tnSapEgressMatchCriteria       TMatchCriteria
--     }
-- 
-- tnSapEgressIndex OBJECT-TYPE
--     SYNTAX       TSapEgressPolicyID
--     MAX-ACCESS   not-accessible
--     STATUS       current
--     DESCRIPTION
--         "the sap-egress policy ID is used as index for the table."
--     ::= { tnSapEgressEntry 1 }
-- 
-- tnSapEgressRowStatus OBJECT-TYPE
--     SYNTAX       RowStatus
--     MAX-ACCESS   read-create
--     STATUS       current
--     DESCRIPTION
--         "Row Status of this policy's entry."
--     ::= { tnSapEgressEntry 2 }
-- 
-- tnSapEgressScope OBJECT-TYPE
--     SYNTAX       TItemScope
--     MAX-ACCESS   read-create
--     STATUS       current
--     DESCRIPTION
--         "scope of the sap-egress policy."
--     DEFVAL { template }
--     ::= { tnSapEgressEntry 3 }
-- 
-- tnSapEgressDescription OBJECT-TYPE
--     SYNTAX       TItemDescription
--     MAX-ACCESS   read-create
--     STATUS       current
--     DESCRIPTION
--         "user-supplied description of this sap-egress policy."
--     DEFVAL { ''H }
--     ::= { tnSapEgressEntry 4 }
-- 
-- tnSapEgressLastChanged OBJECT-TYPE
--     SYNTAX       TimeStamp
--     MAX-ACCESS   read-only
--     STATUS       current
--     DESCRIPTION
--         "timestamp of last change to this row in tnSapEgressTable."
--     ::= { tnSapEgressEntry 5 }
-- 
-- tnSapEgressHsmdaPacketOffset    OBJECT-TYPE
--     SYNTAX      TEgressHsmdaPerPacketOffset
--     UNITS       "bytes"
--     MAX-ACCESS  read-create
--     STATUS      current
--     DESCRIPTION
--         "The value of tnSapEgressHsmdaPacketOffset specifies the
--          value, in bytes, of the adjustment to make to the size of each
--          packet for HSMDA queue accounting."
--     DEFVAL { 0 }
--     ::= { tnSapEgressEntry 6 }
-- 
-- tnSapEgressMatchCriteria  OBJECT-TYPE
--     SYNTAX       TMatchCriteria
--     MAX-ACCESS   read-only
--     STATUS       current
--     DESCRIPTION
--         "The value of tnSapEgressMatchCriteria indicates which type of match
--          criteria the policy should use.
-- 
--          When tnSapEgressMatchCriteria has a value of 'ip', the sap-egress 
--          policy looks for match entries in tnSapIngressIPCriteriaTable
--          or tnSapIngressIPv6CriteriaTable.
-- 
--          The value of tnSapIngressMatchCriteria is set when the first match criteria
--          table entry is created. The value of tnSapEgressMatchCriteria is set to
--          'none' when the last criteria table entry is removed."
--     ::= { tnSapEgressEntry 7 }

--
-- sap-egress policy queue table
--

-- tnSapEgressQueueTable OBJECT-TYPE
--     SYNTAX       SEQUENCE OF TSapEgressQueueEntry
--     MAX-ACCESS   not-accessible
--     STATUS       current
--     DESCRIPTION  "information about all sap-egress policies' queues."
--     ::= { tnSapEgressObjects 2 }
-- 
-- tnSapEgressQueueEntry OBJECT-TYPE
--     SYNTAX       TSapEgressQueueEntry
--     MAX-ACCESS   not-accessible
--     STATUS       current
--     DESCRIPTION
--         "Information about a particular sap-egress queue.
--          Entries are created/deleted by user.
--          There is no StorageType object, entries have a presumed
--          StorageType of nonVolatile."
--     INDEX { tnSysSwitchId, tnSapEgressIndex, tnSapEgressQueueIndex }
--     ::= { tnSapEgressQueueTable 1 }
-- 
-- TSapEgressQueueEntry ::= SEQUENCE
--     {
--         tnSapEgressQueueIndex             TEgressQueueId,
--         tnSapEgressQueueRowStatus         RowStatus,
--         tnSapEgressQueueParent            TNamedItemOrEmpty,
--         tnSapEgressQueueLevel             TLevel,
--         tnSapEgressQueueWeight            TWeight,
--         tnSapEgressQueueCIRLevel          TLevelOrDefault,
--         tnSapEgressQueueCIRWeight         TWeight,
--         tnSapEgressQueueExpedite          INTEGER,
--         tnSapEgressQueueCBS               TBurstSize,
--         tnSapEgressQueueMBS               TBurstSize,
--         tnSapEgressQueueHiPrioOnly        TBurstPercentOrDefault,
--         tnSapEgressQueuePIRAdaptation     TAdaptationRule,
--         tnSapEgressQueueCIRAdaptation     TAdaptationRule,
--         tnSapEgressQueueAdminPIR          TPIRRate,
--         tnSapEgressQueueAdminCIR          TCIRRate,
-- ==        tnSapEgressQueueOperPIR           TPIRRate,
-- ==        tnSapEgressQueueOperCIR           TCIRRate,
--         tnSapEgressQueueLastChanged       TimeStamp,
--         tnSapEgressQueueUsePortParent     TruthValue,
--         tnSapEgressQueuePortLvl           TLevel,
--         tnSapEgressQueuePortWght          TWeight,
--         tnSapEgressQueuePortCIRLvl        TLevelOrDefault,
--         tnSapEgressQueuePortCIRWght       TWeight,
--         tnSapEgressQueuePortAvgOverhead   Unsigned32,
--         tnSapEgressQueuePoolName          TNamedItemOrEmpty,
--         tnSapEgressQueueXPWredQ           TruthValue,
--         tnSapEgressQueueXPWredQSlope      TNamedItem
--     }
-- 
-- tnSapEgressQueueIndex OBJECT-TYPE
--     SYNTAX       TEgressQueueId (1..8)
--     MAX-ACCESS   not-accessible
--     STATUS       current
--     DESCRIPTION
--         "the number of a queue.  zero is not allowed.
--          for sap-egress, only three queues are allowed,
--          so the queue index range is restricted."
--     ::= { tnSapEgressQueueEntry 1 }
-- 
-- tnSapEgressQueueRowStatus OBJECT-TYPE
--     SYNTAX       RowStatus
--     MAX-ACCESS   read-create
--     STATUS       current
--     DESCRIPTION
--         "Row Status of the entry."
--     ::= { tnSapEgressQueueEntry 2 }
-- 
-- tnSapEgressQueueParent OBJECT-TYPE
--     SYNTAX       TNamedItemOrEmpty
--     MAX-ACCESS   read-create
--     STATUS       current
--     DESCRIPTION
--         "The scheduler to which this queue would be feeding to."
--     DEFVAL { ''H }
--     ::= { tnSapEgressQueueEntry 3 }
-- 
-- tnSapEgressQueueLevel OBJECT-TYPE
--     SYNTAX       TLevel
--     MAX-ACCESS   read-create
--     STATUS       current
--     DESCRIPTION
--         "This specifies the level of priority while feeding to the parent."
--     DEFVAL { 1 }
--     ::= { tnSapEgressQueueEntry 4 }
-- 
-- tnSapEgressQueueWeight OBJECT-TYPE
--     SYNTAX       TWeight
--     MAX-ACCESS   read-create
--     STATUS       current
--     DESCRIPTION
--         "The weight that needs to be used by the scheduler to which this queue
--          would be feeding to."
--     DEFVAL { 1 }
--     ::= { tnSapEgressQueueEntry 5 }
-- 
-- tnSapEgressQueueCIRLevel OBJECT-TYPE
--     SYNTAX       TLevelOrDefault
--     MAX-ACCESS   read-create
--     STATUS       current
--     DESCRIPTION
--         "This specifies the level of priority while feeding to the parent.
--          The level '0' means treat all offered load for this queue as for
--          the above CIR traffic."
--     DEFVAL { 0 }
--     ::= { tnSapEgressQueueEntry 6 }
-- 
-- tnSapEgressQueueCIRWeight OBJECT-TYPE
--     SYNTAX       TWeight
--     MAX-ACCESS   read-create
--     STATUS       current
--     DESCRIPTION
--         "The weight that needs to be used until the committed rate by the
--          scheduler to which this queue would be feeding to."
--     DEFVAL { 1 }
--     ::= { tnSapEgressQueueEntry 7 }
-- 
-- tnSapEgressQueueExpedite OBJECT-TYPE
--     SYNTAX       INTEGER {
--                     expedited     (1),
--                     auto-expedited(2),
--                     non-expedited (3)
--                  }
--     MAX-ACCESS   read-create
--     STATUS       current
--     DESCRIPTION
--         "tnSapEgressQueueExpedite specifies the priority that this queue should
--          be assigned by the hardware level schedulers.
-- 
--          The value 'auto-expedited' implies that this attribute should be
--          dynamically updated by looking at the forwarding classes mapping
--          into this queue. In such a case the queue is treated as
--          'non-expedited' if there is even a single non-expedited forwarding
--          class using this queue.
-- 
--          This attribute is associated with the queue at the time of creation
--          and cannot be modified thereafter."
--     DEFVAL { auto-expedited }
--     ::= { tnSapEgressQueueEntry 8 }
-- 
-- tnSapEgressQueueCBS OBJECT-TYPE
--     SYNTAX       TBurstSize
--     MAX-ACCESS   read-create
--     STATUS       current
--     DESCRIPTION
--         "The amount of reserved buffer space (in kilo bytes) for the queue."
--     DEFVAL { -1 }
--     ::= { tnSapEgressQueueEntry 9 }
-- 
-- tnSapEgressQueueMBS OBJECT-TYPE
--     SYNTAX       TBurstSize
--     MAX-ACCESS   read-create
--     STATUS       current
--     DESCRIPTION
--         "The maximum amount of buffer space (in kilo bytes) allowed for the
--         queue."
--     DEFVAL { -1 }
--     ::= { tnSapEgressQueueEntry 10 }
-- 
-- tnSapEgressQueueHiPrioOnly OBJECT-TYPE
--     SYNTAX       TBurstPercentOrDefault
--     MAX-ACCESS   read-create
--     STATUS       current
--     DESCRIPTION
--         "The percentage of buffer space for the queue, used
--          exclusively by high priority packets."
--     DEFVAL { -1 }
--     ::= { tnSapEgressQueueEntry 11 }
-- 
-- tnSapEgressQueuePIRAdaptation OBJECT-TYPE
--     SYNTAX       TAdaptationRule
--     MAX-ACCESS   read-create
--     STATUS       current
--     DESCRIPTION
--         "The adaptation rule to be used while computing the operational PIR
--          value. The adaptation rule specifies the rules to compute the
--          operational values while maintaining minimum offset."
--     DEFVAL { closest }
--     ::= { tnSapEgressQueueEntry 12 }
-- 
-- tnSapEgressQueueCIRAdaptation OBJECT-TYPE
--     SYNTAX       TAdaptationRule
--     MAX-ACCESS   read-create
--     STATUS       current
--     DESCRIPTION
--         "The adaptation rule to be used while computing the operational CIR
--          value. The adaptation rule specifies the rules to compute the
--          operational values while maintaining minimum offset."
--     DEFVAL { closest }
--     ::= { tnSapEgressQueueEntry 13 }
-- 
-- tnSapEgressQueueAdminPIR OBJECT-TYPE
--     SYNTAX       TPIRRate
--     UNITS        "kbps"
--     MAX-ACCESS   read-create
--     STATUS       current
--     DESCRIPTION
--         "The administrative PIR specified by the user."
--     DEFVAL { -1 }
--     ::= { tnSapEgressQueueEntry 14 }
-- 
-- tnSapEgressQueueAdminCIR OBJECT-TYPE
--     SYNTAX       TCIRRate
--     UNITS        "kbps"
--     MAX-ACCESS   read-create
--     STATUS       current
--     DESCRIPTION
--         "The administrative CIR specified by the user."
--     DEFVAL { 0 }
--     ::= { tnSapEgressQueueEntry 15 }
-- 
-- == tnSapEgressQueueOperPIR OBJECT-TYPE
-- ==     SYNTAX       TPIRRate
-- ==     UNITS        "kbps"
-- ==     MAX-ACCESS   read-only
-- ==     STATUS       obsolete
-- ==     DESCRIPTION
-- ==         "The administrative PIR specified by the user."
-- ==     ::= { tnSapEgressQueueEntry 16 }
-- == 
-- == tnSapEgressQueueOperCIR OBJECT-TYPE
-- ==     SYNTAX       TCIRRate
-- ==     UNITS        "kbps"
-- ==     MAX-ACCESS   read-only
-- ==     STATUS       obsolete
-- ==     DESCRIPTION
-- ==         "The operational value derived by computing the CIR value from
-- ==          the administrative CIR and PIR values and their corresponding
-- ==          adaptation rules."
-- ==     ::= { tnSapEgressQueueEntry 17 }
-- 
-- tnSapEgressQueueLastChanged OBJECT-TYPE
--     SYNTAX       TimeStamp
--     MAX-ACCESS   read-only
--     STATUS       current
--     DESCRIPTION
--         "timestamp of last change to this row in tnSapEgressQueueTable."
--     ::= { tnSapEgressQueueEntry 18 }
-- 
-- tnSapEgressQueueUsePortParent  OBJECT-TYPE
--     SYNTAX      TruthValue
--     MAX-ACCESS  read-create
--     STATUS      current
--     DESCRIPTION
--         "The value of the object tnSapEgressQueueUsePortParent specifies
--          whether this queue is parented by a port-level scheduler. When
--          the value is 'true', this SAP egress queue is parented by a 
--          port-level scheduler. This object is mutually exclusive with 
--          tnSapEgressQueueParent. Only one kind of parent is allowed."
--     DEFVAL      { false }
--     ::= { tnSapEgressQueueEntry 19 }
-- 
-- tnSapEgressQueuePortLvl        OBJECT-TYPE
--     SYNTAX       TLevel
--     MAX-ACCESS  read-create
--     STATUS      current
--     DESCRIPTION
--         "The value of the object tnSapEgressQueuePortLvl specifies the
--          port priority this queue will use to receive bandwidth from
--          the port-level scheduler for its above-cir offered load."
--     DEFVAL      { 1 }
--     ::= { tnSapEgressQueueEntry 20 }
-- 
-- tnSapEgressQueuePortWght       OBJECT-TYPE
--     SYNTAX      TWeight
--     MAX-ACCESS  read-create
--     STATUS      current
--     DESCRIPTION
--         "The value of the object tnSapEgressQueuePortWght specifies the
--          weight this queue will use to receive bandwidth from the
--          port-level scheduler for its above-cir offered load."
--     DEFVAL      { 1 }
--     ::= { tnSapEgressQueueEntry 21 }
-- 
-- tnSapEgressQueuePortCIRLvl        OBJECT-TYPE
--     SYNTAX      TLevelOrDefault
--     MAX-ACCESS  read-create
--     STATUS      current
--     DESCRIPTION
--         "The value of the object tnSapEgressQueuePortCIRLvl specifies the
--          port priority this queue will use to receive bandwidth from
--          the port-level scheduler for its within-cir offered load."
--     DEFVAL      { 0 }
--     ::= { tnSapEgressQueueEntry 22 }
-- 
-- tnSapEgressQueuePortCIRWght       OBJECT-TYPE
--     SYNTAX      TWeight
--     MAX-ACCESS  read-create
--     STATUS      current
--     DESCRIPTION
--         "The value of the object tnSapEgressQueuePortCIRWght specifies the
--          weight this queue will use to receive bandwidth from the
--          port-level scheduler for its within-cir offered load."
--     DEFVAL      { 0 }
--     ::= { tnSapEgressQueueEntry 23 }
-- 
-- tnSapEgressQueuePortAvgOverhead  OBJECT-TYPE
--     SYNTAX      Unsigned32 (0..10000)
--     UNITS       "Hundredths of a percent"
--     MAX-ACCESS  read-create
--     STATUS      current
--     DESCRIPTION
--         "The value of tnSapEgressQueuePortAvgOverhead specifies the 
--          encapsulation overhead, in hundredths of a percent,  used to 
--          translate packet-based rate to frame-based rate and vice versa."
--     DEFVAL      { 0 }
--     ::= { tnSapEgressQueueEntry 24 }
-- 
-- tnSapEgressQueuePoolName OBJECT-TYPE   
--     SYNTAX      TNamedItemOrEmpty
--     MAX-ACCESS  read-create
--     STATUS      current
--     DESCRIPTION
--         "The value of tnSapEgressQueuePoolName specifies the name of 
--          the pool to be applied for SAP egress queue."
--     DEFVAL { ''H }    
--     ::= { tnSapEgressQueueEntry 25 }
-- 
-- tnSapEgressQueueXPWredQ OBJECT-TYPE   
--     SYNTAX      TruthValue
--     MAX-ACCESS  read-create
--     STATUS      current
--     DESCRIPTION
--         "The value of tnSapEgressQueueXPWredQ specifies whether to alter the
--          generic pool association of the queue for the purpose of allowing
--          queue-specific WRED slopes with minimal provisioning."
--     DEFVAL { false }    
--     ::= { tnSapEgressQueueEntry 26 }
-- 
-- tnSapEgressQueueXPWredQSlope OBJECT-TYPE   
--     SYNTAX      TNamedItem
--     MAX-ACCESS  read-create
--     STATUS      current
--     DESCRIPTION
--         "The value of tnSapEgressQueueXPWredQSlope specifies the name of 
--          the slope-policy to be applied for SAP egress queue.
--          
--          An 'inconsistentValue' error is returned when this object is set to
--          a non-default value when tnSapEgressQueueXPWredQ is set to 'false'."
--     DEFVAL { "default" }    
--     ::= { tnSapEgressQueueEntry 27 }
--
-- sap-egress policy fc table
--

-- tnSapEgressFCTable OBJECT-TYPE
--     SYNTAX       SEQUENCE OF TSapEgressFCEntry
--     MAX-ACCESS   not-accessible
--     STATUS       current
--     DESCRIPTION  "  "
--     ::= { tnSapEgressObjects 3 }
-- 
-- tnSapEgressFCEntry OBJECT-TYPE
--     SYNTAX       TSapEgressFCEntry
--     MAX-ACCESS   not-accessible
--     STATUS       current
--     DESCRIPTION
--         "Information about a particular sap-egress policy's
--          forwarding class mappings to queues and dot1p values.
--          Entries are created/deleted by user.
--          There is no StorageType object, entries have a presumed
--          StorageType of nonVolatile.
--         "
--     INDEX { tnSysSwitchId, tnSapEgressIndex, tnSapEgressFCName }
--     ::= { tnSapEgressFCTable 1 }
-- 
-- TSapEgressFCEntry ::= SEQUENCE
--     {
--         tnSapEgressFCName               TFCName,
--         tnSapEgressFCRowStatus          RowStatus,
--         tnSapEgressFCQueue              TEgressQueueId,
-- ==        tnSapEgressFCDot1PValue         Dot1PPriority,
--         tnSapEgressFCLastChanged        TimeStamp,
--         tnSapEgressFCHsmdaQueue          TEgressHsmdaQueueId,
--         tnSapEgressFCDot1PHsmdaProfile TruthValue,
--         tnSapEgressFCDot1PInProfile     Dot1PPriority,
--         tnSapEgressFCDot1POutProfile    Dot1PPriority,
--         tnSapEgressFCForceDEValue       TDEValue,
--         tnSapEgressFCDEMark             TruthValue,
--         tnSapEgressFCInProfDscp         TNamedItemOrEmpty,
--         tnSapEgressFCOutProfDscp        TNamedItemOrEmpty,
--         tnSapEgressFCInProfPrec         TPrecValueOrNone,
--         tnSapEgressFCOutProfPrec        TPrecValueOrNone,
--         tnSapEgressFCQGrp               TNamedItemOrEmpty
--     }
-- 
-- tnSapEgressFCName OBJECT-TYPE
--     SYNTAX       TFCName
--     MAX-ACCESS   not-accessible
--     STATUS       current
--     DESCRIPTION
--         "forwarding class name."
--     ::= { tnSapEgressFCEntry 1 }
-- 
-- tnSapEgressFCRowStatus OBJECT-TYPE
--     SYNTAX       RowStatus
--     MAX-ACCESS   read-create
--     STATUS       current
--     DESCRIPTION
--         "Row Status for this queue."
--     ::= { tnSapEgressFCEntry 2 }
-- 
-- tnSapEgressFCQueue OBJECT-TYPE
--     SYNTAX       TEgressQueueId
--     MAX-ACCESS   read-create
--     STATUS       current
--     DESCRIPTION
--         "The queue to use for packets in this forwarding class.
--          No FC can map to the same queue being used by 'premium' class.
-- 
--          An 'inconsistentValue' error is retuned when setting 
--          tnSapEgressFCRowStatus to 'active' when the values of tnSapEgressFCQueue,
--          and tnSapEgressFCQGrp are all set to their default values."
--     DEFVAL { 0 }
--     ::= { tnSapEgressFCEntry 3 }
-- 
-- == tnSapEgressFCDot1PValue OBJECT-TYPE
-- ==     SYNTAX       Dot1PPriority
-- ==     MAX-ACCESS   read-create
-- ==     STATUS       obsolete
-- ==     DESCRIPTION
-- ==         "The value of tnSapEgressFCDot1PValue specifies 802.1p value to use for
-- ==         packets in this forwarding class.
-- == 
-- ==         This object has been replaced by tnSapEgressFCDot1PInProfile and
-- ==         tnSapEgressFCDot1POutProfile objects."
-- ==     DEFVAL { -1 }
-- ==     ::= { tnSapEgressFCEntry 4 }
-- 
-- tnSapEgressFCLastChanged OBJECT-TYPE
--     SYNTAX       TimeStamp
--     MAX-ACCESS   read-only
--     STATUS       current
--     DESCRIPTION
--         "timestamp of last change to this row in tnSapEgressFCTable."
--     ::= { tnSapEgressFCEntry 5 }
-- 
-- tnSapEgressFCHsmdaQueue OBJECT-TYPE
--     SYNTAX       TEgressHsmdaQueueId
--     MAX-ACCESS   read-create
--     STATUS       current
--     DESCRIPTION
--         "The HSMDA queue to use for packets in this forwarding class.
--          This mapping will be used when the SAP is on a HSMDA MDA."
--     DEFVAL { 0 }
--     ::= { tnSapEgressFCEntry 6 }
-- 
-- tnSapEgressFCDot1PHsmdaProfile OBJECT-TYPE
--     SYNTAX       TruthValue
--     MAX-ACCESS   read-create
--     STATUS       current
--     DESCRIPTION
--         "The value of the object tnSapEgressFCDot1PHsmdaProfile specifies 
--          if the system will perform egress profiling on HSMDA queues or not."
--     DEFVAL { false }
--     ::= { tnSapEgressFCEntry 7 }
-- 
-- tnSapEgressFCDot1PInProfile OBJECT-TYPE
--     SYNTAX       Dot1PPriority
--     MAX-ACCESS   read-create
--     STATUS       current
--     DESCRIPTION
--        "The value of tnSapEgressFCDot1PInProfile specifies 802.1p value to set
--        for in-profile frames in this forwarding class.
-- 
--        An inconsistentValue error is returned if this object is set to any value
--        other than '-1', when tnSapEgressFCDot1POutProfile object is set to '-1'."
--     DEFVAL { -1 }
--     ::= { tnSapEgressFCEntry 8 }
-- 
-- tnSapEgressFCDot1POutProfile OBJECT-TYPE
--     SYNTAX       Dot1PPriority
--     MAX-ACCESS   read-create
--     STATUS       current
--     DESCRIPTION
--        "The value of tnSapEgressFCDot1POutProfile specifies 802.1p value to set
--        for out-profile frames in this forwarding class.
--         
--        An inconsistentValue error is returned if this object is set to any value
--        other than '-1', when tnSapEgressFCDot1PInProfile object is set to '-1'."
--     DEFVAL { -1 }
--     ::= { tnSapEgressFCEntry 9 }
-- 
-- tnSapEgressFCForceDEValue OBJECT-TYPE
--     SYNTAX       TDEValue
--     MAX-ACCESS   read-create
--     STATUS       current
--     DESCRIPTION
--        "The value of tnSapEgressFCForceDEValue specifies the DE value to set
--        for all the frames of this forwarding class regardless of frame's profile
--        status.
-- 
--        An inconsistentValue error is returned if this object is set to any value
--        other than '-1', when tnSapEgressFCDEMark object is set to 'false'."
--     DEFVAL { -1 }
--     ::= { tnSapEgressFCEntry 10 }
-- 
-- tnSapEgressFCDEMark OBJECT-TYPE
--     SYNTAX       TruthValue
--     MAX-ACCESS   read-create
--     STATUS       current
--     DESCRIPTION
--        "The value of tnSapEgressFCDEMark specifies whether to set DE value in the
--        frames of this forwarding class.
-- 
--        An inconsistentValue error is returned if this object is set to 'false'
--        when tnSapEgressFCForceDEValue object is not set to '-1'."
--     DEFVAL { false }
--     ::= { tnSapEgressFCEntry 11 }
-- 
-- tnSapEgressFCInProfDscp OBJECT-TYPE
--     SYNTAX       TNamedItemOrEmpty
--     MAX-ACCESS   read-create
--     STATUS       current
--     DESCRIPTION
--        "The value of tnSapEgressFCInProfDscp specifies the DSCP name to set
--        for in-profile frames in this forwarding class.
-- 
--        The values of tnSapEgressFCInProfDscp and tnSapEgressFCOutProfDscp
--        must be set to either the default or non-default values for both.
--        An inconsistentValue error is returned if one object is set to the
--        default and other is set to a non-default value.
-- 
--        The values of tnSapEgressFCInProfPrec and tnSapEgressFCOutProfPrec are
--        reset to default values when tnSapEgressFCInProfDscp is set to any value
--        other than default.
-- 
--        An inconsistentValue error is returned if this object is set to any value
--        other than its default value when setting tnSapEgressFCInProfPrec object
--        or tnSapEgressFCOutProfPrec to a value other than their default values."
--     DEFVAL { ''H }
--     ::= { tnSapEgressFCEntry 12 }
-- 
-- tnSapEgressFCOutProfDscp OBJECT-TYPE
--     SYNTAX       TNamedItemOrEmpty
--     MAX-ACCESS   read-create
--     STATUS       current
--     DESCRIPTION
--        "The value of tnSapEgressFCOutProfDscp specifies the DSCP name to set
--        for out-profile frames in this forwarding class.
-- 
--        The values of tnSapEgressFCInProfDscp and tnSapEgressFCOutProfDscp
--        must be set to either the default or non-default values for both.
--        An inconsistentValue error is returned if one object is set to the
--        default and other is set to a non-default value.
-- 
--        The values of tnSapEgressFCInProfPrec and tnSapEgressFCOutProfPrec are
--        reset to default values when tnSapEgressFCOutProfDscp is set to any value
--        other than default.
--        
--        An inconsistentValue error is returned if this object is set to any value
--        other than its default value when setting tnSapEgressFCInProfPrec object
--        or tnSapEgressFCOutProfPrec to a value other than their default values."
--     DEFVAL { ''H }
--     ::= { tnSapEgressFCEntry 13 }
-- 
-- tnSapEgressFCInProfPrec OBJECT-TYPE
--     SYNTAX       TPrecValueOrNone
--     MAX-ACCESS   read-create
--     STATUS       current
--     DESCRIPTION
--        "The value of tnSapEgressFCInProfPrec specifies the precedence value to
--        set for in-profile frames in this forwarding class.
-- 
--        The values of tnSapEgressFCInProfPrec and tnSapEgressFCOutProfPrec
--        must be set to either the default or non-default values for both.
--        An inconsistentValue error is returned if one object is set to the
--        default and other is set to a non-default value.
-- 
--        The values of tnSapEgressFCInProfDscp and tnSapEgressFCOutProfDscp are
--        reset to default values when tnSapEgressFCOutProfPrec is set to any value
--        other than default.
-- 
--        An inconsistentValue error is returned if this object is set to any value
--        other than its default value when setting tnSapEgressFCInProfDscp object
--        or tnSapEgressFCOutProfDscp to a value other than their default values."
--     DEFVAL { -1 }
--     ::= { tnSapEgressFCEntry 14 }
-- 
-- tnSapEgressFCOutProfPrec OBJECT-TYPE
--     SYNTAX       TPrecValueOrNone
--     MAX-ACCESS   read-create
--     STATUS       current
--     DESCRIPTION
--        "The value of tnSapEgressFCOutProfPrec specifies the precedence value to
--        set for out-profile frames in this forwarding class.
-- 
--        The values of tnSapEgressFCInProfPrec and tnSapEgressFCOutProfPrec must be
--        be set to either the default or non-default values for both.
--        An inconsistentValue error is returned if one object is set to the
--        default and other is set to a non-default value.
-- 
--        The values of tnSapEgressFCInProfDscp and tnSapEgressFCOutProfDscp are
--        reset to default values when tnSapEgressFCOutProfPrec is set to any value
--        other than default.
--        
--        An inconsistentValue error is returned if this object is set to any value
--        other than its default value when setting tnSapEgressFCInProfDscp object
--        or tnSapEgressFCOutProfDscp to a value other than their default values."
--     DEFVAL { -1 }
--     ::= { tnSapEgressFCEntry 15 }
-- 
-- tnSapEgressFCQGrp OBJECT-TYPE
--     SYNTAX       TNamedItemOrEmpty
--     MAX-ACCESS   read-create
--     STATUS       current
--     DESCRIPTION
--         "tnSapEgressFCQGrp specifies the tnQosEgrQGroupName.
-- 
--         This object must be set along with tnSapEgressFCQueue object.
--         An 'inconsistentValue' error is returned if this is set to the default 
--         and the other is set to a non-default value."
--     DEFVAL { ''H }
--     ::= { tnSapEgressFCEntry 16 }

--
-- sap-egress hsmda queue table
--

-- tnSapEgressHsmdaQueueTable OBJECT-TYPE
--     SYNTAX      SEQUENCE OF TSapEgressHsmdaQueueEntry
--     MAX-ACCESS  not-accessible
--     STATUS      current
--     DESCRIPTION
--         "Information about all sap-egress policies' HSMDA queues."
--     ::= { tnSapEgressObjects 4 }
-- 
-- tnSapEgressHsmdaQueueEntry    OBJECT-TYPE
--     SYNTAX      TSapEgressHsmdaQueueEntry
--     MAX-ACCESS  not-accessible
--     STATUS      current
--     DESCRIPTION
--         "Information about a particular HSMDA queue for a sap-egress policy.
--          Entries are created by user."
--     INDEX { tnSysSwitchId, tnSapEgressIndex, tnSapEgressHsmdaQueue }
--     ::= { tnSapEgressHsmdaQueueTable 1}
-- 
-- TSapEgressHsmdaQueueEntry ::= SEQUENCE
--     {
--         tnSapEgressHsmdaQueue                 TEgressHsmdaQueueId,
--         tnSapEgressHsmdaQueueRowStatus        RowStatus,
--         tnSapEgressHsmdaQueueCIRAdaptn        TAdaptationRule,
--         tnSapEgressHsmdaQueuePIRAdaptn        TAdaptationRule,
--         tnSapEgressHsmdaQueueAdminPIR         THsmdaPIRKRate,
--         tnSapEgressHsmdaQueueAdminCIR         THsmdaCIRKRate,
--         tnSapEgressHsmdaQueueSlopePolicy      TNamedItem,
--         tnSapEgressHsmdaQueueLastChanged      TimeStamp
--     }
-- 
-- tnSapEgressHsmdaQueue        OBJECT-TYPE
--     SYNTAX      TEgressHsmdaQueueId (1..8)
--     MAX-ACCESS  not-accessible
--     STATUS      current
--     DESCRIPTION
--         "The HSMDA queue ID is used as the secondary index to the table entry."
--     ::= { tnSapEgressHsmdaQueueEntry 1 }
-- 
-- tnSapEgressHsmdaQueueRowStatus        OBJECT-TYPE
--     SYNTAX      RowStatus
--     MAX-ACCESS  read-create
--     STATUS      current
--     DESCRIPTION
--         "The value of tnSapEgressHsmdaQueueRowStatus is used for the creation
--         and deletion of entries in the tnSapEgressHsmdaQueueTable."
--     ::= { tnSapEgressHsmdaQueueEntry 2 }
-- 
-- tnSapEgressHsmdaQueueCIRAdaptn        OBJECT-TYPE
--     SYNTAX      TAdaptationRule
--     MAX-ACCESS  read-create
--     STATUS      current
--     DESCRIPTION
--         "The value of tnSapEgressHsmdaQueueCIRAdaptn specifies the 
--          adaptation rule to be used while computing the operational CIR
--          value. The adaptation rule specifies the rules to compute the
--          operational values while maintaining minimum offset."
--     DEFVAL { closest }
--     ::= { tnSapEgressHsmdaQueueEntry 3 }
-- 
-- tnSapEgressHsmdaQueuePIRAdaptn        OBJECT-TYPE
--     SYNTAX      TAdaptationRule
--     MAX-ACCESS  read-create
--     STATUS      current
--     DESCRIPTION
--         "The value of tnSapEgressHsmdaQueuePIRAdaptn specifies the 
--          adaptation rule to be used while computing the operational PIR
--          value. The adaptation rule specifies the rules to compute the
--          operational values while maintaining minimum offset."
--     DEFVAL { closest }
--     ::= { tnSapEgressHsmdaQueueEntry 4 }
-- 
-- tnSapEgressHsmdaQueueAdminPIR        OBJECT-TYPE
--     SYNTAX      THsmdaPIRKRate
--     UNITS       "kbps"
--     MAX-ACCESS  read-create
--     STATUS      current
--     DESCRIPTION
--         "The value of tnSapEgressHsmdaQueueAdminPIR specifies the 
--          administrative PIR specified by the user."
--     DEFVAL { -1 }
--     ::= { tnSapEgressHsmdaQueueEntry 5 }
-- 
-- tnSapEgressHsmdaQueueAdminCIR        OBJECT-TYPE
--     SYNTAX      THsmdaCIRKRate
--     UNITS       "kbps"
--     MAX-ACCESS  read-create
--     STATUS      current
--     DESCRIPTION
--         "The value of tnSapEgressHsmdaQueueAdminCIR specifies the 
--          administrative CIR specified by the user."
--     DEFVAL { 0 }
--     ::= { tnSapEgressHsmdaQueueEntry 6 }
-- 
-- tnSapEgressHsmdaQueueSlopePolicy        OBJECT-TYPE
--     SYNTAX      TNamedItem
--     MAX-ACCESS  read-create
--     STATUS      current
--     DESCRIPTION
--         "The value of tnSapEgressHsmdaQueueSlopePolicy specifies the slope
--          policy specified by the user."
--     DEFVAL { "default" }
--     ::= { tnSapEgressHsmdaQueueEntry 7 }
-- 
-- tnSapEgressHsmdaQueueLastChanged        OBJECT-TYPE
--     SYNTAX      TimeStamp
--     MAX-ACCESS  read-only
--     STATUS      current
--     DESCRIPTION
--         "The value of tnSapEgressHsmdaQueueLastChanged indicates the timestamp 
--          of last change to this row in tnSapEgressHsmdaQueueTable."
--     ::= { tnSapEgressHsmdaQueueEntry 8 }

--
-- sap-egress policy dscp table
--

-- tnSapEgressDSCPTable OBJECT-TYPE
--     SYNTAX       SEQUENCE OF TSapEgressDSCPEntry
--     MAX-ACCESS   not-accessible
--     STATUS       current
--     DESCRIPTION
--         "a list of all DSCP entries for all sap-egress policies."
--     ::= { tnSapEgressObjects 5 }
-- 
-- tnSapEgressDSCPEntry OBJECT-TYPE
--     SYNTAX       TSapEgressDSCPEntry
--     MAX-ACCESS   not-accessible
--     STATUS       current
--     DESCRIPTION
--         "Information about a particular DSCP entry for a sap-egress policy.
-- 
--         Entries are created by user.
--         Entries are deleted by user.
-- 
--         There is no StorageType object, entries have a presumed
--         StorageType of nonVolatile.
-- 
--         in the event that one policy has multiple entries, and
--         the tnSapEgressDSCP values are the same, only one queue
--         will be created (the queue for the lexicographically
--         first tnSapEgressDSCP).
--         "
--     INDEX { tnSysSwitchId, tnSapEgressIndex, tnSapEgressDSCP }
--     ::= { tnSapEgressDSCPTable 1 }
-- 
-- TSapEgressDSCPEntry ::= SEQUENCE
--     {
--         tnSapEgressDSCP                    TDSCPName,
--         tnSapEgressDSCPRowStatus           RowStatus,
--         tnSapEgressDSCPLastChanged         TimeStamp,
--         tnSapEgressDSCPHsmdaCntrOverride   TEgressHsmdaCounterIdOrZero,
--         tnSapEgressDSCPfc                  TFCNameOrEmpty, 
--         tnSapEgressDSCPprofile             TProfileOrNone
--     }
-- 
-- tnSapEgressDSCP OBJECT-TYPE
--     SYNTAX       TDSCPName
--     MAX-ACCESS   not-accessible
--     STATUS       current
--     DESCRIPTION
--         ""
--     ::= { tnSapEgressDSCPEntry 1 }
-- 
-- tnSapEgressDSCPRowStatus OBJECT-TYPE
--     SYNTAX       RowStatus
--     MAX-ACCESS   read-create
--     STATUS       current
--     DESCRIPTION
--         "The value of tnSapEgressDSCPRowStatus controls the creation/deletion 
--          of rows in this table."
--     ::= { tnSapEgressDSCPEntry 2 }
-- 
-- tnSapEgressDSCPLastChanged OBJECT-TYPE
--     SYNTAX       TimeStamp
--     MAX-ACCESS   read-only
--     STATUS       current
--     DESCRIPTION
--         "The value of tnSapEgressDSCPLastChanged indicates the sysUpTime
--          at the time of the most recent management-initiated change to this
--          table row."
--     ::= { tnSapEgressDSCPEntry 3 }
-- 
-- tnSapEgressDSCPHsmdaCntrOverride OBJECT-TYPE
--     SYNTAX       TEgressHsmdaCounterIdOrZero
--     MAX-ACCESS   read-create
--     STATUS       current
--     DESCRIPTION
--         "The value of the object tnSapEgressDSCPHsmdaCntrOverride 
--          specifies the counter to use for all the traffic that
--          matches the specific DSCP i.e. tnSapEgressDSCP.
-- 
--          A value of zero implies that the default counters should be used."
--     DEFVAL { 0 }
--     ::= { tnSapEgressDSCPEntry 4 }
-- 
-- tnSapEgressDSCPfc OBJECT-TYPE
--     SYNTAX       TFCNameOrEmpty
--     MAX-ACCESS   read-create
--     STATUS       current
--     DESCRIPTION
--         "The value of tnSapEgressDSCPfc, when specified, will overwrite the
--          forwarding class derived from ingress. The new forwarding class is
--          used for egress remarking and queue mapping decisions."
--     DEFVAL { ''H }
--     ::= { tnSapEgressDSCPEntry 5 }
-- 
-- tnSapEgressDSCPprofile OBJECT-TYPE
--     SYNTAX       TProfileOrNone
--     MAX-ACCESS   read-create
--     STATUS       current
--     DESCRIPTION
--         "The value of tnSapEgressDSCPprofile, when provided, specifies the
--          egress classification rule that will overwrite the profile of the
--          packet derived from the ingress. The new profile value is used for
--          egress remarking and queue congestion behavior."
--     DEFVAL { none }
--     ::= { tnSapEgressDSCPEntry 6 }

--
-- sap-egress policy precedence table
--

-- tnSapEgressPrecTable OBJECT-TYPE
--     SYNTAX       SEQUENCE OF TSapEgressPrecEntry
--     MAX-ACCESS   not-accessible
--     STATUS       current
--     DESCRIPTION 
--         "This table maintains the mapping of a particular
--         precedence value into a forwarding class"
--     ::= { tnSapEgressObjects 6 }
-- 
-- tnSapEgressPrecEntry OBJECT-TYPE
--     SYNTAX       TSapEgressPrecEntry
--     MAX-ACCESS   not-accessible
--     STATUS       current
--     DESCRIPTION
--         "Information about a particular sap-egress policy's
--          IP precedence values to forwarding class mappings.
-- 
--          Entries are created and deleted by user. They have
--          a presumed StorageType of nonVolatile."
--     INDEX { tnSysSwitchId, tnSapEgressIndex, tnSapEgressPrecValue }
--     ::= { tnSapEgressPrecTable 1 }
-- 
-- TSapEgressPrecEntry ::= SEQUENCE
--     {
--         tnSapEgressPrecValue               TPrecValue,
--         tnSapEgressPrecRowStatus           RowStatus,
--         tnSapEgressPrecLastChanged         TimeStamp,
--         tnSapEgressPrecHsmdaCntrOverride   TEgressHsmdaCounterIdOrZero,
--         tnSapEgressPrecFC                  TFCNameOrEmpty, 
--         tnSapEgressPrecProfile             TProfileOrNone
--     }
-- 
-- tnSapEgressPrecValue OBJECT-TYPE
--     SYNTAX       TPrecValue
--     MAX-ACCESS   not-accessible
--     STATUS       current
--     DESCRIPTION
--         "The value of tnSapEgressPrecValue indicates the precedence value
--         for which the mapping is done. It is used as a secondary index for
--         tnSapEgressPrecTable."
--     ::= { tnSapEgressPrecEntry 1 }
-- 
-- tnSapEgressPrecRowStatus OBJECT-TYPE
--     SYNTAX       RowStatus
--     MAX-ACCESS   read-create
--     STATUS       current
--     DESCRIPTION
--         "The value of tnSapEgressPrecRowStatus controls the creation/deletion 
--          of rows in this table."
--     ::= { tnSapEgressPrecEntry 2 }
-- 
-- tnSapEgressPrecLastChanged OBJECT-TYPE
--     SYNTAX       TimeStamp
--     MAX-ACCESS   read-only
--     STATUS       current
--     DESCRIPTION
--         "The value of tnSapEgressPrecLastChanged indicates the sysUpTime
--          at the time of the most recent management-initiated change to this
--          table row."
--     ::= { tnSapEgressPrecEntry 3 }
-- 
-- tnSapEgressPrecHsmdaCntrOverride OBJECT-TYPE
--     SYNTAX       TEgressHsmdaCounterIdOrZero
--     MAX-ACCESS   read-create
--     STATUS       current
--     DESCRIPTION
--         "The value of tnSapEgressPrecHsmdaCntrOverride specifies the counter 
--          to use for all the traffic that matches the specific precedence value
--          i.e. tnSapEgressPrecValue.
-- 
--          A value of zero implies that the default counters should be used."
--     DEFVAL { 0 }
--     ::= { tnSapEgressPrecEntry 4 }
-- 
-- tnSapEgressPrecFC OBJECT-TYPE
--     SYNTAX       TFCNameOrEmpty
--     MAX-ACCESS   read-create
--     STATUS       current
--     DESCRIPTION
--         "The value of tnSapEgressPrecFC, when specified, will overwrite the
--          forwarding class derived from ingress. The new forwarding class is
--          used for egress remarking and queue mapping decisions."
--     DEFVAL { ''H }
--     ::= { tnSapEgressPrecEntry 5 }
-- 
-- tnSapEgressPrecProfile OBJECT-TYPE
--     SYNTAX       TProfileOrNone
--     MAX-ACCESS   read-create
--     STATUS       current
--     DESCRIPTION
--         "The value of tnSapEgressPrecProfile, when provided, specifies the
--          egress classification rule that will overwrite the profile of the
--          packet derived from the ingress. The new profile value is used for
--          egress remarking and queue congestion behavior."
--     DEFVAL { none }
--     ::= { tnSapEgressPrecEntry 6 }

--
-- sap-egress ip-crit table
--

-- tnSapEgrIPCritTable OBJECT-TYPE
--     SYNTAX      SEQUENCE OF TSapEgrIPCritEntry
--     MAX-ACCESS  not-accessible
--     STATUS      current
--     DESCRIPTION
--         "This table maintains the entries for matching
--          cirteria for IP packets on egress"
--     ::= { tnSapEgressObjects 7 }
-- 
-- tnSapEgrIPCritEntry    OBJECT-TYPE
--     SYNTAX      TSapEgrIPCritEntry
--     MAX-ACCESS  not-accessible
--     STATUS      current
--     DESCRIPTION
--         "Information about a particular egress IP matching
--          criteria entry.
-- 
--          Entries are created and deleted by user. They have
--          a presumed StorageType of nonVolatile."
--     INDEX { tnSysSwitchId, tnSapEgressIndex,  tnSapEgrIPCritAddrType, tnSapEgrIPCritIndex }
--     ::= { tnSapEgrIPCritTable 1}
-- 
-- TSapEgrIPCritEntry ::= SEQUENCE
--     {
--         tnSapEgrIPCritAddrType           InetAddressType,
--         tnSapEgrIPCritIndex              Unsigned32,
--         tnSapEgrIPCritRowStatus          RowStatus,
--         tnSapEgrIPCritLastChanged        TimeStamp,
--         tnSapEgrIPCritDescription        TItemDescription,
--         tnSapEgrIPCritActionHsmdaCntrOvr TEgressHsmdaCounterIdOrZero,
--         tnSapEgrIPCritSourceIpAddrType   InetAddressType,
--         tnSapEgrIPCritSourceIpAddr       InetAddress,
--         tnSapEgrIPCritSourceIpMask       InetAddressPrefixLength,
--         tnSapEgrIPCritDestIpAddrType     InetAddressType,
--         tnSapEgrIPCritDestIpAddr         InetAddress,
--         tnSapEgrIPCritDestIpMask         InetAddressPrefixLength,
--         tnSapEgrIPCritProtocol           TIpProtocol,
--         tnSapEgrIPCritSourcePortValue1   TTcpUdpPort,
--         tnSapEgrIPCritSourcePortValue2   TTcpUdpPort,
--         tnSapEgrIPCritSourcePortOperator TTcpUdpPortOperator,
--         tnSapEgrIPCritDestPortValue1     TTcpUdpPort,
--         tnSapEgrIPCritDestPortValue2     TTcpUdpPort,
--         tnSapEgrIPCritDestPortOperator   TTcpUdpPortOperator,
--         tnSapEgrIPCritDSCP               TDSCPNameOrEmpty,
--         tnSapEgrIPCritFragment           TItemMatch,
--         tnSapEgrIPCritActionFC           TFCNameOrEmpty, 
--         tnSapEgrIPCritActionProfile      TProfileOrNone
--     }
-- 
-- tnSapEgrIPCritAddrType OBJECT-TYPE
--     SYNTAX       InetAddressType
--     MAX-ACCESS   not-accessible
--     STATUS       current
--     DESCRIPTION
--         "The value of tnSapEgrIPCritAddrType specifies the index address
--          type this entry should match against."
--     DEFVAL { ipv4 }
--     ::= { tnSapEgrIPCritEntry 1 }
-- 
-- tnSapEgrIPCritIndex        OBJECT-TYPE
--     SYNTAX      Unsigned32
--     MAX-ACCESS  not-accessible
--     STATUS      current
--     DESCRIPTION
--         "The value of tnSapEgrIPCritIndex specifies the index for a sap-egress
--          IP criteria entry."
--     ::= { tnSapEgrIPCritEntry 2 }
-- 
-- tnSapEgrIPCritRowStatus        OBJECT-TYPE
--     SYNTAX      RowStatus
--     MAX-ACCESS  read-create
--     STATUS      current
--     DESCRIPTION
--         "The value of tnSapEgrIPCritRowStatus is used for the creation
--          and deletion of sap-egress IP criteria entries."
--     ::= { tnSapEgrIPCritEntry 3 }
-- 
-- tnSapEgrIPCritLastChanged        OBJECT-TYPE
--     SYNTAX      TimeStamp
--     MAX-ACCESS  read-only
--     STATUS      current
--     DESCRIPTION
--         "The value of tnSapEgrIPCritLastChanged indicates the sysUpTime
--          at the time of the last modification of this entry.
-- 
--          If no changes were made to the entry since the last
--          re-initialization of the local network management subsystem,
--          then this object contains a zero value."
--     ::= { tnSapEgrIPCritEntry 4 }
-- 
-- tnSapEgrIPCritDescription        OBJECT-TYPE
--     SYNTAX      TItemDescription
--     MAX-ACCESS  read-create
--     STATUS      current
--     DESCRIPTION
--         "The value of tnSapEgrIPCritDescription specifies a description
--          of the sap-egress IP criteria entry."
--     DEFVAL { "" }
--     ::= { tnSapEgrIPCritEntry 5 }
-- 
-- tnSapEgrIPCritActionHsmdaCntrOvr OBJECT-TYPE
--     SYNTAX       TEgressHsmdaCounterIdOrZero
--     MAX-ACCESS   read-create
--     STATUS       current
--     DESCRIPTION
--         "The value of the object tnSapEgrIPCritActionHsmdaCntrOvr specifies
--          the Hsmda counter to use for matching packets. This value will be
--          ignored when the sap-egress policy specified by tnSapEgressIndex,
--          is applied to a SAP on a non-Hsmda MDA type. 
-- 
--          A value of zero implies that the default counters should be used."
--     DEFVAL { 0 }
--     ::= { tnSapEgrIPCritEntry 6 }
-- 
-- tnSapEgrIPCritSourceIpAddrType OBJECT-TYPE
--     SYNTAX       InetAddressType
--     MAX-ACCESS   read-create
--     STATUS       current
--     DESCRIPTION
--         "The value of tnSapEgrIPCritSourceIpAddrType specifies the address type
--          of tnSapEgrIPCritSourceIpAddr. If the value of this object is not
--          'none', it must have the same value as tnSapEgrIPCritAddrType."
--     DEFVAL { unknown }
--     ::= { tnSapEgrIPCritEntry 7 }
-- 
-- tnSapEgrIPCritSourceIpAddr OBJECT-TYPE
--     SYNTAX       InetAddress (SIZE(0|4|16))
--     MAX-ACCESS   read-create
--     STATUS       current
--     DESCRIPTION
--         "The value of tnSapEgrIPCritSourceIpAddr specifies the IP address to 
--          match with source-IP of the packet."
--     DEFVAL { ''H }
--     ::= { tnSapEgrIPCritEntry 8 }
-- 
-- tnSapEgrIPCritSourceIpMask OBJECT-TYPE
--     SYNTAX       InetAddressPrefixLength
--     MAX-ACCESS   read-create
--     STATUS       current
--     DESCRIPTION
--         "The value of tnSapEgrIPCritSourceIpMask specifies the number of bits
--          of the source IP address to match."
--     DEFVAL { 0 }
--     ::= { tnSapEgrIPCritEntry 9 }
-- 
-- tnSapEgrIPCritDestIpAddrType OBJECT-TYPE
--     SYNTAX       InetAddressType
--     MAX-ACCESS   read-create
--     STATUS       current
--     DESCRIPTION
--         "The value of tnSapEgrIPCritDestIpAddrType specifies the address type
--          of tnSapEgrIPCritDestIpAddr. If the value of this object is not
--          'none', it must have the same value as tnSapEgrIPCritAddrType."
--     DEFVAL { unknown }
--     ::= { tnSapEgrIPCritEntry 10 }
-- 
-- tnSapEgrIPCritDestIpAddr OBJECT-TYPE
--     SYNTAX       InetAddress (SIZE(0|4|16))
--     MAX-ACCESS   read-create
--     STATUS       current
--     DESCRIPTION
--         "The value of tnSapEgrIPCritDestIpAddr specifies the IP address to 
--          match with destination-IP of the packet."
--     DEFVAL { ''H }
--     ::= { tnSapEgrIPCritEntry 11 }
-- 
-- tnSapEgrIPCritDestIpMask OBJECT-TYPE
--     SYNTAX       InetAddressPrefixLength
--     MAX-ACCESS   read-create
--     STATUS       current
--     DESCRIPTION
--         "The value of tnSapEgrIPCritDestIpMask specifies the number of bits 
--          of the destination IP address to match."
--     DEFVAL { 0 }
--     ::= { tnSapEgrIPCritEntry 12 }
-- 
-- tnSapEgrIPCritProtocol OBJECT-TYPE
--     SYNTAX       TIpProtocol
--     MAX-ACCESS   read-create
--     STATUS       current
--     DESCRIPTION
--         "The value of tnSapEgrIPCritProtocol specifies the IP protocol to match.
--          The value '-1' is used to disable matching by IP protocol."
--     DEFVAL { -1 }
--     ::= { tnSapEgrIPCritEntry 13 }
-- 
-- tnSapEgrIPCritSourcePortValue1 OBJECT-TYPE
--     SYNTAX       TTcpUdpPort
--     MAX-ACCESS   read-create
--     STATUS       current
--     DESCRIPTION
--         "The value of tnSapEgrIPCritSourcePortValue1 specifies the first TCP/UDP
--          source port value. The value of this object is used according to the 
--          value of tnSapEgrIPCritSourcePortOperator."
--     DEFVAL { 0 }
--     ::= { tnSapEgrIPCritEntry 14 }
-- 
-- tnSapEgrIPCritSourcePortValue2 OBJECT-TYPE
--     SYNTAX       TTcpUdpPort
--     MAX-ACCESS   read-create
--     STATUS       current
--     DESCRIPTION
--         "The value of tnSapEgrIPCritSourcePortValue2 specifies the second TCP/UDP
--          source port value. The value of this object is used according to the 
--          value of tnSapEgrIPCritSourcePortOperator."
--     DEFVAL { 0 }
--     ::= { tnSapEgrIPCritEntry 15 }
-- 
-- tnSapEgrIPCritSourcePortOperator OBJECT-TYPE
--     SYNTAX       TTcpUdpPortOperator
--     MAX-ACCESS   read-create
--     STATUS       current
--     DESCRIPTION
--         "The value of tnSapEgrIPCritSourcePortOperator specifies the manner in
--          which tnSapEgrIPCritSourcePortValue1 and tnSapEgrIPCritSourcePortValue2
--          are to be used."
--     DEFVAL { none }
--     ::= { tnSapEgrIPCritEntry 16 }
-- 
-- tnSapEgrIPCritDestPortValue1 OBJECT-TYPE
--     SYNTAX       TTcpUdpPort
--     MAX-ACCESS   read-create
--     STATUS       current
--     DESCRIPTION
--         "The value of tnSapEgrIPCritDestPortValue1 specifies the first TCP/UDP
--          destination port value. The value of this object is used according to the 
--          value of tnSapEgrIPCritDestPortOperator."
--     DEFVAL { 0 }
--     ::= { tnSapEgrIPCritEntry 17 }
-- 
-- tnSapEgrIPCritDestPortValue2 OBJECT-TYPE
--     SYNTAX       TTcpUdpPort
--     MAX-ACCESS   read-create
--     STATUS       current
--     DESCRIPTION
--         "The value of tnSapEgrIPCritDestPortValue2 specifies the second TCP/UDP
--          destination port value. The value of this object is used according to the 
--          value of tnSapEgrIPCritDestPortOperator."
--     DEFVAL { 0 }
--     ::= { tnSapEgrIPCritEntry 18 }
-- 
-- tnSapEgrIPCritDestPortOperator OBJECT-TYPE
--     SYNTAX       TTcpUdpPortOperator
--     MAX-ACCESS   read-create
--     STATUS       current
--     DESCRIPTION
--         "The value of tnSapEgrIPCritDestPortOperator specifies the manner in
--          which tnSapEgrIPCritDestPortValue1 and tnSapEgrIPCritDestPortValue2
--          are to be used."
--     DEFVAL { none }
--     ::= { tnSapEgrIPCritEntry 19 }
-- 
-- tnSapEgrIPCritDSCP OBJECT-TYPE
--     SYNTAX       TDSCPNameOrEmpty
--     MAX-ACCESS   read-create
--     STATUS       current
--     DESCRIPTION
--         "The value of tnSapEgrIPCritDSCP specifies the DSCP value to match in 
--          the packet"
--     DEFVAL { ''H }
--     ::= { tnSapEgrIPCritEntry 20 }
-- 
-- tnSapEgrIPCritFragment OBJECT-TYPE
--     SYNTAX       TItemMatch
--     MAX-ACCESS   read-create
--     STATUS       current
--     DESCRIPTION
--         "The value of tnSapEgrIPCritFragment specifies fragmented packet
--          matching. If the value is 'true', only fragmented packets match. 
--          If the value is 'false', only non-fragmented packets match.
--          If the value is 'off', all packets match regardless."
--     DEFVAL { off }
--     ::= { tnSapEgrIPCritEntry 21 }
-- 
-- tnSapEgrIPCritActionFC OBJECT-TYPE
--     SYNTAX       TFCNameOrEmpty
--     MAX-ACCESS   read-create
--     STATUS       current
--     DESCRIPTION
--         "tnSapEgrIPCritActionFC specifies the forwarding class to be used to
--          classify all the traffic that matches the specific IP criteria.
-- 
--          The value ''H indicates that the FC is derived
--          from ingress classification and profiling functions."
--     DEFVAL { ''H }
--     ::= { tnSapEgrIPCritEntry 22 }
-- 
-- tnSapEgrIPCritActionProfile OBJECT-TYPE
--     SYNTAX       TProfileOrNone
--     MAX-ACCESS   read-create
--     STATUS       current
--     DESCRIPTION
--         "tnSapEgrIPCritActionProfile specifies the profile of the
--          traffic that matches the specific IP criteria.
-- 
--          The value none indicates that the profile is derived
--          from ingress classification and profiling functions."
--     DEFVAL { none }
--     ::= { tnSapEgrIPCritEntry 23 }

--
-- network policy table
--

tnNetworkPolicyTable OBJECT-TYPE
    SYNTAX       SEQUENCE OF TNetworkPolicyEntry
    MAX-ACCESS   not-accessible
    STATUS       current
    DESCRIPTION  "  "
    ::= { tnNetworkObjects 1 }

tnNetworkPolicyEntry OBJECT-TYPE
    SYNTAX       TNetworkPolicyEntry
    MAX-ACCESS   not-accessible
    STATUS       current
    DESCRIPTION
        "Information about a particular Network Policy.

         network policy (1) is the default entry.

         Default Entry is created by the agent, other entries are
         created by user.

         Default Entry cannot be modified/deleted. The other
         entries are deleted by user.

         There is no StorageType object, entries have a presumed
         StorageType of nonVolatile.

         The default Egress FC entries are created as an action
         of setting the rowstatus."
    INDEX { tnSysSwitchId, tnNetworkPolicyIndex }
    ::= { tnNetworkPolicyTable 1 }

TNetworkPolicyEntry ::= SEQUENCE
    {
        tnNetworkPolicyIndex                       TNetworkPolicyID,
        tnNetworkPolicyRowStatus                   RowStatus,
        tnNetworkPolicyScope                       TItemScope,
        tnNetworkPolicyDescription                 TItemDescription,
        tnNetworkPolicyIngressDefaultActionFC      TFCName,
        tnNetworkPolicyIngressDefaultActionProfile TProfile,
        tnNetworkPolicyEgressRemark                TruthValue,
        tnNetworkPolicyLastChanged                 TimeStamp,
        tnNetworkPolicyIngressLerUseDscp           TruthValue,
        tnNetworkPolicyEgressRemarkDscp           TruthValue
    }

tnNetworkPolicyIndex OBJECT-TYPE
    SYNTAX       TNetworkPolicyID
    MAX-ACCESS   not-accessible
    STATUS       current
    DESCRIPTION  ""
    REFERENCE    ""
    ::= { tnNetworkPolicyEntry 1 }

tnNetworkPolicyRowStatus OBJECT-TYPE
    SYNTAX       RowStatus
    MAX-ACCESS   read-create
    STATUS       current
    DESCRIPTION  ""
    ::= { tnNetworkPolicyEntry 2 }

tnNetworkPolicyScope OBJECT-TYPE
    SYNTAX       TItemScope
    MAX-ACCESS   read-create
    STATUS       current
    DESCRIPTION  ""
    DEFVAL { template }
    ::= { tnNetworkPolicyEntry 5 }

tnNetworkPolicyDescription OBJECT-TYPE
    SYNTAX       TItemDescription
    MAX-ACCESS   read-create
    STATUS       current
    DESCRIPTION
        "tnNetworkPolicyDescription holds the description for this policy."
    DEFVAL { ''H }
    ::= { tnNetworkPolicyEntry 6 }

tnNetworkPolicyIngressDefaultActionFC OBJECT-TYPE
    SYNTAX       TFCName
    MAX-ACCESS   read-create
    STATUS       current
    DESCRIPTION
        "tnNetworkPolicyIngressDefaultActionFC specifies the default
         forwarding class to be used while classifying the ingress traffic."
    DEFVAL { 'be'H }
    ::= { tnNetworkPolicyEntry 7 }

tnNetworkPolicyIngressDefaultActionProfile OBJECT-TYPE
    SYNTAX       TProfile
    MAX-ACCESS   read-create
    STATUS       current
    DESCRIPTION
        "tnNetworkPolicyIngressDefaultActionProfile specifies the
         default profile to be used for the ingressing traffic."
    DEFVAL { out }
    ::= { tnNetworkPolicyEntry 8 }

tnNetworkPolicyEgressRemark OBJECT-TYPE
    SYNTAX       TruthValue
    MAX-ACCESS   read-create
    STATUS       current
    DESCRIPTION
        "The object tnNetworkPolicyEgressRemark specifies if the system
         will remark the egress packets or not."
    DEFVAL { false }
    ::= { tnNetworkPolicyEntry 9 }

tnNetworkPolicyLastChanged OBJECT-TYPE
    SYNTAX       TimeStamp
    MAX-ACCESS   read-only
    STATUS       current
    DESCRIPTION
        "Timestamp of last change to this row in tnNetworkPolicyTable."
    ::= { tnNetworkPolicyEntry 10 }

tnNetworkPolicyIngressLerUseDscp OBJECT-TYPE
    SYNTAX       TruthValue
    MAX-ACCESS   read-create
    STATUS       current
    DESCRIPTION
        "The object has significance only for the label edge routers
         which should honor the DSCP markings instead of the LSPEXP bits."
    DEFVAL { false }
    ::= { tnNetworkPolicyEntry 11 }

tnNetworkPolicyEgressRemarkDscp OBJECT-TYPE
    SYNTAX       TruthValue
    MAX-ACCESS   read-create
    STATUS       current
    DESCRIPTION
         "The value of tnNetworkPolicyEgressRemarkDscp object specifies
          whether DSCP bits in the internal IP header should be remarked.
          
          This object is valid only when tnNetworkPolicyEgressRemark is set to
          'true'."
    DEFVAL { false }
    ::= { tnNetworkPolicyEntry 12 }

--
-- network ingress policy dscp table
--

-- tnNetworkIngressDSCPTable OBJECT-TYPE
--     SYNTAX       SEQUENCE OF TNetworkIngressDSCPEntry
--     MAX-ACCESS   not-accessible
--     STATUS       current
--     DESCRIPTION  "  "
--     ::= { tnNetworkObjects 2 }
-- 
-- tnNetworkIngressDSCPEntry OBJECT-TYPE
--     SYNTAX       TNetworkIngressDSCPEntry
--     MAX-ACCESS   not-accessible
--     STATUS       current
--     DESCRIPTION
--         "Information about a dscp map for a network policy.
-- 
--          Some default entries are created by the agent for the
--          default network policy (1). These cannot be deleted or
--          modified. Other entries are created/deleted by user.
-- 
--          There is no StorageType object, entries have a presumed
--          StorageType of nonVolatile.
--         "
--     INDEX { tnSysSwitchId, tnNetworkPolicyIndex, tnNetworkIngressDSCP }
--     ::= { tnNetworkIngressDSCPTable 1 }
-- 
-- TNetworkIngressDSCPEntry ::= SEQUENCE
--     {
--         tnNetworkIngressDSCP            TDSCPName,
--         tnNetworkIngressDSCPRowStatus   RowStatus,
--         tnNetworkIngressDSCPFC          TFCName,
--         tnNetworkIngressDSCPProfile     TProfile,
--         tnNetworkIngressDSCPLastChanged TimeStamp
--     }
-- 
-- tnNetworkIngressDSCP OBJECT-TYPE
--     SYNTAX       TDSCPName
--     MAX-ACCESS   not-accessible
--     STATUS       current
--     DESCRIPTION  ""
--     ::= { tnNetworkIngressDSCPEntry 1 }
-- 
-- tnNetworkIngressDSCPRowStatus OBJECT-TYPE
--     SYNTAX       RowStatus
--     MAX-ACCESS   read-create
--     STATUS       current
--     DESCRIPTION ""
--     ::= { tnNetworkIngressDSCPEntry 2 }
-- 
-- tnNetworkIngressDSCPFC OBJECT-TYPE
--     SYNTAX       TFCName
--     MAX-ACCESS   read-create
--     STATUS       current
--     DESCRIPTION  ""
--     DEFVAL { ''H }
--     ::= { tnNetworkIngressDSCPEntry 3 }
-- 
-- tnNetworkIngressDSCPProfile OBJECT-TYPE
--     SYNTAX       TProfile
--     MAX-ACCESS   read-create
--     STATUS       current
--     DESCRIPTION
--         "there is no DEFVAL for this object.  it must be deliberately
--          set before activating the row."
--     ::= { tnNetworkIngressDSCPEntry 4 }
-- 
-- tnNetworkIngressDSCPLastChanged OBJECT-TYPE
--     SYNTAX       TimeStamp
--     MAX-ACCESS   read-only
--     STATUS       current
--     DESCRIPTION
--         "timestamp of last change to this row in tnNetworkIngressDSCPTable."
--     ::= { tnNetworkIngressDSCPEntry 5 }

--
-- network ingress policy dot1p table
--

tnNetworkIngressDot1pTable OBJECT-TYPE
    SYNTAX       SEQUENCE OF TNetworkIngressDot1pEntry
    MAX-ACCESS   not-accessible
    STATUS       current
    DESCRIPTION  " "
    ::= { tnNetworkObjects 3 }

tnNetworkIngressDot1pEntry OBJECT-TYPE
    SYNTAX       TNetworkIngressDot1pEntry
    MAX-ACCESS   not-accessible
    STATUS       current
    DESCRIPTION
        "Information about a dot1p map for a network policy.

         Some default entries are created by the agent for the
         default network policy (1). These cannot be deleted or
         modified. Other entries are created/deleted by user.

         There is no StorageType object, entries have a presumed
         StorageType of nonVolatile.
        "
    INDEX { tnSysSwitchId, tnNetworkPolicyIndex, tnNetworkIngressDot1pValue }
    ::= { tnNetworkIngressDot1pTable 1 }

TNetworkIngressDot1pEntry ::= SEQUENCE
    {
        tnNetworkIngressDot1pValue       Dot1PPriority,
        tnNetworkIngressDot1pRowStatus   RowStatus,
        tnNetworkIngressDot1pFC          TFCName,
        tnNetworkIngressDot1pProfile     TDEProfile,
        tnNetworkIngressDot1pLastChanged TimeStamp
    }

tnNetworkIngressDot1pValue OBJECT-TYPE
    SYNTAX       Dot1PPriority (0..7)
    MAX-ACCESS   not-accessible
    STATUS       current
    DESCRIPTION  ""
    ::= { tnNetworkIngressDot1pEntry 1 }

tnNetworkIngressDot1pRowStatus OBJECT-TYPE
    SYNTAX       RowStatus
    MAX-ACCESS   read-create
    STATUS       current
    DESCRIPTION  ""
    ::= { tnNetworkIngressDot1pEntry 2 }

tnNetworkIngressDot1pFC OBJECT-TYPE
    SYNTAX       TFCName
    MAX-ACCESS   read-create
    STATUS       current
    DESCRIPTION  ""
    DEFVAL { ''H }
    ::= { tnNetworkIngressDot1pEntry 3 }

tnNetworkIngressDot1pProfile OBJECT-TYPE
    SYNTAX       TDEProfile
    MAX-ACCESS   read-create
    STATUS       current
    DESCRIPTION
        "there is no DEFVAL for this object. It must be deliberately
         set before activating the row."
    ::= { tnNetworkIngressDot1pEntry 4 }

tnNetworkIngressDot1pLastChanged OBJECT-TYPE
    SYNTAX       TimeStamp
    MAX-ACCESS   read-only
    STATUS       current
    DESCRIPTION
        "timestamp of last change to this row in tnNetworkIngressDot1pTable."
    ::= { tnNetworkIngressDot1pEntry 5 }

--
-- network ingress policy lspexp table
--

 tnNetworkIngressLSPEXPTable OBJECT-TYPE
     SYNTAX       SEQUENCE OF TNetworkIngressLSPEXPEntry
     MAX-ACCESS   not-accessible
     STATUS       current
     DESCRIPTION  "  "
     ::= { tnNetworkObjects 4 }
 
 tnNetworkIngressLSPEXPEntry OBJECT-TYPE
     SYNTAX       TNetworkIngressLSPEXPEntry
     MAX-ACCESS   not-accessible
     STATUS       current
     DESCRIPTION
        "Information about LSP EXP mapping for a network policy.
 
          Some default entries are created by the agent for the
          default network policy (1). These cannot be deleted or
          modified. Other entries are created/deleted by user.
 
          There is no StorageType object, entries have a presumed
          StorageType of nonVolatile."
     INDEX { tnSysSwitchId, tnNetworkPolicyIndex, tnNetworkIngressLSPEXP }
     ::= { tnNetworkIngressLSPEXPTable 1 }
 
 TNetworkIngressLSPEXPEntry ::= SEQUENCE
     {
         tnNetworkIngressLSPEXP            TLspExpValue,
         tnNetworkIngressLSPEXPRowStatus   RowStatus,
         tnNetworkIngressLSPEXPFC          TFCName,
         tnNetworkIngressLSPEXPProfile     TProfile,
         tnNetworkIngressLSPEXPLastChanged TimeStamp
     }
 
 tnNetworkIngressLSPEXP OBJECT-TYPE
     SYNTAX       TLspExpValue (0..7)
     MAX-ACCESS   not-accessible
     STATUS       current
     DESCRIPTION  ""
     ::= { tnNetworkIngressLSPEXPEntry 1 }
 
 tnNetworkIngressLSPEXPRowStatus OBJECT-TYPE
     SYNTAX       RowStatus
     MAX-ACCESS   read-create
     STATUS       current
     DESCRIPTION  ""
     ::= { tnNetworkIngressLSPEXPEntry 2 }
 
 tnNetworkIngressLSPEXPFC OBJECT-TYPE
     SYNTAX       TFCName
     MAX-ACCESS   read-create
     STATUS       current
     DESCRIPTION  ""
     DEFVAL { ''H }
     ::= { tnNetworkIngressLSPEXPEntry 3 }
 
 tnNetworkIngressLSPEXPProfile OBJECT-TYPE
     SYNTAX       TProfile
     MAX-ACCESS   read-create
     STATUS       current
     DESCRIPTION
         "there is no DEFVAL for this object.  it must be deliberately
         set before activating the row."
     ::= { tnNetworkIngressLSPEXPEntry 4 }
 
 tnNetworkIngressLSPEXPLastChanged OBJECT-TYPE
     SYNTAX       TimeStamp
     MAX-ACCESS   read-only
     STATUS       current
     DESCRIPTION
         "timestamp of last change to this row in tnNetworkIngressLSPEXPTable."
     ::= { tnNetworkIngressLSPEXPEntry 5 }

--
-- network egress fc table
--

tnNetworkEgressFCTable OBJECT-TYPE
    SYNTAX       SEQUENCE OF TNetworkEgressFCEntry
    MAX-ACCESS   not-accessible
    STATUS       current
    DESCRIPTION
        "Information about all network policies' egress FC traffic disposition."
    ::= { tnNetworkObjects 7 }

tnNetworkEgressFCEntry OBJECT-TYPE
    SYNTAX       TNetworkEgressFCEntry
    MAX-ACCESS   not-accessible
    STATUS       current
    DESCRIPTION
        "Information about a particular network policy's egress
         per-forwarding-class traffic disposition.

         Entries are created/deleted as an action of creating/deleting
         a row in the tnNetworkPolicyTable.

         There is no StorageType object, entries have a presumed
         StorageType of nonVolatile."
    INDEX { tnSysSwitchId, tnNetworkPolicyIndex, tnNetworkEgressFCName }
    ::= { tnNetworkEgressFCTable 1 }

TNetworkEgressFCEntry ::= SEQUENCE
    {
        tnNetworkEgressFCName              TFCName,
        tnNetworkEgressFCDSCPInProfile     TDSCPNameOrEmpty,
        tnNetworkEgressFCDSCPOutProfile    TDSCPNameOrEmpty,
        tnNetworkEgressFCLspExpInProfile   TLspExpValue,
        tnNetworkEgressFCLspExpOutProfile  TLspExpValue,
        tnNetworkEgressFCDot1pInProfile    Dot1PPriority,
        tnNetworkEgressFCDot1pOutProfile   Dot1PPriority,
        tnNetworkEgressFCLastChanged       TimeStamp,
        tnNetworkEgressFCForceDEValue      TDEValue,
        tnNetworkEgressFCDEMark            TruthValue,
        tnNetworkEgressFCQGrpQueue         TEgressQueueId
    }

tnNetworkEgressFCName OBJECT-TYPE
    SYNTAX       TFCName
    MAX-ACCESS   not-accessible
    STATUS       current
    DESCRIPTION
        "the name of the forwarding class (FC)."
    ::= { tnNetworkEgressFCEntry 1 }

tnNetworkEgressFCDSCPInProfile OBJECT-TYPE
    SYNTAX       TDSCPNameOrEmpty
    MAX-ACCESS   read-write
    STATUS       current
    DESCRIPTION
        "the DSCP to use for in-profile traffic."
    ::= { tnNetworkEgressFCEntry 2 }

tnNetworkEgressFCDSCPOutProfile OBJECT-TYPE
    SYNTAX       TDSCPNameOrEmpty
    MAX-ACCESS   read-write
    STATUS       current
    DESCRIPTION
        "the DSCP to use for out-of-profile traffic."
    ::= { tnNetworkEgressFCEntry 3 }

tnNetworkEgressFCLspExpInProfile OBJECT-TYPE
    SYNTAX       TLspExpValue
    MAX-ACCESS   read-write
    STATUS       current
    DESCRIPTION
        "the lsp-exp value to use for in-profile traffic."
    ::= { tnNetworkEgressFCEntry 4 }

tnNetworkEgressFCLspExpOutProfile OBJECT-TYPE
    SYNTAX       TLspExpValue
    MAX-ACCESS   read-write
    STATUS       current
    DESCRIPTION
        "the lsp-exp value to use for out-of-profile traffic."
    ::= { tnNetworkEgressFCEntry 5 }

tnNetworkEgressFCDot1pInProfile OBJECT-TYPE
    SYNTAX       Dot1PPriority
    MAX-ACCESS   read-write
    STATUS       current
    DESCRIPTION
        "the Dot1p to use for in-profile traffic."
    ::= { tnNetworkEgressFCEntry 6 }

tnNetworkEgressFCDot1pOutProfile OBJECT-TYPE
    SYNTAX       Dot1PPriority
    MAX-ACCESS   read-write
    STATUS       current
    DESCRIPTION
        "the Dot1p to use for out-of-profile traffic."
    ::= { tnNetworkEgressFCEntry 7 }

tnNetworkEgressFCLastChanged OBJECT-TYPE
    SYNTAX       TimeStamp
    MAX-ACCESS   read-only
    STATUS       current
    DESCRIPTION
        "timestamp of last change to this row in tnNetworkEgressFCTable."
    ::= { tnNetworkEgressFCEntry 8 }

tnNetworkEgressFCForceDEValue OBJECT-TYPE
    SYNTAX       TDEValue
    MAX-ACCESS   read-write
    STATUS       current
    DESCRIPTION
        "The value of tnNetworkEgressFCForceDEValue specifies the DE value to set
        for network egress packets in this forwarding class regardless of
        profile status of the frames.

       An inconsistentValue error is returned if this object is set to any value
       other than '-1', when tnNetworkEgressFCDEMark object is set to
       'false'."
    DEFVAL { -1 }
    ::= { tnNetworkEgressFCEntry 9 }

tnNetworkEgressFCDEMark OBJECT-TYPE
    SYNTAX       TruthValue
    MAX-ACCESS   read-write
    STATUS       current
    DESCRIPTION
       "The value of tnNetworkEgressFCDEMark specifies whether to set DE value
       in the frames of this forwarding class.

       An inconsistentValue error is returned if this object is set to 'false'
       when tnNetworkEgressFCForceDEValue object is not set to '-1'."
    DEFVAL { false }
    ::= { tnNetworkEgressFCEntry 10 }

tnNetworkEgressFCQGrpQueue OBJECT-TYPE
    SYNTAX       TEgressQueueId
    MAX-ACCESS   read-write
    STATUS       current
    DESCRIPTION
        "tnNetworkEgressFCQGrpQueue specifies the specific queue from queue-group
        TIMETRA-VRTR-MIB::vRtrIfQosQGrp to be used for packets in this
        forwarding class."
    DEFVAL { 0 }
    ::= { tnNetworkEgressFCEntry 11 }

--
-- Dummy Scalars
--
tnNetworkScalar1 OBJECT-TYPE
    SYNTAX      Unsigned32
    MAX-ACCESS  read-only
    STATUS      current
    DESCRIPTION
        "A dummy scalar that satisfies a SNMP get request quickly when
         there is no 11QPE24 card provisioned.  Otherwise, it has to
         traverse the remaining 11QPE24 MIB to get to the next applicable
         item."
    ::= { tnNetworkObjects 101 }

tnNetworkScalar2 OBJECT-TYPE
    SYNTAX      Unsigned32
    MAX-ACCESS  read-only
    STATUS      current
    DESCRIPTION
        ""
    ::= { tnNetworkObjects 102 }

--
-- network-queue policy table
--

tnNetworkQueuePolicyTable OBJECT-TYPE
    SYNTAX       SEQUENCE OF TNetworkQueuePolicyEntry
    MAX-ACCESS   not-accessible
    STATUS       current
    DESCRIPTION  "  "
    ::= { tnNetworkQueueObjects 1 }

tnNetworkQueuePolicyEntry OBJECT-TYPE
    SYNTAX       TNetworkQueuePolicyEntry
    MAX-ACCESS   not-accessible
    STATUS       current
    DESCRIPTION  ""
    INDEX { tnSysSwitchId, tnNetworkQueuePolicy }
    ::= { tnNetworkQueuePolicyTable 1 }

TNetworkQueuePolicyEntry ::= SEQUENCE
    {
        tnNetworkQueuePolicy                TNamedItem,
        tnNetworkQueuePolicyRowStatus       RowStatus,
        tnNetworkQueuePolicyDescription     TItemDescription,
        tnNetworkQueuePolicyLastChanged     TimeStamp
    }

tnNetworkQueuePolicy OBJECT-TYPE
    SYNTAX       TNamedItem
    MAX-ACCESS   not-accessible
    STATUS       current
    DESCRIPTION  ""
    ::= { tnNetworkQueuePolicyEntry 1 }

tnNetworkQueuePolicyRowStatus OBJECT-TYPE
    SYNTAX       RowStatus
    MAX-ACCESS   read-create
    STATUS       current
    DESCRIPTION  ""
    ::= { tnNetworkQueuePolicyEntry 2 }

tnNetworkQueuePolicyDescription OBJECT-TYPE
    SYNTAX       TItemDescription
    MAX-ACCESS   read-create
    STATUS       current
    DESCRIPTION  ""
    DEFVAL { ''H }
    ::= { tnNetworkQueuePolicyEntry 3 }

tnNetworkQueuePolicyLastChanged OBJECT-TYPE
    SYNTAX       TimeStamp
    MAX-ACCESS   read-only
    STATUS       current
    DESCRIPTION  ""
    ::= { tnNetworkQueuePolicyEntry 8 }

--
-- network-queue policy queue table
--

tnNetworkQueueTable OBJECT-TYPE
    SYNTAX       SEQUENCE OF TNetworkQueueEntry
    MAX-ACCESS   not-accessible
    STATUS       current
    DESCRIPTION  ""
    ::= { tnNetworkQueueObjects 2 }

tnNetworkQueueEntry OBJECT-TYPE
    SYNTAX       TNetworkQueueEntry
    MAX-ACCESS   not-accessible
    STATUS       current
    DESCRIPTION  ""
    INDEX { tnSysSwitchId, tnNetworkQueuePolicy, tnNetworkQueue }
    ::= { tnNetworkQueueTable 1 }

TNetworkQueueEntry ::= SEQUENCE
    {
        tnNetworkQueue                 TQueueId,
        tnNetworkQueueRowStatus        RowStatus,
        tnNetworkQueuePoolName         TNamedItemOrEmpty,
        tnNetworkQueueParent           TNamedItemOrEmpty,
        tnNetworkQueueLevel            TLevel,
        tnNetworkQueueWeight           TWeight,
        tnNetworkQueueCIRLevel         TLevelOrDefault,
        tnNetworkQueueCIRWeight        TWeight,
        tnNetworkQueueMCast            TruthValue,
        tnNetworkQueueExpedite         INTEGER,
        tnNetworkQueueCIR              TRatePercent,
        tnNetworkQueuePIR              TPIRRatePercent,
        tnNetworkQueueCBS              TBurstHundredthsOfPercent,
        tnNetworkQueueMBS              TBurstHundredthsOfPercent,
        tnNetworkQueueHiPrioOnly       TBurstPercentOrDefault,
        tnNetworkQueueLastChanged      TimeStamp,
        tnNetworkQueueUsePortParent    TruthValue,
        tnNetworkQueuePortLvl          TLevel,
        tnNetworkQueuePortWght         TWeight,
        tnNetworkQueuePortCIRLvl       TLevelOrDefault,
        tnNetworkQueuePortCIRWght      TWeight,
        tnNetworkQueuePortAvgOverhead  Unsigned32,
        tnNetworkQueueCIRAdaptation    TAdaptationRule,
        tnNetworkQueuePIRAdaptation    TAdaptationRule
    }

tnNetworkQueue OBJECT-TYPE
    SYNTAX       TQueueId (1..16)
    MAX-ACCESS   not-accessible
    STATUS       current
    DESCRIPTION
        "The queue ID is used as the secondary index to the table entry."
    ::= { tnNetworkQueueEntry 1 }

tnNetworkQueueRowStatus OBJECT-TYPE
    SYNTAX       RowStatus
    MAX-ACCESS   read-create
    STATUS       current
    DESCRIPTION
        "Row Status of the entry. This allows creation/deletion of rows in this
         table."
    ::= { tnNetworkQueueEntry 2 }

tnNetworkQueuePoolName OBJECT-TYPE
    SYNTAX       TNamedItemOrEmpty
    MAX-ACCESS   read-create
    STATUS       current
    DESCRIPTION
        "The tnNetworkQueuePoolName specifies the pool that is associated
         with this network queue. If tnNetworkQueuePoolName is empty, no pool
         has been associated with the queue."
    DEFVAL { ''H }
    ::= { tnNetworkQueueEntry 3 }

tnNetworkQueueParent OBJECT-TYPE
    SYNTAX       TNamedItemOrEmpty
    MAX-ACCESS   read-create
    STATUS       current
    DESCRIPTION
        "The scheduler to which this queue would be feeding to."
    DEFVAL { ''H }
    ::= { tnNetworkQueueEntry 4 }

tnNetworkQueueLevel OBJECT-TYPE
    SYNTAX       TLevel
    MAX-ACCESS   read-create
    STATUS       current
    DESCRIPTION
        "This specifies the level of priority while feeding to the parent."
    DEFVAL { 1 }
    ::= { tnNetworkQueueEntry 5 }

tnNetworkQueueWeight OBJECT-TYPE
    SYNTAX       TWeight
    MAX-ACCESS   read-create
    STATUS       current
    DESCRIPTION
        "The weight that needs to be used by the scheduler to which this queue
         would be feeding to."
    DEFVAL { 1 }
    ::= { tnNetworkQueueEntry 6 }

tnNetworkQueueCIRLevel OBJECT-TYPE
    SYNTAX       TLevelOrDefault
    MAX-ACCESS   read-create
    STATUS       current
    DESCRIPTION
        "This specifies the level of priority while feeding to the parent.
         The level '0' means treat all offered load for this queue as for
         the above CIR traffic."
    DEFVAL { 0 }
    ::= { tnNetworkQueueEntry 7 }

tnNetworkQueueCIRWeight OBJECT-TYPE
    SYNTAX       TWeight
    MAX-ACCESS   read-create
    STATUS       current
    DESCRIPTION
        "The weight that needs to be used until the committed rate by the
         scheduler to which this queue would be feeding to."
    DEFVAL { 1 }
    ::= { tnNetworkQueueEntry 8 }

tnNetworkQueueMCast OBJECT-TYPE
    SYNTAX       TruthValue
    MAX-ACCESS   read-create
    STATUS       current
    DESCRIPTION
        "This object specifies if this is a multicast queue or not."
    DEFVAL { false }
    ::= { tnNetworkQueueEntry 9 }

tnNetworkQueueExpedite OBJECT-TYPE
    SYNTAX       INTEGER {
                     expedited     (1),
                     auto-expedited(2),
                     non-expedited (3)
                 }
    MAX-ACCESS   read-create
    STATUS       current
    DESCRIPTION
        "tnNetworkQueueExpedite specifies the priority that this queue should
         be assigned by the hardware level schedulers.

         The value 'auto-expedited' implies that this attribute should be
         dynamically updated by looking at the forwarding classes mapping
         into this queue. In such a case the queue is treated as
         'non-expedited' if there is even a single non-expedited forwarding
         class using this queue.

         This attribute is associated with the queue at the time of creation
         and cannot be modified thereafter."
    DEFVAL { auto-expedited }
    ::= { tnNetworkQueueEntry 10 }

tnNetworkQueueCIR OBJECT-TYPE
    SYNTAX       TRatePercent
    MAX-ACCESS   read-create
    STATUS       current
    DESCRIPTION
        "The percentage of max rate allowed."
    DEFVAL { 0 }
    ::= { tnNetworkQueueEntry 11 }

tnNetworkQueuePIR OBJECT-TYPE
    SYNTAX       TPIRRatePercent
    MAX-ACCESS   read-create
    STATUS       current
    DESCRIPTION
        "The percentage of max rate allowed."
    DEFVAL { 100 }
    ::= { tnNetworkQueueEntry 12 }

tnNetworkQueueCBS OBJECT-TYPE
    SYNTAX       TBurstHundredthsOfPercent
    UNITS        "Hundredths of a percent"
    MAX-ACCESS   read-create
    STATUS       current
    DESCRIPTION
        "The percentage of reserved buffer space for the queue, 
         defined to two decimal places."
    DEFVAL { 100 }
    ::= { tnNetworkQueueEntry 13 }

tnNetworkQueueMBS OBJECT-TYPE
    SYNTAX       TBurstHundredthsOfPercent
    UNITS        "Hundredths of a percent"
    MAX-ACCESS   read-create
    STATUS       current
    DESCRIPTION
        "The percentage of reserved buffer space for the queue, 
         defined to two decimal places."
    DEFVAL { 10000 }
    ::= { tnNetworkQueueEntry 14 }

tnNetworkQueueHiPrioOnly OBJECT-TYPE
    SYNTAX       TBurstPercentOrDefault
    MAX-ACCESS   read-create
    STATUS       current
    DESCRIPTION
        "The percentage of buffer space for the queue, used
         exclusively by high priority packets."
    DEFVAL { -1 }
    ::= { tnNetworkQueueEntry 15 }

tnNetworkQueueLastChanged OBJECT-TYPE
    SYNTAX       TimeStamp
    MAX-ACCESS   read-only
    STATUS       current
    DESCRIPTION
        "The value of the object tnNetworkQueueLastChanged indicates the 
         timestamp of last change to this row in tnNetworkQueueTable."
    ::= { tnNetworkQueueEntry 16 }

tnNetworkQueueUsePortParent  OBJECT-TYPE
    SYNTAX      TruthValue
    MAX-ACCESS  read-create
    STATUS      current
    DESCRIPTION
        "The value of the object tnNetworkQueueUsePortParent specifies
         whether this queue is parented by a port-level scheduler. When
         the value is 'true', this network queue is parented by a 
         port-level scheduler."
    DEFVAL      { false }
    ::= { tnNetworkQueueEntry 17 }

tnNetworkQueuePortLvl        OBJECT-TYPE
    SYNTAX       TLevel
    MAX-ACCESS  read-create
    STATUS      current
    DESCRIPTION
        "The value of the object tnNetworkQueuePortLvl specifies the
         port priority this queue will use to receive bandwidth from
         the port-level scheduler for its above-cir offered load."
    DEFVAL      { 1 }
    ::= { tnNetworkQueueEntry 18 }

tnNetworkQueuePortWght       OBJECT-TYPE
    SYNTAX      TWeight
    MAX-ACCESS  read-create
    STATUS      current
    DESCRIPTION
        "The value of the object tnNetworkQueuePortWght specifies the
         weight this queue will use to receive bandwidth from the
         port-level scheduler for its above-cir offered load."
    DEFVAL      { 1 }
    ::= { tnNetworkQueueEntry 19 }

tnNetworkQueuePortCIRLvl        OBJECT-TYPE
    SYNTAX      TLevelOrDefault
    MAX-ACCESS  read-create
    STATUS      current
    DESCRIPTION
        "The value of the object tnNetworkQueuePortCIRLvl specifies the
         port priority this queue will use to receive bandwidth from
         the port-level scheduler for its within-cir offered load."
    DEFVAL      { 0 }
    ::= { tnNetworkQueueEntry 20 }

tnNetworkQueuePortCIRWght       OBJECT-TYPE
    SYNTAX      TWeight
    MAX-ACCESS  read-create
    STATUS      current
    DESCRIPTION
        "The value of the object tnNetworkQueuePortCIRWght specifies the
         weight this queue will use to receive bandwidth from the
         port-level scheduler for its within-cir offered load."
    DEFVAL      { 0 }
    ::= { tnNetworkQueueEntry 21 }

tnNetworkQueuePortAvgOverhead    OBJECT-TYPE
    SYNTAX      Unsigned32 (0..10000)
    UNITS       "Hundredths of a percent"
    MAX-ACCESS  read-create
    STATUS      current
    DESCRIPTION
        "The value of tnNetworkQueuePortAvgOverhead specifies the 
         encapsulation overhead, in hundredths of a percent,  used to 
         translate packet-based rate to frame-based rate and vice versa."
    DEFVAL      { 0 }
    ::= { tnNetworkQueueEntry 22 }

tnNetworkQueueCIRAdaptation       OBJECT-TYPE
    SYNTAX      TAdaptationRule
    MAX-ACCESS  read-create
    STATUS      current
    DESCRIPTION
        "The value of tnNetworkQueueCIRAdaptation specifies the adaptation rule
         to be used while computing the operational CIR value. The adaptation
         rule specifies the rules to compute the operational value while
         maintaining the minimum offset."
    DEFVAL      { closest }
    ::= { tnNetworkQueueEntry 23 }

tnNetworkQueuePIRAdaptation       OBJECT-TYPE
    SYNTAX      TAdaptationRule
    MAX-ACCESS  read-create
    STATUS      current
    DESCRIPTION
        "The value of tnNetworkQueuePIRAdaptation specifies the adaptation rule
         to be used while computing the operational PIR value. The adaptation
         rule specifies the rules to compute the operational value while
         maintaining the minimum offset."
    DEFVAL      { closest }
    ::= { tnNetworkQueueEntry 24 }

--
-- network-queue policy fc table
--

-- tnNetworkQueueFCTable OBJECT-TYPE
--     SYNTAX       SEQUENCE OF TNetworkQueueFCEntry
--     MAX-ACCESS   not-accessible
--     STATUS       current
--     DESCRIPTION  ""
--     ::= { tnNetworkQueueObjects 3 }
-- 
-- tnNetworkQueueFCEntry OBJECT-TYPE
--     SYNTAX       TNetworkQueueFCEntry
--     MAX-ACCESS   not-accessible
--     STATUS       current
--     DESCRIPTION  ""
--     INDEX { tnSysSwitchId, tnNetworkQueuePolicy, tnNetworkQueueFCName }
--     ::= { tnNetworkQueueFCTable 1 }
-- 
-- TNetworkQueueFCEntry ::= SEQUENCE
--     {
--         tnNetworkQueueFCName          TFCName,
--         tnNetworkQueueFCRowStatus     RowStatus,
--         tnNetworkQueueFC              TQueueId,
--         tnNetworkQueueFCMCast         TQueueId,
--         tnNetworkQueueFCLastChanged   TimeStamp
--     }
-- 
-- tnNetworkQueueFCName OBJECT-TYPE
--     SYNTAX       TFCName
--     MAX-ACCESS   not-accessible
--     STATUS       current
--     DESCRIPTION
--         "Forwarding class name."
--     ::= { tnNetworkQueueFCEntry 1 }
-- 
-- tnNetworkQueueFCRowStatus OBJECT-TYPE
--     SYNTAX       RowStatus
--     MAX-ACCESS   read-create
--     STATUS       current
--     DESCRIPTION
--         "Row Status for this queue."
--     ::= { tnNetworkQueueFCEntry 2 }
-- 
-- tnNetworkQueueFC OBJECT-TYPE
--     SYNTAX       TQueueId (1..16)
--     MAX-ACCESS   read-create
--     STATUS       current
--     DESCRIPTION
--         "The specific queue to be used for packets in this forwarding class."
--     DEFVAL { 1 }
--     ::= { tnNetworkQueueFCEntry 3 }
-- 
-- tnNetworkQueueFCMCast OBJECT-TYPE
--     SYNTAX       TQueueId (1..16)
--     MAX-ACCESS   read-create
--     STATUS       current
--     DESCRIPTION
--         "The specific multicast queue to be used for packets in this forwarding
--          class. The queue is used only for specific entities and will be
--          ignored wherever it is irrelevant."
--     DEFVAL { 9 }
--     ::= { tnNetworkQueueFCEntry 4 }
-- 
-- tnNetworkQueueFCLastChanged OBJECT-TYPE
--     SYNTAX       TimeStamp
--     MAX-ACCESS   read-only
--     STATUS       current
--     DESCRIPTION
--         "timestamp of last change to this row in tnNetworkQueueFCTable."
--     ::= { tnNetworkQueueFCEntry 7 }

--
-- shared queue policy table
--

-- tnSharedQueuePolicyTable OBJECT-TYPE
--     SYNTAX       SEQUENCE OF TSharedQueuePolicyEntry
--     MAX-ACCESS   not-accessible
--     STATUS       current
--     DESCRIPTION
--         "Defines the Nokia 7x50 SR series Shared Queue Policy Table
--          for providing, via SNMP, the capability of defining the queue
--          policies.
-- 
--          tnSharedQueuePolicyTable holds a list of all shared queue
--          policies in the managed system. Shared queue policies should
--          exist in this table before being referenced elsewhere.
-- 
--          There is a default queue policy 'default' created by the
--          agent and can not be deleted."
--     ::= { tnSharedQueueObjects 1 }
-- 
-- tnSharedQueuePolicyEntry OBJECT-TYPE
--     SYNTAX       TSharedQueuePolicyEntry
--     MAX-ACCESS   not-accessible
--     STATUS       current
--     DESCRIPTION
--         "Defines an entry in the tnSharedQueuePolicyTable. Entries are
--          created and deleted in this table by SNMP sets to
--          tnSharedQueuePolicyRowStatus."
--     INDEX { tnSysSwitchId, tnSharedQueuePolicy }
--     ::= { tnSharedQueuePolicyTable 1 }
-- 
-- TSharedQueuePolicyEntry ::= SEQUENCE
--     {
--         tnSharedQueuePolicy                TNamedItem,
--         tnSharedQueuePolicyRowStatus       RowStatus,
--         tnSharedQueuePolicyLastChanged     TimeStamp,
--         tnSharedQueuePolicyDescription     TItemDescription
--     }
-- 
-- tnSharedQueuePolicy OBJECT-TYPE
--     SYNTAX       TNamedItem
--     MAX-ACCESS   not-accessible
--     STATUS       current
--     DESCRIPTION
--         "tnSharedQueuePolicy serves as an index and uniquely identifies
--          a queue policy in the managed system."
--     ::= { tnSharedQueuePolicyEntry 1 }
-- 
-- tnSharedQueuePolicyRowStatus OBJECT-TYPE
--     SYNTAX       RowStatus
--     MAX-ACCESS   read-create
--     STATUS       current
--     DESCRIPTION
--         "tnSharedQueuePolicyRowStatus allows entries to be created and
--          deleted in the tnSharedQueuePolicyTable. The deletion of an
--          entry in this table will fail if the action is performed on the
--          default policy or the policy is being used within the system."
--     REFERENCE
--         "See definition of RowStatus in RFC 2579, 'Textual Conventions
--          for SMIv2.'"
--     ::= { tnSharedQueuePolicyEntry 2 }
-- 
-- tnSharedQueuePolicyLastChanged OBJECT-TYPE
--     SYNTAX       TimeStamp
--     MAX-ACCESS   read-only
--     STATUS       current
--     DESCRIPTION
--         "tnSharedQueuePolicyLastChanged indicates the value of sysUpTime
--          when the queue policy entry was last modified."
--     ::= { tnSharedQueuePolicyEntry 3 }
-- 
-- tnSharedQueuePolicyDescription OBJECT-TYPE
--     SYNTAX       TItemDescription
--     MAX-ACCESS   read-create
--     STATUS       current
--     DESCRIPTION
--         "tnSharedQueuePolicyDescription specifies the user provided
--          description string for this queue policy entry. It can consist
--          of only the printable, seven-bit ASCII characters."
--     DEFVAL { ''H }
--     ::= { tnSharedQueuePolicyEntry 4 }

--
-- queue policy queue table
--

-- tnSharedQueueTable OBJECT-TYPE
--     SYNTAX       SEQUENCE OF TSharedQueueEntry
--     MAX-ACCESS   not-accessible
--     STATUS       current
--     DESCRIPTION
--         "Defines the Nokia 7x50 SR series Shared Queue Table for
--          providing, via SNMP, the capability of defining the queues for
--          the shared queue policies existing in the tnSharedQueuePolicyTable.
-- 
--          tnSharedQueueTable holds a list of all the shared queues in the
--          managed system defined for the queue policies. Queues should exist
--          in this table before being referenced by the forwarding class
--          mappings within the queue policy as defined in the
--          tnSharedQueueFCTable.
-- 
--          There is a default queue with the queue identifier '1' which
--          gets created automatically when a new queue policy is created."
--     ::= { tnSharedQueueObjects 2 }
-- 
-- tnSharedQueueEntry OBJECT-TYPE
--     SYNTAX       TSharedQueueEntry
--     MAX-ACCESS   not-accessible
--     STATUS       current
--     DESCRIPTION
--         "Defines an entry in the tnSharedQueueTable.
-- 
--          Entries are created/deleted in this table by SNMP sets to
--          tnSharedQueueRowStatus.
-- 
--          An exception to this rule is the default queue. The default queue
--          is created/deleted as a result of the creation/deletion of a new
--          queue policy in the tnSharedQueuePolicyTable."
--     INDEX { tnSysSwitchId, tnSharedQueuePolicy, tnSharedQueueId }
--     ::= { tnSharedQueueTable 1 }
-- 
-- TSharedQueueEntry ::= SEQUENCE
--     {
--         tnSharedQueueId               TQueueId,
--         tnSharedQueueRowStatus        RowStatus,
--         tnSharedQueueLastChanged      TimeStamp, 
--         tnSharedQueuePoolName         TNamedItemOrEmpty,
--         tnSharedQueueParent           TNamedItemOrEmpty,
--         tnSharedQueueLevel            TLevel,
--         tnSharedQueueWeight           TWeight,
--         tnSharedQueueCIRLevel         TLevelOrDefault,
--         tnSharedQueueCIRWeight        TWeight,
--         tnSharedQueueExpedite         INTEGER,
--         tnSharedQueueCIR              TRatePercent,
--         tnSharedQueuePIR              TPIRRatePercent,
--         tnSharedQueueCBS              TBurstPercent,
--         tnSharedQueueMBS              TBurstPercent,
--         tnSharedQueueHiPrioOnly       TBurstPercentOrDefault,
--         tnSharedQueueIsMultipoint     TruthValue
--     }
-- 
-- tnSharedQueueId OBJECT-TYPE
--     SYNTAX       TQueueId (1..32)
--     MAX-ACCESS   not-accessible
--     STATUS       current
--     DESCRIPTION
--         "tnSharedQueueId serves as the secondary index. When used in
--          conjunction with tnSharedQueuePolicy, it uniquely identifies
--          a shared queue in the managed system."
--     ::= { tnSharedQueueEntry 1 }
-- 
-- tnSharedQueueRowStatus OBJECT-TYPE
--     SYNTAX       RowStatus
--     MAX-ACCESS   read-create
--     STATUS       current
--     DESCRIPTION
--         "tnSharedQueueRowStatus allows entries to be created and deleted
--          in the tnSharedQueueTable. The deletion of an entry in this table
--          will fail if the action is performed on the default queue or if
--          the queue is being referenced by a forwarding class mapping in
--          the queue policy."
--     REFERENCE
--         "See definition of RowStatus in RFC 2579, 'Textual Conventions for
--          SMIv2.'"
--     ::= { tnSharedQueueEntry 2 }
-- 
-- tnSharedQueueLastChanged OBJECT-TYPE
--     SYNTAX       TimeStamp
--     MAX-ACCESS   read-only
--     STATUS       current
--     DESCRIPTION
--         "tnSharedQueueLastChanged indicates the value of sysUpTime when
--          the queue entry was last modified."
--     ::= { tnSharedQueueEntry 3 }
-- 
-- tnSharedQueuePoolName OBJECT-TYPE
--     SYNTAX       TNamedItemOrEmpty
--     MAX-ACCESS   read-create
--     STATUS       current
--     DESCRIPTION
--         "tnSharedQueuePoolName specifies the pool from which the queue
--          should be allocating its buffer. By default it will share the
--          default pool being used by the entity where the queue is
--          instantiated."
--     DEFVAL { ''H }
--     ::= { tnSharedQueueEntry 4 }
-- 
-- tnSharedQueueParent OBJECT-TYPE
--     SYNTAX       TNamedItemOrEmpty
--     MAX-ACCESS   read-create
--     STATUS       current
--     DESCRIPTION
--         "tnSharedQueueParent specifies the scheduler to which this queue
--          should be feeding into. By default there would be no parent for
--          the queue and it will be controlled by the entity where the
--          queue is instantiated."
--     DEFVAL { ''H }
--     ::= { tnSharedQueueEntry 5 }
-- 
-- tnSharedQueueLevel OBJECT-TYPE
--     SYNTAX       TLevel
--     MAX-ACCESS   read-create
--     STATUS       current
--     DESCRIPTION
--         "tnSharedQueueLevel specifies the level of priority to be used
--          by the parent entity to compute the priority of this queue
--          when the traffic is exceeding the committed rate."
--     DEFVAL { 1 }
--     ::= { tnSharedQueueEntry 6 }
-- 
-- tnSharedQueueWeight OBJECT-TYPE
--     SYNTAX       TWeight
--     MAX-ACCESS   read-create
--     STATUS       current
--     DESCRIPTION
--         "tnSharedQueueWeight specifies the weight that this queue should
--          be assigned by the parent among all the entities feeding into
--          the parent with the same level when the traffic is exceeding the
--          committed rate."
--     DEFVAL { 1 }
--     ::= { tnSharedQueueEntry 7 }
-- 
-- tnSharedQueueCIRLevel OBJECT-TYPE
--     SYNTAX       TLevelOrDefault
--     MAX-ACCESS   read-create
--     STATUS       current
--     DESCRIPTION
--         "tnSharedQueueCIRLevel specifies the level of priority to be used
--          by the parent entity to compute the priority of this queue when
--          the traffic is conforming to the committed rate.
-- 
--          The level '0' means treat all offered load for this queue same
--          as the load which is exceeding the committed rate."
--     DEFVAL { 0 }
--     ::= { tnSharedQueueEntry 8 }
-- 
-- tnSharedQueueCIRWeight OBJECT-TYPE
--     SYNTAX       TWeight
--     MAX-ACCESS   read-create
--     STATUS       current
--     DESCRIPTION
--         "tnSharedQueueCIRWeight specifies the weight that this queue should
--          be assigned by the parent among all the entities feeding into the
--          parent with the same level when the traffic is conforming to the
--          committed rate."
--     DEFVAL { 1 }
--     ::= { tnSharedQueueEntry 9 }
-- 
-- tnSharedQueueExpedite OBJECT-TYPE
--     SYNTAX       INTEGER {
--                      expedited     (1),
--                      auto-expedited(2),
--                      non-expedited (3)
--                  }
--     MAX-ACCESS   read-create
--     STATUS       current
--     DESCRIPTION
--         "tnSharedQueueExpedite specifies the priority that this queue should
--          be assigned by the hardware level schedulers.
-- 
--          The value 'auto-expedited' implies that this attribute should be
--          dynamically updated by looking at the forwarding classes mapping
--          into this queue. In such a case the queue is treated as
--          'non-expedited' if there is even a single non-expedited forwarding
--          class using this queue."
--     DEFVAL { auto-expedited }
--     ::= { tnSharedQueueEntry 10 }
-- 
-- tnSharedQueueCIR OBJECT-TYPE
--     SYNTAX       TRatePercent
--     MAX-ACCESS   read-create
--     STATUS       current
--     DESCRIPTION
--         "tnSharedQueueCIR specifies the committed rate as a percentage of
--          maximum rate for this queue."
--     DEFVAL { 0 }
--     ::= { tnSharedQueueEntry 11 }
-- 
-- tnSharedQueuePIR OBJECT-TYPE
--     SYNTAX       TPIRRatePercent
--     MAX-ACCESS   read-create
--     STATUS       current
--     DESCRIPTION
--         "tnSharedQueuePIR specifies the peak rate as a percentage of
--          maximum rate for this queue."
--     DEFVAL { 100 }
--     ::= { tnSharedQueueEntry 12 }
-- 
-- tnSharedQueueCBS OBJECT-TYPE
--     SYNTAX       TBurstPercent
--     MAX-ACCESS   read-create
--     STATUS       current
--     DESCRIPTION
--         "tnSharedQueueCBS specifies the committed burst size as a percentage
--          of maximum reserved buffer space for the queue."
--     DEFVAL { 0 }
--     ::= { tnSharedQueueEntry 13 }
-- 
-- tnSharedQueueMBS OBJECT-TYPE
--     SYNTAX       TBurstPercent
--     MAX-ACCESS   read-create
--     STATUS       current
--     DESCRIPTION
--         "tnSharedQueueMBS specifies the maximum burst size as a percentage
--          of maximum reserved buffer space for the queue."
--     DEFVAL { 100 }
--     ::= { tnSharedQueueEntry 14 }
-- 
-- tnSharedQueueHiPrioOnly OBJECT-TYPE
--     SYNTAX       TBurstPercentOrDefault
--     MAX-ACCESS   read-create
--     STATUS       current
--     DESCRIPTION
--         "tnSharedQueueHiPrioOnly specifies the percentage of buffer space
--          to be exclusively by high priority packets as a percentage of
--          maximum reserved buffer space for the queue."
--     DEFVAL { -1 }
--     ::= { tnSharedQueueEntry 15 }
-- 
-- tnSharedQueueIsMultipoint        OBJECT-TYPE
--     SYNTAX      TruthValue
--     MAX-ACCESS  read-create
--     STATUS      current
--     DESCRIPTION
--         "The value of tnSharedQueueIsMultipoint specifies whether this
--         shared queue is a multipoint-shared queue.
--         
--         This object can only be modified at row creation time; any attempt to 
--         set it after creation is silently ignored."
--     DEFVAL { false }
--     ::= { tnSharedQueueEntry 16 }

--
-- queue policy fc table
--

-- tnSharedQueueFCTable OBJECT-TYPE
--     SYNTAX       SEQUENCE OF TSharedQueueFCEntry
--     MAX-ACCESS   not-accessible
--     STATUS       current
--     DESCRIPTION
--         "Defines the Nokia 7x50 SR series forwarding class to
--          shared queue mapping table for providing, via SNMP, the
--          capability of defining the forwarding class to shared queue
--          mapping for the queue policies existing in the
--          tnSharedQueuePolicyTable.
-- 
--          tnSharedQueueFCTable holds a list of forwarding class to
--          queue mappings managed system defined for the queue policies.
--          The forwarding classes which are not existing in this table
--          should use the default shared queue for this policy."
--     ::= { tnSharedQueueObjects 3 }
-- 
-- tnSharedQueueFCEntry OBJECT-TYPE
--     SYNTAX       TSharedQueueFCEntry
--     MAX-ACCESS   not-accessible
--     STATUS       current
--     DESCRIPTION
--         "Defines an entry in the tnSharedQueueFCTable.
-- 
--          Entries are created/deleted in this table by SNMP sets to
--          tnSharedQueueFCRowStatus."
--     INDEX { tnSysSwitchId, tnSharedQueuePolicy, tnSharedQueueFCName }
--     ::= { tnSharedQueueFCTable 1 }
-- 
-- TSharedQueueFCEntry ::= SEQUENCE
--     {
--         tnSharedQueueFCName          TFCName,
--         tnSharedQueueFCRowStatus     RowStatus,
--         tnSharedQueueFCLastChanged   TimeStamp,
--         tnSharedQueueFCQueue         TQueueId,
--         tnSharedQueueFCMCastQueue    TQueueId,
--         tnSharedQueueFCBCastQueue    TQueueId,
--         tnSharedQueueFCUnknownQueue  TQueueId
--     }
-- 
-- tnSharedQueueFCName OBJECT-TYPE
--     SYNTAX       TFCName
--     MAX-ACCESS   not-accessible
--     STATUS       current
--     DESCRIPTION
--         "tnSharedQueueFCName serves as the secondary index. When used in
--          conjunction with tnSharedQueuePolicy, it uniquely identifies a
--          forwarding class to queue mapping in the managed system."
--     ::= { tnSharedQueueFCEntry 1 }
-- 
-- tnSharedQueueFCRowStatus OBJECT-TYPE
--     SYNTAX       RowStatus
--     MAX-ACCESS   read-create
--     STATUS       current
--     DESCRIPTION
--         "tnSharedQueueFCRowStatus allows entries to be created and
--          deleted in the tnSharedQueueFCTable. Deletion of an entry from
--          this table will cause the forwarding class to use the default
--          mapping."
--     REFERENCE
--         "See definition of RowStatus in RFC 2579, 'Textual Conventions
--          for SMIv2.'"
--     ::= { tnSharedQueueFCEntry 2 }
-- 
-- tnSharedQueueFCLastChanged OBJECT-TYPE
--     SYNTAX       TimeStamp
--     MAX-ACCESS   read-only
--     STATUS       current
--     DESCRIPTION
--         "tnSharedQueueFCLastChanged indicates the value of sysUpTime
--          when the forwarding class to queue mapping entry was last
--          modified."
--     ::= { tnSharedQueueFCEntry 3 }
-- 
-- tnSharedQueueFCQueue OBJECT-TYPE
--     SYNTAX       TQueueId (1..8)
--     MAX-ACCESS   read-create
--     STATUS       current
--     DESCRIPTION
--         "tnSharedQueueFCQueue specifies the logical queue that the
--          traffic classified into this forwarding class should use."
--     DEFVAL { 1 }
--     ::= { tnSharedQueueFCEntry 4 }
-- 
-- tnSharedQueueFCMCastQueue OBJECT-TYPE
--     SYNTAX       TQueueId (9..16)
--     MAX-ACCESS   read-create
--     STATUS       current
--     DESCRIPTION
--         "The value of tnSharedQueueFCMCastQueue specifies the logical 
--          queue that mutlticast traffic classified into this forwarding 
--          class should use."
--     DEFVAL { 9 }
--     ::= { tnSharedQueueFCEntry 5 }
-- 
-- tnSharedQueueFCBCastQueue OBJECT-TYPE
--     SYNTAX       TQueueId (17..24)
--     MAX-ACCESS   read-create
--     STATUS       current
--     DESCRIPTION
--         "The value of tnSharedQueueFCBCastQueue specifies the logical 
--          queue that broadscast traffic classified into this forwarding 
--          class should use."
--     DEFVAL { 17 }
--     ::= { tnSharedQueueFCEntry 6 }
-- 
-- tnSharedQueueFCUnknownQueue OBJECT-TYPE
--     SYNTAX       TQueueId (25..32)
--     MAX-ACCESS   read-create
--     STATUS       current
--     DESCRIPTION
--         "The value of tnSharedQueueFCUnknownQueue specifies the logical 
--          queue that unknown traffic classified into this forwarding 
--          class should use."
--     DEFVAL { 25 }
--     ::= { tnSharedQueueFCEntry 7 }

--
-- ingress queue group table
--

-- tnQosIngQGroupTableLastChanged OBJECT-TYPE
--     SYNTAX       TimeStamp
--     MAX-ACCESS   read-only
--     STATUS       current
--     DESCRIPTION
--         "tnQosIngQGroupTableLastChanged indicates the timestamp of last change
--         to the tnQosIngQGroupTable."
--     ::= { tnQosTimeStampObjects 6 }
-- 
-- tnQosIngQGroupTable OBJECT-TYPE
--     SYNTAX       SEQUENCE OF TQosIngQGroupEntry
--     MAX-ACCESS   not-accessible
--     STATUS       current
--     DESCRIPTION
--         "tnQosIngQGroupTable defines Ingress Queue Group Table for providing,
--          via SNMP, the capability of defining the queue groups for the queues
--          existing in the tnQosIngQueueTable.
-- 
--          tnQosIngQGroupTable holds a list of all the queue-groups in
--          the managed system defined. Queue-groups should exist
--          in this table before being referenced by the forwarding class
--          mappings within the queue policy as defined in the
--          tnSapIngressFCTable."
--     ::= { tnSharedQueueObjects 4 }
-- 
-- tnQosIngQGroupEntry OBJECT-TYPE
--     SYNTAX       TQosIngQGroupEntry
--     MAX-ACCESS   not-accessible
--     STATUS       current
--     DESCRIPTION
--         "tnQosIngQGroupEntry defines an entry in the tnQosIngQGroupTable.
-- 
--          Entries are created/deleted in this table by SNMP sets to
--          tnQosIngQGroupRowStatus."
--     INDEX { tnSysSwitchId, tnQosIngQGroupName }
--     ::= { tnQosIngQGroupTable 1 }
-- 
-- TQosIngQGroupEntry ::= SEQUENCE
--     {
--         tnQosIngQGroupName             TNamedItem,
--         tnQosIngQGroupRowStatus        RowStatus,
--         tnQosIngQGroupLastChanged      TimeStamp,
--         tnQosIngQGroupDescr            TItemDescription
--     }
-- 
-- tnQosIngQGroupName OBJECT-TYPE
--     SYNTAX       TNamedItem
--     MAX-ACCESS   not-accessible
--     STATUS       current
--     DESCRIPTION
--         "tnQosIngQGroupName defines the Ingress Queue Group name.
--          It uniquely identifies an ingress queue group in the managed
--          system."
--     ::= { tnQosIngQGroupEntry 1 }
-- 
-- tnQosIngQGroupRowStatus OBJECT-TYPE
--     SYNTAX       RowStatus
--     MAX-ACCESS   read-create
--     STATUS       current
--     DESCRIPTION
--         "tnQosIngQGroupRowStatus allows entries to be created and deleted
--          in the tnQosIngQGroupTable. The deletion of an entry in this table
--          will fail if the queue is being referenced by a forwarding class
--          mapping in the queue policy."
--     REFERENCE
--         "See definition of RowStatus in RFC 2579, 'Textual Conventions for
--          SMIv2.'"
--     ::= { tnQosIngQGroupEntry 2 }
-- 
-- tnQosIngQGroupLastChanged OBJECT-TYPE
--     SYNTAX       TimeStamp
--     MAX-ACCESS   read-only
--     STATUS       current
--     DESCRIPTION
--         "tnQosIngQGroupLastChanged indicates the value of sysUpTime when
--          the queue entry was last modified."
--     ::= { tnQosIngQGroupEntry 3 }
-- 
-- tnQosIngQGroupDescr OBJECT-TYPE
--     SYNTAX       TItemDescription
--     MAX-ACCESS   read-create
--     STATUS       current
--     DESCRIPTION
--         "tnQosIngQGroupDescr specifies the description of the queue-group."
--     DEFVAL { ''H }
--     ::= { tnQosIngQGroupEntry 4 }

--
-- ingress queue table
--

-- tnQosIngQTableLastChanged OBJECT-TYPE
--     SYNTAX       TimeStamp
--     MAX-ACCESS   read-only
--     STATUS       current
--     DESCRIPTION
--         "tnQosIngQTableLastChanged indicates the timestamp of last change to
--         the tnQosIngQueueTable."
--     ::= { tnQosTimeStampObjects 7 }
-- 
-- tnQosIngQueueTable OBJECT-TYPE
--     SYNTAX       SEQUENCE OF TQosIngQueueEntry
--     MAX-ACCESS   not-accessible
--     STATUS       current
--     DESCRIPTION
--         "tnQosIngQueueTable defines all ingress queues."
--     ::= { tnSharedQueueObjects 5 }
-- 
-- tnQosIngQueueEntry OBJECT-TYPE
--     SYNTAX       TQosIngQueueEntry
--     MAX-ACCESS   not-accessible
--     STATUS       current
--     DESCRIPTION
--         "tnQosIngQueueEntry defines a particular ingress queue.
--          Entries are created by user by setting tnQosIngQueueRowStatus."
--     INDEX { tnSysSwitchId, tnQosIngQGroupName, tnQosIngQueue }
--     ::= { tnQosIngQueueTable 1 }
-- 
-- TQosIngQueueEntry ::= SEQUENCE
--     {
--         tnQosIngQueue                 TIngressQueueId,
--         tnQosIngQueueRowStatus        RowStatus,
--         tnQosIngQueueParent           TNamedItemOrEmpty,
--         tnQosIngQueueLevel            TLevel,
--         tnQosIngQueueWeight           TWeight,
--         tnQosIngQueueCIRLevel         TLevelOrDefault,
--         tnQosIngQueueCIRWeight        TWeight,
--         tnQosIngQueueMCast            TruthValue,
--         tnQosIngQueueExpedite         INTEGER,
--         tnQosIngQueueCBS              TBurstSize,
--         tnQosIngQueueMBS              TBurstSize,
--         tnQosIngQueueHiPrioOnly       TBurstPercentOrDefault,
--         tnQosIngQueuePIRAdaptation    TAdaptationRule,
--         tnQosIngQueueCIRAdaptation    TAdaptationRule,
--         tnQosIngQueueAdminPIR         TPIRRate,
--         tnQosIngQueueAdminCIR         TCIRRate,
--         tnQosIngQueueLastChanged      TimeStamp,
--         tnQosIngQueuePoliced          TruthValue,
--         tnQosIngQueueMode             TQueueMode,
--         tnQosIngQueuePoolName         TNamedItemOrEmpty
--     }
-- 
-- tnQosIngQueue OBJECT-TYPE
--     SYNTAX       TIngressQueueId (1..32)
--     MAX-ACCESS   not-accessible
--     STATUS       current
--     DESCRIPTION
--         "tnQosIngQueue specifies the queue ID which is used as the
--         secondary index to the table entry."
--     ::= { tnQosIngQueueEntry 1 }
-- 
-- tnQosIngQueueRowStatus OBJECT-TYPE
--     SYNTAX       RowStatus
--     MAX-ACCESS   read-create
--     STATUS       current
--     DESCRIPTION
--         "tnQosIngQueueRowStatus is the Row-Status of the entry.
--          This allows creation/deletion of rows in this table."
--     ::= { tnQosIngQueueEntry 2 }
-- 
-- tnQosIngQueueParent OBJECT-TYPE
--     SYNTAX       TNamedItemOrEmpty
--     MAX-ACCESS   read-create
--     STATUS       current
--     DESCRIPTION
--         "tnQosIngQueueParent specifies the scheduler to which this queue would
--         be feeding."
--     DEFVAL { ''H }
--     ::= { tnQosIngQueueEntry 3 }
-- 
-- tnQosIngQueueLevel OBJECT-TYPE
--     SYNTAX       TLevel
--     MAX-ACCESS   read-create
--     STATUS       current
--     DESCRIPTION
--         "tnQosIngQueueLevel specifies the level of priority while feeding
--         the parent."
--     DEFVAL { 1 }
--     ::= { tnQosIngQueueEntry 4 }
-- 
-- tnQosIngQueueWeight OBJECT-TYPE
--     SYNTAX       TWeight
--     MAX-ACCESS   read-create
--     STATUS       current
--     DESCRIPTION
--         "tnQosIngQueueWeight specifies the weight that needs to be used by the
--         scheduler to which this queue would be feeding."
--     DEFVAL { 1 }
--     ::= { tnQosIngQueueEntry 5 }
-- 
-- tnQosIngQueueCIRLevel OBJECT-TYPE
--     SYNTAX       TLevelOrDefault
--     MAX-ACCESS   read-create
--     STATUS       current
--     DESCRIPTION
--         "tnQosIngQueueCIRLevel specifies the level of priority while feeding
--         to the parent.  The level '0' means treat all offered load for this
--         queue as for the above CIR traffic."
--     DEFVAL { 0 }
--     ::= { tnQosIngQueueEntry 6 }
-- 
-- tnQosIngQueueCIRWeight OBJECT-TYPE
--     SYNTAX       TWeight
--     MAX-ACCESS   read-create
--     STATUS       current
--     DESCRIPTION
--         "tnQosIngQueueCIRWeight specifies the weight that needs to be used
--         until the committed rate by the scheduler to which this queue would
--         be feeding."
--     DEFVAL { 1 }
--     ::= { tnQosIngQueueEntry 7 }
-- 
-- tnQosIngQueueMCast OBJECT-TYPE
--     SYNTAX       TruthValue
--     MAX-ACCESS   read-create
--     STATUS       current
--     DESCRIPTION
--         "tnQosIngQueueMCast specifies if this is a multicast queue."
--     DEFVAL { false }
--     ::= { tnQosIngQueueEntry 8 }
-- 
-- tnQosIngQueueExpedite OBJECT-TYPE
--     SYNTAX       INTEGER {
--                     expedited     (1),
--                     bestEffort    (3)
--                  }
--     MAX-ACCESS   read-create
--     STATUS       current
--     DESCRIPTION
--         "tnQosIngQueueExpedite specifies the priority that this queue should
--          be assigned by the hardware level schedulers.
-- 
--          This attribute is associated with the queue at the time of creation and
--          cannot be modified thereafter."
--     DEFVAL { bestEffort }
--     ::= { tnQosIngQueueEntry 9 }
-- 
-- tnQosIngQueueCBS OBJECT-TYPE
--     SYNTAX       TBurstSize
--     UNITS        "kilo-bytes"
--     MAX-ACCESS   read-create
--     STATUS       current
--     DESCRIPTION
--         "tnQosIngQueueCBS specifies the amount of reserved buffer space
--         for the queue."
--     DEFVAL { -1 }
--     ::= { tnQosIngQueueEntry 10 }
-- 
-- tnQosIngQueueMBS OBJECT-TYPE
--     SYNTAX       TBurstSize
--     UNITS        "kilo-bytes"
--     MAX-ACCESS   read-create
--     STATUS       current
--     DESCRIPTION
--         "tnQosIngQueueMBS specifies the maximum amount of buffer space allowed
--         for the queue."
--     DEFVAL { -1 }
--     ::= { tnQosIngQueueEntry 11 }
-- 
-- tnQosIngQueueHiPrioOnly OBJECT-TYPE
--     SYNTAX       TBurstPercentOrDefault
--     MAX-ACCESS   read-create
--     STATUS       current
--     DESCRIPTION
--         "tnQosIngQueueHiPrioOnly specifies the percentage of buffer space for
--         the queue, used exclusively by high priority packets."
--     DEFVAL { -1 }
--     ::= { tnQosIngQueueEntry 12 }
-- 
-- tnQosIngQueuePIRAdaptation OBJECT-TYPE
--     SYNTAX       TAdaptationRule
--     MAX-ACCESS   read-create
--     STATUS       current
--     DESCRIPTION
--         "tnQosIngQueuePIRAdaptation specifies the adaptation rule to be used
--         while computing the operational PIR value. The adaptation rule
--         specifies the rules to compute the operational values while maintaining
--         minimum offset."
--     DEFVAL { closest }
--     ::= { tnQosIngQueueEntry 13 }
-- 
-- tnQosIngQueueCIRAdaptation OBJECT-TYPE
--     SYNTAX       TAdaptationRule
--     MAX-ACCESS   read-create
--     STATUS       current
--     DESCRIPTION
--         "tnQosIngQueueCIRAdaptation specifies the adaptation rule to be used
--         while computing the operational CIR value. The adaptation rule
--         specifies the rules to compute the operational values while maintaining
--         minimum offset."
--     DEFVAL { closest }
--     ::= { tnQosIngQueueEntry 14 }
-- 
-- tnQosIngQueueAdminPIR OBJECT-TYPE
--     SYNTAX       TPIRRate
--     UNITS        "kbps"
--     MAX-ACCESS   read-create
--     STATUS       current
--     DESCRIPTION
--         "tnQosIngQueueAdminPIR specifies the administrative PIR specified by
--         the user."
--     DEFVAL { -1 }
--     ::= { tnQosIngQueueEntry 15 }
-- 
-- tnQosIngQueueAdminCIR OBJECT-TYPE
--     SYNTAX       TCIRRate
--     UNITS        "kbps"
--     MAX-ACCESS   read-create
--     STATUS       current
--     DESCRIPTION
--         "tnQosIngQueueAdminCIR specifies the administrative CIR specified by
--         the user."
--     DEFVAL { 0 }
--     ::= { tnQosIngQueueEntry 16 }
-- 
-- tnQosIngQueueLastChanged OBJECT-TYPE
--     SYNTAX       TimeStamp
--     MAX-ACCESS   read-only
--     STATUS       current
--     DESCRIPTION
--         "tnQosIngQueueLastChanged specifies the timestamp of last change to
--         this row in tnQosIngQueueTable."
--     ::= { tnQosIngQueueEntry 17 }
-- 
-- tnQosIngQueuePoliced OBJECT-TYPE
--     SYNTAX       TruthValue
--     MAX-ACCESS   read-create
--     STATUS       current
--     DESCRIPTION
--         "tnQosIngQueuePoliced specifies that the out of profile
--          traffic feeding into the physical queue instance should be
--          dropped. tnQosIngQueuePoliced overrides the bandwidth
--          specified by the object tnQosIngQueueAdminCIR."
--     DEFVAL { false }
--     ::= { tnQosIngQueueEntry 18 }
-- 
-- tnQosIngQueueMode OBJECT-TYPE
--     SYNTAX       TQueueMode
--     MAX-ACCESS   read-create
--     STATUS       current
--     DESCRIPTION
--         "tnQosIngQueueMode specifies the mode in which the queue
--          is operating. This attribute is associated with the queue
--          at the time of creation and cannot be modified thereafter."
--     DEFVAL { priority }
--     ::= { tnQosIngQueueEntry 19 }
-- 
-- tnQosIngQueuePoolName OBJECT-TYPE   
--     SYNTAX      TNamedItemOrEmpty
--     MAX-ACCESS  read-create
--     STATUS      current
--     DESCRIPTION
--         "tnQosIngQueuePoolName specifies the name of the pool to be applied
--         for the ingress queue."
--     DEFVAL { ''H }    
--     ::= { tnQosIngQueueEntry 20 }

--
-- egress queue group table
--

-- tnQosEgrQGroupTableLastChanged OBJECT-TYPE
--     SYNTAX       TimeStamp
--     MAX-ACCESS   read-only
--     STATUS       current
--     DESCRIPTION
--         "tnQosEgrQGroupTableLastChanged indicates the timestamp of last change
--         to the tnQosEgrQGroupTable."
--     ::= { tnQosTimeStampObjects 8 }
-- 
-- tnQosEgrQGroupTable OBJECT-TYPE
--     SYNTAX       SEQUENCE OF TQosEgrQGroupEntry
--     MAX-ACCESS   not-accessible
--     STATUS       current
--     DESCRIPTION
--         "tnQosEgrQGroupTable defines the Ingress Queue Group Table for
--          providing, via SNMP, the capability of defining the queue groups
--          for the queues existing in the tnQosEgrQueueTable.
-- 
--          tnQosEgrQGroupTable holds a list of all the queue-groups in
--          the managed system defined. Queue-groups should exist
--          in this table before being referenced by the forwarding class
--          mappings within the queue policy as defined in the
--          tnSapIngressFCTable."
--     ::= { tnSharedQueueObjects 6 }
-- 
-- tnQosEgrQGroupEntry OBJECT-TYPE
--     SYNTAX       TQosEgrQGroupEntry
--     MAX-ACCESS   not-accessible
--     STATUS       current
--     DESCRIPTION
--         "tnQosEgrQGroupEntry defines an entry in the tnQosEgrQGroupTable.
-- 
--          Entries are created/deleted in this table by SNMP sets to
--          tnQosEgrQGroupRowStatus."
--     INDEX { tnSysSwitchId, tnQosEgrQGroupName }
--     ::= { tnQosEgrQGroupTable 1 }
-- 
-- TQosEgrQGroupEntry ::= SEQUENCE
--     {
--         tnQosEgrQGroupName             TNamedItem,
--         tnQosEgrQGroupRowStatus        RowStatus,
--         tnQosEgrQGroupLastChanged      TimeStamp,
--         tnQosEgrQGroupDescr            TItemDescription
--     }
-- 
-- tnQosEgrQGroupName OBJECT-TYPE
--     SYNTAX       TNamedItem
--     MAX-ACCESS   not-accessible
--     STATUS       current
--     DESCRIPTION
--         "tnQosEgrQGroupName defines the Ingress Queue Group name.
--          It uniquely identifies an ingress queue group in the managed
--          system."
--     ::= { tnQosEgrQGroupEntry 1 }
-- 
-- tnQosEgrQGroupRowStatus OBJECT-TYPE
--     SYNTAX       RowStatus
--     MAX-ACCESS   read-create
--     STATUS       current
--     DESCRIPTION
--         "tnQosEgrQGroupRowStatus allows entries to be created and deleted
--          in the tnQosEgrQGroupTable. The deletion of an entry in this table
--          will fail if the queue is being referenced by a forwarding class
--          mapping in the queue policy."
--     REFERENCE
--         "See definition of RowStatus in RFC 2579, 'Textual Conventions for
--          SMIv2.'"
--     ::= { tnQosEgrQGroupEntry 2 }
-- 
-- tnQosEgrQGroupLastChanged OBJECT-TYPE
--     SYNTAX       TimeStamp
--     MAX-ACCESS   read-only
--     STATUS       current
--     DESCRIPTION
--         "tnQosEgrQGroupLastChanged indicates the value of sysUpTime when
--          the queue entry was last modified."
--     ::= { tnQosEgrQGroupEntry 3 }
-- 
-- tnQosEgrQGroupDescr OBJECT-TYPE
--     SYNTAX       TItemDescription
--     MAX-ACCESS   read-create
--     STATUS       current
--     DESCRIPTION
--         "tnQosEgrQGroupDescr specifies the description of the queue-group."
--     DEFVAL { ''H }
--     ::= { tnQosEgrQGroupEntry 4 }

--
-- qos egress policy queue table
--

-- tnQosEgrQTableLastChanged OBJECT-TYPE
--     SYNTAX       TimeStamp
--     MAX-ACCESS   read-only
--     STATUS       current
--     DESCRIPTION
--         "tnQosEgrQTableLastChanged indicates the timestamp of last change to
--         the tnQosEgrQueueTable."
--     ::= { tnQosTimeStampObjects 9 }
-- 
-- tnQosEgrQueueTable OBJECT-TYPE
--     SYNTAX       SEQUENCE OF TQosEgrQueueEntry
--     MAX-ACCESS   not-accessible
--     STATUS       current
--     DESCRIPTION
--         "tnQosEgrQueueTable defines all egress queues."
--     ::= { tnSharedQueueObjects 7 }
-- 
-- tnQosEgrQueueEntry OBJECT-TYPE
--     SYNTAX       TQosEgrQueueEntry
--     MAX-ACCESS   not-accessible
--     STATUS       current
--     DESCRIPTION
--         "tnQosEgrQueueEntry defines a particular egress queue.
--          Entries are created and deleted by user."
--     INDEX { tnSysSwitchId, tnQosEgrQGroupName, tnQosEgrQueue }
--     ::= { tnQosEgrQueueTable 1 }
-- 
-- TQosEgrQueueEntry ::= SEQUENCE
--     {
--         tnQosEgrQueue                  TEgressQueueId,
--         tnQosEgrQueueRowStatus         RowStatus,
--         tnQosEgrQueueParent            TNamedItemOrEmpty,
--         tnQosEgrQueueLevel             TLevel,
--         tnQosEgrQueueWeight            TWeight,
--         tnQosEgrQueueCIRLevel          TLevelOrDefault,
--         tnQosEgrQueueCIRWeight         TWeight,
--         tnQosEgrQueueExpedite          INTEGER,
--         tnQosEgrQueueCBS               TBurstSize,
--         tnQosEgrQueueMBS               TBurstSize,
--         tnQosEgrQueueHiPrioOnly        TBurstPercentOrDefault,
--         tnQosEgrQueuePIRAdaptation     TAdaptationRule,
--         tnQosEgrQueueCIRAdaptation     TAdaptationRule,
--         tnQosEgrQueueAdminPIR          TPIRRate,
--         tnQosEgrQueueAdminCIR          TCIRRate,
--         tnQosEgrQueueLastChanged       TimeStamp,
--         tnQosEgrQueueUsePortParent     TruthValue,
--         tnQosEgrQueuePortLvl           TLevel,
--         tnQosEgrQueuePortWght          TWeight,
--         tnQosEgrQueuePortCIRLvl        TLevelOrDefault,
--         tnQosEgrQueuePortCIRWght       TWeight,
--         tnQosEgrQueuePoolName          TNamedItemOrEmpty,
--         tnQosEgrQueueXPWredQ           TruthValue,  
--         tnQosEgrQueueXPWredQSlope      TNamedItem   
--     }
-- 
-- tnQosEgrQueue OBJECT-TYPE
--     SYNTAX       TEgressQueueId (1..8)
--     MAX-ACCESS   not-accessible
--     STATUS       current
--     DESCRIPTION
--         "The value of tnQosEgrQueue identifies the queue index which is used as
--          the second index to the table entry.  Zero is not allowed."
--     ::= { tnQosEgrQueueEntry 1 }
-- 
-- tnQosEgrQueueRowStatus OBJECT-TYPE
--     SYNTAX       RowStatus
--     MAX-ACCESS   read-create
--     STATUS       current
--     DESCRIPTION
--         "This is the Row Status of the entry.
--          This allows creation/deletion of rows in this table."
--     ::= { tnQosEgrQueueEntry 2 }
-- 
-- tnQosEgrQueueParent OBJECT-TYPE
--     SYNTAX       TNamedItemOrEmpty
--     MAX-ACCESS   read-create
--     STATUS       current
--     DESCRIPTION
--         "The value of tnQosEgrQueueParent specifies the scheduler to which this
--          queue would be feeding."
--     DEFVAL { ''H }
--     ::= { tnQosEgrQueueEntry 3 }
-- 
-- tnQosEgrQueueLevel OBJECT-TYPE
--     SYNTAX       TLevel
--     MAX-ACCESS   read-create
--     STATUS       current
--     DESCRIPTION
--         "The value of tnQosEgrQueueLevel specifies the level of priority while
--          feeding the parent."
--     DEFVAL { 1 }
--     ::= { tnQosEgrQueueEntry 4 }
-- 
-- tnQosEgrQueueWeight OBJECT-TYPE
--     SYNTAX       TWeight
--     MAX-ACCESS   read-create
--     STATUS       current
--     DESCRIPTION
--         "The value of tnQosEgrQueueWeight specifies the weight that needs to be
--          used by the scheduler to which this queue would be feeding."
--     DEFVAL { 1 }
--     ::= { tnQosEgrQueueEntry 5 }
-- 
-- tnQosEgrQueueCIRLevel OBJECT-TYPE
--     SYNTAX       TLevelOrDefault
--     MAX-ACCESS   read-create
--     STATUS       current
--     DESCRIPTION
--         "The value of tnQosEgrQueueCIRLevel specifies the level of priority
--          while feeding the parent.  The level '0' means treat all offered
--          load for this queue as for the above CIR traffic."
--     DEFVAL { 0 }
--     ::= { tnQosEgrQueueEntry 6 }
-- 
-- tnQosEgrQueueCIRWeight OBJECT-TYPE
--     SYNTAX       TWeight
--     MAX-ACCESS   read-create
--     STATUS       current
--     DESCRIPTION
--         "The value of tnQosEgrQueueCIRWeight specifies the weight that needs to
--          be used until the committed rate by the scheduler to which this queue
--          would be feeding."
--     DEFVAL { 1 }
--     ::= { tnQosEgrQueueEntry 7 }
-- 
-- tnQosEgrQueueExpedite OBJECT-TYPE
--     SYNTAX       INTEGER {
--                     expedited     (1),
--                     bestEffort    (3)
--                  }
--     MAX-ACCESS   read-create
--     STATUS       current
--     DESCRIPTION
--         "The value of tnQosEgrQueueExpedite specifies the priority that this
--          queue should be assigned by the hardware level schedulers.
-- 
--          This attribute is associated with the queue at the time of creation
--          and cannot be modified thereafter."
--     DEFVAL { bestEffort }
--     ::= { tnQosEgrQueueEntry 8 }
-- 
-- tnQosEgrQueueCBS OBJECT-TYPE
--     SYNTAX       TBurstSize
--     UNITS        "kilo-bytes"
--     MAX-ACCESS   read-create
--     STATUS       current
--     DESCRIPTION
--         "The value of tnQosEgrQueueCBS specifies the amount of reserved buffer
--          space for the queue."
--     DEFVAL { -1 }
--     ::= { tnQosEgrQueueEntry 9 }
-- 
-- tnQosEgrQueueMBS OBJECT-TYPE
--     SYNTAX       TBurstSize
--     UNITS        "kilo-bytes"
--     MAX-ACCESS   read-create
--     STATUS       current
--     DESCRIPTION
--         "The value of tnQosEgrQueueMBS specifies the maximum amount of buffer
--          space allowed for the queue."
--     DEFVAL { -1 }
--     ::= { tnQosEgrQueueEntry 10 }
-- 
-- tnQosEgrQueueHiPrioOnly OBJECT-TYPE
--     SYNTAX       TBurstPercentOrDefault
--     MAX-ACCESS   read-create
--     STATUS       current
--     DESCRIPTION
--         "The value of tnQosEgrQueueHiPrioOnly specifies the percentage of buffer
--          space for the queue, used exclusively by high priority packets."
--     DEFVAL { -1 }
--     ::= { tnQosEgrQueueEntry 11 }
-- 
-- tnQosEgrQueuePIRAdaptation OBJECT-TYPE
--     SYNTAX       TAdaptationRule
--     MAX-ACCESS   read-create
--     STATUS       current
--     DESCRIPTION
--         "The value of tnQosEgrQueuePIRAdaptation specifies the adaptation rule to
--          be used while computing the operational PIR value. The adaptation rule
--          specifies the rules to compute the operational values while
--          maintaining minimum offset."
--     DEFVAL { closest }
--     ::= { tnQosEgrQueueEntry 12 }
-- 
-- tnQosEgrQueueCIRAdaptation OBJECT-TYPE
--     SYNTAX       TAdaptationRule
--     MAX-ACCESS   read-create
--     STATUS       current
--     DESCRIPTION
--         "The value of tnQosEgrQueueCIRAdaptation specifies the adaptation rule
--          to be used while computing the operational CIR value. The adaptation
--          rule specifies the rules to compute the operational values while
--          maintaining minimum offset."
--     DEFVAL { closest }
--     ::= { tnQosEgrQueueEntry 13 }
-- 
-- tnQosEgrQueueAdminPIR OBJECT-TYPE
--     SYNTAX       TPIRRate
--     UNITS        "kbps"
--     MAX-ACCESS   read-create
--     STATUS       current
--     DESCRIPTION
--         "The value of tnQosEgrQueueAdminPIR specifies the administrative PIR."
--     DEFVAL { -1 }
--     ::= { tnQosEgrQueueEntry 14 }
-- 
-- tnQosEgrQueueAdminCIR OBJECT-TYPE
--     SYNTAX       TCIRRate
--     UNITS        "kbps"
--     MAX-ACCESS   read-create
--     STATUS       current
--     DESCRIPTION
--         "The value of tnQosEgrQueueAdminCIR specifies the administrative CIR."
--     DEFVAL { 0 }
--     ::= { tnQosEgrQueueEntry 15 }
-- 
-- tnQosEgrQueueLastChanged OBJECT-TYPE
--     SYNTAX       TimeStamp
--     MAX-ACCESS   read-only
--     STATUS       current
--     DESCRIPTION
--         "The value of tnQosEgrQueueLastChanged indicates the timestamp of last 
--          change to this row in tnQosEgrQueueTable."
--     ::= { tnQosEgrQueueEntry 18 }
-- 
-- tnQosEgrQueueUsePortParent  OBJECT-TYPE
--     SYNTAX      TruthValue
--     MAX-ACCESS  read-create
--     STATUS      current
--     DESCRIPTION
--         "The value of tnQosEgrQueueUsePortParent specifies whether this queue is
--          parented by a port-level scheduler. When the value is 'true', this SAP
--          egress queue is parented by a port-level scheduler. This object is 
--          mutually exclusive with tnQosEgrQueueParent. Only one kind of parent is
--          allowed."
--     DEFVAL      { false }
--     ::= { tnQosEgrQueueEntry 19 }
-- 
-- tnQosEgrQueuePortLvl        OBJECT-TYPE
--     SYNTAX       TLevel
--     MAX-ACCESS  read-create
--     STATUS      current
--     DESCRIPTION
--         "The value of the object tnQosEgrQueuePortLvl specifies the
--          port priority this queue will use to receive bandwidth from
--          the port-level scheduler for its above-cir offered load."
--     DEFVAL      { 1 }
--     ::= { tnQosEgrQueueEntry 20 }
-- 
-- tnQosEgrQueuePortWght       OBJECT-TYPE
--     SYNTAX      TWeight
--     MAX-ACCESS  read-create
--     STATUS      current
--     DESCRIPTION
--         "The value of the object tnQosEgrQueuePortWght specifies the
--          weight this queue will use to receive bandwidth from the
--          port-level scheduler for its above-cir offered load."
--     DEFVAL      { 1 }
--     ::= { tnQosEgrQueueEntry 21 }
-- 
-- tnQosEgrQueuePortCIRLvl        OBJECT-TYPE
--     SYNTAX      TLevelOrDefault
--     MAX-ACCESS  read-create
--     STATUS      current
--     DESCRIPTION
--         "The value of the object tnQosEgrQueuePortCIRLvl specifies the
--          port priority this queue will use to receive bandwidth from
--          the port-level scheduler for its within-cir offered load."
--     DEFVAL      { 0 }
--     ::= { tnQosEgrQueueEntry 22 }
-- 
-- tnQosEgrQueuePortCIRWght       OBJECT-TYPE
--     SYNTAX      TWeight
--     MAX-ACCESS  read-create
--     STATUS      current
--     DESCRIPTION
--         "The value of the object tnQosEgrQueuePortCIRWght specifies the
--          weight this queue will use to receive bandwidth from the
--          port-level scheduler for its within-cir offered load."
--     DEFVAL      { 0 }
--     ::= { tnQosEgrQueueEntry 23 }
-- 
-- tnQosEgrQueuePoolName OBJECT-TYPE   
--     SYNTAX      TNamedItemOrEmpty
--     MAX-ACCESS  read-create
--     STATUS      current
--     DESCRIPTION
--         "The value of tnQosEgrQueuePoolName specifies the name of 
--          the pool to be applied for SAP egress queue."
--     DEFVAL { ''H }    
--     ::= { tnQosEgrQueueEntry 24 }
-- 
-- tnQosEgrQueueXPWredQ OBJECT-TYPE   
--     SYNTAX      TruthValue
--     MAX-ACCESS  read-create
--     STATUS      current
--     DESCRIPTION
--         "The value of tnQosEgrQueueXPWredQ specifies whether to alter the
--          generic pool association of the queue for the purpose of allowing
--          queue-specific WRED slopes with minimal provisioning."
--     DEFVAL { false }    
--     ::= { tnQosEgrQueueEntry 25 }
-- 
-- tnQosEgrQueueXPWredQSlope OBJECT-TYPE   
--     SYNTAX      TNamedItem
--     MAX-ACCESS  read-create
--     STATUS      current
--     DESCRIPTION
--         "The value of tnQosEgrQueueXPWredQSlope specifies the name of 
--          the slope-policy to be applied for QOS egress queue.
--          
--          When tnQosEgrQueueXPWredQ has the value 'false', an 'inconsistentValue'
--          error is returned if an attempt is made to set this object to a value
--          other than 'default'."
--     DEFVAL { "default" }    
--     ::= { tnQosEgrQueueEntry 26 }
--
-- Slope policy table
--

tnSlopePolicyTable OBJECT-TYPE
    SYNTAX       SEQUENCE OF TSlopePolicyEntry
    MAX-ACCESS   not-accessible
    STATUS       current
    DESCRIPTION
        "Slope Policy Table. Each entry in this table defines the RED
        slopes for the high and the low priority traffic."
    ::= { tnSlopeObjects 1 }

tnSlopePolicyEntry OBJECT-TYPE
    SYNTAX       TSlopePolicyEntry
    MAX-ACCESS   not-accessible
    STATUS       current
    DESCRIPTION
        "Slope Policy Entry."
    INDEX { tnSysSwitchId, tnSlopePolicy }
    ::= { tnSlopePolicyTable 1 }

TSlopePolicyEntry ::= SEQUENCE
    {
        tnSlopePolicy            TNamedItem,
        tnSlopeRowStatus         RowStatus,
        tnSlopeDescription       TItemDescription,
        tnSlopeHiAdminStatus     INTEGER,
        tnSlopeHiStartAverage    Unsigned32,
        tnSlopeHiMaxAverage      Unsigned32,
        tnSlopeHiMaxProbability  Unsigned32,
        tnSlopeLoAdminStatus     INTEGER,
        tnSlopeLoStartAverage    Unsigned32,
        tnSlopeLoMaxAverage      Unsigned32,
        tnSlopeLoMaxProbability  Unsigned32,
        tnSlopeTimeAvgFactor     Unsigned32,
        tnSlopeLastChanged       TimeStamp
    }

tnSlopePolicy OBJECT-TYPE
    SYNTAX       TNamedItem
    MAX-ACCESS   not-accessible
    STATUS       current
    DESCRIPTION
        "tnSlopePolicy maintains the name of the slope policy
        identifying the policy."
    ::= { tnSlopePolicyEntry 1 }

tnSlopeRowStatus OBJECT-TYPE
    SYNTAX       RowStatus
    MAX-ACCESS   read-create
    STATUS       current
    DESCRIPTION
        "Row Status of the entry. This allows creation/deletion of rows in this
         table."
    ::= { tnSlopePolicyEntry 2 }

tnSlopeDescription OBJECT-TYPE
    SYNTAX       TItemDescription
    MAX-ACCESS   read-create
    STATUS       current
    DESCRIPTION
        "User-provided description of the policy."
    DEFVAL { ''H }
    ::= { tnSlopePolicyEntry 3 }

tnSlopeHiAdminStatus OBJECT-TYPE
    SYNTAX       INTEGER {
                     up  (1),
                     down(2)
                 }
    MAX-ACCESS   read-create
    STATUS       current
    DESCRIPTION
        "tnSlopeHiAdminStatus specifies the admin state for the high priority RED
         slope. If the tnSlopeHiAdminStatus is set to 'down', the RED slope is
         inactive."
    DEFVAL { down }
    ::= { tnSlopePolicyEntry 4 }

tnSlopeHiStartAverage OBJECT-TYPE
    SYNTAX       Unsigned32 (0..100)
    MAX-ACCESS   read-create
    STATUS       current
    DESCRIPTION
        "The percentage of the buffer utilized after which the drop probability
         starts to rise above 0."
    DEFVAL { 70 }
    ::= { tnSlopePolicyEntry 5 }

tnSlopeHiMaxAverage OBJECT-TYPE
    SYNTAX       Unsigned32 (0..100)
    MAX-ACCESS   read-create
    STATUS       current
    DESCRIPTION
        "The percentage of the buffer utilized after which the drop probability
         is 100 percent. This implies that all packets beyond this point will be
         dropped."
    DEFVAL { 90 }
    ::= { tnSlopePolicyEntry 6 }

tnSlopeHiMaxProbability OBJECT-TYPE
    SYNTAX       Unsigned32 (0..100)
    MAX-ACCESS   read-create
    STATUS       current
    DESCRIPTION
        "The drop probability increases steadily from 0 at the
         tnSlopeHiStartAverage upto the tnSlopeHiMaxProbability at the
         tnSlopeHiMaxAverage."
    DEFVAL { 80 }
    ::= { tnSlopePolicyEntry 7 }

tnSlopeLoAdminStatus OBJECT-TYPE
    SYNTAX       INTEGER {
                     up(1),
                     down(2)
                 }
    MAX-ACCESS   read-create
    STATUS       current
    DESCRIPTION
        "tnSlopeLoAdminStatus specifies the admin state for the high priority RED
        slope. If the tnSlopeLoAdminStatus is set to 'down', the RED slope is
        inactive."
    DEFVAL { down }
    ::= { tnSlopePolicyEntry 8 }

tnSlopeLoStartAverage OBJECT-TYPE
    SYNTAX       Unsigned32 (0..100)
    MAX-ACCESS   read-create
    STATUS       current
    DESCRIPTION
        "The percentage of the buffer utilized after which the drop probability
        starts to rise above 0."
    DEFVAL { 50 }
    ::= { tnSlopePolicyEntry 9 }

tnSlopeLoMaxAverage OBJECT-TYPE
    SYNTAX       Unsigned32 (0..100)
    MAX-ACCESS   read-create
    STATUS       current
    DESCRIPTION
        "The percentage of the buffer utilized after which the drop probability
        is 100 percent. This implies that all packets beyond this point will be
        dropped."
    DEFVAL { 75 }
    ::= { tnSlopePolicyEntry 10 }

tnSlopeLoMaxProbability OBJECT-TYPE
    SYNTAX       Unsigned32 (0..100)
    MAX-ACCESS   read-create
    STATUS       current
    DESCRIPTION
        "The drop probability increases steadily from 0 at the
        tnSlopeLoStartAverage upto the tnSlopeLoMaxProbability at the
        tnSlopeLoMaxAverage."
    DEFVAL { 80 }
    ::= { tnSlopePolicyEntry 11 }

tnSlopeTimeAvgFactor OBJECT-TYPE
    SYNTAX       Unsigned32 (0..15)
    MAX-ACCESS   read-create
    STATUS       current
    DESCRIPTION
        "The time average factor describes the weighting between the previous
        shared buffer average utilization result and the new shared buffer
        utilization in determining the new shared buffer average utilization."
    DEFVAL { 7 }
    ::= { tnSlopePolicyEntry 12 }

tnSlopeLastChanged OBJECT-TYPE
    SYNTAX       TimeStamp
    MAX-ACCESS   read-only
    STATUS       current
    DESCRIPTION
        "Timestamp of when this entry was last changed."
    ::= { tnSlopePolicyEntry 13 }

--
-- Slope policy table
--

-- tnHsmdaSlopePolicyTable OBJECT-TYPE
--     SYNTAX       SEQUENCE OF THsmdaSlopePolicyEntry
--     MAX-ACCESS   not-accessible
--     STATUS       current
--     DESCRIPTION
--         "The tnHsmdaSlopePolicyTable has an entry for each HSMDA slope
--          policy configured on this system."
--     ::= { tnSlopeObjects 2 }
-- 
-- tnHsmdaSlopePolicyEntry OBJECT-TYPE
--     SYNTAX       THsmdaSlopePolicyEntry
--     MAX-ACCESS   not-accessible
--     STATUS       current
--     DESCRIPTION
--         "Each row represents a particular HSMDA slope policy. Entries are 
--          created and deleted by the user."
--     INDEX { tnSysSwitchId, tnHsmdaSlopePolicyName }
--     ::= { tnHsmdaSlopePolicyTable 1 }
-- 
-- THsmdaSlopePolicyEntry ::= SEQUENCE
--     {
--         tnHsmdaSlopePolicyName        TNamedItem,
--         tnHsmdaSlopePolicyRowStatus   RowStatus,
--         tnHsmdaSlopeLastChanged       TimeStamp,
--         tnHsmdaSlopeDescription       TItemDescription,
--         tnHsmdaSlopeQueueMbs          Unsigned32,
--         tnHsmdaSlopeHiAdminStatus     TmnxEnabledDisabled,
--         tnHsmdaSlopeHiStartDepth      Unsigned32,
--         tnHsmdaSlopeHiMaxDepth        Unsigned32,
--         tnHsmdaSlopeHiMaxProbability  Unsigned32,
--         tnHsmdaSlopeLoAdminStatus     TmnxEnabledDisabled,
--         tnHsmdaSlopeLoStartDepth      Unsigned32,
--         tnHsmdaSlopeLoMaxDepth        Unsigned32,
--         tnHsmdaSlopeLoMaxProbability  Unsigned32
--     }
-- 
-- tnHsmdaSlopePolicyName OBJECT-TYPE
--     SYNTAX       TNamedItem
--     MAX-ACCESS   not-accessible
--     STATUS       current
--     DESCRIPTION
--         "The value of tnHsmdaSlopePolicyName specifies the name of the HSMDA
--          slope policy."
--     ::= { tnHsmdaSlopePolicyEntry 1 }
-- 
-- tnHsmdaSlopePolicyRowStatus OBJECT-TYPE
--     SYNTAX       RowStatus
--     MAX-ACCESS   read-create
--     STATUS       current
--     DESCRIPTION
--         "The value of tnHsmdaSlopePolicyRowStatus is used for the creation
--          and deletion of HSMDA slope policies."
--     ::= { tnHsmdaSlopePolicyEntry 2 }
-- 
-- tnHsmdaSlopeLastChanged OBJECT-TYPE
--     SYNTAX       TimeStamp
--     MAX-ACCESS   read-only
--     STATUS       current
--     DESCRIPTION
--         "The value of tnHsmdaSlopeLastChanged indicates the sysUpTime
--          at the time of the last modification of this entry.
-- 
--          If no changes were made to the entry since the last
--          re-initialization of the local network management subsystem,
--          then this object contains a zero value."
--     ::= { tnHsmdaSlopePolicyEntry 3 }
-- 
-- tnHsmdaSlopeDescription OBJECT-TYPE
--     SYNTAX       TItemDescription
--     MAX-ACCESS   read-create
--     STATUS       current
--     DESCRIPTION
--         "The value of tnHsmdaSlopeDescription specifies the description
--          of this HSMDA slope policy."
--     DEFVAL { "" }
--     ::= { tnHsmdaSlopePolicyEntry 4 }
-- 
-- tnHsmdaSlopeQueueMbs          OBJECT-TYPE
--     SYNTAX       Unsigned32 (0..500000)
--     UNITS        "bytes"
--     MAX-ACCESS   read-create
--     STATUS       current
--     DESCRIPTION
--         "The value of tnHsmdaSlopeQueueMbs specifies the maximum amount of buffer
--          space, in bytes, allowed for any HSMDA queue associated with this HSMDA
--          slope policy.
-- 
--          Specifying a value of 0 effectively disables all queues associated with
--          this slope policy causing each queue to discard all packets."
--     DEFVAL { 16800 }
--     ::= { tnHsmdaSlopePolicyEntry 5 }
-- 
-- tnHsmdaSlopeHiAdminStatus OBJECT-TYPE
--     SYNTAX       TmnxEnabledDisabled
--     MAX-ACCESS   read-create
--     STATUS       current
--     DESCRIPTION
--         "The value of tnHsmdaSlopeHiAdminStatus specifies the admin state for
--          the high priority RED slope. If the tnHsmdaSlopeHiAdminStatus is set
--          to 'disabled', the RED slope is inactive."
--     DEFVAL { enabled }
--     ::= { tnHsmdaSlopePolicyEntry 6 }
-- 
-- tnHsmdaSlopeHiStartDepth OBJECT-TYPE
--     SYNTAX       Unsigned32 (1..10000)
--     UNITS        "hundredths of a percent"
--     MAX-ACCESS   read-create
--     STATUS       current
--     DESCRIPTION
--         "The value of tnHsmdaSlopeHiStartDepth specifies the percentage of the
--          buffer utilized after which the drop probability starts to rise
--          above 0."
--     DEFVAL { 10000 }
--     ::= { tnHsmdaSlopePolicyEntry 7 }
-- 
-- tnHsmdaSlopeHiMaxDepth OBJECT-TYPE
--     SYNTAX       Unsigned32 (1..10000)
--     UNITS        "hundredths of a percent"
--     MAX-ACCESS   read-create
--     STATUS       current
--     DESCRIPTION
--         "The value of tnHsmdaSlopeHiMaxDepth specifies the percentage of the
--          buffer utilized after which the drop probability is 100 percent.
--          This implies that all packets beyond this point will be
--          dropped."
--     DEFVAL { 10000 }
--     ::= { tnHsmdaSlopePolicyEntry 8 }
-- 
-- tnHsmdaSlopeHiMaxProbability OBJECT-TYPE
--     SYNTAX       Unsigned32 (1..10000)
--     UNITS        "hundredths of a percent"
--     MAX-ACCESS   read-create
--     STATUS       current
--     DESCRIPTION
--         "The value of tnHsmdaSlopeHiMaxProbability specifies the drop 
--          probability, as a percentage, when the Hsmda queue depth reaches
--          tnHsmdaSlopeHiMaxDepth. The drop increases steadily from 0 at
--          the tnHsmdaSlopeHiStartDepth up to the tnHsmdaSlopeHiMaxProbability
--          at the tnHsmdaSlopeHiMaxDepth."
--     DEFVAL { 10000 }
--     ::= { tnHsmdaSlopePolicyEntry 9 }
-- 
-- tnHsmdaSlopeLoAdminStatus OBJECT-TYPE
--     SYNTAX       TmnxEnabledDisabled
--     MAX-ACCESS   read-create
--     STATUS       current
--     DESCRIPTION
--         "The value of tnHsmdaSlopeLoAdminStatus specifies the admin state for
--          the low priority RED slope. If the tnHsmdaSlopeLoAdminStatus is set
--          to 'disabled', the RED slope is inactive."
--     DEFVAL { enabled }
--     ::= { tnHsmdaSlopePolicyEntry 10 }
-- 
-- tnHsmdaSlopeLoStartDepth OBJECT-TYPE
--     SYNTAX       Unsigned32 (1..10000)
--     UNITS        "hundredths of a percent"
--     MAX-ACCESS   read-create
--     STATUS       current
--     DESCRIPTION
--         "The value of tnHsmdaSlopeLoStartDepth specifies the percentage of the
--          buffer utilized after which the drop probability starts to rise
--          above 0."
--     DEFVAL { 9000 }
--     ::= { tnHsmdaSlopePolicyEntry 11 }
-- 
-- tnHsmdaSlopeLoMaxDepth OBJECT-TYPE
--     SYNTAX       Unsigned32 (1..10000)
--     UNITS        "hundredths of a percent"
--     MAX-ACCESS   read-create
--     STATUS       current
--     DESCRIPTION
--         "The value of tnHsmdaSlopeLoMaxDepth specifies the percentage of the
--          buffer utilized after which the drop probability is 100 percent.
--          This implies that all packets beyond this point will be
--          dropped."
--     DEFVAL { 9000 }
--     ::= { tnHsmdaSlopePolicyEntry 12 }
-- 
-- tnHsmdaSlopeLoMaxProbability OBJECT-TYPE
--     SYNTAX       Unsigned32 (1..10000)
--     UNITS        "hundredths of a percent"
--     MAX-ACCESS   read-create
--     STATUS       current
--     DESCRIPTION
--         "The value of tnHsmdaSlopeLoMaxProbability specifies the drop 
--          probability, as a percentage, when the Hsmda queue depth reaches
--          tnHsmdaSlopeLoMaxDepth. The drop increases steadily from 0 at
--          the tnHsmdaSlopeLoStartDepth up to the tnHsmdaSlopeLoMaxProbability
--          at the tnHsmdaSlopeLoMaxDepth."
--     DEFVAL { 10000 }
--     ::= { tnHsmdaSlopePolicyEntry 13 }

--
-- Scheduler policy table
--

-- tnSchedulerPolicyTable OBJECT-TYPE
--     SYNTAX       SEQUENCE OF TSchedulerPolicyEntry
--     MAX-ACCESS   not-accessible
--     STATUS       current
--     DESCRIPTION
--         " "
--     ::= { tnSchedulerObjects 1 }
-- 
-- tnSchedulerPolicyEntry OBJECT-TYPE
--     SYNTAX       TSchedulerPolicyEntry
--     MAX-ACCESS   not-accessible
--     STATUS       current
--     DESCRIPTION
--         "Information about a particular Scheduler Policy."
--     INDEX { tnSysSwitchId, IMPLIED tnSchedulerPolicyName }
--     ::= { tnSchedulerPolicyTable 1 }
-- 
-- TSchedulerPolicyEntry ::= SEQUENCE
--     {
--         tnSchedulerPolicyName            TNamedItem,
--         tnSchedulerPolicyRowStatus       RowStatus,
--         tnSchedulerPolicyDescription     TItemDescription,
--         tnSchedulerPolicyLastChanged     TimeStamp,
--         tnSchedulerPolicyFrameBasedAccnt TruthValue
--     }
-- 
-- tnSchedulerPolicyName OBJECT-TYPE
--     SYNTAX       TNamedItem
--     MAX-ACCESS   not-accessible
--     STATUS       current
--     DESCRIPTION
--         "Name of the scheduler policy."
--     ::= { tnSchedulerPolicyEntry 1 }
-- 
-- tnSchedulerPolicyRowStatus OBJECT-TYPE
--     SYNTAX       RowStatus
--     MAX-ACCESS   read-create
--     STATUS       current
--     DESCRIPTION
--         "Row Status of the entry."
--     ::= { tnSchedulerPolicyEntry 2 }
-- 
-- tnSchedulerPolicyDescription OBJECT-TYPE
--     SYNTAX      TItemDescription
--     MAX-ACCESS  read-create
--     STATUS      current
--     DESCRIPTION
--         "Description for the scheduler policy"
--     DEFVAL { ''H }
--     ::= { tnSchedulerPolicyEntry 3 }
-- 
-- tnSchedulerPolicyLastChanged OBJECT-TYPE
--     SYNTAX       TimeStamp
--     MAX-ACCESS   read-only
--     STATUS       current
--     DESCRIPTION
--         "timestamp of last change to this row in tnSchedulerPolicyTable."
--     ::= { tnSchedulerPolicyEntry 4 }
-- 
-- tnSchedulerPolicyFrameBasedAccnt OBJECT-TYPE
--     SYNTAX       TruthValue
--     MAX-ACCESS   read-create
--     STATUS       current
--     DESCRIPTION
--         "The value of tnSchedulerPolicyFrameBasedAccnt specifies whether
--          to use frame-based accounting for the schedulers within the
--          scheduler policy and the children queues parented to the
--          scheduling policy.
-- 
--          If the value is 'false', the default packet-based accounting
--          method will be used."
--     DEFVAL { false }
--     ::= { tnSchedulerPolicyEntry 5 }

--
-- Virtual Scheduler table
--

-- tnVirtualSchedulerTable OBJECT-TYPE
--     SYNTAX       SEQUENCE OF TVirtualSchedulerEntry
--     MAX-ACCESS   not-accessible
--     STATUS       current
--     DESCRIPTION
--         " "
--     ::= { tnSchedulerObjects 2 }
-- 
-- tnVirtualSchedulerEntry OBJECT-TYPE
--     SYNTAX       TVirtualSchedulerEntry
--     MAX-ACCESS   not-accessible
--     STATUS       current
--     DESCRIPTION
--         "Information about a particular Scheduler belonging to a Scheduler
--         Policy."
--     INDEX { tnSysSwitchId, tnSchedulerPolicyName, tnVirtualSchedulerTier,
--             IMPLIED tnVirtualSchedulerName }
--     ::= { tnVirtualSchedulerTable 1 }
-- 
-- TVirtualSchedulerEntry ::= SEQUENCE
--     {
--         tnVirtualSchedulerTier          INTEGER,
--         tnVirtualSchedulerName          TNamedItem,
--         tnVirtualSchedulerRowStatus     RowStatus,
--         tnVirtualSchedulerDescription   TItemDescription,
--         tnVirtualSchedulerParent        TNamedItemOrEmpty,
--         tnVirtualSchedulerLevel         TLevel,
--         tnVirtualSchedulerWeight        TWeight,
--         tnVirtualSchedulerCIRLevel      TLevelOrDefault,
--         tnVirtualSchedulerCIRWeight     TWeight,
--         tnVirtualSchedulerPIR           TPIRRate,
--         tnVirtualSchedulerCIR           TCIRRate,
--         tnVirtualSchedulerSummedCIR     TruthValue,
--         tnVirtualSchedulerLastChanged   TimeStamp,
--         tnVirtualSchedulerUsePortParent TruthValue,
--         tnVirtualSchedulerPortLvl       TLevel,
--         tnVirtualSchedulerPortWght      TWeight,
--         tnVirtualSchedulerPortCIRLvl    TLevelOrDefault,
--         tnVirtualSchedulerPortCIRWght   TWeight
--     }
-- 
-- tnVirtualSchedulerTier OBJECT-TYPE
--     SYNTAX       INTEGER (1..3)
--     MAX-ACCESS   not-accessible
--     STATUS       current
--     DESCRIPTION
--         "Tier to which this scheduler belongs to."
--     ::= { tnVirtualSchedulerEntry 1 }
-- 
-- tnVirtualSchedulerName OBJECT-TYPE
--     SYNTAX       TNamedItem
--     MAX-ACCESS   not-accessible
--     STATUS       current
--     DESCRIPTION
--         "Name of the scheduler policy."
--     ::= { tnVirtualSchedulerEntry 2 }
-- 
-- tnVirtualSchedulerRowStatus OBJECT-TYPE
--     SYNTAX       RowStatus
--     MAX-ACCESS   read-create
--     STATUS       current
--     DESCRIPTION
--         "Row Status of the entry."
--     ::= { tnVirtualSchedulerEntry 3 }
-- 
-- tnVirtualSchedulerDescription OBJECT-TYPE
--     SYNTAX       TItemDescription
--     MAX-ACCESS   read-create
--     STATUS       current
--     DESCRIPTION
--         "Description for the scheduler policy"
--     DEFVAL { ''H }
--     ::= { tnVirtualSchedulerEntry 4 }
-- 
-- tnVirtualSchedulerParent OBJECT-TYPE
--     SYNTAX       TNamedItemOrEmpty
--     MAX-ACCESS   read-create
--     STATUS       current
--     DESCRIPTION
--         "The scheduler to which this scheduler would be feeding."
--     DEFVAL { ''H }
--     ::= { tnVirtualSchedulerEntry 5 }
-- 
-- tnVirtualSchedulerLevel OBJECT-TYPE
--     SYNTAX  TLevel
--     MAX-ACCESS   read-create
--     STATUS       current
--     DESCRIPTION
--         "This specifies the level of priority while feeding the parent."
--     DEFVAL { 1 }
--     ::= { tnVirtualSchedulerEntry 6 }
-- 
-- tnVirtualSchedulerWeight OBJECT-TYPE
--     SYNTAX       TWeight
--     MAX-ACCESS   read-create
--     STATUS       current
--     DESCRIPTION
--         "The weight that needs to be used by the scheduler to which this queue
--          would be feeding."
--     DEFVAL { 1 }
--     ::= { tnVirtualSchedulerEntry 7 }
-- 
-- tnVirtualSchedulerCIRLevel OBJECT-TYPE
--     SYNTAX  TLevelOrDefault
--     MAX-ACCESS   read-create
--     STATUS       current
--     DESCRIPTION
--         "This specifies the level of priority while feeding the parent.
--          The level '0' means treat all offered load for this queue as for
--          the above CIR traffic."
--     DEFVAL { 0 }
--     ::= { tnVirtualSchedulerEntry 8 }
-- 
-- tnVirtualSchedulerCIRWeight OBJECT-TYPE
--     SYNTAX       TWeight
--     MAX-ACCESS   read-create
--     STATUS       current
--     DESCRIPTION
--         "The weight that needs to be used until the committed rate by the
--          scheduler to which this queue would be feeding."
--     DEFVAL { 1 }
--     ::= { tnVirtualSchedulerEntry 9 }
-- 
-- tnVirtualSchedulerPIR OBJECT-TYPE
--     SYNTAX       TPIRRate
--     UNITS        "kbps"
--     MAX-ACCESS   read-create
--     STATUS       current
--     DESCRIPTION
--         "The rate allowed for this scheduler. A value of -1 implies
--          maximum."
--     DEFVAL { -1 }
--     ::= { tnVirtualSchedulerEntry 10 }
-- 
-- tnVirtualSchedulerCIR OBJECT-TYPE
--     SYNTAX       TCIRRate
--     UNITS        "kbps"
--     MAX-ACCESS   read-create
--     STATUS       current
--     DESCRIPTION
--         "The rate allowed for this scheduler. A value of -1 implies
--          maximum."
--     DEFVAL { 0 }
--     ::= { tnVirtualSchedulerEntry 11 }
-- 
-- tnVirtualSchedulerSummedCIR OBJECT-TYPE
--     SYNTAX       TruthValue
--     MAX-ACCESS   read-create
--     STATUS       current
--     DESCRIPTION
--         "tnVirtualSchedulerSummedCIR specifies if the CIR should be
--          used as the summed value of the children. If set to 'true',
--          tnVirtualSchedulerCIR loses its meaning."
--     DEFVAL { true }
--     ::= { tnVirtualSchedulerEntry 12 }
-- 
-- tnVirtualSchedulerLastChanged OBJECT-TYPE
--     SYNTAX       TimeStamp
--     MAX-ACCESS   read-only
--     STATUS       current
--     DESCRIPTION
--         "The value of the object tnVirtualSchedulerLastChanged indicates the
--          timestamp of last change to this row in tnVirtualSchedulerTable."
--     ::= { tnVirtualSchedulerEntry 13 }
-- 
-- tnVirtualSchedulerUsePortParent  OBJECT-TYPE
--     SYNTAX      TruthValue
--     MAX-ACCESS  read-create
--     STATUS      current
--     DESCRIPTION
--         "The value of the object tnVirtualSchedulerUsePortParent specifies
--          whether this scheduler is parented by a port-level scheduler. When
--          the value is 'true', this virtual scheduler is parented by a 
--          port-level scheduler. This object is mutually exclusive with 
--          tnVirtualSchedulerParent. Only one kind of parent is allowed."
--     DEFVAL      { false }
--     ::= { tnVirtualSchedulerEntry 14 }
-- 
-- tnVirtualSchedulerPortLvl        OBJECT-TYPE
--     SYNTAX       TLevel
--     MAX-ACCESS  read-create
--     STATUS      current
--     DESCRIPTION
--         "The value of the object tnVirtualSchedulerPortLvl specifies the
--          port priority this scheduler will use to receive bandwidth from
--          the port-level scheduler for its above-cir offered load."
--     DEFVAL      { 1 }
--     ::= { tnVirtualSchedulerEntry 15 }
-- 
-- tnVirtualSchedulerPortWght       OBJECT-TYPE
--     SYNTAX      TWeight
--     MAX-ACCESS  read-create
--     STATUS      current
--     DESCRIPTION
--         "The value of the object tnVirtualSchedulerPortWght specifies the
--          weight this scheduler will use to receive bandwidth from the
--          port-level scheduler for its above-cir offered load."
--     DEFVAL      { 1 }
--     ::= { tnVirtualSchedulerEntry 16 }
-- 
-- tnVirtualSchedulerPortCIRLvl     OBJECT-TYPE
--     SYNTAX      TLevelOrDefault
--     MAX-ACCESS  read-create
--     STATUS      current
--     DESCRIPTION
--         "The value of the object tnVirtualSchedulerPortCIRLvl specifies the
--          port priority this scheduler will use to receive bandwidth from
--          the port-level scheduler for its within-cir offered load."
--     DEFVAL      { 0 }
--     ::= { tnVirtualSchedulerEntry 17 }
-- 
-- tnVirtualSchedulerPortCIRWght    OBJECT-TYPE
--     SYNTAX      TWeight
--     MAX-ACCESS  read-create
--     STATUS      current
--     DESCRIPTION
--         "The value of the object tnVirtualSchedulerPortCIRWght specifies the
--          weight this scheduler will use to receive bandwidth from the
--          port-level scheduler for its within-cir offered load."
--     DEFVAL      { 0 }
--     ::= { tnVirtualSchedulerEntry 18 }

--
--  Port Scheduler plcy table
--

tnPortSchedulerPlcyTable       OBJECT-TYPE
    SYNTAX      SEQUENCE OF TPortSchedulerPlcyEntry
    MAX-ACCESS  not-accessible
    STATUS      current
    DESCRIPTION
        "The tnPortSchedulerPlcyTable has an entry for each port scheduler
         configured on this system."
    ::= { tnSchedulerObjects 3 }

tnPortSchedulerPlcyEntry       OBJECT-TYPE
    SYNTAX      TPortSchedulerPlcyEntry
    MAX-ACCESS  not-accessible
    STATUS      current
    DESCRIPTION
        "Each row represents a particular port scheduler. Entries are created
         and deleted by the user."
    INDEX { tnSysSwitchId, IMPLIED tnPortSchedulerPlcyName }
    ::= { tnPortSchedulerPlcyTable 1 }

TPortSchedulerPlcyEntry ::= SEQUENCE
    {
        tnPortSchedulerPlcyName                  TNamedItem,
        tnPortSchedulerPlcyRowStatus             RowStatus,
        tnPortSchedulerPlcyDescription           TItemDescription,
        tnPortSchedulerPlcyLastChanged           TimeStamp,
        tnPortSchedulerPlcyMaxRate               TPortSchedulerPIR,
        tnPortSchedulerPlcyLvl1PIR               TPortSchedulerPIR,
        tnPortSchedulerPlcyLvl1CIR               TPortSchedulerCIR,
        tnPortSchedulerPlcyLvl2PIR               TPortSchedulerPIR,
        tnPortSchedulerPlcyLvl2CIR               TPortSchedulerCIR,
        tnPortSchedulerPlcyLvl3PIR               TPortSchedulerPIR,
        tnPortSchedulerPlcyLvl3CIR               TPortSchedulerCIR,
        tnPortSchedulerPlcyLvl4PIR               TPortSchedulerPIR,
        tnPortSchedulerPlcyLvl4CIR               TPortSchedulerCIR,
        tnPortSchedulerPlcyLvl5PIR               TPortSchedulerPIR,
        tnPortSchedulerPlcyLvl5CIR               TPortSchedulerCIR,
        tnPortSchedulerPlcyLvl6PIR               TPortSchedulerPIR,
        tnPortSchedulerPlcyLvl6CIR               TPortSchedulerCIR,
        tnPortSchedulerPlcyLvl7PIR               TPortSchedulerPIR,
        tnPortSchedulerPlcyLvl7CIR               TPortSchedulerCIR,
        tnPortSchedulerPlcyLvl8PIR               TPortSchedulerPIR,
        tnPortSchedulerPlcyLvl8CIR               TPortSchedulerCIR,
        tnPortSchedulerPlcyOrphanLvl             TLevel,
        tnPortSchedulerPlcyOrphanWeight          TWeight,
        tnPortSchedulerPlcyOrphanCIRLvl          TLevelOrDefault,
        tnPortSchedulerPlcyOrphanCIRWght         TWeight
    }

tnPortSchedulerPlcyName  OBJECT-TYPE
    SYNTAX      TNamedItem
    MAX-ACCESS  not-accessible
    STATUS      current
    DESCRIPTION
        "The value of tnPortSchedulerPlcyName specifies the name of the port
         scheduler."
    ::= { tnPortSchedulerPlcyEntry 1 } 

tnPortSchedulerPlcyRowStatus     OBJECT-TYPE
    SYNTAX      RowStatus
    MAX-ACCESS  read-create
    STATUS      current
    DESCRIPTION
        "The value of tnPortSchedulerPlcyRowStatus is used for the creation
         and deletion of port scheduler policies."
    ::= { tnPortSchedulerPlcyEntry 2 } 
        
tnPortSchedulerPlcyDescription   OBJECT-TYPE
    SYNTAX      TItemDescription
    MAX-ACCESS  read-create
    STATUS      current
    DESCRIPTION
        "The value of tnPortSchedulerPlcyDescription specifies the description
         of this port scheduler."
    DEFVAL      { "" }
    ::= { tnPortSchedulerPlcyEntry 3 } 

tnPortSchedulerPlcyLastChanged        OBJECT-TYPE
    SYNTAX      TimeStamp
    MAX-ACCESS  read-only
    STATUS      current
    DESCRIPTION
        "The value of tnPortSchedulerPlcyLastChanged indicates the value of 
         sysUpTime at the time of the most recent management change to this
         row."
    ::= { tnPortSchedulerPlcyEntry 4 }

tnPortSchedulerPlcyMaxRate        OBJECT-TYPE
    SYNTAX      TPortSchedulerPIR
    UNITS       "kbps"
    MAX-ACCESS  read-create
    STATUS      current
    DESCRIPTION
        "The value of tnPortSchedulerPlcyMaxRate specifies the explicit maximum
         frame based bandwidth limit of this port scheduler."
    DEFVAL      { -1 }
    ::= { tnPortSchedulerPlcyEntry 5 }

tnPortSchedulerPlcyLvl1PIR        OBJECT-TYPE
    SYNTAX      TPortSchedulerPIR
    UNITS       "kbps"
    MAX-ACCESS  read-create
    STATUS      current
    DESCRIPTION
        "The value of tnPortSchedulerPlcyLvl1PIR specifies the total bandwidth
         limit, PIR, for priority level 1."
    DEFVAL      { -1 }
    ::= { tnPortSchedulerPlcyEntry 6 }

tnPortSchedulerPlcyLvl1CIR        OBJECT-TYPE
    SYNTAX      TPortSchedulerCIR
    UNITS       "kbps"
    MAX-ACCESS  read-create
    STATUS      current
    DESCRIPTION
        "The value of tnPortSchedulerPlcyLvl1CIR specifies the within-cir
         bandwidth limit for priority level 1."
    DEFVAL      { -1 }
    ::= { tnPortSchedulerPlcyEntry 7 }

tnPortSchedulerPlcyLvl2PIR        OBJECT-TYPE
    SYNTAX      TPortSchedulerPIR
    UNITS       "kbps"
    MAX-ACCESS  read-create
    STATUS      current
    DESCRIPTION
        "The value of tnPortSchedulerPlcyLvl2PIR specifies the total bandwidth
         limit, PIR, for priority level 2."
    DEFVAL      { -1 }
    ::= { tnPortSchedulerPlcyEntry 8 }

tnPortSchedulerPlcyLvl2CIR        OBJECT-TYPE
    SYNTAX      TPortSchedulerCIR
    UNITS       "kbps"
    MAX-ACCESS  read-create
    STATUS      current
    DESCRIPTION
        "The value of tnPortSchedulerPlcyLvl2CIR specifies the within-cir
         bandwidth limit for priority level 2."
    DEFVAL      { -1 }
    ::= { tnPortSchedulerPlcyEntry 9 }

tnPortSchedulerPlcyLvl3PIR        OBJECT-TYPE
    SYNTAX      TPortSchedulerPIR
    UNITS       "kbps"
    MAX-ACCESS  read-create
    STATUS      current
    DESCRIPTION
        "The value of tnPortSchedulerPlcyLvl3PIR specifies the total bandwidth
         limit, PIR, for priority level 3."
    DEFVAL      { -1 }
    ::= { tnPortSchedulerPlcyEntry 10 }

tnPortSchedulerPlcyLvl3CIR        OBJECT-TYPE
    SYNTAX      TPortSchedulerCIR
    UNITS       "kbps"
    MAX-ACCESS  read-create
    STATUS      current
    DESCRIPTION
        "The value of tnPortSchedulerPlcyLvl3CIR specifies the within-cir
         bandwidth limit for priority level 3."
    DEFVAL      { -1 }
    ::= { tnPortSchedulerPlcyEntry 11 }

tnPortSchedulerPlcyLvl4PIR        OBJECT-TYPE
    SYNTAX      TPortSchedulerPIR
    UNITS       "kbps"
    MAX-ACCESS  read-create
    STATUS      current
    DESCRIPTION
        "The value of tnPortSchedulerPlcyLvl4PIR specifies the total bandwidth
         limit, PIR, for priority level 4."
    DEFVAL      { -1 }
    ::= { tnPortSchedulerPlcyEntry 12 }

tnPortSchedulerPlcyLvl4CIR        OBJECT-TYPE
    SYNTAX      TPortSchedulerCIR
    UNITS       "kbps"
    MAX-ACCESS  read-create
    STATUS      current
    DESCRIPTION
        "The value of tnPortSchedulerPlcyLvl4CIR specifies the within-cir
         bandwidth limit for priority level 4."
    DEFVAL      { -1 }
    ::= { tnPortSchedulerPlcyEntry 13 }

tnPortSchedulerPlcyLvl5PIR        OBJECT-TYPE
    SYNTAX      TPortSchedulerPIR
    UNITS       "kbps"
    MAX-ACCESS  read-create
    STATUS      current
    DESCRIPTION
        "The value of tnPortSchedulerPlcyLvl5PIR specifies the total bandwidth
         limit, PIR, for priority level 5."
    DEFVAL      { -1 }
    ::= { tnPortSchedulerPlcyEntry 14 }

tnPortSchedulerPlcyLvl5CIR        OBJECT-TYPE
    SYNTAX      TPortSchedulerCIR
    UNITS       "kbps"
    MAX-ACCESS  read-create
    STATUS      current
    DESCRIPTION
        "The value of tnPortSchedulerPlcyLvl5CIR specifies the within-cir
         bandwidth limit for priority level 5."
    DEFVAL      { -1 }
    ::= { tnPortSchedulerPlcyEntry 15 }

tnPortSchedulerPlcyLvl6PIR        OBJECT-TYPE
    SYNTAX      TPortSchedulerPIR
    UNITS       "kbps"
    MAX-ACCESS  read-create
    STATUS      current
    DESCRIPTION
        "The value of tnPortSchedulerPlcyLvl6PIR specifies the total bandwidth
         limit, PIR, for priority level 6."
    DEFVAL      { -1 }
    ::= { tnPortSchedulerPlcyEntry 16 }

tnPortSchedulerPlcyLvl6CIR        OBJECT-TYPE
    SYNTAX      TPortSchedulerCIR
    UNITS       "kbps"
    MAX-ACCESS  read-create
    STATUS      current
    DESCRIPTION
        "The value of tnPortSchedulerPlcyLvl6CIR specifies the within-cir
         bandwidth limit for priority level 6."
    DEFVAL      { -1 }
    ::= { tnPortSchedulerPlcyEntry 17 }

tnPortSchedulerPlcyLvl7PIR        OBJECT-TYPE
    SYNTAX      TPortSchedulerPIR
    UNITS       "kbps"
    MAX-ACCESS  read-create
    STATUS      current
    DESCRIPTION
        "The value of tnPortSchedulerPlcyLvl7PIR specifies the total bandwidth
         limit, PIR, for priority level 7."
    DEFVAL      { -1 }
    ::= { tnPortSchedulerPlcyEntry 18 }

tnPortSchedulerPlcyLvl7CIR        OBJECT-TYPE
    SYNTAX      TPortSchedulerCIR
    UNITS       "kbps"
    MAX-ACCESS  read-create
    STATUS      current
    DESCRIPTION
        "The value of tnPortSchedulerPlcyLvl7CIR specifies the within-cir
         bandwidth limit for priority level 7."
    DEFVAL      { -1 }
    ::= { tnPortSchedulerPlcyEntry 19 }

tnPortSchedulerPlcyLvl8PIR        OBJECT-TYPE
    SYNTAX      TPortSchedulerPIR
    UNITS       "kbps"
    MAX-ACCESS  read-create
    STATUS      current
    DESCRIPTION
        "The value of tnPortSchedulerPlcyLvl8PIR specifies the total bandwidth
         limit, PIR, for priority level 8."
    DEFVAL      { -1 }
    ::= { tnPortSchedulerPlcyEntry 20 }

tnPortSchedulerPlcyLvl8CIR        OBJECT-TYPE
    SYNTAX      TPortSchedulerCIR
    UNITS       "kbps"
    MAX-ACCESS  read-create
    STATUS      current
    DESCRIPTION
        "The value of tnPortSchedulerPlcyLvl8CIR specifies the within-cir
         bandwidth limit for priority level 8."
    DEFVAL      { -1 }
    ::= { tnPortSchedulerPlcyEntry 21 }

tnPortSchedulerPlcyOrphanLvl        OBJECT-TYPE
    SYNTAX      TLevel
    MAX-ACCESS  read-create
    STATUS      current
    DESCRIPTION
        "The value of tnPortSchedulerPlcyOrphanLvl specifies the port priority
         of orphaned queues and schedulers that are above-cir."
    DEFVAL      { 1 }
    ::= { tnPortSchedulerPlcyEntry 22 }

tnPortSchedulerPlcyOrphanWeight        OBJECT-TYPE
    SYNTAX      TWeight
    MAX-ACCESS  read-create
    STATUS      current
    DESCRIPTION
        "The value of tnPortSchedulerPlcyOrphanWeight specifies the weight of
         orphaned queues and schedulers that are above-cir."
    DEFVAL      { 0 } 
    ::= { tnPortSchedulerPlcyEntry 23 }

tnPortSchedulerPlcyOrphanCIRLvl        OBJECT-TYPE
    SYNTAX      TLevelOrDefault
    MAX-ACCESS  read-create
    STATUS      current
    DESCRIPTION
        "The value of tnPortSchedulerPlcyOrphanCIRLvl specifies the port priority
         of orphaned queues and schedulers that are within-cir."
    DEFVAL      { 0 }
    ::= { tnPortSchedulerPlcyEntry 24 }

tnPortSchedulerPlcyOrphanCIRWght        OBJECT-TYPE
    SYNTAX      TWeight
    MAX-ACCESS  read-create
    STATUS      current
    DESCRIPTION
        "The value of tnPortSchedulerPlcyOrphanCIRWght specifies the weight of
         orphaned queues and schedulers that are within-cir."
    DEFVAL      { 0 }
    ::= { tnPortSchedulerPlcyEntry 25 }

--
-- Hsmda Scheduler Policy Table
--

-- tnHsmdaSchedulerPlcyTable OBJECT-TYPE
--     SYNTAX      SEQUENCE OF THsmdaSchedulerPlcyEntry
--     MAX-ACCESS  not-accessible
--     STATUS      current
--     DESCRIPTION
--         "The tnHsmdaSchedulerPlcyTable has an entry for each HSMDA scheduler
--          policy configured on this system."
--     ::= { tnSchedulerObjects 4 }
-- 
-- tnHsmdaSchedulerPlcyEntry    OBJECT-TYPE
--     SYNTAX      THsmdaSchedulerPlcyEntry
--     MAX-ACCESS  not-accessible
--     STATUS      current
--     DESCRIPTION
--         "Each row represents a particular HSMDA scheduler policy. Entries are 
--          created and deleted by the user."
--     INDEX { tnSysSwitchId, tnHsmdaSchedulerPlcyName }
--     ::= { tnHsmdaSchedulerPlcyTable 1}
-- 
-- THsmdaSchedulerPlcyEntry ::= SEQUENCE
--     {
--         tnHsmdaSchedulerPlcyName              TNamedItem,
--         tnHsmdaSchedulerPlcyRowStatus         RowStatus,
--         tnHsmdaSchedulerPlcyDescription       TItemDescription,
--         tnHsmdaSchedulerPlcyMaxRate           THsmdaPIRMRate,
--         tnHsmdaSchedulerPlcyLvl1Rate          THsmdaPIRMRate,
--         tnHsmdaSchedulerPlcyLvl1GrpId         THsmdaSchedulerPolicyGroupId,
--         tnHsmdaSchedulerPlcyLvl1WgtInGrp      THsmdaWeight,
--         tnHsmdaSchedulerPlcyLvl2Rate          THsmdaPIRMRate,
--         tnHsmdaSchedulerPlcyLvl2GrpId         THsmdaSchedulerPolicyGroupId,
--         tnHsmdaSchedulerPlcyLvl2WgtInGrp      THsmdaWeight,
--         tnHsmdaSchedulerPlcyLvl3Rate          THsmdaPIRMRate,
--         tnHsmdaSchedulerPlcyLvl3GrpId         THsmdaSchedulerPolicyGroupId,
--         tnHsmdaSchedulerPlcyLvl3WgtInGrp      THsmdaWeight,
--         tnHsmdaSchedulerPlcyLvl4Rate          THsmdaPIRMRate,
--         tnHsmdaSchedulerPlcyLvl4GrpId         THsmdaSchedulerPolicyGroupId,
--         tnHsmdaSchedulerPlcyLvl4WgtInGrp      THsmdaWeight,
--         tnHsmdaSchedulerPlcyLvl5Rate          THsmdaPIRMRate,
--         tnHsmdaSchedulerPlcyLvl5GrpId         THsmdaSchedulerPolicyGroupId,
--         tnHsmdaSchedulerPlcyLvl5WgtInGrp      THsmdaWeight,
--         tnHsmdaSchedulerPlcyLvl6Rate          THsmdaPIRMRate,
--         tnHsmdaSchedulerPlcyLvl6GrpId         THsmdaSchedulerPolicyGroupId,
--         tnHsmdaSchedulerPlcyLvl6WgtInGrp      THsmdaWeight,
--         tnHsmdaSchedulerPlcyLvl7Rate          THsmdaPIRMRate,
--         tnHsmdaSchedulerPlcyLvl7GrpId         THsmdaSchedulerPolicyGroupId,
--         tnHsmdaSchedulerPlcyLvl7WgtInGrp      THsmdaWeight,
--         tnHsmdaSchedulerPlcyLvl8Rate          THsmdaPIRMRate,
--         tnHsmdaSchedulerPlcyLvl8GrpId         THsmdaSchedulerPolicyGroupId,
--         tnHsmdaSchedulerPlcyLvl8WgtInGrp      THsmdaWeight,
--         tnHsmdaSchedulerPlcyLastChanged       TimeStamp,
--         tnHsmdaSchedulerPlcyGrp1Rate          THsmdaPIRMRate,
--         tnHsmdaSchedulerPlcyGrp2Rate          THsmdaPIRMRate
--     }
-- 
-- tnHsmdaSchedulerPlcyName        OBJECT-TYPE
--     SYNTAX      TNamedItem
--     MAX-ACCESS  not-accessible
--     STATUS      current
--     DESCRIPTION
--         "The value of tnHsmdaSchedulerPlcyName specifies the name of the HSMDA
--          scheduler policy."
--     ::= { tnHsmdaSchedulerPlcyEntry 1 }
-- 
-- tnHsmdaSchedulerPlcyRowStatus        OBJECT-TYPE
--     SYNTAX      RowStatus
--     MAX-ACCESS  read-create
--     STATUS      current
--     DESCRIPTION
--         "The value of tnHsmdaSchedulerPlcyRowStatus is used for the creation
--          and deletion of HSMDA scheduler policies."
--     ::= { tnHsmdaSchedulerPlcyEntry 2 }
-- 
-- tnHsmdaSchedulerPlcyDescription        OBJECT-TYPE
--     SYNTAX      TItemDescription
--     MAX-ACCESS  read-create
--     STATUS      current
--     DESCRIPTION
--         "The value of tnHsmdaSchedulerPlcyDescription specifies the description
--          of this HSMDA scheduling policy."
--     ::= { tnHsmdaSchedulerPlcyEntry 3 }
-- 
-- tnHsmdaSchedulerPlcyMaxRate        OBJECT-TYPE
--     SYNTAX      THsmdaPIRMRate
--     UNITS       "Mbps"
--     MAX-ACCESS  read-create
--     STATUS      current
--     DESCRIPTION
--         "The value of tnHsmdaSchedulerPlcyMaxRate specifies the explicit maximum
--          frame based bandwidth limit, in megabits per second, of this HSMDA 
--          scheduler policy."
--     DEFVAL { -1 }
--     ::= { tnHsmdaSchedulerPlcyEntry 4 }
-- 
-- tnHsmdaSchedulerPlcyLvl1Rate        OBJECT-TYPE
--     SYNTAX      THsmdaPIRMRate
--     UNITS       "Mbps"
--     MAX-ACCESS  read-create
--     STATUS      current
--     DESCRIPTION
--         "The value of tnHsmdaSchedulerPlcyLvl1Rate specifies the explicit maximum
--          frame based bandwidth limit, in megabits per second, for this HSMDA 
--          scheduler policy level."
--     DEFVAL { -1 }
--     ::= { tnHsmdaSchedulerPlcyEntry 5 }
-- 
-- tnHsmdaSchedulerPlcyLvl1GrpId        OBJECT-TYPE
--     SYNTAX      THsmdaSchedulerPolicyGroupId
--     MAX-ACCESS  read-create
--     STATUS      current
--     DESCRIPTION
--         "The value of tnHsmdaSchedulerPlcyLvl1GrpId specifies the group this
--          HSMDA scheduler policy level belongs to.
-- 
--          If the value is 0, this level is not assigned to a scheduler 
--          policy group."
--     DEFVAL { 0 }
--     ::= { tnHsmdaSchedulerPlcyEntry 6 }
-- 
-- tnHsmdaSchedulerPlcyLvl1WgtInGrp        OBJECT-TYPE
--     SYNTAX      THsmdaWeight
--     MAX-ACCESS  read-create
--     STATUS      current
--     DESCRIPTION
--         "The value of tnHsmdaSchedulerPlcyLvl1WgtInGrp specifies the weight
--          the HSMDA scheduler policy should apply to this policy level within 
--          the group it belongs to.
-- 
--          The value of tnHsmdaSchedulerPlcyLvl1WgtInGrp will only be 
--          used if this policy level has been assigned to a group 
--          by setting tnHsmdaSchedulerPlcyLvl1GrpId to a non-zero value."
--     DEFVAL { 1 }
--     ::= { tnHsmdaSchedulerPlcyEntry 7 }
-- 
-- tnHsmdaSchedulerPlcyLvl2Rate        OBJECT-TYPE
--     SYNTAX      THsmdaPIRMRate
--     UNITS       "Mbps"
--     MAX-ACCESS  read-create
--     STATUS      current
--     DESCRIPTION
--         "The value of tnHsmdaSchedulerPlcyLvl2Rate specifies the explicit maximum
--          frame based bandwidth limit, in megabits per second, for this HSMDA 
--          scheduler policy level."
--     DEFVAL { -1 }
--     ::= { tnHsmdaSchedulerPlcyEntry 8 }
-- 
-- tnHsmdaSchedulerPlcyLvl2GrpId        OBJECT-TYPE
--     SYNTAX      THsmdaSchedulerPolicyGroupId
--     MAX-ACCESS  read-create
--     STATUS      current
--     DESCRIPTION
--         "The value of tnHsmdaSchedulerPlcyLvl2GrpId specifies the group this
--          HSMDA scheduler policy level belongs to.
-- 
--          If the value is 0, this level is not assigned to a scheduler 
--          policy group."
--     DEFVAL { 0 }
--     ::= { tnHsmdaSchedulerPlcyEntry 9 }
-- 
-- tnHsmdaSchedulerPlcyLvl2WgtInGrp        OBJECT-TYPE
--     SYNTAX      THsmdaWeight
--     MAX-ACCESS  read-create
--     STATUS      current
--     DESCRIPTION
--         "The value of tnHsmdaSchedulerPlcyLvl2WgtInGrp specifies the weight
--          the HSMDA scheduler policy should apply to this policy level within 
--          the group it belongs to.
-- 
--          The value of tnHsmdaSchedulerPlcyLvl2WgtInGrp will only be 
--          used if this policy level has been assigned to a group 
--          by setting tnHsmdaSchedulerPlcyLvl2GrpId to a non-zero value."
--     DEFVAL { 1 }
--     ::= { tnHsmdaSchedulerPlcyEntry 10 }
-- 
-- tnHsmdaSchedulerPlcyLvl3Rate        OBJECT-TYPE
--     SYNTAX      THsmdaPIRMRate
--     UNITS       "Mbps"
--     MAX-ACCESS  read-create
--     STATUS      current
--     DESCRIPTION
--         "The value of tnHsmdaSchedulerPlcyLvl3Rate specifies the explicit maximum
--          frame based bandwidth limit, in megabits per second, for this HSMDA 
--          scheduler policy level."
--     DEFVAL { -1 }
--     ::= { tnHsmdaSchedulerPlcyEntry 11 }
-- 
-- tnHsmdaSchedulerPlcyLvl3GrpId        OBJECT-TYPE
--     SYNTAX      THsmdaSchedulerPolicyGroupId
--     MAX-ACCESS  read-create
--     STATUS      current
--     DESCRIPTION
--         "The value of tnHsmdaSchedulerPlcyLvl3GrpId specifies the group this
--          HSMDA scheduler policy level belongs to.
-- 
--          If the value is 0, this level is not assigned to a scheduler 
--          policy group."
--     DEFVAL { 0 }
--     ::= { tnHsmdaSchedulerPlcyEntry 12 }
-- 
-- tnHsmdaSchedulerPlcyLvl3WgtInGrp        OBJECT-TYPE
--     SYNTAX      THsmdaWeight
--     MAX-ACCESS  read-create
--     STATUS      current
--     DESCRIPTION
--         "The value of tnHsmdaSchedulerPlcyLvl3WgtInGrp specifies the weight
--          the HSMDA scheduler policy should apply to this policy level within 
--          the group it belongs to.
-- 
--          The value of tnHsmdaSchedulerPlcyLvl3WgtInGrp will only be 
--          used if this policy level has been assigned to a group 
--          by setting tnHsmdaSchedulerPlcyLvl3GrpId to a non-zero value."
--     DEFVAL { 1 }
--     ::= { tnHsmdaSchedulerPlcyEntry 13 }
-- 
-- tnHsmdaSchedulerPlcyLvl4Rate        OBJECT-TYPE
--     SYNTAX      THsmdaPIRMRate
--     UNITS       "Mbps"
--     MAX-ACCESS  read-create
--     STATUS      current
--     DESCRIPTION
--         "The value of tnHsmdaSchedulerPlcyLvl4Rate specifies the explicit maximum
--          frame based bandwidth limit, in megabits per second, for this HSMDA 
--          scheduler policy level."
--     DEFVAL { -1 }
--     ::= { tnHsmdaSchedulerPlcyEntry 14 }
-- 
-- tnHsmdaSchedulerPlcyLvl4GrpId        OBJECT-TYPE
--     SYNTAX      THsmdaSchedulerPolicyGroupId
--     MAX-ACCESS  read-create
--     STATUS      current
--     DESCRIPTION
--         "The value of tnHsmdaSchedulerPlcyLvl4GrpId specifies the group this
--          HSMDA scheduler policy level belongs to.
-- 
--          If the value is 0, this level is not assigned to a scheduler 
--          policy group."
--     DEFVAL { 0 }
--     ::= { tnHsmdaSchedulerPlcyEntry 15 }
-- 
-- tnHsmdaSchedulerPlcyLvl4WgtInGrp        OBJECT-TYPE
--     SYNTAX      THsmdaWeight
--     MAX-ACCESS  read-create
--     STATUS      current
--     DESCRIPTION
--         "The value of tnHsmdaSchedulerPlcyLvl4WgtInGrp specifies the weight
--          the HSMDA scheduler policy should apply to this policy level within 
--          the group it belongs to.
-- 
--          The value of tnHsmdaSchedulerPlcyLvl4WgtInGrp will only be 
--          used if this policy level has been assigned to a group 
--          by setting tnHsmdaSchedulerPlcyLvl4GrpId to a non-zero value."
--     DEFVAL { 1 }
--     ::= { tnHsmdaSchedulerPlcyEntry 16 }
-- 
-- tnHsmdaSchedulerPlcyLvl5Rate        OBJECT-TYPE
--     SYNTAX      THsmdaPIRMRate
--     UNITS       "Mbps"
--     MAX-ACCESS  read-create
--     STATUS      current
--     DESCRIPTION
--         "The value of tnHsmdaSchedulerPlcyLvl5Rate specifies the explicit maximum
--          frame based bandwidth limit, in megabits per second, for this HSMDA 
--          scheduler policy level."
--     DEFVAL { -1 }
--     ::= { tnHsmdaSchedulerPlcyEntry 17 }
-- 
-- tnHsmdaSchedulerPlcyLvl5GrpId        OBJECT-TYPE
--     SYNTAX      THsmdaSchedulerPolicyGroupId
--     MAX-ACCESS  read-create
--     STATUS      current
--     DESCRIPTION
--         "The value of tnHsmdaSchedulerPlcyLvl5GrpId specifies the group this
--          HSMDA scheduler policy level belongs to.
-- 
--          If the value is 0, this level is not assigned to a scheduler 
--          policy group."
--     DEFVAL { 0 }
--     ::= { tnHsmdaSchedulerPlcyEntry 18 }
-- 
-- tnHsmdaSchedulerPlcyLvl5WgtInGrp        OBJECT-TYPE
--     SYNTAX      THsmdaWeight
--     MAX-ACCESS  read-create
--     STATUS      current
--     DESCRIPTION
--         "The value of tnHsmdaSchedulerPlcyLvl5WgtInGrp specifies the weight
--          the HSMDA scheduler policy should apply to this policy level within 
--          the group it belongs to.
-- 
--          The value of tnHsmdaSchedulerPlcyLvl5WgtInGrp will only be 
--          used if this policy level has been assigned to a group 
--          by setting tnHsmdaSchedulerPlcyLvl5GrpId to a non-zero value."
--     DEFVAL { 1 }
--     ::= { tnHsmdaSchedulerPlcyEntry 19 }
-- 
-- tnHsmdaSchedulerPlcyLvl6Rate        OBJECT-TYPE
--     SYNTAX      THsmdaPIRMRate
--     UNITS       "Mbps"
--     MAX-ACCESS  read-create
--     STATUS      current
--     DESCRIPTION
--         "The value of tnHsmdaSchedulerPlcyLvl6Rate specifies the explicit maximum
--          frame based bandwidth limit, in megabits per second, for this HSMDA 
--          scheduler policy level."
--     DEFVAL { -1 }
--     ::= { tnHsmdaSchedulerPlcyEntry 20 }
-- 
-- tnHsmdaSchedulerPlcyLvl6GrpId        OBJECT-TYPE
--     SYNTAX      THsmdaSchedulerPolicyGroupId
--     MAX-ACCESS  read-create
--     STATUS      current
--     DESCRIPTION
--         "The value of tnHsmdaSchedulerPlcyLvl6GrpId specifies the group this
--          HSMDA scheduler policy level belongs to.
-- 
--          If the value is 0, this level is not assigned to a scheduler 
--          policy group."
--     DEFVAL { 0 }
--     ::= { tnHsmdaSchedulerPlcyEntry 21 }
-- 
-- tnHsmdaSchedulerPlcyLvl6WgtInGrp        OBJECT-TYPE
--     SYNTAX      THsmdaWeight
--     MAX-ACCESS  read-create
--     STATUS      current
--     DESCRIPTION
--         "The value of tnHsmdaSchedulerPlcyLvl6WgtInGrp specifies the weight
--          the HSMDA scheduler policy should apply to this policy level within 
--          the group it belongs to.
-- 
--          The value of tnHsmdaSchedulerPlcyLvl6WgtInGrp will only be 
--          used if this policy level has been assigned to a group 
--          by setting tnHsmdaSchedulerPlcyLvl6GrpId to a non-zero value."
--     DEFVAL { 1 }
--     ::= { tnHsmdaSchedulerPlcyEntry 22 }
-- 
-- tnHsmdaSchedulerPlcyLvl7Rate        OBJECT-TYPE
--     SYNTAX      THsmdaPIRMRate
--     UNITS       "Mbps"
--     MAX-ACCESS  read-create
--     STATUS      current
--     DESCRIPTION
--         "The value of tnHsmdaSchedulerPlcyLvl7Rate specifies the explicit maximum
--          frame based bandwidth limit, in megabits per second, for this HSMDA 
--          scheduler policy level."
--     DEFVAL { -1 }
--     ::= { tnHsmdaSchedulerPlcyEntry 23 }
-- 
-- tnHsmdaSchedulerPlcyLvl7GrpId        OBJECT-TYPE
--     SYNTAX      THsmdaSchedulerPolicyGroupId
--     MAX-ACCESS  read-create
--     STATUS      current
--     DESCRIPTION
--         "The value of tnHsmdaSchedulerPlcyLvl7GrpId specifies the group this
--          HSMDA scheduler policy level belongs to.
-- 
--          If the value is 0, this level is not assigned to a scheduler 
--          policy group."
--     DEFVAL { 0 }
--     ::= { tnHsmdaSchedulerPlcyEntry 24 }
-- 
-- tnHsmdaSchedulerPlcyLvl7WgtInGrp        OBJECT-TYPE
--     SYNTAX      THsmdaWeight
--     MAX-ACCESS  read-create
--     STATUS      current
--     DESCRIPTION
--         "The value of tnHsmdaSchedulerPlcyLvl7WgtInGrp specifies the weight
--          the HSMDA scheduler policy should apply to this policy level within 
--          the group it belongs to.
-- 
--          The value of tnHsmdaSchedulerPlcyLvl7WgtInGrp will only be 
--          used if this policy level has been assigned to a group 
--          by setting tnHsmdaSchedulerPlcyLvl7GrpId to a non-zero value."
--     DEFVAL { 1 }
--     ::= { tnHsmdaSchedulerPlcyEntry 25 }
-- 
-- tnHsmdaSchedulerPlcyLvl8Rate        OBJECT-TYPE
--     SYNTAX      THsmdaPIRMRate
--     UNITS       "Mbps"
--     MAX-ACCESS  read-create
--     STATUS      current
--     DESCRIPTION
--         "The value of tnHsmdaSchedulerPlcyLvl8Rate specifies the explicit maximum
--          frame based bandwidth limit, in megabits per second, for this HSMDA 
--          scheduler policy level."
--     DEFVAL { -1 }
--     ::= { tnHsmdaSchedulerPlcyEntry 26 }
-- 
-- tnHsmdaSchedulerPlcyLvl8GrpId        OBJECT-TYPE
--     SYNTAX      THsmdaSchedulerPolicyGroupId
--     MAX-ACCESS  read-create
--     STATUS      current
--     DESCRIPTION
--         "The value of tnHsmdaSchedulerPlcyLvl8GrpId specifies the group this
--          HSMDA scheduler policy level belongs to.
-- 
--          If the value is 0, this level is not assigned to a scheduler 
--          policy group."
--     DEFVAL { 0 }
--     ::= { tnHsmdaSchedulerPlcyEntry 27 }
-- 
-- tnHsmdaSchedulerPlcyLvl8WgtInGrp        OBJECT-TYPE
--     SYNTAX      THsmdaWeight
--     MAX-ACCESS  read-create
--     STATUS      current
--     DESCRIPTION
--         "The value of tnHsmdaSchedulerPlcyLvl8WgtInGrp specifies the weight
--          the HSMDA scheduler policy should apply to this policy level within 
--          the group it belongs to.
-- 
--          The value of tnHsmdaSchedulerPlcyLvl8WgtInGrp will only be 
--          used if this policy level has been assigned to a group 
--          by setting tnHsmdaSchedulerPlcyLvl8GrpId to a non-zero value."
--     DEFVAL { 1 }
--     ::= { tnHsmdaSchedulerPlcyEntry 28 }
-- 
-- tnHsmdaSchedulerPlcyLastChanged        OBJECT-TYPE
--     SYNTAX      TimeStamp
--     MAX-ACCESS  read-only
--     STATUS      current
--     DESCRIPTION
--         "The value of tnHsmdaSchedulerPlcyLastChanged indicates the timestamp of 
--          last change to this row in tnHsmdaSchedulerPlcyTable."
--     ::= { tnHsmdaSchedulerPlcyEntry 29 }
-- 
-- tnHsmdaSchedulerPlcyGrp1Rate           OBJECT-TYPE
--     SYNTAX      THsmdaPIRMRate
--     UNITS       "Mbps"
--     MAX-ACCESS  read-create
--     STATUS      current
--     DESCRIPTION
--         "The value of tnHsmdaSchedulerPlcyGrp1Rate specifies the explicit 
--          maximum frame based bandwidth limit, in megabits per second, for 
--          group 1 for this HSMDA scheduler policy group."
--     DEFVAL { -1 }
--     ::= { tnHsmdaSchedulerPlcyEntry 30 }
-- 
-- tnHsmdaSchedulerPlcyGrp2Rate           OBJECT-TYPE
--     SYNTAX      THsmdaPIRMRate
--     UNITS       "Mbps"
--     MAX-ACCESS  read-create
--     STATUS      current
--     DESCRIPTION
--         "The value of tnHsmdaSchedulerPlcyGrp2Rate specifies the explicit 
--          maximum frame based bandwidth limit, in megabits per second, for 
--          group 2 for this HSMDA scheduler policy group."
--     DEFVAL { -1 }
--     ::= { tnHsmdaSchedulerPlcyEntry 31 }

--
-- Dummy Scalars
--
tnSchedulerScalar1 OBJECT-TYPE
    SYNTAX      Unsigned32
    MAX-ACCESS  read-only
    STATUS      current
    DESCRIPTION
        "A dummy scalar that satisfies a SNMP get request quickly when
         there is no 11QPE24 card provisioned.  Otherwise, it has to
         traverse the remaining 11QPE24 MIB to get to the next applicable
         item."
    ::= { tnSchedulerObjects 101 }

tnSchedulerScalar2 OBJECT-TYPE
    SYNTAX      Unsigned32
    MAX-ACCESS  read-only
    STATUS      current
    DESCRIPTION
        ""
    ::= { tnSchedulerObjects 102 }

--
-- Qos Domain Time Stamps
--
-- tnQosDomainLastChanged OBJECT-TYPE
--     SYNTAX       TimeStamp
--     MAX-ACCESS   read-only
--     STATUS       current
--     DESCRIPTION
--         "The value of the object tnQosDomainLastChanged indicates the
--          timestamp of last change to the QoS Domain."
--     ::= { tnQosTimeStampObjects 1 }
-- 
-- tnDSCPNameTableLastChanged OBJECT-TYPE
--     SYNTAX       TimeStamp
--     MAX-ACCESS   read-only
--     STATUS       current
--     DESCRIPTION
--         "The value of the object tnDSCPNameTableLastChanged indicates the
--          timestamp of last change  to the DSCP Name Table."
--     ::= { tnQosTimeStampObjects 5 }
-- 
-- tnFCNameTableLastChanged OBJECT-TYPE
--     SYNTAX       TimeStamp
--     MAX-ACCESS   read-only
--     STATUS       current
--     DESCRIPTION
--         "The value of the object tnFCNameTableLastChanged indicates the
--          timestamp of last change to the FC Name Table."
--     ::= { tnQosTimeStampObjects 10 }
-- 
-- tnSapIngressTableLastChanged OBJECT-TYPE
--     SYNTAX       TimeStamp
--     MAX-ACCESS   read-only
--     STATUS       current
--     DESCRIPTION
--         "The value of the object tnSapIngressTableLastChanged indicates the
--          timestamp of last change  to the Sap Ingress Policy Table."
--     ::= { tnQosTimeStampObjects 20 }
-- 
-- tnSapIngressQueueTableLastChanged OBJECT-TYPE
--     SYNTAX       TimeStamp
--     MAX-ACCESS   read-only
--     STATUS       current
--     DESCRIPTION
--         "tnSapIngressQueueTableLastChanged maintains the timestamp of
--         the last change made to the Sap Ingress Queue Table."
--     ::= { tnQosTimeStampObjects 21 }
-- 
-- tnSapIngressDSCPTableLastChanged OBJECT-TYPE
--     SYNTAX       TimeStamp
--     MAX-ACCESS   read-only
--     STATUS       current
--     DESCRIPTION
--         "tnSapIngressDSCPTableLastChanged maintains the timestamp of the
--         last change made to the Sap Ingress DSCP Mapping Table."
--     ::= { tnQosTimeStampObjects 22 }
-- 
-- tnSapIngressDot1pTableLastChanged OBJECT-TYPE
--     SYNTAX       TimeStamp
--     MAX-ACCESS   read-only
--     STATUS       current
--     DESCRIPTION
--         "tnSapIngressDot1pTableLastChanged maintains the timestamp of the
--         last change made to the Sap Ingress Dot1p Table."
--     ::= { tnQosTimeStampObjects 23 }
-- 
-- tnSapIngressIPCriteriaTableLastChanged OBJECT-TYPE
--     SYNTAX       TimeStamp
--     MAX-ACCESS   read-only
--     STATUS       current
--     DESCRIPTION
--         "tnSapIngressIPCriteriaTableLastChanged maintains the timestamp of
--         the last change made to the Sap Ingress IP Criteria Table."
--     ::= { tnQosTimeStampObjects 24 }
-- 
-- tnSapIngressMacCriteriaTableLastChanged OBJECT-TYPE
--     SYNTAX       TimeStamp
--     MAX-ACCESS   read-only
--     STATUS       current
--     DESCRIPTION
--         "tnSapIngressMacCriteriaTableLastChanged maintains the timestamp
--         of the last change made to the Sap Ingress Mac Criteria Table."
--     ::= { tnQosTimeStampObjects 25 }
-- 
-- tnSapIngressFCTableLastChanged OBJECT-TYPE
--     SYNTAX       TimeStamp
--     MAX-ACCESS   read-only
--     STATUS       current
--     DESCRIPTION
--         "tnSapIngressFCTableLastChanged maintains the timestamp of the
--         last change made to the Sap Ingress FC Table."
--     ::= { tnQosTimeStampObjects 26 }
-- 
-- tnSapIngressPrecTableLastChanged OBJECT-TYPE
--     SYNTAX       TimeStamp
--     MAX-ACCESS   read-only
--     STATUS       current
--     DESCRIPTION
--         "tnSapIngressPrecTableLastChanged maintains the timestamp of the
--         last change made to the Sap Ingress Precedence Table."
--     ::= { tnQosTimeStampObjects 27 }
-- 
-- tnSapEgressTableLastChanged OBJECT-TYPE
--     SYNTAX       TimeStamp
--     MAX-ACCESS   read-only
--     STATUS       current
--     DESCRIPTION
--         "tnSapEgressTableLastChanged maintains the timestamp of the
--         last change made to the Sap Egress Policy Table."
--     ::= { tnQosTimeStampObjects 30 }
-- 
-- tnSapEgressQueueTableLastChanged OBJECT-TYPE
--     SYNTAX       TimeStamp
--     MAX-ACCESS   read-only
--     STATUS       current
--     DESCRIPTION
--         "tnSapEgressQueueTableLastChanged maintains the timestamp of
--         the last change made to the Sap Egress Queue Table."
--     ::= { tnQosTimeStampObjects 31 }
-- 
-- tnSapEgressFCTableLastChanged OBJECT-TYPE
--     SYNTAX       TimeStamp
--     MAX-ACCESS   read-only
--     STATUS       current
--     DESCRIPTION
--         "tnSapEgressFCTableLastChanged maintains the timestamp of the
--         last change made to the Sap Egress FC Table."
--     ::= { tnQosTimeStampObjects 32 }
-- 
-- tnNetworkPolicyTableLastChanged OBJECT-TYPE
--     SYNTAX       TimeStamp
--     MAX-ACCESS   read-only
--     STATUS       current
--     DESCRIPTION
--         "tnNetworkPolicyTableLastChanged maintains the timestamp of the
--         last change made to the Network Policy Table."
--     ::= { tnQosTimeStampObjects 40 }
-- 
-- tnNetworkIngressDSCPTableLastChanged OBJECT-TYPE
--     SYNTAX       TimeStamp
--     MAX-ACCESS   read-only
--     STATUS       current
--     DESCRIPTION
--         "tnNetworkIngressDSCPTableLastChanged maintains the timestamp of
--         the last change made to the Network Ingress DSCP Mapping Table."
--     ::= { tnQosTimeStampObjects 41 }
-- 
-- tnNetworkIngressLSPEXPTableLastChanged OBJECT-TYPE
--     SYNTAX       TimeStamp
--     MAX-ACCESS   read-only
--     STATUS       current
--     DESCRIPTION
--         "tnNetworkIngressLSPEXPTableLastChanged maintains the timestamp
--         of the last change made to the Network Ingress LSPEXP Table."
--     ::= { tnQosTimeStampObjects 42 }
-- 
-- tnNetworkEgressFCTableLastChanged OBJECT-TYPE
--     SYNTAX       TimeStamp
--     MAX-ACCESS   read-only
--     STATUS       current
--     DESCRIPTION
--         "tnNetworkEgressFCTableLastChanged maintains the timestamp of
--         the last change made to the Network Egress FC Table."
--     ::= { tnQosTimeStampObjects 43 }
-- 
-- tnNetworkIngressDot1pTableLastChanged OBJECT-TYPE
--     SYNTAX       TimeStamp
--     MAX-ACCESS   read-only
--     STATUS       current
--     DESCRIPTION
--         "tnNetworkIngressDot1pTableLastChanged maintains the timestamp
--         of the last change made to the Network Ingress Dot1p Table."
--     ::= { tnQosTimeStampObjects 44 }
-- 
-- tnNetworkQueuePolicyTableLastChanged OBJECT-TYPE
--     SYNTAX       TimeStamp
--     MAX-ACCESS   read-only
--     STATUS       current
--     DESCRIPTION
--         "tnNetworkQueuePolicyTableLastChanged maintains the timestamp of
--         the last change made to the Network Queue Policy Table."
--     ::= { tnQosTimeStampObjects 50 }
-- 
-- tnNetworkQueueTableLastChanged OBJECT-TYPE
--     SYNTAX       TimeStamp
--     MAX-ACCESS   read-only
--     STATUS       current
--     DESCRIPTION
--         "tnNetworkQueueTableLastChanged maintains the timestamp of the
--         last change made to the Network Queue Table."
--     ::= { tnQosTimeStampObjects 51 }
-- 
-- tnNetworkQueueFCTableLastChanged OBJECT-TYPE
--     SYNTAX       TimeStamp
--     MAX-ACCESS   read-only
--     STATUS       current
--     DESCRIPTION
--         "tnNetworkQueueFCTableLastChanged maintains the timestamp of the
--         last change made to the Network Queue FC Table."
--     ::= { tnQosTimeStampObjects 52 }
-- 
-- tnSlopePolicyTableLastChanged OBJECT-TYPE
--     SYNTAX       TimeStamp
--     MAX-ACCESS   read-only
--     STATUS       current
--     DESCRIPTION
--         "tnSlopePolicyTableLastChanged maintains the timestamp of the
--         last change made to the Slope Policy Table."
--     ::= { tnQosTimeStampObjects 55 }
-- 
-- tnSchedulerPolicyTableLastChanged OBJECT-TYPE
--     SYNTAX       TimeStamp
--     MAX-ACCESS   read-only
--     STATUS       current
--     DESCRIPTION
--         "tnSchedulerPolicyTableLastChanged maintains the timestamp of
--         the last change made to the Scheduler Policy Table."
--     ::= { tnQosTimeStampObjects 60 }
-- 
-- tnVirtualSchedulerTableLastChanged OBJECT-TYPE
--     SYNTAX       TimeStamp
--     MAX-ACCESS   read-only
--     STATUS       current
--     DESCRIPTION
--         "tnVirtualSchedulerTableLastChanged maintains the timestamp of
--         the last change made to the Virtual Scheduler Table."
--     ::= { tnQosTimeStampObjects 61 }
-- 
-- tnAtmTdpTableLastChanged OBJECT-TYPE
--     SYNTAX       TimeStamp
--     MAX-ACCESS   read-only
--     STATUS       current
--     DESCRIPTION
--         "tnAtmTdpTableLastChanged maintains the timestamp of
--          the last change made to the Traffic Descriptor Profile Table."
--     ::= { tnQosTimeStampObjects 62 }
-- 
-- tnSharedQueuePolicyTableLastChanged OBJECT-TYPE
--     SYNTAX       TimeStamp
--     MAX-ACCESS   read-only
--     STATUS       current
--     DESCRIPTION
--         "tnSharedQueuePolicyTableLastChanged maintains the timestamp of
--         the last change made to the Queue Policy Table."
--     ::= { tnQosTimeStampObjects 63 }
-- 
-- tnSharedQueueTableLastChanged OBJECT-TYPE
--     SYNTAX       TimeStamp
--     MAX-ACCESS   read-only
--     STATUS       current
--     DESCRIPTION
--         "tnSharedQueueTableLastChanged maintains the timestamp of the
--         last change made to the Queue Table."
--     ::= { tnQosTimeStampObjects 64 }
-- 
-- tnSharedQueueFCTableLastChanged OBJECT-TYPE
--     SYNTAX       TimeStamp
--     MAX-ACCESS   read-only
--     STATUS       current
--     DESCRIPTION
--         "tnSharedQueueFCTableLastChanged maintains the timestamp of the
--         last change made to the Queue FC Table."
--     ::= { tnQosTimeStampObjects 65 }
-- 
-- 
-- tnSapIngressIPv6CriteriaTableLastChanged OBJECT-TYPE
--     SYNTAX       TimeStamp
--     MAX-ACCESS   read-only
--     STATUS       current
--     DESCRIPTION
--         "The value of the object tnSapIngressIPv6CriteriaTableLastChanged
--          indicates the timestamp of the last change made to the Sap Ingress
--          IPv6 Criteria Table."
--     ::= { tnQosTimeStampObjects 66 }
-- 
-- tnSapIngrHsmdaQueueTblLastChngd OBJECT-TYPE
--     SYNTAX       TimeStamp
--     MAX-ACCESS   read-only
--     STATUS       current
--     DESCRIPTION
--         "tnSapIngrHsmdaQueueTblLastChngd maintains the timestamp of the
--         last change made to the Sap Ingress HSMDA Queue Table."
--     ::= { tnQosTimeStampObjects 67 }
-- 
-- tnSapEgrHsmdaQueueTblLastChngd OBJECT-TYPE
--     SYNTAX       TimeStamp
--     MAX-ACCESS   read-only
--     STATUS       current
--     DESCRIPTION
--         "tnSapEgrHsmdaQueueTblLastChngd maintains the timestamp of the
--         last change made to the Sap Egress HSMDA Queue Table."
--     ::= { tnQosTimeStampObjects 68 }
-- 
-- tnHsmdaSchedPlcyTblLastChngd OBJECT-TYPE
--     SYNTAX       TimeStamp
--     MAX-ACCESS   read-only
--     STATUS       current
--     DESCRIPTION
--         "tnHsmdaSchedPlcyTblLastChngd maintains the timestamp of the
--         last change made to the HSMDA Scheduler Policy Table."
--     ::= { tnQosTimeStampObjects 69 }
-- 
-- tnHsmdaSchedPlcyGrpTblLastChngd OBJECT-TYPE
--     SYNTAX       TimeStamp
--     MAX-ACCESS   read-only
--     STATUS       current
--     DESCRIPTION
--         "tnHsmdaSchedPlcyGrpTblLastChngd maintains the timestamp of the
--         last change made to the HSMDA Scheduler Policy Group Table."
--     ::= { tnQosTimeStampObjects 70 }
-- 
-- tnHsmdaPoolPlcyTblLastChngd OBJECT-TYPE
--     SYNTAX       TimeStamp
--     MAX-ACCESS   read-only
--     STATUS       current
--     DESCRIPTION
--         "tnHsmdaPoolPlcyTblLastChngd maintains the timestamp of the
--         last change made to the HSMDA Pool Policy Table."
--     ::= { tnQosTimeStampObjects 71 }
-- 
-- tnHsmdaSlopePolicyTableLastChanged OBJECT-TYPE
--     SYNTAX       TimeStamp
--     MAX-ACCESS   read-only
--     STATUS       current
--     DESCRIPTION
--         "tnHsmdaSlopePolicyTableLastChanged maintains the timestamp of the
--         last change made to the Hsmda Slope Policy Table."
--     ::= { tnQosTimeStampObjects 72 }
-- 
-- tnNamedPoolPolicyTableLastChanged OBJECT-TYPE
--     SYNTAX       TimeStamp
--     MAX-ACCESS   read-only
--     STATUS       current
--     DESCRIPTION
--         "The value of tnNamedPoolPolicyTableLastChanged indicates the sysUpTime
--          at the time of the last modification of an entry in the
--          tnNamedPoolPolicyTable.
-- 
--          If no changes were made to the table since the last re-initialization
--          of the local network management subsystem, then this object
--          contains a zero value."
--     ::= { tnQosTimeStampObjects 73 }
-- 
-- tnQ1NamedPoolTableLastChanged OBJECT-TYPE
--     SYNTAX       TimeStamp
--     MAX-ACCESS   read-only
--     STATUS       current
--     DESCRIPTION
--         "The value of tnQ1NamedPoolTableLastChanged indicates the sysUpTime
--          at the time of the last modification of an entry in the
--          tnQ1NamedPoolTable.
-- 
--          If no changes were made to the table since the last re-initialization
--          of the local network management subsystem, then this object
--          contains a zero value."
--     ::= { tnQosTimeStampObjects 74 }
-- 
-- tnMcMlpppIngrProfTableLastChanged OBJECT-TYPE
--     SYNTAX       TimeStamp
--     MAX-ACCESS   read-only
--     STATUS       current
--     DESCRIPTION
--         "The value of tnMcMlpppIngrProfTableLastChanged indicates the sysUpTime
--          at the time of the last modification of an entry in the
--          tnMcMlpppIngrProfTable.
-- 
--          If no changes were made to the table since the last re-initialization
--          of the local network management subsystem, then this object
--          contains a zero value."
--     ::= { tnQosTimeStampObjects 75 }
-- 
-- tnMcMlpppIngrClassTableLastChanged OBJECT-TYPE
--     SYNTAX       TimeStamp
--     MAX-ACCESS   read-only
--     STATUS       current
--     DESCRIPTION
--         "The value of tnMcMlpppIngrClassTableLastChanged indicates the sysUpTime
--          at the time of the last modification of an entry in the
--          tnMcMlpppIngrClassTable.
-- 
--          If no changes were made to the table since the last re-initialization
--          of the local network management subsystem, then this object
--          contains a zero value."
--     ::= { tnQosTimeStampObjects 76 }
-- 
-- tnMcMlpppEgrProfTableLastChanged OBJECT-TYPE
--     SYNTAX       TimeStamp
--     MAX-ACCESS   read-only
--     STATUS       current
--     DESCRIPTION
--         "The value of tnMcMlpppEgrProfTableLastChanged indicates the sysUpTime
--          at the time of the last modification of an entry in the
--          tnMcMlpppEgrProfTable.
-- 
--          If no changes were made to the table since the last re-initialization
--          of the local network management subsystem, then this object
--          contains a zero value."
--     ::= { tnQosTimeStampObjects 77 }
-- 
-- tnMcMlpppEgrClassTableLastChanged OBJECT-TYPE
--     SYNTAX       TimeStamp
--     MAX-ACCESS   read-only
--     STATUS       current
--     DESCRIPTION
--         "The value of tnMcMlpppEgrClassTableLastChanged indicates the sysUpTime
--          at the time of the last modification of an entry in the
--          tnMcMlpppEgrClassTable.
-- 
--          If no changes were made to the table since the last re-initialization
--          of the local network management subsystem, then this object
--          contains a zero value."
--     ::= { tnQosTimeStampObjects 78 }
-- 
-- tnMcMlpppEgrFCTableLastChanged OBJECT-TYPE
--     SYNTAX       TimeStamp
--     MAX-ACCESS   read-only
--     STATUS       current
--     DESCRIPTION
--         "The value of tnMcMlpppEgrFCTableLastChanged indicates the sysUpTime
--          at the time of the last modification of an entry in the
--          tnMcMlpppEgrFCTable.
-- 
--          If no changes were made to the table since the last re-initialization
--          of the local network management subsystem, then this object
--          contains a zero value."
--     ::= { tnQosTimeStampObjects 79 }
-- 
-- tnMcFrIngrProfTableLastChanged OBJECT-TYPE
--     SYNTAX       TimeStamp
--     MAX-ACCESS   read-only
--     STATUS       current
--     DESCRIPTION
--         "The value of tnMcFrIngrProfTableLastChanged indicates the sysUpTime
--          at the time of the last modification of an entry in the
--          tnMcFrIngrProfTable.
-- 
--          If no changes were made to the table since the last re-initialization
--          of the local network management subsystem, then this object
--          contains a zero value."
--     ::= { tnQosTimeStampObjects 80 }
-- 
-- tnMcFrIngrClassTableLastChanged OBJECT-TYPE
--     SYNTAX       TimeStamp
--     MAX-ACCESS   read-only
--     STATUS       current
--     DESCRIPTION
--         "The value of tnMcFrIngrClassTableLastChanged indicates the sysUpTime
--          at the time of the last modification of an entry in the
--          tnMcFrIngrClassTable.
-- 
--          If no changes were made to the table since the last re-initialization
--          of the local network management subsystem, then this object
--          contains a zero value."
--     ::= { tnQosTimeStampObjects 81 }
-- 
-- tnMcFrEgrProfTableLastChanged OBJECT-TYPE
--     SYNTAX       TimeStamp
--     MAX-ACCESS   read-only
--     STATUS       current
--     DESCRIPTION
--         "The value of tnMcFrEgrProfTableLastChanged indicates the sysUpTime
--          at the time of the last modification of an entry in the
--          tnMcFrEgrProfTable.
-- 
--          If no changes were made to the table since the last re-initialization
--          of the local network management subsystem, then this object
--          contains a zero value."
--     ::= { tnQosTimeStampObjects 82 }
-- 
-- tnMcFrEgrClassTableLastChanged OBJECT-TYPE
--     SYNTAX       TimeStamp
--     MAX-ACCESS   read-only
--     STATUS       current
--     DESCRIPTION
--         "The value of tnMcFrEgrClassTableLastChanged indicates the sysUpTime
--          at the time of the last modification of an entry in the
--          tnMcFrEgrClassTable.
-- 
--          If no changes were made to the table since the last re-initialization
--          of the local network management subsystem, then this object
--          contains a zero value."
--     ::= { tnQosTimeStampObjects 83 }

--
-- Atm Traffic Descriptor Table
--

-- tnAtmTdpTable OBJECT-TYPE
--     SYNTAX       SEQUENCE OF TnAtmTdpEntry
--     MAX-ACCESS   not-accessible
--     STATUS       current
--     DESCRIPTION
--         "This table contains information on ATM traffic
--          descriptors for controlling ATM traffic
--          management capabilities."
--     ::= { tnAtmTdpObjects 1}

-- tnAtmTdpEntry OBJECT-TYPE
--     SYNTAX       TnAtmTdpEntry
--     MAX-ACCESS   not-accessible
--     STATUS       current
--     DESCRIPTION
--         "This list contains ATM traffic descriptor
--          objects and the associated parameters. All objects that
--          do not apply to a given service category are given default
--          values of zero."
--     INDEX  {tnAtmTdpIndex}
--     ::= { tnAtmTdpTable 1}

-- TnAtmTdpEntry ::= SEQUENCE
--     {
--         tnAtmTdpIndex        AtmTrafficDescrParamIndex,
--         tnAtmTdpSir          Unsigned32,
--         tnAtmTdpPir          Unsigned32,
--         tnAtmTdpMbs          Unsigned32,
--         tnAtmTdpMir          Unsigned32,
--         tnAtmTdpShaping      INTEGER,
--         tnAtmTdpServCat      AtmServiceCategory,
--         tnAtmTdpDescription  TItemDescription,
--         tnAtmTdpLastChanged  TimeStamp,
--         tnAtmTdpRowStatus    RowStatus,
--         tnAtmTdpDescrType    TAtmTdpDescrType,
--         tnAtmTdpCdvt         Unsigned32,
--         tnAtmTdpPolicing     INTEGER,
--         tnAtmTdpCLPTagging   INTEGER
--     }

-- tnAtmTdpIndex OBJECT-TYPE
--     SYNTAX       AtmTrafficDescrParamIndex (1..1000)
--     MAX-ACCESS   not-accessible
--     STATUS       current
--     DESCRIPTION
--         "This object is used to identify an entity
--          inside the tnAtmTdpTable.
--          When creating a new row in the table
--          the value of this index may be obtained
--          by retrieving the value of tnAtmTdpIndexNext."
--     ::= { tnAtmTdpEntry 1 }

-- tnAtmTdpSir OBJECT-TYPE
--     SYNTAX       Unsigned32 (0..4294967295)
--     MAX-ACCESS   read-create
--     STATUS       current
--     DESCRIPTION
--         "tnAtmTdpSir identifies the sustained information rate
--          in kilobits per second.
--          The default Sir is determined by the Service Category.
--          The following default applies to Sir that is modifiable
--          depending upon a given service category:

--            Applicable Service Category  Default Sir Value
--                    RT-VBR                       0
--                   NRT-VBR                       0

--          Note that for the service categories given above,
--          the value of Sir must be less than or equal to
--          the value of Pir."
--     ::= { tnAtmTdpEntry 2 }

-- tnAtmTdpPir OBJECT-TYPE
--     SYNTAX       Unsigned32 (0..4294967295)
--     MAX-ACCESS   read-create
--     STATUS       current
--     DESCRIPTION
--         "tnAtmTdpPir identifies the peak information rate
--          in kilobits per second.
--          The default Pir is determined by the Service Category.
--          The following default applies to Pir that is modifiable
--          depending upon a given service category:

--            Applicable Service Category   Default Pir Value
--                 UBR (with/without Mir)          4294967295
--                 CBR                             0
--              RT-VBR                             0
--             NRT-VBR                             0"
--     ::= { tnAtmTdpEntry 3 }

-- tnAtmTdpMbs OBJECT-TYPE
--     SYNTAX       Unsigned32 (0..4294967295)
--     MAX-ACCESS   read-create
--     STATUS       current
--     DESCRIPTION
--         "tnAtmTdpMbs identifies the maximum burst size
--          in cells.
--          The default Mbs is determined by the Service Category.
--          The following default applies to Mbs that is modifiable
--          depending upon a given service category:

--            Applicable Service Category  Default Mbs Value
--                     RT-VBR                     32
--                    NRT-VBR                     32"
--     ::= { tnAtmTdpEntry 4 }

-- tnAtmTdpMir OBJECT-TYPE
--     SYNTAX       Unsigned32 (0..4294967295)
--     MAX-ACCESS   read-create
--     STATUS       current
--     DESCRIPTION
--         "tnAtmTdpMir identifies the Minimum Information Rate
--          in kilobits per second.
--          The default Mir is determined by the Service Category.
--          The following default applies for Mir that is modifiable
--          depending upon a given service category:

--            Applicable Service Category  Default Mir Value
--              UBR (with/without Mir)             0

--          Note that for the service categories given above,
--          the value of Mir must be less than or equal to
--          the value of Pir."
--     ::= { tnAtmTdpEntry 5 }

-- tnAtmTdpShaping OBJECT-TYPE
--     SYNTAX       INTEGER {
--                      disabled(0),
--                      enabled(1)
--                  }
--     MAX-ACCESS   read-create
--     STATUS       current
--     DESCRIPTION
--         "tnAtmTdpShaping determines whether egress shaping should occur.
--          The default tnAtmTdpShaping is determined by the Service Category.
--          The following default applies for tnAtmTdpShaping
--          depending upon a given service category:

--           Applicable Service Category  Default Shaping Value
--                 UBR                         disabled
--                 CBR                         enabled
--              RT-VBR                         enabled
--             NRT-VBR                         enabled

--          For a Service Category of UBR, tnAtmTdpShaping cannot be enabled.
        
--          For CBR and RT-VBR service cateories disabling shaping is 
--          MDA-dependent.

--          Shaping is only applied in the egress direction."
--     ::= { tnAtmTdpEntry 6 }

-- tnAtmTdpServCat OBJECT-TYPE
--     SYNTAX       AtmServiceCategory
--     MAX-ACCESS   read-create
--     STATUS       current
--     DESCRIPTION
--         "tnAtmTdpServCat determines the ATM service category."
--     DEFVAL { ubr }
--     ::= { tnAtmTdpEntry 7 }

-- tnAtmTdpDescription OBJECT-TYPE
--     SYNTAX       TItemDescription
--     MAX-ACCESS   read-create
--     STATUS       current
--     DESCRIPTION
--         "The value of tnAtmTdpDescription specifies an ASCII string used
--          to describe the ATM traffic descriptor."
--     ::= { tnAtmTdpEntry 8 }

-- tnAtmTdpLastChanged OBJECT-TYPE
--     SYNTAX       TimeStamp
--     MAX-ACCESS   read-only
--     STATUS       current
--     DESCRIPTION
--         "tnAtmTdpLastChanged maintains the timestamp of the last change
--          made to a row in the Traffic Descriptor Profile Table."
--     ::= { tnAtmTdpEntry 9 }

-- tnAtmTdpRowStatus OBJECT-TYPE
--     SYNTAX       RowStatus
--     MAX-ACCESS   read-create
--     STATUS       current
--     DESCRIPTION
--         "tnAtmTdpRowStatus is used to create/modify/delete a new row in
--          this table. Only createAndGo/Active/Destroy are supported"
--     ::= { tnAtmTdpEntry 10 }

-- tnAtmTdpDescrType OBJECT-TYPE
--     SYNTAX       TAtmTdpDescrType
--     MAX-ACCESS   read-create
--     STATUS       current
--     DESCRIPTION
--         "tnAtmTdpDescrType identifies the types of ATM traffic descriptor.
--          The default is determined by the value of tnAtmTdpServCat.
--          The following default rules apply:

--          Applicable Service Category       tnAtmTdpDescrType
--                 UBR                          clp0And1pcr
--                 CBR                          clp0And1pcr
--              RT-VBR                    clp0And1pcrPlusClp0And1scr
--             NRT-VBR                    clp0And1pcrPlusClp0And1scr"
--     ::= { tnAtmTdpEntry 11 }

-- tnAtmTdpCdvt OBJECT-TYPE
--     SYNTAX       Unsigned32 (0..4294967295)
--     MAX-ACCESS   read-create
--     STATUS       current
--     DESCRIPTION
--         "tnAtmTdpCdvt identifies the Cell Delay Variation
--          Tolerance in microseconds.
--          The following default applies for Cdvt that is modifiable
--          depending upon a given service category:

--            Applicable Service Category  Default Cdvt Value
--              CBR/RT-VBR/NRT-VBR/UBR             250 "

--     ::= { tnAtmTdpEntry 12 }

-- tnAtmTdpPolicing OBJECT-TYPE
--     SYNTAX       INTEGER {
--                      disabled(0),
--                      enabled(1)
--                  }
--     MAX-ACCESS   read-create
--     STATUS       current
--     DESCRIPTION
--         "tnAtmTdpPolicing determines whether ingress traffic is policed.
--          Policing by default is disabled. Policing is valid for CBR, UBR
--          RT-VBR and NRT-VBR. This is cell-based policing.

--           tnAtmTdpDescrType           Policing Scheme    Applicable Serv Cat
--            clp0And1pcr                 CBR.1             CBR and UBR
--            clp0And1pcrPlusClp0And1scr  VBR.1             RT/NRT-VBR
--            clp0And1pcrPlusClp0scr      VBR.2             RT/NRT-VBR
--            clp0And1pcrPlusClp0scrTag   VBR.3             RT/NRT-VBR"
--     ::= { tnAtmTdpEntry 13 }

-- tnAtmTdpCLPTagging OBJECT-TYPE
--     SYNTAX       INTEGER {
--                      disabled(0),
--                      enabled(1)
--                  }
--     MAX-ACCESS   read-create
--     STATUS       current
--     DESCRIPTION
--         "tnAtmTdpCLPTagging controls the setting of the CLP bit in the 
--          ATM cell  header for egress traffic on an IES or VPRN SAP. 
--          If disabled (the default), all traffic has the CLP bit set 
--          to zero. If enabled, traffic queued on expedited queues has 
--          the CLP bit set to zero, while traffic on non-expedited queues 
--          has the CLP bit set to one."
--     DEFVAL { 0 }
--     ::= { tnAtmTdpEntry 14 }



--
-- Named Pool Policy Table
--

-- tnNamedPoolPolicyTable OBJECT-TYPE
--     SYNTAX       SEQUENCE OF TNamedPoolPolicyEntry
--     MAX-ACCESS   not-accessible
--     STATUS       current
--     DESCRIPTION
--         "This table contains information on Named buffer pools policy."
--     ::= { tnPoolObjects 1 }
-- 
-- tnNamedPoolPolicyEntry OBJECT-TYPE
--     SYNTAX       TNamedPoolPolicyEntry
--     MAX-ACCESS   not-accessible
--     STATUS       current
--     DESCRIPTION
--         "This list contains Named buffer pools policy related information."
--     INDEX  {tnSysSwitchId, tnNamedPoolPolicyName}
--     ::= { tnNamedPoolPolicyTable 1}
-- 
-- TNamedPoolPolicyEntry ::= SEQUENCE
--     {
--        tnNamedPoolPolicyName               TNamedItem,
--        tnNamedPoolPolicyRowStatus          RowStatus,
--        tnNamedPoolPolicyLastChanged        TimeStamp,
--        tnNamedPoolPolicyDescription        TItemDescription,
--        tnNamedPoolPolicyQ1DefaultWeight    Unsigned32,
--        tnNamedPoolPolicyQ1MdaWeight        Unsigned32,
--        tnNamedPoolPolicyQ1PortWeight       Unsigned32
--     }
-- 
-- tnNamedPoolPolicyName OBJECT-TYPE
--     SYNTAX      TNamedItem
--     MAX-ACCESS  not-accessible
--     STATUS      current
--     DESCRIPTION
--         "The value of tnNamedPoolPolicyName indicates the name of 
--          Named pool policy."
--     ::= { tnNamedPoolPolicyEntry 1 }
-- 
-- tnNamedPoolPolicyRowStatus OBJECT-TYPE
--     SYNTAX      RowStatus
--     MAX-ACCESS  read-create
--     STATUS      current
--     DESCRIPTION
--         "The value of tnNamedPoolPolicyRowStatus is used for 
--          creation or deletion of named pool policies."
--     ::= { tnNamedPoolPolicyEntry 2 }
-- 
-- tnNamedPoolPolicyLastChanged OBJECT-TYPE
--     SYNTAX      TimeStamp
--     MAX-ACCESS  read-only
--     STATUS      current
--     DESCRIPTION
--         "The value of tnNamedPoolPolicyLastChanged indicates the 
--          sysUpTime when this row was last modified."
--     ::= { tnNamedPoolPolicyEntry 3 }
-- 
-- tnNamedPoolPolicyDescription OBJECT-TYPE
--     SYNTAX      TItemDescription
--     MAX-ACCESS  read-create
--     STATUS      current
--     DESCRIPTION
--         "The value of tnNamedPoolPolicyDescription specifies the 
--          description for a specific named pool policy."
--     DEFVAL { "" }
--     ::= { tnNamedPoolPolicyEntry 4 }
-- 
-- tnNamedPoolPolicyQ1DefaultWeight OBJECT-TYPE
--     SYNTAX      Unsigned32 (0..100)
--     MAX-ACCESS  read-create
--     STATUS      current
--     DESCRIPTION
--         "The value of tnNamedPoolPolicyQ1DefaultWeight specifies 
--          the port allocation weight given to the default pools."
--     DEFVAL { 50 }
--     ::= { tnNamedPoolPolicyEntry 5 }
-- 
-- tnNamedPoolPolicyQ1MdaWeight OBJECT-TYPE
--     SYNTAX      Unsigned32 (0..100)
--     MAX-ACCESS  read-create
--     STATUS      current
--     DESCRIPTION
--         "The value of tnNamedPoolPolicyQ1MdaWeight specifies 
--          the port allocation weight given to the MDA named pools."
--     DEFVAL { 50 }
--     ::= { tnNamedPoolPolicyEntry 6 }
-- 
-- tnNamedPoolPolicyQ1PortWeight OBJECT-TYPE
--     SYNTAX      Unsigned32 (0..100)
--     MAX-ACCESS  read-create
--     STATUS      current
--     DESCRIPTION
--         "The value of tnNamedPoolPolicyQ1PortWeight specifies 
--          the port allocation weight given to the local port 
--          named pools."
--     DEFVAL { 50 }
--     ::= { tnNamedPoolPolicyEntry 7 }

--
-- Q1 Named Pool Table
--

-- tnQ1NamedPoolTable OBJECT-TYPE
--     SYNTAX       SEQUENCE OF TQ1NamedPoolEntry
--     MAX-ACCESS   not-accessible
--     STATUS       current
--     DESCRIPTION
--         "This table contains information on Q1 pools policy."
--     ::= { tnPoolObjects 2 }
-- 
-- tnQ1NamedPoolEntry OBJECT-TYPE
--     SYNTAX       TQ1NamedPoolEntry
--     MAX-ACCESS   not-accessible
--     STATUS       current
--     DESCRIPTION
--         "This list contains Q1 pools policy related information."
--     INDEX  {tnSysSwitchId, tnQ1NamedPoolPolicyName, 
--             tnQ1NamedPoolName}
--     ::= { tnQ1NamedPoolTable 1}
-- 
-- TQ1NamedPoolEntry ::= SEQUENCE
--     {
--        tnQ1NamedPoolPolicyName               TNamedItem,
--        tnQ1NamedPoolName                     TNamedItem,
--        tnQ1NamedPoolRowStatus                RowStatus,
--        tnQ1NamedPoolLastChanged              TimeStamp,
--        tnQ1NamedPoolDescription              TItemDescription,
--        tnQ1NamedPoolNetworkAllocWeight       Unsigned32,
--        tnQ1NamedPoolAccessAllocWeight        Unsigned32,
--        tnQ1NamedPoolSlopePolicy              TNamedItemOrEmpty,
--        tnQ1NamedPoolReservedCbs              Integer32
--     }
-- 
-- tnQ1NamedPoolPolicyName OBJECT-TYPE
--     SYNTAX      TNamedItem
--     MAX-ACCESS  not-accessible
--     STATUS      current
--     DESCRIPTION
--         "The value of tnQ1NamedPoolPolicyName indicates the name of 
--          the existing Q1 named pool policy."
--     ::= { tnQ1NamedPoolEntry 1 }
-- 
-- tnQ1NamedPoolName OBJECT-TYPE
--     SYNTAX      TNamedItem
--     MAX-ACCESS  not-accessible
--     STATUS      current
--     DESCRIPTION
--         "The value of tnQ1NamedPoolName indicates the name of 
--          the existing pool within the policy."
--     ::= { tnQ1NamedPoolEntry 2 }
-- 
-- tnQ1NamedPoolRowStatus OBJECT-TYPE
--     SYNTAX      RowStatus
--     MAX-ACCESS  read-create
--     STATUS      current
--     DESCRIPTION
--         "The value of tnQ1NamedPoolRowStatus is used for 
--          creation or deletion of Q1 named pools."       
--     ::= { tnQ1NamedPoolEntry 3 }
-- 
-- tnQ1NamedPoolLastChanged OBJECT-TYPE
--     SYNTAX      TimeStamp
--     MAX-ACCESS  read-only
--     STATUS      current
--     DESCRIPTION
--         "The value of tnQ1NamedPoolLastChanged indicates the 
--          sysUpTime when this row was last modified. "
--     ::= { tnQ1NamedPoolEntry 4 }
-- 
-- tnQ1NamedPoolDescription OBJECT-TYPE
--     SYNTAX      TItemDescription
--     MAX-ACCESS  read-create
--     STATUS      current
--     DESCRIPTION
--         "The value of tnQ1NamedPoolDescription specifies the 
--          description for a specific Q1 named pool."
--     DEFVAL { "" }
--     ::= { tnQ1NamedPoolEntry 5 }
-- 
-- tnQ1NamedPoolNetworkAllocWeight OBJECT-TYPE
--     SYNTAX      Unsigned32 (0..100)
--     MAX-ACCESS  read-create
--     STATUS      current
--     DESCRIPTION
--         "The value of tnQ1NamedPoolNetworkAllocWeight specifies 
--          the weight used to divide network associated buffer 
--          space between named pools."
--     DEFVAL { 50 }
--     ::= { tnQ1NamedPoolEntry 6 }
-- 
-- 
-- tnQ1NamedPoolAccessAllocWeight OBJECT-TYPE
--     SYNTAX      Unsigned32 (0..100)
--     MAX-ACCESS  read-create
--     STATUS      current
--     DESCRIPTION
--         "The value of tnQ1NamedPoolAccessAllocWeight specifies 
--          the weight used to divide access associated buffer 
--          space between named pools."
--     DEFVAL { 50 }
--     ::= { tnQ1NamedPoolEntry 7 }
-- 
-- tnQ1NamedPoolSlopePolicy OBJECT-TYPE
--     SYNTAX      TNamedItemOrEmpty
--     MAX-ACCESS  read-create
--     STATUS      current
--     DESCRIPTION
--         "The value of tnQ1NamedPoolSlopePolicy specifies the 
--          name of the slop-policy which is used to override 
--          the default slope-policy for the named buffer pool."
--     DEFVAL { ''H }
--     ::= { tnQ1NamedPoolEntry 8 }
-- 
-- tnQ1NamedPoolReservedCbs OBJECT-TYPE
--     SYNTAX      Integer32
--     MAX-ACCESS  read-create
--     STATUS      current
--     DESCRIPTION
--         "The value of tnQ1NamedPoolReservedCbs specifies the 
--          reserved CBS size of the pool. The reserved CBS 
--          (Committed Burst Size) defines the amount of buffer 
--          space within the pool that is not considered shared."
--     DEFVAL { 30 }
--     ::= { tnQ1NamedPoolEntry 9 }

--
-- The following object may be used in conjunction with
-- the atmTrafficDescrParamTable for the creation of
-- new table entries.
--

-- tnAtmTdpIndexNext OBJECT-TYPE
--     SYNTAX       Integer32 (0..1000)
--     MAX-ACCESS   read-only
--     STATUS       current
--     DESCRIPTION
--         "This object contains an appropriate value to be used for
--          tnAtmTdpIndex when creating entries in the tnAtmTdpTable.
--          The value 0 indicates that no unassigned entries are
--          available. To obtain the tnAtmTdpIndex value for a new
--          entry, the manager issues a management protocol
--          retrieval operation to obtain the current value of this
--          object.  After each retrieval, the agent should modify the
--          value to the next unassigned index.
--          After a manager retrieves a value the agent will determine
--          through its local policy when this index value will be made
--          available for reuse."
--     ::= { tnAtmTdpObjects 2 }

---
--- The following objects are to be used in
--- conjunction with the tnAtmTdpTable
--- for information on profile limits and consumed
--- profiles.
---

-- tnAtmTdpsMaxSupported OBJECT-TYPE
--     SYNTAX       Integer32
--     MAX-ACCESS   read-only
--     STATUS       current
--     DESCRIPTION
--         "This object contains the maximum number of ATM
--          Traffic Descriptor Profiles that can be configured
--          on this system."
--     ::= { tnAtmTdpObjects 3 }

-- tnAtmTdpsCurrentlyConfigured OBJECT-TYPE
--     SYNTAX       Integer32
--     MAX-ACCESS   read-only
--     STATUS       current
--     DESCRIPTION
--         "This object contains the number of currently configured
--          ATM Traffic Descriptor Profiles on this system."
--     ::= { tnAtmTdpObjects 4 }

--
-- Hsmda Pool Policy Table
--

-- tnHsmdaPoolPolicyTable OBJECT-TYPE
--     SYNTAX      SEQUENCE OF THsmdaPoolPolicyEntry
--     MAX-ACCESS  not-accessible
--     STATUS      current
--     DESCRIPTION
--         "The tnHsmdaPoolPolicyTable has an entry for each HSMDA pool
--          policy configured on this system."
--     ::= { tnPoolObjects 3 }
-- 
-- tnHsmdaPoolPolicyEntry    OBJECT-TYPE
--     SYNTAX      THsmdaPoolPolicyEntry
--     MAX-ACCESS  not-accessible
--     STATUS      current
--     DESCRIPTION
--         "Each row represents a particular HSMDA pool policy. Entries are 
--          created and deleted by the user."
--     INDEX { tnSysSwitchId, tnHsmdaPoolPolicyName }
--     ::= { tnHsmdaPoolPolicyTable 1}
-- 
-- THsmdaPoolPolicyEntry ::= SEQUENCE
--     {
--          tnHsmdaPoolPolicyName             TNamedItem,
--          tnHsmdaPoolPolicyRowStatus        RowStatus,
--          tnHsmdaPoolLastChanged            TimeStamp,
--          tnHsmdaPoolDescription            TItemDescription,
--          tnHsmdaPoolSystemReserve          Unsigned32,
--          tnHsmdaPoolRoot1AllocWeight       TWeight,
--          tnHsmdaPoolRoot2AllocWeight       TWeight,
--          tnHsmdaPoolRoot3AllocWeight       TWeight,
--          tnHsmdaPoolRoot4AllocWeight       TWeight,
--          tnHsmdaPoolRoot5AllocWeight       TWeight,
--          tnHsmdaPoolRoot6AllocWeight       TWeight,
--          tnHsmdaPoolRoot7AllocWeight       TWeight,
--          tnHsmdaPoolRoot8AllocWeight       TWeight,
--          tnHsmdaPoolClass1Parent           Unsigned32,
--          tnHsmdaPoolClass1AllocPercent     Unsigned32,
--          tnHsmdaPoolClass2Parent           Unsigned32,
--          tnHsmdaPoolClass2AllocPercent     Unsigned32,
--          tnHsmdaPoolClass3Parent           Unsigned32,
--          tnHsmdaPoolClass3AllocPercent     Unsigned32,
--          tnHsmdaPoolClass4Parent           Unsigned32,
--          tnHsmdaPoolClass4AllocPercent     Unsigned32,
--          tnHsmdaPoolClass5Parent           Unsigned32,
--          tnHsmdaPoolClass5AllocPercent     Unsigned32,
--          tnHsmdaPoolClass6Parent           Unsigned32,
--          tnHsmdaPoolClass6AllocPercent     Unsigned32,
--          tnHsmdaPoolClass7Parent           Unsigned32,
--          tnHsmdaPoolClass7AllocPercent     Unsigned32,
--          tnHsmdaPoolClass8Parent           Unsigned32,
--          tnHsmdaPoolClass8AllocPercent     Unsigned32
--     }
-- 
-- tnHsmdaPoolPolicyName        OBJECT-TYPE
--     SYNTAX      TNamedItem
--     MAX-ACCESS  not-accessible
--     STATUS      current
--     DESCRIPTION
--         "The value of tnHsmdaPoolPolicyName specifies the name of the HSMDA
--          pool policy."
--     ::= { tnHsmdaPoolPolicyEntry 1 }
-- 
-- tnHsmdaPoolPolicyRowStatus        OBJECT-TYPE
--     SYNTAX      RowStatus
--     MAX-ACCESS  read-create
--     STATUS      current
--     DESCRIPTION
--         "The value of tnHsmdaPoolPolicyRowStatus is used for the creation
--          and deletion of HSMDA pool policies."
--     ::= { tnHsmdaPoolPolicyEntry 2 }
-- 
-- tnHsmdaPoolLastChanged        OBJECT-TYPE
--     SYNTAX      TimeStamp
--     MAX-ACCESS  read-only
--     STATUS      current
--     DESCRIPTION
--         "The value of tnHsmdaPoolLastChanged indicates the sysUpTime
--          at the time of the last modification of this entry.
-- 
--          If no changes were made to the entry since the last
--          re-initialization of the local network management subsystem,
--          then this object contains a zero value."
--     ::= { tnHsmdaPoolPolicyEntry 3 }
-- 
-- tnHsmdaPoolDescription        OBJECT-TYPE
--     SYNTAX      TItemDescription
--     MAX-ACCESS  read-create
--     STATUS      current
--     DESCRIPTION
--         "The value of tnHsmdaPoolDescription specifies the description
--          of this HSMDA pool policy."
--     DEFVAL { "" }
--     ::= { tnHsmdaPoolPolicyEntry 4 }
-- 
-- tnHsmdaPoolSystemReserve        OBJECT-TYPE
--     SYNTAX      Unsigned32 (100..3000)
--     UNITS       "hundredths of a percent"
--     MAX-ACCESS  read-create
--     STATUS      current
--     DESCRIPTION
--         "The value of tnHsmdaPoolSystemReserve specifies the percentage of HSMDA
--          buffers that will be reserved for internal system use.
-- 
--          When this value is set, all the provisioned buffer pool allocation
--          sizes will be re-evaluated. This includes the port class allocations
--          specified by indirectly by tmnxPortIngPoolPercentRate and 
--          tmnxPortEgrPoolPercentRate, and class and root pools specified
--          indirectly by tnHsmdaPoolClass1AllocPercent through
--          tnHsmdaPoolClass8AllocPercent and tnHsmdaPoolRoot1AllocWeight through
--          tnHsmdaPoolRoot8AllocWeight."
--     DEFVAL { 1000 }
--     ::= { tnHsmdaPoolPolicyEntry 5 }
-- 
-- tnHsmdaPoolRoot1AllocWeight        OBJECT-TYPE
--     SYNTAX      TWeight (1..100)
--     MAX-ACCESS  read-create
--     STATUS      current
--     DESCRIPTION
--         "The value of tnHsmdaPoolRoot1AllocWeight specifies the weight that
--          will be applied to the first root pool and is divided by the sum
--          of all root pool weights to derive the pool's buffer allocation
--          factor."
--     DEFVAL { 75 }
--     ::= { tnHsmdaPoolPolicyEntry 6 }
-- 
-- tnHsmdaPoolRoot2AllocWeight        OBJECT-TYPE
--     SYNTAX      TWeight
--     MAX-ACCESS  read-create
--     STATUS      current
--     DESCRIPTION
--         "The value of tnHsmdaPoolRoot2AllocWeight specifies the weight that
--          will be applied to the second root pool and is divided by the sum
--          of all root pool weights to derive the pool's buffer allocation
--          factor."
--     DEFVAL { 25 }
--     ::= { tnHsmdaPoolPolicyEntry 7 }
-- 
-- tnHsmdaPoolRoot3AllocWeight        OBJECT-TYPE
--     SYNTAX      TWeight
--     MAX-ACCESS  read-create
--     STATUS      current
--     DESCRIPTION
--         "The value of tnHsmdaPoolRoot3AllocWeight specifies the weight that
--          will be applied to the third root pool and is divided by the sum
--          of all root pool weights to derive the pool's buffer allocation
--          factor."
--     DEFVAL { 0 }
--     ::= { tnHsmdaPoolPolicyEntry 8 }
-- 
-- tnHsmdaPoolRoot4AllocWeight        OBJECT-TYPE
--     SYNTAX      TWeight
--     MAX-ACCESS  read-create
--     STATUS      current
--     DESCRIPTION
--         "The value of tnHsmdaPoolRoot4AllocWeight specifies the weight that
--          will be applied to the fourth root pool and is divided by the sum
--          of all root pool weights to derive the pool's buffer allocation
--          factor."
--     DEFVAL { 0 }
--     ::= { tnHsmdaPoolPolicyEntry 9 }
-- 
-- tnHsmdaPoolRoot5AllocWeight        OBJECT-TYPE
--     SYNTAX      TWeight
--     MAX-ACCESS  read-create
--     STATUS      current
--     DESCRIPTION
--         "The value of tnHsmdaPoolRoot5AllocWeight specifies the weight that
--          will be applied to the fifth root pool and is divided by the sum
--          of all root pool weights to derive the pool's buffer allocation
--          factor."
--     DEFVAL { 0 }
--     ::= { tnHsmdaPoolPolicyEntry 10 }
-- 
-- tnHsmdaPoolRoot6AllocWeight        OBJECT-TYPE
--     SYNTAX      TWeight
--     MAX-ACCESS  read-create
--     STATUS      current
--     DESCRIPTION
--         "The value of tnHsmdaPoolRoot6AllocWeight specifies the weight that
--          will be applied to the sixth root pool and is divided by the sum
--          of all root pool weights to derive the pool's buffer allocation
--          factor."
--     DEFVAL { 0 }
--     ::= { tnHsmdaPoolPolicyEntry 11 }
-- 
-- tnHsmdaPoolRoot7AllocWeight        OBJECT-TYPE
--     SYNTAX      TWeight
--     MAX-ACCESS  read-create
--     STATUS      current
--     DESCRIPTION
--         "The value of tnHsmdaPoolRoot7AllocWeight specifies the weight that
--          will be applied to the seventh root pool and is divided by the sum
--          of all root pool weights to derive the pool's buffer allocation
--          factor."
--     DEFVAL { 0 }
--     ::= { tnHsmdaPoolPolicyEntry 12 }
-- 
-- tnHsmdaPoolRoot8AllocWeight        OBJECT-TYPE
--     SYNTAX      TWeight
--     MAX-ACCESS  read-create
--     STATUS      current
--     DESCRIPTION
--         "The value of tnHsmdaPoolRoot8AllocWeight specifies the weight that
--          will be applied to the eighth root pool and is divided by the sum
--          of all root pool weights to derive the pool's buffer allocation
--          factor."
--     DEFVAL { 0 }
--     ::= { tnHsmdaPoolPolicyEntry 13 }
-- 
-- tnHsmdaPoolClass1Parent        OBJECT-TYPE
--     SYNTAX      Unsigned32 (1..8)
--     MAX-ACCESS  read-create
--     STATUS      current
--     DESCRIPTION
--         "The value of tnHsmdaPoolClass1Parent specifies the root pool to which
--          the first class pool will be associated."
--     DEFVAL { 1 }
--     ::= { tnHsmdaPoolPolicyEntry 14 }
-- 
-- tnHsmdaPoolClass1AllocPercent        OBJECT-TYPE
--     SYNTAX      Unsigned32 (1..10000)
--     UNITS       "hundredths of a percent"
--     MAX-ACCESS  read-create
--     STATUS      current
--     DESCRIPTION
--         "The value of tnHsmdaPoolClass1AllocPercent specifies, indirectly,
--          the size of the first class pool. The specified percentage, in
--          hundredths of a percent, determines what percentage of the root
--          pool with which it is associated, as specified by
--          tnHsmdaPoolClass1Parent, will be available to this class.
-- 
--          The sum of the class pool percentages for a root pool may exceed
--          100 percent(10000 hundredths of a percent), allowing the root pool
--          to be oversubscribed. The sum of the class pool percentages for
--          a root pool may also total less than 100 percent, allowing the
--          root pool to be undersubscribed."
--     DEFVAL { 4000 }
--     ::= { tnHsmdaPoolPolicyEntry 15 }
-- 
-- tnHsmdaPoolClass2Parent        OBJECT-TYPE
--     SYNTAX      Unsigned32 (1..8)
--     MAX-ACCESS  read-create
--     STATUS      current
--     DESCRIPTION
--         "The value of tnHsmdaPoolClass2Parent specifies the root pool to which
--          the second class pool will be associated."
--     DEFVAL { 1 }
--     ::= { tnHsmdaPoolPolicyEntry 16 }
-- 
-- tnHsmdaPoolClass2AllocPercent        OBJECT-TYPE
--     SYNTAX      Unsigned32 (1..10000)
--     UNITS       "hundredths of a percent"
--     MAX-ACCESS  read-create
--     STATUS      current
--     DESCRIPTION
--         "The value of tnHsmdaPoolClass2AllocPercent specifies, indirectly,
--          the size of the first class pool. The specified percentage, in
--          hundredths of a percent, determines what percentage of the root
--          pool with which it is associated, as specified by
--          tnHsmdaPoolClass2Parent, will be available to this class.
-- 
--          The sum of the class pool percentages for a root pool may exceed
--          100 percent(10000 hundredths of a percent), allowing the root pool
--          to be oversubscribed. The sum of the class pool percentages for
--          a root pool may also total less than 100 percent, allowing the
--          root pool to be undersubscribed."
--     DEFVAL { 3500 }
--     ::= { tnHsmdaPoolPolicyEntry 17 }
-- 
-- tnHsmdaPoolClass3Parent        OBJECT-TYPE
--     SYNTAX      Unsigned32 (1..8)
--     MAX-ACCESS  read-create
--     STATUS      current
--     DESCRIPTION
--         "The value of tnHsmdaPoolClass3Parent specifies the root pool to which
--          the third class pool will be associated."
--     DEFVAL { 1 }
--     ::= { tnHsmdaPoolPolicyEntry 18 }
-- 
-- tnHsmdaPoolClass3AllocPercent        OBJECT-TYPE
--     SYNTAX      Unsigned32 (1..10000)
--     UNITS       "hundredths of a percent"
--     MAX-ACCESS  read-create
--     STATUS      current
--     DESCRIPTION
--         "The value of tnHsmdaPoolClass3AllocPercent specifies, indirectly,
--          the size of the first class pool. The specified percentage, in
--          hundredths of a percent, determines what percentage of the root
--          pool with which it is associated, as specified by
--          tnHsmdaPoolClass3Parent, will be available to this class.
-- 
--          The sum of the class pool percentages for a root pool may exceed
--          100 percent(10000 hundredths of a percent), allowing the root pool
--          to be oversubscribed. The sum of the class pool percentages for
--          a root pool may also total less than 100 percent, allowing the
--          root pool to be undersubscribed."
--     DEFVAL { 3000 }
--     ::= { tnHsmdaPoolPolicyEntry 19 }
-- 
-- tnHsmdaPoolClass4Parent        OBJECT-TYPE
--     SYNTAX      Unsigned32 (1..8)
--     MAX-ACCESS  read-create
--     STATUS      current
--     DESCRIPTION
--         "The value of tnHsmdaPoolClass4Parent specifies the root pool to which
--          the fourth class pool will be associated."
--     DEFVAL { 1 }
--     ::= { tnHsmdaPoolPolicyEntry 20 }
-- 
-- tnHsmdaPoolClass4AllocPercent        OBJECT-TYPE
--     SYNTAX      Unsigned32 (1..10000)
--     UNITS       "hundredths of a percent"
--     MAX-ACCESS  read-create
--     STATUS      current
--     DESCRIPTION
--         "The value of tnHsmdaPoolClass4AllocPercent specifies, indirectly,
--          the size of the first class pool. The specified percentage, in
--          hundredths of a percent, determines what percentage of the root
--          pool with which it is associated, as specified by
--          tnHsmdaPoolClass4Parent, will be available to this class.
-- 
--          The sum of the class pool percentages for a root pool may exceed
--          100 percent(10000 hundredths of a percent), allowing the root pool
--          to be oversubscribed. The sum of the class pool percentages for
--          a root pool may also total less than 100 percent, allowing the
--          root pool to be undersubscribed."
--     DEFVAL { 2500 }
--     ::= { tnHsmdaPoolPolicyEntry 21 }
-- 
-- tnHsmdaPoolClass5Parent        OBJECT-TYPE
--     SYNTAX      Unsigned32 (1..8)
--     MAX-ACCESS  read-create
--     STATUS      current
--     DESCRIPTION
--         "The value of tnHsmdaPoolClass5Parent specifies the root pool to which
--          the fifth class pool will be associated."
--     DEFVAL { 1 }
--     ::= { tnHsmdaPoolPolicyEntry 22 }
-- 
-- tnHsmdaPoolClass5AllocPercent        OBJECT-TYPE
--     SYNTAX      Unsigned32 (1..10000)
--     UNITS       "hundredths of a percent"
--     MAX-ACCESS  read-create
--     STATUS      current
--     DESCRIPTION
--         "The value of tnHsmdaPoolClass5AllocPercent specifies, indirectly,
--          the size of the first class pool. The specified percentage, in
--          hundredths of a percent, determines what percentage of the root
--          pool with which it is associated, as specified by
--          tnHsmdaPoolClass5Parent, will be available to this class.
-- 
--          The sum of the class pool percentages for a root pool may exceed
--          100 percent(10000 hundredths of a percent), allowing the root pool
--          to be oversubscribed. The sum of the class pool percentages for
--          a root pool may also total less than 100 percent, allowing the
--          root pool to be undersubscribed."
--     DEFVAL { 2000 }
--     ::= { tnHsmdaPoolPolicyEntry 23 }
-- 
-- tnHsmdaPoolClass6Parent        OBJECT-TYPE
--     SYNTAX      Unsigned32 (1..8)
--     MAX-ACCESS  read-create
--     STATUS      current
--     DESCRIPTION
--         "The value of tnHsmdaPoolClass6Parent specifies the root pool to which
--          the sixth class pool will be associated."
--     DEFVAL { 2 }
--     ::= { tnHsmdaPoolPolicyEntry 24 }
-- 
-- tnHsmdaPoolClass6AllocPercent        OBJECT-TYPE
--     SYNTAX      Unsigned32 (1..10000)
--     UNITS       "hundredths of a percent"
--     MAX-ACCESS  read-create
--     STATUS      current
--     DESCRIPTION
--         "The value of tnHsmdaPoolClass6AllocPercent specifies, indirectly,
--          the size of the first class pool. The specified percentage, in
--          hundredths of a percent, determines what percentage of the root
--          pool with which it is associated, as specified by
--          tnHsmdaPoolClass6Parent, will be available to this class.
-- 
--          The sum of the class pool percentages for a root pool may exceed
--          100 percent(10000 hundredths of a percent), allowing the root pool
--          to be oversubscribed. The sum of the class pool percentages for
--          a root pool may also total less than 100 percent, allowing the
--          root pool to be undersubscribed."
--     DEFVAL { 5000 }
--     ::= { tnHsmdaPoolPolicyEntry 25 }
-- 
-- tnHsmdaPoolClass7Parent        OBJECT-TYPE
--     SYNTAX      Unsigned32 (1..8)
--     MAX-ACCESS  read-create
--     STATUS      current
--     DESCRIPTION
--         "The value of tnHsmdaPoolClass7Parent specifies the root pool to which
--          the seventh class pool will be associated."
--     DEFVAL { 2 }
--     ::= { tnHsmdaPoolPolicyEntry 26 }
-- 
-- tnHsmdaPoolClass7AllocPercent        OBJECT-TYPE
--     SYNTAX      Unsigned32 (1..10000)
--     UNITS       "hundredths of a percent"
--     MAX-ACCESS  read-create
--     STATUS      current
--     DESCRIPTION
--         "The value of tnHsmdaPoolClass7AllocPercent specifies, indirectly,
--          the size of the first class pool. The specified percentage, in
--          hundredths of a percent, determines what percentage of the root
--          pool with which it is associated, as specified by
--          tnHsmdaPoolClass7Parent, will be available to this class.
-- 
--          The sum of the class pool percentages for a root pool may exceed
--          100 percent(10000 hundredths of a percent), allowing the root pool
--          to be oversubscribed. The sum of the class pool percentages for
--          a root pool may also total less than 100 percent, allowing the
--          root pool to be undersubscribed."
--     DEFVAL { 4000 }
--     ::= { tnHsmdaPoolPolicyEntry 27 }
-- 
-- tnHsmdaPoolClass8Parent        OBJECT-TYPE
--     SYNTAX      Unsigned32 (1..8)
--     MAX-ACCESS  read-create
--     STATUS      current
--     DESCRIPTION
--         "The value of tnHsmdaPoolClass8Parent specifies the root pool to which
--          the eigth class pool will be associated."
--     DEFVAL { 2 }
--     ::= { tnHsmdaPoolPolicyEntry 28 }
-- 
-- tnHsmdaPoolClass8AllocPercent        OBJECT-TYPE
--     SYNTAX      Unsigned32 (1..10000)
--     UNITS       "hundredths of a percent"
--     MAX-ACCESS  read-create
--     STATUS      current
--     DESCRIPTION
--         "The value of tnHsmdaPoolClass8AllocPercent specifies, indirectly,
--          the size of the first class pool. The specified percentage, in
--          hundredths of a percent, determines what percentage of the root
--          pool with which it is associated, as specified by
--          tnHsmdaPoolClass8Parent, will be available to this class.
-- 
--          The sum of the class pool percentages for a root pool may exceed
--          100 percent(10000 hundredths of a percent), allowing the root pool
--          to be oversubscribed. The sum of the class pool percentages for
--          a root pool may also total less than 100 percent, allowing the
--          root pool to be undersubscribed."
--     DEFVAL { 3000 }
--     ::= { tnHsmdaPoolPolicyEntry 29 }

--
-- Multi-class mlppp Ingress profile table
--

-- tnMcMlpppIngrProfTable OBJECT-TYPE
--     SYNTAX       SEQUENCE OF TMcMlpppIngrProfEntry
--     MAX-ACCESS   not-accessible
--     STATUS       current
--     DESCRIPTION
--         "The tnMcMlpppIngrProfTable has an entry for each ingress multi-class 
--          mlppp profile configured in the system."
--     ::= { tnMcMlpppIngressObjects 1 }
-- 
-- tnMcMlpppIngrProfEntry OBJECT-TYPE
--     SYNTAX       TMcMlpppIngrProfEntry
--     MAX-ACCESS   not-accessible
--     STATUS       current
--     DESCRIPTION
--         "Each row entry contains information about a particular ingress 
--          multi-class mlppp profile.
--          
--          Multi-class mlppp ingress profile 1 is created by the agent. 
--          It cannot be deleted.
--          
--          Other entries are created by the user."
--     INDEX { tnSysSwitchId, tnMcMlpppIngrProfIndex }
--     ::= { tnMcMlpppIngrProfTable 1 }
-- 
-- TMcMlpppIngrProfEntry ::= SEQUENCE
--     {
--         tnMcMlpppIngrProfIndex                 TMlpppQoSProfileId,
--         tnMcMlpppIngrProfDescription           TItemDescription,
--         tnMcMlpppIngrProfLastChanged           TimeStamp,
--         tnMcMlpppIngrProfRowStatus             RowStatus
--     }
-- 
-- tnMcMlpppIngrProfIndex OBJECT-TYPE
--     SYNTAX       TMlpppQoSProfileId
--     MAX-ACCESS   not-accessible
--     STATUS       current
--     DESCRIPTION  
--         "The value of tnMcMlpppIngrProfIndex specifies a specific multi-class 
--          ingress profile."
--     ::= { tnMcMlpppIngrProfEntry 1 }
-- 
-- tnMcMlpppIngrProfDescription OBJECT-TYPE
--     SYNTAX       TItemDescription
--     MAX-ACCESS   read-create
--     STATUS       current
--     DESCRIPTION  
--         "The value of tnMcMlpppIngrProfDescription holds the description for
--          this profile."
--     DEFVAL { ''H }
--     ::= { tnMcMlpppIngrProfEntry 2 }
--     
-- tnMcMlpppIngrProfLastChanged OBJECT-TYPE
--     SYNTAX       TimeStamp
--     MAX-ACCESS   read-only
--     STATUS       current
--     DESCRIPTION  
--         "The value of tnMcMlpppIngrProfTable indicates the sysUpTime for the 
--          last change to this row."
--     ::= { tnMcMlpppIngrProfEntry 3 }
--     
-- tnMcMlpppIngrProfRowStatus OBJECT-TYPE
--     SYNTAX       RowStatus
--     MAX-ACCESS   read-create
--     STATUS       current
--     DESCRIPTION  
--         "The value of tnMcMlpppIngrProfRowStatus controls the creation
--          and deletion of rows in this table."
--     ::= { tnMcMlpppIngrProfEntry 4 }

--
-- Multi-class mlppp ingress class table
--

-- tnMcMlpppIngrClassTable OBJECT-TYPE
--    SYNTAX       SEQUENCE OF TnMcMlpppIngrClassEntry
--    MAX-ACCESS   not-accessible
--    STATUS       current
--    DESCRIPTION
--        "The tnMcMlpppIngrClassTable has an entry for each multi-class
--         mlppp ingress class per multi-class mlppp ingress profile in
--         the system."
--    ::= { tnMcMlpppIngressObjects 2 }

-- tnMcMlpppIngrClassEntry OBJECT-TYPE
--    SYNTAX       TnMcMlpppIngrClassEntry
--    MAX-ACCESS   not-accessible
--    STATUS       current
--    DESCRIPTION
--        "Each entry contains information about a particular 
--         mlppp ingress multi-class class per mlppp ingress profile.
--         Entries are created/destroyed as each tnMcMlpppIngrProfEntry
--         is created/destroyed."
--    INDEX { tnMcMlpppIngrProfIndex, tnMcMlpppIngrClassIndex }
--    ::= { tnMcMlpppIngrClassTable 1 }

-- TnMcMlpppIngrClassEntry ::= SEQUENCE
--    {
--        tnMcMlpppIngrClassIndex              TmnxMcMlpppClassIndex,
--        tnMcMlpppIngrClassReassemblyTmout    Unsigned32,
--        tnMcMlpppIngrClassLastChanged        TimeStamp 
--    }

-- tnMcMlpppIngrClassIndex OBJECT-TYPE
--    SYNTAX       TmnxMcMlpppClassIndex
--    MAX-ACCESS   not-accessible
--    STATUS       current
--    DESCRIPTION  
--        "The value of tnMcMlpppIngrClassIndex specifies a specific mlppp ingress
--         class per multi-class mlppp ingress profile."
--    ::= { tnMcMlpppIngrClassEntry 1 }

-- tnMcMlpppIngrClassReassemblyTmout OBJECT-TYPE
--    SYNTAX       Unsigned32 (1..1000)
--    MAX-ACCESS   read-write
--    STATUS       current
--    DESCRIPTION  
--        "The value of tnMcMlpppIngrClassReassemblyTmout specifies the
--         reassembly timeout for a specific mlppp multi-class ingress class.
--         The default reassembly timeout value is determined by the 
--         tnMcMlpppIngrClassIndex value.
--         Currently only four multi-class classes are supported per profile.

--                    tnMcMlpppIngrClassIndex    Default Reassembly Value
--                             0                           10
--                             1                           10
--                             2                           100
--                             3                           1000"
--    
--    ::= { tnMcMlpppIngrClassEntry 2 }    

-- tnMcMlpppIngrClassLastChanged OBJECT-TYPE
--    SYNTAX       TimeStamp
--    MAX-ACCESS   read-only
--    STATUS       current
--    DESCRIPTION  
--        "The value of tnMcMlpppIngrClassLastChanged indicates the sysUpTime 
--         for the last change to this entry."
--    ::= { tnMcMlpppIngrClassEntry 3 }  
        
--
-- Multi-class mlppp egress profile table
--

-- tnMcMlpppEgrProfTable OBJECT-TYPE
--     SYNTAX       SEQUENCE OF TMcMlpppEgrProfEntry
--     MAX-ACCESS   not-accessible
--     STATUS       current
--     DESCRIPTION
--         "The tnMcMlpppEgrProfTable has an entry for each egress multi-class 
--          mlppp profile configured in the system."
--     ::= { tnMcMlpppEgressObjects 1 }
-- 
-- tnMcMlpppEgrProfEntry OBJECT-TYPE
--     SYNTAX       TMcMlpppEgrProfEntry
--     MAX-ACCESS   not-accessible
--     STATUS       current
--     DESCRIPTION
--         "Each row entry contains information about a particular egress
--          multi-class mlppp profile.
--          
--          Multi-class mlppp egress profiles 1,2 and 3 are created by the agent. 
--          They cannot be deleted.
--          
--          Other entries are created by the user."
--     INDEX { tnSysSwitchId, tnMcMlpppEgrProfIndex }
--     ::= { tnMcMlpppEgrProfTable 1 }
-- 
-- TMcMlpppEgrProfEntry ::= SEQUENCE
--     {
--         tnMcMlpppEgrProfIndex                TMlpppQoSProfileId,
--         tnMcMlpppEgrProfDescription          TItemDescription,
--         tnMcMlpppEgrProfLastChanged          TimeStamp,
--         tnMcMlpppEgrProfRowStatus            RowStatus
--     }
-- 
-- tnMcMlpppEgrProfIndex OBJECT-TYPE
--     SYNTAX       TMlpppQoSProfileId
--     MAX-ACCESS   not-accessible
--     STATUS       current
--     DESCRIPTION  
--         "The value of tnMcMlpppEgrProfIndex specifies a specific multi-class 
--          egress profile."
--     ::= { tnMcMlpppEgrProfEntry 1 }
-- 
-- tnMcMlpppEgrProfDescription OBJECT-TYPE
--     SYNTAX       TItemDescription
--     MAX-ACCESS   read-create
--     STATUS       current
--     DESCRIPTION  
--         "The value of tnMcMlpppEgrProfDescription holds the description for
--          this profile."
--     DEFVAL { ''H }
--     ::= { tnMcMlpppEgrProfEntry 2 }
--     
-- tnMcMlpppEgrProfLastChanged OBJECT-TYPE
--     SYNTAX       TimeStamp
--     MAX-ACCESS   read-only
--     STATUS       current
--     DESCRIPTION  
--         "The value of tnMcMlpppEgrProfLastChanged indicates the sysUpTime 
--          for the last change to this row."
--     ::= { tnMcMlpppEgrProfEntry 3 }
--     
-- tnMcMlpppEgrProfRowStatus OBJECT-TYPE
--     SYNTAX       RowStatus
--     MAX-ACCESS   read-create
--     STATUS       current
--     DESCRIPTION  
--         "The value of tnMcMlpppEgrProfRowStatus controls the creation
--          and deletion of rows in this table."
--     ::= { tnMcMlpppEgrProfEntry 4 }

--
-- Multi-class mlppp egress class table
--

-- tnMcMlpppEgrClassTable OBJECT-TYPE
--    SYNTAX       SEQUENCE OF TnMcMlpppEgrClassEntry
--    MAX-ACCESS   not-accessible
--    STATUS       current
--    DESCRIPTION
--        "The tnMcMlpppEgrClassTable has an entry for each multiclass
--         mlppp egress profile in the system."
--    ::= { tnMcMlpppEgressObjects 3 }

-- tnMcMlpppEgrClassEntry OBJECT-TYPE
--    SYNTAX       TnMcMlpppEgrClassEntry
--    MAX-ACCESS   not-accessible
--    STATUS       current
--    DESCRIPTION
--        "Each entry contains information about a particular 
--         mlppp egress multi-class class per mlppp multi-class
--         mlppp egress profile.
--         Entries are created/destroyed as each tnMcMlpppEgrProfEntry
--         is created/destroyed."
--    INDEX { tnMcMlpppEgrProfIndex, tnMcMlpppEgrClassIndex }
--    ::= { tnMcMlpppEgrClassTable 1 }

-- TnMcMlpppEgrClassEntry ::= SEQUENCE
--    {
--        tnMcMlpppEgrClassIndex       TmnxMcMlpppClassIndex,
--        tnMcMlpppEgrClassMir         Unsigned32,
--        tnMcMlpppEgrClassWeight      Unsigned32, 
--        tnMcMlpppEgrClassMaxSize     Unsigned32,
--        tnMcMlpppEgrClassLastChanged TimeStamp
--    }

-- tnMcMlpppEgrClassIndex OBJECT-TYPE
--    SYNTAX       TmnxMcMlpppClassIndex
--    MAX-ACCESS   not-accessible
--    STATUS       current
--    DESCRIPTION  
--        "The value of tnMcMlpppEgrClassIndex specifies a specific mlppp egress class 
--         per multi-class mlppp egress profile."
--    ::= { tnMcMlpppEgrClassEntry 1 }

-- tnMcMlpppEgrClassMir OBJECT-TYPE
--    SYNTAX       Unsigned32 (0|1..100)
--    UNITS        "percent"
--    MAX-ACCESS   read-write
--    STATUS       current
--    DESCRIPTION  
--        "The value of tnMcMlpppEgrClassMir specifies the Minimum Information
--         Rate given as a percentage. A value of zero represents this object
--         is not applicable for this class.
--         The default Mir is determined by the tnMcMlpppEgrClassIndex value.
--         Currently only four multi-class classes are supported per profile.

--               tnMcMlpppEgrClassIndex     Default Mir Value
--                         0                      100
--                         1                      85
--                         2                      0
--                         3                      0"        
--    ::= { tnMcMlpppEgrClassEntry 2 }

-- tnMcMlpppEgrClassWeight OBJECT-TYPE
--    SYNTAX       Unsigned32 (0|1..100)
--    UNITS        "percent"
--    MAX-ACCESS   read-write
--    STATUS       current
--    DESCRIPTION  
--        "The value of tnMcMlpppEgrClassWeight specifies the weight of this
--         multiclass class given as a percentage. A value of zero represents 
--         this object is not applicable for this class.
--         The default Weight is determined by the tnMcMlpppEgrClassIndex value.
--         Currently only four multi-class classes are supported per profile.

--               tnMcMlpppEgrClassIndex     Default Weight Value
--                         0                      0
--                         1                      0
--                         2                      66
--                         3                      33" 
--    ::= { tnMcMlpppEgrClassEntry 3 }
--    
-- tnMcMlpppEgrClassMaxSize OBJECT-TYPE
--    SYNTAX       Unsigned32 (1..1000)
--    UNITS       "milliseconds"
--    MAX-ACCESS   read-write
--    STATUS       current
--    DESCRIPTION  
--        "The value of tnMcMlpppEgrClassMaxSize specifies the buffer queue size.
--         The default buffer size is determined by the tnMcMlpppEgrClassIndex
--         value.
--         Currently only four multi-class classes are supported per profile.

--               tnMcMlpppEgrClassIndex     Default Max Size
--                        0                      25
--                        1                      5
--                        2                      200
--                        3                      1000" 
--        
--    ::= { tnMcMlpppEgrClassEntry 4 }

-- tnMcMlpppEgrClassLastChanged OBJECT-TYPE
--    SYNTAX       TimeStamp
--    MAX-ACCESS   read-only
--    STATUS       current
--    DESCRIPTION  
--        "The value of tnMcMlpppEgrClassLastChanged indicates the sysUpTime 
--         for the last change to this entry."
--    ::= { tnMcMlpppEgrClassEntry 5 }      
--
-- Multi-class mlppp egress fc table
--

-- tnMcMlpppEgrFCTable OBJECT-TYPE
--     SYNTAX       SEQUENCE OF TMcMlpppEgrFCEntry
--     MAX-ACCESS   not-accessible
--     STATUS       current
--     DESCRIPTION
--         "The tnMcMlpppEgrFCTable has an entry for all egress FC Mappings 
--          to multi-class mlppp classes."
--     ::= { tnMcMlpppEgressObjects 4 }
-- 
-- tnMcMlpppEgrFCEntry OBJECT-TYPE
--     SYNTAX       TMcMlpppEgrFCEntry
--     MAX-ACCESS   not-accessible
--     STATUS       current
--     DESCRIPTION
--         "Each entry contains information about all egress FC Mappings to
--          multi-class mlppp classes. Entries are created/destroyed as each 
--          tnMcMlpppEgrProfEntry is created/destroyed."
--     INDEX { tnSysSwitchId, tnMcMlpppEgrProfIndex, tnMcMlpppEgrFCName }
--     ::= { tnMcMlpppEgrFCTable 1 }
-- 
-- TMcMlpppEgrFCEntry ::= SEQUENCE
--     {
--         tnMcMlpppEgrFCName        TFCName,  
--         tnMcMlpppEgrFCClass       Unsigned32,
--         tnMcMlpppEgrFCLastChanged TimeStamp
--     }
-- 
-- tnMcMlpppEgrFCName OBJECT-TYPE
--     SYNTAX       TFCName
--     MAX-ACCESS   not-accessible
--     STATUS       current
--     DESCRIPTION
--         "The value tnMcMlpppEgrFCName specifies of the name of the forwarding class."
--     ::= { tnMcMlpppEgrFCEntry 1 }
--     
-- tnMcMlpppEgrFCClass OBJECT-TYPE
--     SYNTAX       Unsigned32 (0..3)
--     MAX-ACCESS   read-write
--     STATUS       current
--     DESCRIPTION  
--         "The value of tnMcMlpppEgrFCClass specifies the mlppp multi-class class
--          for the per-forwarding-class specified. The default class value is determined
--          by the Forwarding Class Name.    
--             
--             Forwarding Class Name             Mlppp Class Value
--                    be                                 3
--                    l2                                 2 
--                    af                                 2 
--                    l1                                 2 
--                    h2                                 2
--                    ef                                 1  
--                    h1                                 0
--                    nc                                 0"           
--     ::= { tnMcMlpppEgrFCEntry 2 }
-- 
-- tnMcMlpppEgrFCLastChanged OBJECT-TYPE
--     SYNTAX       TimeStamp
--     MAX-ACCESS   read-only
--     STATUS       current
--     DESCRIPTION  
--         "The value of tnMcMlpppEgrFCLastChanged indicates the sysUpTime 
--          for the last change to this entry."
--     ::= { tnMcMlpppEgrFCEntry 3 }

--
-- Multi-class Frame-Relay Ingress profile table
--

-- tnMcFrIngrProfTable OBJECT-TYPE
--     SYNTAX       SEQUENCE OF TMcFrIngrProfEntry
--     MAX-ACCESS   not-accessible
--     STATUS       current
--     DESCRIPTION
--         "The tnMcFrIngrProfTable has an entry for each ingress multi-class 
--          frame-relay profile configured in the system."
--     ::= { tnMcFrIngressObjects 1 }
-- 
-- tnMcFrIngrProfEntry OBJECT-TYPE
--     SYNTAX       TMcFrIngrProfEntry
--     MAX-ACCESS   not-accessible
--     STATUS       current
--     DESCRIPTION
--         "Each row entry contains information about a particular ingress 
--          multi-class frame-relay profile.
--          
--          Multi-class frame-relay ingress profile 1 is created by the agent. 
--          It cannot be modified/deleted.
--          
--          Other entries are created by the user."
--     INDEX { tnSysSwitchId, tnMcFrIngrProfIndex }
--     ::= { tnMcFrIngrProfTable 1 }
-- 
-- TMcFrIngrProfEntry ::= SEQUENCE
--     {
--         tnMcFrIngrProfIndex                 TMcFrQoSProfileId,
--         tnMcFrIngrProfDescription           TItemDescription,
--         tnMcFrIngrProfLastChanged           TimeStamp,
--         tnMcFrIngrProfRowStatus             RowStatus
--     }
-- 
-- tnMcFrIngrProfIndex OBJECT-TYPE
--     SYNTAX       TMcFrQoSProfileId
--     MAX-ACCESS   not-accessible
--     STATUS       current
--     DESCRIPTION  
--         "The value of tnMcFrIngrProfIndex specifies a specific multi-class 
--          ingress profile."
--     ::= { tnMcFrIngrProfEntry 1 }
-- 
-- tnMcFrIngrProfDescription OBJECT-TYPE
--     SYNTAX       TItemDescription
--     MAX-ACCESS   read-create
--     STATUS       current
--     DESCRIPTION  
--         "The value of tnMcFrIngrProfDescription holds the description for
--          this profile."
--     DEFVAL { ''H }
--     ::= { tnMcFrIngrProfEntry 2 }
--     
-- tnMcFrIngrProfLastChanged OBJECT-TYPE
--     SYNTAX       TimeStamp
--     MAX-ACCESS   read-only
--     STATUS       current
--     DESCRIPTION  
--         "The value of tnMcFrIngrProfTable indicates the sysUpTime for the 
--          last change to this row."
--     ::= { tnMcFrIngrProfEntry 3 }
--     
-- tnMcFrIngrProfRowStatus OBJECT-TYPE
--     SYNTAX       RowStatus
--     MAX-ACCESS   read-create
--     STATUS       current
--     DESCRIPTION  
--         "The value of tnMcFrIngrProfRowStatus controls the creation
--          and deletion of rows in this table."
--     ::= { tnMcFrIngrProfEntry 4 }

--
-- Multi-class Frame-Relay ingress class table
--

-- tnMcFrIngrClassTable OBJECT-TYPE
--     SYNTAX       SEQUENCE OF TMcFrIngrClassEntry
--     MAX-ACCESS   not-accessible
--     STATUS       current
--     DESCRIPTION
--         "The tnMcFrIngrClassTable has an entry for each multi-class
--          frame-relay ingress class per multi-class frame-relay ingress 
--          profile in the system."
--     ::= { tnMcFrIngressObjects 2 }
-- 
-- tnMcFrIngrClassEntry OBJECT-TYPE
--     SYNTAX       TMcFrIngrClassEntry
--     MAX-ACCESS   not-accessible
--     STATUS       current
--     DESCRIPTION
--         "Each entry contains information about a particular frame-relay 
--          ingress multi-class class per frame-relay ingress profile.
--          
--          Entries are created/destroyed as each tnMcFrIngrProfEntry
--          is created/destroyed."
--     INDEX { tnSysSwitchId, tnMcFrIngrProfIndex, tnMcFrIngrClassIndex }
--     ::= { tnMcFrIngrClassTable 1 }
-- 
-- TMcFrIngrClassEntry ::= SEQUENCE
--     {
--         tnMcFrIngrClassIndex              TmnxMcFrClassIndex,
--         tnMcFrIngrClassReassemblyTmout    Unsigned32,
--         tnMcFrIngrClassLastChanged        TimeStamp 
--     }
-- 
-- tnMcFrIngrClassIndex OBJECT-TYPE
--     SYNTAX       TmnxMcFrClassIndex
--     MAX-ACCESS   not-accessible
--     STATUS       current
--     DESCRIPTION  
--         "The value of tnMcFrIngrClassIndex specifies a specific frame-relay
--          ingress class per multi-class frame-relay ingress profile."
--     ::= { tnMcFrIngrClassEntry 1 }
-- 
-- tnMcFrIngrClassReassemblyTmout OBJECT-TYPE
--     SYNTAX       Unsigned32 (1..1000)
--     MAX-ACCESS   read-write
--     STATUS       current
--     DESCRIPTION  
--         "The value of tnMcFrIngrClassReassemblyTmout specifies the
--          reassembly timeout for a specific frame-relay multi-class ingress class.
--          Currently only four multi-class classes are supported per profile."
--     ::= { tnMcFrIngrClassEntry 2 }    
-- 
-- tnMcFrIngrClassLastChanged OBJECT-TYPE
--     SYNTAX       TimeStamp
--     MAX-ACCESS   read-only
--     STATUS       current
--     DESCRIPTION  
--         "The value of tnMcFrIngrClassLastChanged indicates the sysUpTime 
--          for the last change to this entry."
--     ::= { tnMcFrIngrClassEntry 3 }  
        
--
-- Multi-class Frame-Relay egress profile table
--

-- tnMcFrEgrProfTable OBJECT-TYPE
--     SYNTAX       SEQUENCE OF TMcFrEgrProfEntry
--     MAX-ACCESS   not-accessible
--     STATUS       current
--     DESCRIPTION
--         "The tnMcFrEgrProfTable has an entry for each egress multi-class 
--          frame-relay profile configured in the system."
--     ::= { tnMcFrEgressObjects 1 }
-- 
-- tnMcFrEgrProfEntry OBJECT-TYPE
--     SYNTAX       TMcFrEgrProfEntry
--     MAX-ACCESS   not-accessible
--     STATUS       current
--     DESCRIPTION
--         "Each row entry contains information about a particular egress
--          multi-class frame-relay profile.
--          
--          Multi-class frame-relay egress profile 1 is created by the agent. 
--          It cannot be modified/deleted.
--          
--          Other entries are created by the user."
--     INDEX { tnSysSwitchId, tnMcFrEgrProfIndex }
--     ::= { tnMcFrEgrProfTable 1 }
-- 
-- TMcFrEgrProfEntry ::= SEQUENCE
--     {
--         tnMcFrEgrProfIndex                TMcFrQoSProfileId,
--         tnMcFrEgrProfDescription          TItemDescription,
--         tnMcFrEgrProfLastChanged          TimeStamp,
--         tnMcFrEgrProfRowStatus            RowStatus
--     }
-- 
-- tnMcFrEgrProfIndex OBJECT-TYPE
--     SYNTAX       TMcFrQoSProfileId
--     MAX-ACCESS   not-accessible
--     STATUS       current
--     DESCRIPTION  
--         "The value of tnMcFrEgrProfIndex specifies a specific multi-class 
--          egress profile."
--     ::= { tnMcFrEgrProfEntry 1 }
-- 
-- tnMcFrEgrProfDescription OBJECT-TYPE
--     SYNTAX       TItemDescription
--     MAX-ACCESS   read-create
--     STATUS       current
--     DESCRIPTION  
--         "The value of tnMcFrEgrProfDescription holds the description for
--          this profile."
--     DEFVAL { ''H }
--     ::= { tnMcFrEgrProfEntry 2 }
--     
-- tnMcFrEgrProfLastChanged OBJECT-TYPE
--     SYNTAX       TimeStamp
--     MAX-ACCESS   read-only
--     STATUS       current
--     DESCRIPTION  
--         "The value of tnMcFrEgrProfLastChanged indicates the sysUpTime 
--          for the last change to this row."
--     ::= { tnMcFrEgrProfEntry 3 }
--     
-- tnMcFrEgrProfRowStatus OBJECT-TYPE
--     SYNTAX       RowStatus
--     MAX-ACCESS   read-create
--     STATUS       current
--     DESCRIPTION  
--         "The value of tnMcFrEgrProfRowStatus controls the creation
--          and deletion of rows in this table."
--     ::= { tnMcFrEgrProfEntry 4 }

--
-- Multi-class Frame-Relay egress class table
--

-- tnMcFrEgrClassTable OBJECT-TYPE
--     SYNTAX       SEQUENCE OF TMcFrEgrClassEntry
--     MAX-ACCESS   not-accessible
--     STATUS       current
--     DESCRIPTION
--         "The tnMcFrEgrClassTable has an entry for each multiclass
--          mlppp egress profile in the system."
--     ::= { tnMcFrEgressObjects 3 }
-- 
-- tnMcFrEgrClassEntry OBJECT-TYPE
--     SYNTAX       TMcFrEgrClassEntry
--     MAX-ACCESS   not-accessible
--     STATUS       current
--     DESCRIPTION
--         "Each entry contains information about a particular 
--          frame-relay egress multi-class class per multi-class
--          frame-relay egress profile.
--          Entries are created/destroyed as each tnMcFrEgrProfEntry
--          is created/destroyed."
--     INDEX { tnSysSwitchId, tnMcFrEgrProfIndex, tnMcFrEgrClassIndex }
--     ::= { tnMcFrEgrClassTable 1 }
-- 
-- TMcFrEgrClassEntry ::= SEQUENCE
--     {
--         tnMcFrEgrClassIndex       TmnxMcFrClassIndex,
--         tnMcFrEgrClassMir         Unsigned32,
--         tnMcFrEgrClassWeight      Unsigned32, 
--         tnMcFrEgrClassMaxSize     Unsigned32,
--         tnMcFrEgrClassLastChanged TimeStamp
--     }
-- 
-- tnMcFrEgrClassIndex OBJECT-TYPE
--     SYNTAX       TmnxMcFrClassIndex
--     MAX-ACCESS   not-accessible
--     STATUS       current
--     DESCRIPTION  
--         "The value of tnMcFrEgrClassIndex specifies a specific frame-relay
--          egress class per multi-class frame-relay egress profile."
--     ::= { tnMcFrEgrClassEntry 1 }
-- 
-- tnMcFrEgrClassMir OBJECT-TYPE
--     SYNTAX       Unsigned32 (0|1..100)
--     UNITS        "percent"
--     MAX-ACCESS   read-write
--     STATUS       current
--     DESCRIPTION  
--         "The value of tnMcFrEgrClassMir specifies the Minimum Information
--          Rate given as a percentage. A value of zero represents this object
--          is not applicable for this class.
--          Currently only four multi-class classes are supported per profile."        
--     ::= { tnMcFrEgrClassEntry 2 }
-- 
-- tnMcFrEgrClassWeight OBJECT-TYPE
--     SYNTAX       Unsigned32 (0|1..100)
--     UNITS        "percent"
--     MAX-ACCESS   read-write
--     STATUS       current
--     DESCRIPTION  
--         "The value of tnMcMlpppEgrClassWeight specifies the weight of this
--          multiclass class given as a percentage. A value of zero represents 
--          this object is not applicable for this class.
--          Currently only four multi-class classes are supported per profile." 
--     ::= { tnMcFrEgrClassEntry 3 }
--     
-- tnMcFrEgrClassMaxSize OBJECT-TYPE
--     SYNTAX       Unsigned32 (1..1000)
--     UNITS       "milliseconds"
--     MAX-ACCESS   read-write
--     STATUS       current
--     DESCRIPTION  
--         "The value of tnMcFrEgrClassMaxSize specifies the buffer queue size.
--          The default buffer size is determined by the tnMcFrEgrClassIndex
--          value.
--          Currently only four multi-class classes are supported per profile." 
--     ::= { tnMcFrEgrClassEntry 4 }
-- 
-- tnMcFrEgrClassLastChanged OBJECT-TYPE
--     SYNTAX       TimeStamp
--     MAX-ACCESS   read-only
--     STATUS       current
--     DESCRIPTION  
--         "The value of tnMcFrEgrClassLastChanged indicates the sysUpTime 
--          for the last change to this entry."
--     ::= { tnMcFrEgrClassEntry 5 }      
                                
--
-- Conformance Information
--

-- tnQosCompliances OBJECT IDENTIFIER ::= { tnQosConformance 1 }
-- tnQosGroups      OBJECT IDENTIFIER ::= { tnQosConformance 2 }

--
-- compliance statements
--

-- tnQosCompliance   MODULE-COMPLIANCE
--    ::= { tnQosCompliances 1 }

-- tnQosR2r1Compliance   MODULE-COMPLIANCE
--    ::= { tnQosCompliances 2 }

-- tnQosV3v0Compliance   MODULE-COMPLIANCE
--    ::= { tnQosCompliances 3 }

-- tnQos7450V4v0Compliance   MODULE-COMPLIANCE
--    STATUS   obsolete
--    DESCRIPTION
--        "The compliance statement for management of QOS features
--         on Nokia 7450 ESS series systems release R4.0."
--    MODULE  this module
--        MANDATORY-GROUPS {
--            tnQosGlobalGroup,
--            tnQosDSCPGroup,
--            tnQosFCGroup,
--            tnQosSapIngressV4v0Group,
--            tnQosSapEgressR2r1Group,
--            tnQosNetworkR2r1Group,
--            tnQosSlopeGroup,
--            tnQosSchedulerGroup,
--            tnQosAtmTdpV3v0Group,
--            tnQosQueueV4v0Group
--            tnQosSapIpv6FilterR4r0Group
--        }
--    ::= { tnQosCompliances 4 }

-- tnQos7750V4v0Compliance   MODULE-COMPLIANCE
--    STATUS   obsolete
--    DESCRIPTION
--        "The compliance statement for management of QOS features
--         on Nokia 7750 SR series systems release R4.0."
--    MODULE  this module
--        MANDATORY-GROUPS {
--            tnQosGlobalGroup,
--            tnQosDSCPGroup,
--            tnQosFCGroup,
--            tnQosSapIngressV4v0Group,
--            tnQosSapEgressR2r1Group,
--            tnQosNetworkR2r1Group,
--            tnQosSlopeGroup,
--            tnQosSchedulerGroup,
--            tnQosAtmTdpV3v0Group,
--            tnQosQueueV4v0Group,
--            tnQosSapIpv6FilterR4r0Group
--        }
--    ::= { tnQosCompliances 5 }

-- tnQos7450V5v0Compliance   MODULE-COMPLIANCE
--    STATUS   obsolete
--    DESCRIPTION
--        "The compliance statement for management of QOS features
--         on Nokia 7450 ESS series systems release R5.0."
--    MODULE  this module
--        MANDATORY-GROUPS {
--            tnQosGlobalGroup,
--            tnQosDSCPGroup,
--            tnQosFCGroup,
--            tnQosSapIngressV4v0Group,
--            tnQosSapEgressV5v0Group,
--            tnQosNetworkV5v0Group,
--            tnQosSlopeGroup,
--            tnQosSchedulerV5v0Group,
--            tnQosAtmTdpV5v0Group,
--            tnQosQueueV4v0Group
--            tnQosSapIpv6FilterR4r0Group
--        }
--    ::= { tnQosCompliances 6 }

-- tnQos7750V5v0Compliance   MODULE-COMPLIANCE
--    STATUS   obsolete
--    DESCRIPTION
--        "The compliance statement for management of QOS features
--         on Nokia 7750 SR series systems release R5.0."
--    MODULE  this module
--        MANDATORY-GROUPS {
--            tnQosGlobalGroup,
--            tnQosDSCPGroup,
--            tnQosFCGroup,
--            tnQosSapIngressV4v0Group,
--            tnQosSapEgressV5v0Group,
--            tnQosNetworkV5v0Group,
--            tnQosSlopeGroup,
--            tnQosSchedulerV5v0Group,
--            tnQosAtmTdpV5v0Group,
--            tnQosQueueV4v0Group,
--            tnQosSapIpv6FilterR4r0Group
--        }
--    ::= { tnQosCompliances 7 }

-- tnQos7450V6v0Compliance   MODULE-COMPLIANCE
--    STATUS   obsolete
--    DESCRIPTION
--        "The compliance statement for management of QOS features
--         on Nokia 7450 ESS series systems release R6.0."
--    MODULE  this module
--        MANDATORY-GROUPS {
--            tnQosGlobalGroup,
--            tnQosDSCPGroup,
--            tnQosFCGroup,
--            tnQosSapIngressV6v0Group,
--            tnQosSapEgressV6v0Group,
--            tnQosNetworkV6v0Group,
--            tnQosSlopeGroup,
--            tnQosSchedulerV5v0Group,
--            tnQosAtmTdpV5v0Group,
--            tnQosQueueV4v0Group,
--            tnQosSapIpv6FilterR4r0Group
--            tnQosHsmdaV6v0Group,
--            tnQosFrameBasedV6v0Group,
--            tnQosNamedPoolPolicyV6v0Group
--        }
--    ::= { tnQosCompliances 8 }

-- tnQos7750V6v0Compliance   MODULE-COMPLIANCE
--    STATUS   obsolete
--    DESCRIPTION
--        "The compliance statement for management of QOS features
--         on Nokia 7750 SR series systems release R6.0."
--    MODULE  this module
--        MANDATORY-GROUPS {
--            tnQosGlobalGroup,
--            tnQosDSCPGroup,
--            tnQosFCGroup,
--            tnQosSapIngressV6v0Group,
--            tnQosSapEgressV6v0Group,
--            tnQosNetworkV6v0Group,
--            tnQosSlopeGroup,
--            tnQosSchedulerV5v0Group,
--            tnQosAtmTdpV5v0Group,
--            tnQosQueueV4v0Group,
--            tnQosSapIpv6FilterR4r0Group,
--            tnQosHsmdaV6v0Group,
--            tnQosFrameBasedV6v0Group,
--            tnQosNamedPoolPolicyV6v0Group
--        }
--    ::= { tnQosCompliances 9 }

-- tnQos7450V6v1Compliance   MODULE-COMPLIANCE
--    STATUS   obsolete
--    DESCRIPTION
--        "The compliance statement for management of QOS features
--         on Nokia 7450 ESS series systems release R6.1."
--    MODULE  this module
--        MANDATORY-GROUPS {
--            tnQosGlobalGroup,
--            tnQosDSCPGroup,
--            tnQosFCGroup,
--            tnQosSapIngressV6v0Group,
--            tnQosSapEgressV6v0Group,
--            tnQosNetworkV6v0Group,
--            tnQosSlopeGroup,
--            tnQosSchedulerV5v0Group,
--            tnQosAtmTdpV5v0Group,
--            tnQosQueueV4v0Group,
--            tnQosSapIpv6FilterR4r0Group
--            tnQosHsmdaV6v0Group,
--            tnQosFrameBasedV6v0Group,
--            tnQosNamedPoolPolicyV6v0Group,
--            tnQosMcMlpppIngrGroup,
--            tnQosMcMlpppEgrGroup
--        }
--    ::= { tnQosCompliances 10 }

-- tnQos77x0V6v1Compliance   MODULE-COMPLIANCE
--    STATUS   obsolete
--    DESCRIPTION
--        "The compliance statement for management of QOS features
--         on Nokia 7750 SR series systems release R6.1."
--    MODULE  this module
--        MANDATORY-GROUPS {
--            tnQosGlobalGroup,
--            tnQosDSCPGroup,
--            tnQosFCGroup,
--            tnQosSapIngressV6v0Group,
--            tnQosSapEgressV6v0Group,
--            tnQosNetworkV6v0Group,
--            tnQosSlopeGroup,
--            tnQosSchedulerV5v0Group,
--            tnQosAtmTdpV5v0Group,
--            tnQosQueueV4v0Group,
--            tnQosSapIpv6FilterR4r0Group,
--            tnQosHsmdaV6v0Group,
--            tnQosFrameBasedV6v0Group,
--            tnQosNamedPoolPolicyV6v0Group,
--            tnQosMcMlpppIngrGroup,
--            tnQosMcMlpppEgrGroup
--        }
--    ::= { tnQosCompliances 11 }

-- tnQos7450V7v0Compliance   MODULE-COMPLIANCE
--    STATUS   current
--    DESCRIPTION
--        "The compliance statement for management of QOS features
--         on Nokia 7450 ESS series systems release R6.1."
--    MODULE  this module
--        MANDATORY-GROUPS {
--            tnQosGlobalGroup,
--            tnQosDSCPGroup,
--            tnQosFCGroup,
--            tnQosSapIngressV6v0Group,
--            tnQosSapEgressV6v0Group,
--            tnQosNetworkV7v0Group,
--            tnQosSlopeGroup,
--            tnQosSchedulerV5v0Group,
--            tnQosAtmTdpV5v0Group,
--            tnQosQueueV4v0Group,
--            tnQosSapIpv6FilterR4r0Group
--            tnQosHsmdaV7v0Group,
--            tnQosFrameBasedV6v0Group,
--            tnQosNamedPoolPolicyV6v0Group,
--            tnQosMcMlpppIngrGroup,
--            tnQosMcMlpppEgrGroup,
--            tnQosQueueObjGroup,
--            tnQosQGrpFCGroup,
--            tnQosSapAtmV7v0Group,
--            tnQosSapEgrQWredGroup
--        }
--    ::= { tnQosCompliances 12 }

-- tnQos77x0V7v0Compliance   MODULE-COMPLIANCE
--    STATUS   current
--    DESCRIPTION
--        "The compliance statement for management of QOS features
--         on Nokia 7750 SR series systems release R6.1."
--    MODULE  this module
--        MANDATORY-GROUPS {
--            tnQosGlobalGroup,
--            tnQosDSCPGroup,
--            tnQosFCGroup,
--            tnQosSapIngressV6v0Group,
--            tnQosSapEgressV6v0Group,
--            tnQosNetworkV7v0Group,
--            tnQosSlopeGroup,
--            tnQosSchedulerV5v0Group,
--            tnQosAtmTdpV5v0Group,
--            tnQosQueueV4v0Group,
--            tnQosSapIpv6FilterR4r0Group,
--            tnQosHsmdaV7v0Group,
--            tnQosFrameBasedV6v0Group,
--            tnQosNamedPoolPolicyV6v0Group,
--            tnQosMcMlpppIngrGroup,
--            tnQosMcMlpppEgrGroup,
--            tnQosQueueObjGroup,
--            tnQosQGrpFCGroup,
--            tnQosSapAtmV7v0Group,
--            tnQosMcFrIngrGroup,
--            tnQosMcFrEgrGroup,
--            tnQosSapEgrQWredGroup
--        }
--    ::= { tnQosCompliances 13 }
    
--
-- units of conformance
--
-- tnQosGlobalGroup OBJECT-GROUP
--    OBJECTS {
--        tnQosDomainLastChanged
--    }
--    STATUS      current
--    DESCRIPTION
--        "The group of objects supporting general management of QOS
--         features on Nokia 7x50 SR series systems."
--    ::= { tnQosGroups 1 }

-- tnQosDSCPGroup OBJECT-GROUP
--    OBJECTS {
--        tnDSCPNameRowStatus,
--        tnDSCPNameStorageType,
--        tnDSCPNameDscpValue,
--        tnDSCPNameLastChanged,
--        tnDSCPNameTableLastChanged
--    }
--    STATUS      current
--    DESCRIPTION
--        "The group of objects supporting management of Differential Services
--         Code Points on Nokia 7x50 SR series systems."
--    ::= { tnQosGroups 2 }

-- tnQosFCGroup OBJECT-GROUP
--    OBJECTS {
--        tnFCRowStatus,
--        tnFCStorageType,
--        tnFCValue,
--        tnFCNameLastChanged,
--        tnFCNameTableLastChanged
--    }
--    STATUS      current
--    DESCRIPTION
--        "The group of objects supporting management of Forwarding Classes
--         on catel 7x50 SR series systems."
--    ::= { tnQosGroups 3 }

-- tnQosSapIngressGroup OBJECT-GROUP
--    ::= { tnQosGroups 4 }

-- tnQosSapEgressGroup OBJECT-GROUP
--    ::= { tnQosGroups 5 }

-- tnQosNetworkGroup OBJECT-GROUP
--    ::= { tnQosGroups 6 }

-- tnQosSlopeGroup OBJECT-GROUP
--    OBJECTS {
--        tnSlopeRowStatus,
--        tnSlopeDescription,
--        tnSlopeHiAdminStatus,
--        tnSlopeHiStartAverage,
--        tnSlopeHiMaxAverage,
--        tnSlopeHiMaxProbability,
--        tnSlopeLoAdminStatus,
--        tnSlopeLoStartAverage,
--        tnSlopeLoMaxAverage,
--        tnSlopeLoMaxProbability,
--        tnSlopeTimeAvgFactor,
--        tnSlopeLastChanged,
--        tnSlopePolicyTableLastChanged
--    }
--    STATUS      current
--    DESCRIPTION
--        "The group of objects supporting management of Slope policies
--         on Nokia 7x50 SR series systems."
--    ::= { tnQosGroups 7 }

-- tnQosSchedulerGroup OBJECT-GROUP
--    OBJECTS {
--        tnSchedulerPolicyRowStatus,
--        tnSchedulerPolicyDescription,
--        tnSchedulerPolicyLastChanged,
--        tnSchedulerPolicyTableLastChanged,
--        tnVirtualSchedulerRowStatus,
--        tnVirtualSchedulerDescription,
--        tnVirtualSchedulerParent,
--        tnVirtualSchedulerLevel,
--        tnVirtualSchedulerWeight,
--        tnVirtualSchedulerCIRLevel,
--        tnVirtualSchedulerCIRWeight,
--        tnVirtualSchedulerPIR,
--        tnVirtualSchedulerCIR,
--        tnVirtualSchedulerSummedCIR,
--        tnVirtualSchedulerLastChanged,
--        tnVirtualSchedulerTableLastChanged
--    }
--    STATUS      obsolete
--    DESCRIPTION
--        "The group of objects supporting management of Scheduler policies
--         on Nokia 7x50 SR series systems."
--    ::= { tnQosGroups 8 }

-- tnQosAtmTdpR2r1Group OBJECT-GROUP
--    ::= { tnQosGroups 9 }

-- tnQosObsoleteObjectsGroup    OBJECT-GROUP
--    OBJECTS {
--        tnSapIngressQueueOperPIR,
--        tnSapIngressQueueOperCIR,
--        tnSapEgressQueueOperPIR,
--        tnSapEgressQueueOperCIR
--    }
--    STATUS    current
--    DESCRIPTION
--        "The group of obsolete objects in the TIMETRA-QOS-MIB."
--    ::= { tnQosGroups 10 }

-- tnQosSapIngressR2r1Group OBJECT-GROUP
--    ::= { tnQosGroups 11 }

-- tnQosSapEgressR2r1Group OBJECT-GROUP
--    OBJECTS {
--        tnSapEgressRowStatus,
--        tnSapEgressScope,
--        tnSapEgressDescription,
--        tnSapEgressLastChanged,
--        tnSapEgressTableLastChanged,
--        tnSapEgressQueueRowStatus,
--        tnSapEgressQueueParent,
--        tnSapEgressQueueLevel,
--        tnSapEgressQueueWeight,
--        tnSapEgressQueueCIRLevel,
--        tnSapEgressQueueCIRWeight,
--        tnSapEgressQueueExpedite,
--        tnSapEgressQueueCBS,
--        tnSapEgressQueueMBS,
--        tnSapEgressQueueHiPrioOnly,
--        tnSapEgressQueueCIRAdaptation,
--        tnSapEgressQueuePIRAdaptation,
--        tnSapEgressQueueAdminPIR,
--        tnSapEgressQueueAdminCIR,
--        tnSapEgressQueueLastChanged,
--        tnSapEgressQueueTableLastChanged,
--        tnSapEgressFCRowStatus,
--        tnSapEgressFCQueue,
--        tnSapEgressFCDot1PValue,
--        tnSapEgressFCLastChanged,
--        tnSapEgressFCTableLastChanged
--    }
--    STATUS      obsolete
--    DESCRIPTION
--        "The group of objects supporting management of SAP egress QoS
--         policies on Nokia 7x50 SR series systems."
--    ::= { tnQosGroups 12 }

-- tnQosNetworkR2r1Group OBJECT-GROUP
--    OBJECTS {
--        tnNetworkPolicyRowStatus,
--        tnNetworkPolicyScope,
--        tnNetworkPolicyDescription,
--        tnNetworkPolicyIngressDefaultActionFC,
--        tnNetworkPolicyIngressDefaultActionProfile,
--        tnNetworkPolicyEgressRemark,
--        tnNetworkPolicyLastChanged,
--        tnNetworkPolicyIngressLerUseDscp,
--        tnNetworkPolicyTableLastChanged,
--        tnNetworkIngressDSCPRowStatus,
--        tnNetworkIngressDSCPFC,
--        tnNetworkIngressDSCPProfile,
--        tnNetworkIngressDSCPLastChanged,
--        tnNetworkIngressDSCPTableLastChanged,
--        tnNetworkIngressDot1pRowStatus,
--        tnNetworkIngressDot1pFC,
--        tnNetworkIngressDot1pProfile,
--        tnNetworkIngressDot1pLastChanged,
--        tnNetworkIngressDot1pTableLastChanged,
--        tnNetworkIngressLSPEXPRowStatus,
--        tnNetworkIngressLSPEXPFC,
--        tnNetworkIngressLSPEXPProfile,
--        tnNetworkIngressLSPEXPLastChanged,
--        tnNetworkIngressLSPEXPTableLastChanged,
--        tnNetworkEgressFCDSCPInProfile,
--        tnNetworkEgressFCDSCPOutProfile,
--        tnNetworkEgressFCLspExpInProfile,
--        tnNetworkEgressFCLspExpOutProfile,
--        tnNetworkEgressFCDot1pInProfile,
--        tnNetworkEgressFCDot1pOutProfile,
--        tnNetworkEgressFCLastChanged,
--        tnNetworkEgressFCTableLastChanged,
--        tnNetworkQueuePolicyRowStatus,
--        tnNetworkQueuePolicyDescription,
--        tnNetworkQueuePolicyLastChanged,
--        tnNetworkQueuePolicyTableLastChanged,
--        tnNetworkQueueRowStatus,
--        tnNetworkQueuePoolName,
--        tnNetworkQueueParent,
--        tnNetworkQueueLevel,
--        tnNetworkQueueWeight,
--        tnNetworkQueueCIRLevel,
--        tnNetworkQueueCIRWeight,
--        tnNetworkQueueMCast,
--        tnNetworkQueueExpedite,
--        tnNetworkQueueCIR,
--        tnNetworkQueuePIR,
--        tnNetworkQueueCBS,
--        tnNetworkQueueMBS,
--        tnNetworkQueueHiPrioOnly,
--        tnNetworkQueueLastChanged ,
--        tnNetworkQueueTableLastChanged,
--        tnNetworkQueueFCRowStatus,
--        tnNetworkQueueFC,
--        tnNetworkQueueFCMCast,
--        tnNetworkQueueFCLastChanged,
--        tnNetworkQueueFCTableLastChanged
--    }
--    STATUS      obsolete
--    DESCRIPTION
--        "The group of objects supporting management of Network QoS policies
--         on Nokia 7x50 SR series systems."
--    ::= { tnQosGroups 13 }

-- tnQosQueueR2r1Group OBJECT-GROUP
--    ::= { tnQosGroups 14 }

-- tnQosAtmTdpV3v0Group OBJECT-GROUP
--     OBJECTS   {
--         tnAtmTdpSir,
--         tnAtmTdpPir,
--         tnAtmTdpMbs,
--         tnAtmTdpMir,
--         tnAtmTdpShaping,
--         tnAtmTdpServCat,
--         tnAtmTdpLastChanged,
--         tnAtmTdpDescription,
--         tnAtmTdpRowStatus,
--         tnAtmTdpDescrType,
--         tnAtmTdpCdvt,
--         tnAtmTdpPolicing,
--         tnAtmTdpIndexNext,
--         tnAtmTdpsMaxSupported,
--         tnAtmTdpsCurrentlyConfigured,
--         tnAtmTdpTableLastChanged
--     }
--     STATUS    obsolete
--     DESCRIPTION
--         "The group of objects for ATM Traffic Descriptor Profiles
--          on Nokia 7x50 SR series systems release 3.0."
--     ::= { tnQosGroups 15 }


-- tnQosSapIpv6FilterR4r0Group OBJECT-GROUP
--    OBJECTS {
--        tnSapIngressIPv6CriteriaRowStatus,
--        tnSapIngressIPv6CriteriaDescription,
--        tnSapIngressIPv6CriteriaActionFC,
--        tnSapIngressIPv6CriteriaActionPriority,
--        tnSapIngressIPv6CriteriaSourceIpAddr,
--        tnSapIngressIPv6CriteriaSourceIpMask,
--        tnSapIngressIPv6CriteriaDestIpAddr,
--        tnSapIngressIPv6CriteriaDestIpMask,
--        tnSapIngressIPv6CriteriaNextHeader,
--        tnSapIngressIPv6CriteriaSourcePortValue1,
--        tnSapIngressIPv6CriteriaSourcePortValue2,
--        tnSapIngressIPv6CriteriaSourcePortOperator,
--        tnSapIngressIPv6CriteriaDestPortValue1,
--        tnSapIngressIPv6CriteriaDestPortValue2,
--        tnSapIngressIPv6CriteriaDestPortOperator,
--        tnSapIngressIPv6CriteriaDSCP,
--        tnSapIngressIPv6CriteriaLastChanged,
--        tnSapIngressIPv6CriteriaTableLastChanged
--    }
--    STATUS    current
--    DESCRIPTION
--        "The group of objects for Qos Policies related to IPv6
--         on Nokia 7x50 SR series systems release 4.0."
--    ::= { tnQosGroups 16 }

-- tnQosQueueV4v0Group OBJECT-GROUP
--    OBJECTS {
--        tnSharedQueuePolicyRowStatus,
--        tnSharedQueuePolicyDescription,
--        tnSharedQueuePolicyLastChanged,
--        tnSharedQueuePolicyTableLastChanged,
--        tnSharedQueueRowStatus,
--        tnSharedQueuePoolName,
--        tnSharedQueueParent,
--        tnSharedQueueLevel,
--        tnSharedQueueWeight,
--        tnSharedQueueCIRLevel,
--        tnSharedQueueCIRWeight,
--        tnSharedQueueExpedite,
--        tnSharedQueueCIR,
--        tnSharedQueuePIR,
--        tnSharedQueueCBS,
--        tnSharedQueueMBS,
--        tnSharedQueueHiPrioOnly,
--        tnSharedQueueLastChanged,
--        tnSharedQueueIsMultipoint,
--        tnSharedQueueTableLastChanged,
--        tnSharedQueueFCRowStatus,
--        tnSharedQueueFCQueue,
--        tnSharedQueueFCLastChanged,
--        tnSharedQueueFCTableLastChanged,
--        tnSharedQueueFCMCastQueue,
--        tnSharedQueueFCBCastQueue,
--        tnSharedQueueFCUnknownQueue
--    }
--    STATUS      current
--    DESCRIPTION
--        "The group of objects supporting management of QoS queue policies
--         on Nokia 7x50 SR series systems release 4.0."
--    ::= { tnQosGroups 18 }

-- tnQosSapIngressV4v0Group OBJECT-GROUP
--    OBJECTS {
--        tnSapIngressRowStatus,
--        tnSapIngressScope,
--        tnSapIngressDescription,
--        tnSapIngressDefaultFC,
--        tnSapIngressDefaultFCPriority,
--        tnSapIngressMatchCriteria,
--        tnSapIngressLastChanged,
--        tnSapIngressTableLastChanged,
--        tnSapIngressQueueRowStatus,
--        tnSapIngressQueueParent,
--        tnSapIngressQueueLevel,
--        tnSapIngressQueueWeight,
--        tnSapIngressQueueCIRLevel,
--        tnSapIngressQueueCIRWeight,
--        tnSapIngressQueueMCast,
--        tnSapIngressQueueExpedite,
--        tnSapIngressQueueCBS,
--        tnSapIngressQueueMBS,
--        tnSapIngressQueueHiPrioOnly,
--        tnSapIngressQueueCIRAdaptation,
--        tnSapIngressQueuePIRAdaptation,
--        tnSapIngressQueueAdminPIR,
--        tnSapIngressQueueAdminCIR,
--        tnSapIngressQueueLastChanged,
--        tnSapIngressQueueMode,
--        tnSapIngressQueueTableLastChanged,
--        tnSapIngressQueuePoliced,
--        tnSapIngressDSCPRowStatus,
--        tnSapIngressDSCPFC,
--        tnSapIngressDSCPPriority,
--        tnSapIngressDSCPLastChanged,
--        tnSapIngressDSCPTableLastChanged,
--        tnSapIngressDot1pRowStatus,
--        tnSapIngressDot1pFC,
--        tnSapIngressDot1pPriority,
--        tnSapIngressDot1pLastChanged,
--        tnSapIngressDot1pTableLastChanged,
--        tnSapIngressIPCriteriaRowStatus,
--        tnSapIngressIPCriteriaDescription,
--        tnSapIngressIPCriteriaActionFC,
--        tnSapIngressIPCriteriaActionPriority,
--        tnSapIngressIPCriteriaSourceIpAddr,
--        tnSapIngressIPCriteriaSourceIpMask,
--        tnSapIngressIPCriteriaDestIpAddr,
--        tnSapIngressIPCriteriaDestIpMask,
--        tnSapIngressIPCriteriaProtocol,
--        tnSapIngressIPCriteriaSourcePortValue1,
--        tnSapIngressIPCriteriaSourcePortValue2,
--        tnSapIngressIPCriteriaSourcePortOperator,
--        tnSapIngressIPCriteriaDestPortValue1,
--        tnSapIngressIPCriteriaDestPortValue2,
--        tnSapIngressIPCriteriaDestPortOperator,
--        tnSapIngressIPCriteriaDSCP,
--        tnSapIngressIPCriteriaFragment,
--        tnSapIngressIPCriteriaLastChanged,
--        tnSapIngressIPCriteriaTableLastChanged,
--        tnSapIngressMacCriteriaRowStatus,
--        tnSapIngressMacCriteriaDescription,
--        tnSapIngressMacCriteriaActionFC,
--        tnSapIngressMacCriteriaActionPriority,
--        tnSapIngressMacCriteriaFrameType,
--        tnSapIngressMacCriteriaSrcMacAddr,
--        tnSapIngressMacCriteriaSrcMacMask,
--        tnSapIngressMacCriteriaDstMacAddr,
--        tnSapIngressMacCriteriaDstMacMask,
--        tnSapIngressMacCriteriaDot1PValue,
--        tnSapIngressMacCriteriaDot1PMask,
--        tnSapIngressMacCriteriaEthernetType,
--        tnSapIngressMacCriteriaDSAP,
--        tnSapIngressMacCriteriaDSAPMask,
--        tnSapIngressMacCriteriaSSAP,
--        tnSapIngressMacCriteriaSSAPMask,
--        tnSapIngressMacCriteriaSnapPid,
--        tnSapIngressMacCriteriaSnapOui,
--        tnSapIngressMacCriteriaLastChanged,
--        tnSapIngressMacCriteriaTableLastChanged,
--        tnSapIngressFCRowStatus,
--        tnSapIngressFCQueue,
--        tnSapIngressFCMCastQueue,
--        tnSapIngressFCBCastQueue,
--        tnSapIngressFCUnknownQueue,
--        tnSapIngressFCLastChanged,
--        tnSapIngressFCInProfRemark,
--        tnSapIngressFCInProfDscp,
--        tnSapIngressFCInProfPrec,
--        tnSapIngressFCOutProfRemark,
--        tnSapIngressFCOutProfDscp,
--        tnSapIngressFCOutProfPrec,
--        tnSapIngressFCProfile,
--        tnSapIngressFCTableLastChanged,
--        tnSapIngressPrecRowStatus,
--        tnSapIngressPrecFC,
--        tnSapIngressPrecFCPriority,
--        tnSapIngressPrecLastChanged,
--        tnSapIngressPrecTableLastChanged
--    }
--    STATUS      obsolete
--    DESCRIPTION
--        "The group of objects supporting management of SAP ingress QoS
--         policies on Nokia 7x50 SR series systems release 4.0."
--    ::= { tnQosGroups 19 }

-- tnQosSchedulerV5v0Group OBJECT-GROUP
--    OBJECTS {
--        tnSchedulerPolicyRowStatus,
--        tnSchedulerPolicyDescription,
--        tnSchedulerPolicyLastChanged,
--        tnSchedulerPolicyTableLastChanged,
--        tnVirtualSchedulerRowStatus,
--        tnVirtualSchedulerDescription,
--        tnVirtualSchedulerParent,
--        tnVirtualSchedulerLevel,
--        tnVirtualSchedulerWeight,
--        tnVirtualSchedulerCIRLevel,
--        tnVirtualSchedulerCIRWeight,
--        tnVirtualSchedulerPIR,
--        tnVirtualSchedulerCIR,
--        tnVirtualSchedulerSummedCIR,
--        tnVirtualSchedulerLastChanged,
--        tnVirtualSchedulerUsePortParent,
--        tnVirtualSchedulerPortLvl,
--        tnVirtualSchedulerPortWght,
--        tnVirtualSchedulerPortCIRLvl,
--        tnVirtualSchedulerPortCIRWght,
--        tnVirtualSchedulerTableLastChanged,
--        tnPortSchedulerPlcyRowStatus,
--        tnPortSchedulerPlcyDescription,
--        tnPortSchedulerPlcyLastChanged,
--        tnPortSchedulerPlcyMaxRate,
--        tnPortSchedulerPlcyLvl1PIR,
--        tnPortSchedulerPlcyLvl1CIR,
--        tnPortSchedulerPlcyLvl2PIR,
--        tnPortSchedulerPlcyLvl2CIR,
--        tnPortSchedulerPlcyLvl3PIR,
--        tnPortSchedulerPlcyLvl3CIR,
--        tnPortSchedulerPlcyLvl4PIR,
--        tnPortSchedulerPlcyLvl4CIR,
--        tnPortSchedulerPlcyLvl5PIR,
--        tnPortSchedulerPlcyLvl5CIR,
--        tnPortSchedulerPlcyLvl6PIR,
--        tnPortSchedulerPlcyLvl6CIR,
--        tnPortSchedulerPlcyLvl7PIR,
--        tnPortSchedulerPlcyLvl7CIR,
--        tnPortSchedulerPlcyLvl8PIR,
--        tnPortSchedulerPlcyLvl8CIR,
--        tnPortSchedulerPlcyOrphanLvl,
--        tnPortSchedulerPlcyOrphanWeight,
--        tnPortSchedulerPlcyOrphanCIRLvl,
--        tnPortSchedulerPlcyOrphanCIRWght
--    }
--    STATUS      current
--    DESCRIPTION
--        "The group of objects supporting management of Scheduler policies
--         on Nokia 7x50 SR series systems."
--    ::= { tnQosGroups 20 }

-- tnQosSapEgressV5v0Group OBJECT-GROUP
--    OBJECTS {
--        tnSapEgressRowStatus,
--        tnSapEgressScope,
--        tnSapEgressDescription,
--        tnSapEgressLastChanged,
--        tnSapEgressTableLastChanged,
--        tnSapEgressQueueRowStatus,
--        tnSapEgressQueueParent,
--        tnSapEgressQueueLevel,
--        tnSapEgressQueueWeight,
--        tnSapEgressQueueCIRLevel,
--        tnSapEgressQueueCIRWeight,
--        tnSapEgressQueueExpedite,
--        tnSapEgressQueueCBS,
--        tnSapEgressQueueMBS,
--        tnSapEgressQueueHiPrioOnly,
--        tnSapEgressQueueCIRAdaptation,
--        tnSapEgressQueuePIRAdaptation,
--        tnSapEgressQueueAdminPIR,
--        tnSapEgressQueueAdminCIR,
--        tnSapEgressQueueLastChanged,
--        tnSapEgressQueueTableLastChanged,
--        tnSapEgressFCRowStatus,
--        tnSapEgressFCQueue,
--        tnSapEgressFCDot1PValue,
--        tnSapEgressFCLastChanged,
--        tnSapEgressFCTableLastChanged,
--        tnSapEgressQueueUsePortParent,
--        tnSapEgressQueuePortLvl,
--        tnSapEgressQueuePortWght,
--        tnSapEgressQueuePortCIRLvl,
--        tnSapEgressQueuePortCIRWght,
--        tnSapEgressQueuePortAvgOverhead
--    }
--    STATUS      obsolete
--    DESCRIPTION
--        "The group of objects supporting management of SAP egress QoS
--         policies on Nokia 7x50 SR series systems."
--    ::= { tnQosGroups 21 }

-- tnQosNetworkV5v0Group OBJECT-GROUP
--    OBJECTS {
--        tnNetworkPolicyRowStatus,
--        tnNetworkPolicyScope,
--        tnNetworkPolicyDescription,
--        tnNetworkPolicyIngressDefaultActionFC,
--        tnNetworkPolicyIngressDefaultActionProfile,
--        tnNetworkPolicyEgressRemark,
--        tnNetworkPolicyLastChanged,
--        tnNetworkPolicyIngressLerUseDscp,
--        tnNetworkPolicyTableLastChanged,
--        tnNetworkIngressDSCPRowStatus,
--        tnNetworkIngressDSCPFC,
--        tnNetworkIngressDSCPProfile,
--        tnNetworkIngressDSCPLastChanged,
--        tnNetworkIngressDSCPTableLastChanged,
--        tnNetworkIngressDot1pRowStatus,
--        tnNetworkIngressDot1pFC,
--        tnNetworkIngressDot1pProfile,
--        tnNetworkIngressDot1pLastChanged,
--        tnNetworkIngressDot1pTableLastChanged,
--        tnNetworkIngressLSPEXPRowStatus,
--        tnNetworkIngressLSPEXPFC,
--        tnNetworkIngressLSPEXPProfile,
--        tnNetworkIngressLSPEXPLastChanged,
--        tnNetworkIngressLSPEXPTableLastChanged,
--        tnNetworkEgressFCDSCPInProfile,
--        tnNetworkEgressFCDSCPOutProfile,
--        tnNetworkEgressFCLspExpInProfile,
--        tnNetworkEgressFCLspExpOutProfile,
--        tnNetworkEgressFCDot1pInProfile,
--        tnNetworkEgressFCDot1pOutProfile,
--        tnNetworkEgressFCLastChanged,
--        tnNetworkEgressFCTableLastChanged,
--        tnNetworkQueuePolicyRowStatus,
--        tnNetworkQueuePolicyDescription,
--        tnNetworkQueuePolicyLastChanged,
--        tnNetworkQueuePolicyTableLastChanged,
--        tnNetworkQueueRowStatus,
--        tnNetworkQueuePoolName,
--        tnNetworkQueueParent,
--        tnNetworkQueueLevel,
--        tnNetworkQueueWeight,
--        tnNetworkQueueCIRLevel,
--        tnNetworkQueueCIRWeight,
--        tnNetworkQueueMCast,
--        tnNetworkQueueExpedite,
--        tnNetworkQueueCIR,
--        tnNetworkQueuePIR,
--        tnNetworkQueueCBS,
--        tnNetworkQueueMBS,
--        tnNetworkQueueHiPrioOnly,
--        tnNetworkQueueLastChanged,
--        tnNetworkQueueUsePortParent,
--        tnNetworkQueuePortLvl,
--        tnNetworkQueuePortWght,
--        tnNetworkQueuePortCIRLvl,
--        tnNetworkQueuePortCIRWght,
--        tnNetworkQueuePortAvgOverhead,
--        tnNetworkQueuePIRAdaptation,       
--        tnNetworkQueueCIRAdaptation,
--        tnNetworkQueueTableLastChanged,
--        tnNetworkQueueFCRowStatus,
--        tnNetworkQueueFC,
--        tnNetworkQueueFCMCast,
--        tnNetworkQueueFCLastChanged,
--        tnNetworkQueueFCTableLastChanged
--    }
--    STATUS      obsolete
--    DESCRIPTION
--        "The group of objects supporting management of Network QoS policies
--         on Nokia 7x50 SR series systems."
--    ::= { tnQosGroups 22 }

-- tnQosHsmdaV6v0Group OBJECT-GROUP
--    OBJECTS {
--        tnHsmdaSchedulerPlcyRowStatus,
--        tnHsmdaSchedulerPlcyDescription,
--        tnHsmdaSchedulerPlcyMaxRate,
--        tnHsmdaSchedulerPlcyLvl1Rate,
--        tnHsmdaSchedulerPlcyLvl1GrpId,
--        tnHsmdaSchedulerPlcyLvl1WgtInGrp,
--        tnHsmdaSchedulerPlcyLvl2Rate,
--        tnHsmdaSchedulerPlcyLvl2GrpId,
--        tnHsmdaSchedulerPlcyLvl2WgtInGrp,
--        tnHsmdaSchedulerPlcyLvl3Rate,
--        tnHsmdaSchedulerPlcyLvl3GrpId,
--        tnHsmdaSchedulerPlcyLvl3WgtInGrp,
--        tnHsmdaSchedulerPlcyLvl4Rate,
--        tnHsmdaSchedulerPlcyLvl4GrpId,
--        tnHsmdaSchedulerPlcyLvl4WgtInGrp,
--        tnHsmdaSchedulerPlcyLvl5Rate,
--        tnHsmdaSchedulerPlcyLvl5GrpId,
--        tnHsmdaSchedulerPlcyLvl5WgtInGrp,
--        tnHsmdaSchedulerPlcyLvl6Rate,
--        tnHsmdaSchedulerPlcyLvl6GrpId,
--        tnHsmdaSchedulerPlcyLvl6WgtInGrp,
--        tnHsmdaSchedulerPlcyLvl7Rate,
--        tnHsmdaSchedulerPlcyLvl7GrpId,
--        tnHsmdaSchedulerPlcyLvl7WgtInGrp,
--        tnHsmdaSchedulerPlcyLvl8Rate,
--        tnHsmdaSchedulerPlcyLvl8GrpId,
--        tnHsmdaSchedulerPlcyLvl8WgtInGrp,
--        tnHsmdaSchedulerPlcyLastChanged,
--        tnHsmdaSchedulerPlcyGrp1Rate,
--        tnHsmdaSchedulerPlcyGrp2Rate,
--        tnSapEgressFCHsmdaQueue,
--        tnSapEgressFCDot1PHsmdaProfile,
--        tnSapEgressHsmdaQueueRowStatus,
--        tnSapEgressHsmdaQueueCIRAdaptn,
--        tnSapEgressHsmdaQueuePIRAdaptn,
--        tnSapEgressHsmdaQueueAdminPIR,
--        tnSapEgressHsmdaQueueAdminCIR,
--        tnSapEgressHsmdaQueueSlopePolicy,
--        tnSapEgressHsmdaQueueLastChanged,
--        tnSapIngressHsmdaPacketOffset,
--        tnSapIngressDefFCHsmdaCntrOvr,
--        tnSapIngressMacCritType,
--        tnSapIngressPolicyName,
--        tnSapIngressDot1pHsmdaCntrOvr,
--        tnSapIngressDSCPHsmdaCntrOvr,
--        tnSapIngressFCHsmdaQueue,
--        tnSapIngressFCHsmdaMCastQueue,
--        tnSapIngressFCHsmdaBCastQueue,
--        tnSapIngressPrecHsmdaCntrOvr,
--        tnSapIngressHsmdaQueueRowStatus,
--        tnSapIngressHsmdaQueueLastChanged,
--        tnSapIngressHsmdaQueueCIRAdaptn,
--        tnSapIngressHsmdaQueuePIRAdaptn,
--        tnSapIngressHsmdaQueueAdminPIR,
--        tnSapIngressHsmdaQueueAdminCIR,
--        tnSapIngressHsmdaQueueSlopePolicy,
--        tnSapIngressHsmdaQueuePoliced,
--        tnHsmdaPoolPolicyRowStatus,
--        tnHsmdaPoolLastChanged,
--        tnHsmdaPoolDescription,
--        tnHsmdaPoolSystemReserve,
--        tnHsmdaPoolRoot1AllocWeight,
--        tnHsmdaPoolRoot2AllocWeight,
--        tnHsmdaPoolRoot3AllocWeight,
--        tnHsmdaPoolRoot4AllocWeight,
--        tnHsmdaPoolRoot5AllocWeight,
--        tnHsmdaPoolRoot6AllocWeight,
--        tnHsmdaPoolRoot7AllocWeight,
--        tnHsmdaPoolRoot8AllocWeight,
--        tnHsmdaPoolClass1Parent,
--        tnHsmdaPoolClass1AllocPercent,
--        tnHsmdaPoolClass2Parent,
--        tnHsmdaPoolClass2AllocPercent,
--        tnHsmdaPoolClass3Parent,
--        tnHsmdaPoolClass3AllocPercent,
--        tnHsmdaPoolClass4Parent,
--        tnHsmdaPoolClass4AllocPercent,
--        tnHsmdaPoolClass5Parent,
--        tnHsmdaPoolClass5AllocPercent,
--        tnHsmdaPoolClass6Parent,
--        tnHsmdaPoolClass6AllocPercent,
--        tnHsmdaPoolClass7Parent,
--        tnHsmdaPoolClass7AllocPercent,
--        tnHsmdaPoolClass8Parent,
--        tnHsmdaPoolClass8AllocPercent,
--        tnHsmdaSlopePolicyRowStatus,
--        tnHsmdaSlopeLastChanged,
--        tnHsmdaSlopeDescription,
--        tnHsmdaSlopeQueueMbs,
--        tnHsmdaSlopeHiAdminStatus,
--        tnHsmdaSlopeHiStartDepth,
--        tnHsmdaSlopeHiMaxDepth,
--        tnHsmdaSlopeHiMaxProbability,
--        tnHsmdaSlopeLoAdminStatus,
--        tnHsmdaSlopeLoStartDepth,
--        tnHsmdaSlopeLoMaxDepth,
--        tnHsmdaSlopeLoMaxProbability,
--        tnSapIngrHsmdaQueueTblLastChngd,
--        tnSapEgrHsmdaQueueTblLastChngd,
--        tnHsmdaSchedPlcyTblLastChngd,
--        tnHsmdaSchedPlcyGrpTblLastChngd,
--        tnHsmdaPoolPlcyTblLastChngd,
--        tnHsmdaSlopePolicyTableLastChanged,
--        tnSapIngressIPCritHsmdaCntrOvr,
--        tnSapEgressDSCPRowStatus,
--        tnSapEgressDSCPLastChanged,
--        tnSapEgressDSCPHsmdaCntrOverride,
--        tnSapEgressPrecRowStatus,
--        tnSapEgressPrecLastChanged,
--        tnSapEgressPrecHsmdaCntrOverride,
--        tnSapEgrIPCritRowStatus,
--        tnSapEgrIPCritLastChanged,
--        tnSapEgrIPCritDescription,
--        tnSapEgrIPCritActionHsmdaCntrOvr,
--        tnSapEgrIPCritSourceIpAddrType,
--        tnSapEgrIPCritSourceIpAddr,
--        tnSapEgrIPCritSourceIpMask,
--        tnSapEgrIPCritDestIpAddrType,
--        tnSapEgrIPCritDestIpAddr,
--        tnSapEgrIPCritDestIpMask,
--        tnSapEgrIPCritProtocol,
--        tnSapEgrIPCritSourcePortValue1,
--        tnSapEgrIPCritSourcePortValue2,
--        tnSapEgrIPCritSourcePortOperator,
--        tnSapEgrIPCritDestPortValue1,
--        tnSapEgrIPCritDestPortValue2,
--        tnSapEgrIPCritDestPortOperator,
--        tnSapEgrIPCritDSCP,
--        tnSapEgrIPCritFragment,
--        tnSapEgressMatchCriteria,
--        tnSapEgressHsmdaPacketOffset
--   }
--    STATUS      obsolete
--    DESCRIPTION
--        "The group of objects supporting management of QoS policies 
--         for HSMDA MDAs on Nokia 7x50 SR series systems release 6.0."
--    ::= { tnQosGroups 23 }

-- tnQosAtmTdpV5v0Group OBJECT-GROUP
--     OBJECTS   {
--         tnAtmTdpSir,
--         tnAtmTdpPir,
--         tnAtmTdpMbs,
--         tnAtmTdpMir,
--         tnAtmTdpShaping,
--         tnAtmTdpServCat,
--         tnAtmTdpLastChanged,
--         tnAtmTdpDescription,
--         tnAtmTdpRowStatus,
--         tnAtmTdpDescrType,
--         tnAtmTdpCdvt,
--         tnAtmTdpPolicing,
--         tnAtmTdpCLPTagging,
--         tnAtmTdpIndexNext,
--         tnAtmTdpsMaxSupported,
--         tnAtmTdpsCurrentlyConfigured,
--         tnAtmTdpTableLastChanged
--     }
--     STATUS    current
--     DESCRIPTION
--         "The group of objects for ATM Traffic Descriptor Profiles
--          on Nokia 7x50 SR series systems release 5.0."
--     ::= { tnQosGroups 24 }

-- tnQosSapIngressV6v0Group OBJECT-GROUP
--    OBJECTS {
--        tnSapIngressRowStatus,
--        tnSapIngressScope,
--        tnSapIngressDescription,
--        tnSapIngressDefaultFC,
--        tnSapIngressDefaultFCPriority,
--        tnSapIngressMatchCriteria,
--        tnSapIngressLastChanged,
--        tnSapIngressTableLastChanged,
--        tnSapIngressQueueRowStatus,
--        tnSapIngressQueueParent,
--        tnSapIngressQueueLevel,
--        tnSapIngressQueueWeight,
--        tnSapIngressQueueCIRLevel,
--        tnSapIngressQueueCIRWeight,
--        tnSapIngressQueueMCast,
--        tnSapIngressQueueExpedite,
--        tnSapIngressQueueCBS,
--        tnSapIngressQueueMBS,
--        tnSapIngressQueueHiPrioOnly,
--        tnSapIngressQueueCIRAdaptation,
--        tnSapIngressQueuePIRAdaptation,
--        tnSapIngressQueueAdminPIR,
--        tnSapIngressQueueAdminCIR,
--        tnSapIngressQueueLastChanged,
--        tnSapIngressQueueMode,
--        tnSapIngressQueuePoolName,
--        tnSapIngressQueueTableLastChanged,
--        tnSapIngressQueuePoliced,
--        tnSapIngressDSCPRowStatus,
--        tnSapIngressDSCPFC,
--        tnSapIngressDSCPPriority,
--        tnSapIngressDSCPLastChanged,
--        tnSapIngressDSCPTableLastChanged,
--        tnSapIngressDot1pRowStatus,
--        tnSapIngressDot1pFC,
--        tnSapIngressDot1pPriority,
--        tnSapIngressDot1pLastChanged,
--        tnSapIngressDot1pTableLastChanged,
--        tnSapIngressIPCriteriaRowStatus,
--        tnSapIngressIPCriteriaDescription,
--        tnSapIngressIPCriteriaActionFC,
--        tnSapIngressIPCriteriaActionPriority,
--        tnSapIngressIPCriteriaSourceIpAddr,
--        tnSapIngressIPCriteriaSourceIpMask,
--        tnSapIngressIPCriteriaDestIpAddr,
--        tnSapIngressIPCriteriaDestIpMask,
--        tnSapIngressIPCriteriaProtocol,
--        tnSapIngressIPCriteriaSourcePortValue1,
--        tnSapIngressIPCriteriaSourcePortValue2,
--        tnSapIngressIPCriteriaSourcePortOperator,
--        tnSapIngressIPCriteriaDestPortValue1,
--        tnSapIngressIPCriteriaDestPortValue2,
--        tnSapIngressIPCriteriaDestPortOperator,
--        tnSapIngressIPCriteriaDSCP,
--        tnSapIngressIPCriteriaFragment,
--        tnSapIngressIPCriteriaLastChanged,
--        tnSapIngressIPCriteriaTableLastChanged,
--        tnSapIngressMacCriteriaRowStatus,
--        tnSapIngressMacCriteriaDescription,
--        tnSapIngressMacCriteriaActionFC,
--        tnSapIngressMacCriteriaActionPriority,
--        tnSapIngressMacCriteriaFrameType,
--        tnSapIngressMacCriteriaSrcMacAddr,
--        tnSapIngressMacCriteriaSrcMacMask,
--        tnSapIngressMacCriteriaDstMacAddr,
--        tnSapIngressMacCriteriaDstMacMask,
--        tnSapIngressMacCriteriaDot1PValue,
--        tnSapIngressMacCriteriaDot1PMask,
--        tnSapIngressMacCriteriaEthernetType,
--        tnSapIngressMacCriteriaDSAP,
--        tnSapIngressMacCriteriaDSAPMask,
--        tnSapIngressMacCriteriaSSAP,
--        tnSapIngressMacCriteriaSSAPMask,
--        tnSapIngressMacCriteriaSnapPid,
--        tnSapIngressMacCriteriaSnapOui,
--        tnSapIngressMacCriteriaLastChanged,
--        tnSapIngressMacCriteriaTableLastChanged,
--        tnSapIngressFCRowStatus,
--        tnSapIngressFCQueue,
--        tnSapIngressFCMCastQueue,
--        tnSapIngressFCBCastQueue,
--        tnSapIngressFCUnknownQueue,
--        tnSapIngressFCLastChanged,
--        tnSapIngressFCInProfRemark,
--        tnSapIngressFCInProfDscp,
--        tnSapIngressFCInProfPrec,
--        tnSapIngressFCDE1OutOfProfile,
--        tnSapIngressFCOutProfRemark,
--        tnSapIngressFCOutProfDscp,
--        tnSapIngressFCOutProfPrec,
--        tnSapIngressFCProfile,
--        tnSapIngressFCTableLastChanged,
--        tnSapIngressPrecRowStatus,
--        tnSapIngressPrecFC,
--        tnSapIngressPrecFCPriority,
--        tnSapIngressPrecLastChanged,
--        tnSapIngressPrecTableLastChanged
--    }
--    STATUS      current
--    DESCRIPTION
--        "The group of objects supporting management of SAP ingress QoS
--         policies on Nokia 7x50 SR series systems release 6.0."
--    ::= { tnQosGroups 25 }

-- tnQosSapEgressV6v0Group OBJECT-GROUP
--    OBJECTS {
--        tnSapEgressRowStatus,
--        tnSapEgressScope,
--        tnSapEgressDescription,
--        tnSapEgressLastChanged,
--        tnSapEgressTableLastChanged,
--        tnSapEgressQueueRowStatus,
--        tnSapEgressQueueParent,
--        tnSapEgressQueueLevel,
--        tnSapEgressQueueWeight,
--        tnSapEgressQueueCIRLevel,
--        tnSapEgressQueueCIRWeight,
--        tnSapEgressQueueExpedite,
--        tnSapEgressQueueCBS,
--        tnSapEgressQueueMBS,
--        tnSapEgressQueueHiPrioOnly,
--        tnSapEgressQueueCIRAdaptation,
--        tnSapEgressQueuePIRAdaptation,
--        tnSapEgressQueueAdminPIR,
--        tnSapEgressQueueAdminCIR,
--        tnSapEgressQueueLastChanged,
--        tnSapEgressQueueTableLastChanged,
--        tnSapEgressFCRowStatus,
--        tnSapEgressFCQueue,
--        tnSapEgressFCLastChanged,
--        tnSapEgressFCTableLastChanged,
--        tnSapEgressFCDot1PInProfile,
--        tnSapEgressFCDot1POutProfile,
--        tnSapEgressFCForceDEValue,
--        tnSapEgressFCDEMark,
--        tnSapEgressFCInProfDscp,
--        tnSapEgressFCOutProfDscp,
--        tnSapEgressFCInProfPrec,
--        tnSapEgressFCOutProfPrec,
--        tnSapEgressQueueUsePortParent,
--        tnSapEgressQueuePortLvl,
--        tnSapEgressQueuePortWght,
--        tnSapEgressQueuePortCIRLvl,
--        tnSapEgressQueuePortCIRWght,
--        tnSapEgressQueuePortAvgOverhead,
--        tnSapEgressQueuePoolName
--    }
--    STATUS      current
--    DESCRIPTION
--        "The group of objects supporting management of SAP egress QoS
--         policies on Nokia 7x50 SR series systems."
--    ::= { tnQosGroups 26 }

-- tnQosNetworkV6v0Group OBJECT-GROUP
--    OBJECTS {
--        tnNetworkPolicyRowStatus,
--        tnNetworkPolicyScope,
--        tnNetworkPolicyDescription,
--        tnNetworkPolicyIngressDefaultActionFC,
--        tnNetworkPolicyIngressDefaultActionProfile,
--        tnNetworkPolicyEgressRemark,
--        tnNetworkPolicyLastChanged,
--        tnNetworkPolicyIngressLerUseDscp,
--        tnNetworkPolicyTableLastChanged,
--        tnNetworkIngressDSCPRowStatus,
--        tnNetworkIngressDSCPFC,
--        tnNetworkIngressDSCPProfile,
--        tnNetworkIngressDSCPLastChanged,
--        tnNetworkIngressDSCPTableLastChanged,
--        tnNetworkIngressDot1pRowStatus,
--        tnNetworkIngressDot1pFC,
--        tnNetworkIngressDot1pProfile,
--        tnNetworkIngressDot1pLastChanged,
--        tnNetworkIngressDot1pTableLastChanged,
--        tnNetworkIngressLSPEXPRowStatus,
--        tnNetworkIngressLSPEXPFC,
--        tnNetworkIngressLSPEXPProfile,
--        tnNetworkIngressLSPEXPLastChanged,
--        tnNetworkIngressLSPEXPTableLastChanged,
--        tnNetworkEgressFCDSCPInProfile,
--        tnNetworkEgressFCDSCPOutProfile,
--        tnNetworkEgressFCLspExpInProfile,
--        tnNetworkEgressFCLspExpOutProfile,
--        tnNetworkEgressFCDot1pInProfile,
--        tnNetworkEgressFCDot1pOutProfile,
--        tnNetworkEgressFCLastChanged,
--        tnNetworkEgressFCForceDEValue,
--        tnNetworkEgressFCDEMark,
--        tnNetworkEgressFCTableLastChanged,
--        tnNetworkQueuePolicyRowStatus,
--        tnNetworkQueuePolicyDescription,
--        tnNetworkQueuePolicyLastChanged,
--        tnNetworkQueuePolicyTableLastChanged,
--        tnNetworkQueueRowStatus,
--        tnNetworkQueuePoolName,
--        tnNetworkQueueParent,
--        tnNetworkQueueLevel,
--        tnNetworkQueueWeight,
--        tnNetworkQueueCIRLevel,
--        tnNetworkQueueCIRWeight,
--        tnNetworkQueueMCast,
--        tnNetworkQueueExpedite,
--        tnNetworkQueueCIR,
--        tnNetworkQueuePIR,
--        tnNetworkQueueCBS,
--        tnNetworkQueueMBS,
--        tnNetworkQueueHiPrioOnly,
--        tnNetworkQueueLastChanged,
--        tnNetworkQueueUsePortParent,
--        tnNetworkQueuePortLvl,
--        tnNetworkQueuePortWght,
--        tnNetworkQueuePortCIRLvl,
--        tnNetworkQueuePortCIRWght,
--        tnNetworkQueuePortAvgOverhead,
--        tnNetworkQueuePIRAdaptation,       
--        tnNetworkQueueCIRAdaptation,
--        tnNetworkQueueTableLastChanged,
--        tnNetworkQueueFCRowStatus,
--        tnNetworkQueueFC,
--        tnNetworkQueueFCMCast,
--        tnNetworkQueueFCLastChanged,
--        tnNetworkQueueFCTableLastChanged
--    }
--    STATUS      obsolete
--    DESCRIPTION
--        "The group of objects supporting management of Network QoS policies
--         on Nokia 7x50 SR series systems."
--    ::= { tnQosGroups 27 }

-- tnQosFrameBasedV6v0Group OBJECT-GROUP
--    OBJECTS {
--        tnSchedulerPolicyFrameBasedAccnt
--   }
--    STATUS      current
--    DESCRIPTION
--        "The group of objects supporting management of frame-based queue
--         accounting on Nokia 7x50 SR series systems release 6.0."
--    ::= { tnQosGroups 28 }

-- tnQosObsoletedV6v0Group OBJECT-GROUP
--    OBJECTS {
--        tnSapEgressFCDot1PValue
--    }
--    STATUS      current
--    DESCRIPTION
--        "The group of obsolete objects for the QoS on
--         Nokia 7x50 SR series systems."
--    ::= { tnQosGroups 29 }

-- tnQosNamedPoolPolicyV6v0Group OBJECT-GROUP
--    OBJECTS {
--        tnNamedPoolPolicyTableLastChanged,
--        tnNamedPoolPolicyRowStatus,
--        tnNamedPoolPolicyLastChanged,
--        tnNamedPoolPolicyDescription,
--        tnNamedPoolPolicyQ1DefaultWeight,
--        tnNamedPoolPolicyQ1MdaWeight,
--        tnNamedPoolPolicyQ1PortWeight,
--        tnQ1NamedPoolTableLastChanged,
--        tnQ1NamedPoolRowStatus,
--        tnQ1NamedPoolLastChanged,
--        tnQ1NamedPoolDescription,
--        tnQ1NamedPoolNetworkAllocWeight,
--        tnQ1NamedPoolAccessAllocWeight,
--        tnQ1NamedPoolSlopePolicy,
--        tnQ1NamedPoolReservedCbs
--    }
--    STATUS      current
--    DESCRIPTION
--        "The group of objects for the named pool policy on
--         Nokia 7x50 SR series systems."
--    ::= { tnQosGroups 30 }

-- tnQosMcMlpppIngrGroup OBJECT-GROUP
--    OBJECTS {
--        tnMcMlpppIngrProfDescription,
--        tnMcMlpppIngrProfLastChanged,
--        tnMcMlpppIngrProfRowStatus,
--        tnMcMlpppIngrProfTableLastChanged,
--        tnMcMlpppIngrClassReassemblyTmout,
--        tnMcMlpppIngrClassLastChanged,
--        tnMcMlpppIngrClassTableLastChanged
--    }
--    STATUS      current
--    DESCRIPTION
--        "The group of objects for the multi-class mlppp ingress information on
--         Nokia 7x50 SR series systems."
--    ::= { tnQosGroups 31 }

-- tnQosMcMlpppEgrGroup OBJECT-GROUP
--    OBJECTS {
--        tnMcMlpppEgrProfDescription,
--        tnMcMlpppEgrProfLastChanged,
--        tnMcMlpppEgrProfRowStatus,       
--        tnMcMlpppEgrProfTableLastChanged,
--        tnMcMlpppEgrClassMir,
--        tnMcMlpppEgrClassWeight,
--        tnMcMlpppEgrClassMaxSize,
--        tnMcMlpppEgrClassLastChanged,        
--        tnMcMlpppEgrClassTableLastChanged,
--        tnMcMlpppEgrFCClass,
--        tnMcMlpppEgrFCLastChanged,
--        tnMcMlpppEgrFCTableLastChanged
--    }
--    STATUS      current
--    DESCRIPTION
--        "The group of objects for the multi-class mlppp egress information on
--         Nokia 7x50 SR series systems."
--    ::= { tnQosGroups 32 }

-- tnQosQueueObjGroup OBJECT-GROUP
--    OBJECTS {
--       tnQosEgrQGroupDescr,
--       tnQosEgrQGroupLastChanged,
--       tnQosEgrQGroupRowStatus,
--       tnQosEgrQGroupTableLastChanged,
--       tnQosEgrQTableLastChanged,
--       tnQosEgrQueueAdminCIR,  
--       tnQosEgrQueueAdminPIR,  
--       tnQosEgrQueueCBS,  
--       tnQosEgrQueueCIRAdaptation,  
--       tnQosEgrQueueCIRLevel,  
--       tnQosEgrQueueCIRWeight,  
--       tnQosEgrQueueExpedite,  
--       tnQosEgrQueueHiPrioOnly,  
--       tnQosEgrQueueLastChanged,  
--       tnQosEgrQueueLevel,  
--       tnQosEgrQueueMBS,  
--       tnQosEgrQueuePIRAdaptation,  
--       tnQosEgrQueueParent,  
--       tnQosEgrQueuePoolName,  
--       tnQosEgrQueuePortCIRLvl,  
--       tnQosEgrQueuePortCIRWght,  
--       tnQosEgrQueuePortLvl,  
--       tnQosEgrQueuePortWght,  
--       tnQosEgrQueueRowStatus,  
--       tnQosEgrQueueUsePortParent,  
--       tnQosEgrQueueWeight,  
--       tnQosIngQTableLastChanged,
--       tnQosIngQGroupDescr,
--       tnQosIngQGroupLastChanged,
--       tnQosIngQGroupRowStatus,
--       tnQosIngQGroupTableLastChanged,
--       tnQosIngQueueAdminCIR,
--       tnQosIngQueueAdminPIR,
--       tnQosIngQueueCBS,
--       tnQosIngQueueCIRAdaptation,
--       tnQosIngQueueCIRLevel,
--       tnQosIngQueueCIRWeight,
--       tnQosIngQueueExpedite,
--       tnQosIngQueueHiPrioOnly,
--       tnQosIngQueueLastChanged,
--       tnQosIngQueueLevel,
--       tnQosIngQueueMBS,
--       tnQosIngQueueMCast,
--       tnQosIngQueueMode,
--       tnQosIngQueuePIRAdaptation,
--       tnQosIngQueueParent,
--       tnQosIngQueuePoliced,
--       tnQosIngQueuePoolName,
--       tnQosIngQueueRowStatus,
--       tnQosIngQueueWeight
--       }
--    STATUS      current
--    DESCRIPTION
--        "The group of objects for the multi-class mlppp egress information on
--         Nokia 7x50 SR series systems."
--    ::= { tnQosGroups 33 }

-- tnQosQGrpFCGroup OBJECT-GROUP
--    OBJECTS {
--        tnSapIngressFCQGrp,
--        tnSapIngressFCQGrpMCast,
--        tnSapIngressFCQGrpBCast,
--        tnSapIngressFCQGrpUnknown,
--        tnSapEgressFCQGrp,
--        tnNetworkEgressFCQGrpQueue
--        }
--    STATUS      current
--    DESCRIPTION
--        "The group of objects for the multi-class mlppp egress information on
--         Nokia 7x50 SR series systems."
--    ::= { tnQosGroups 34 }

-- tnQosNetworkV7v0Group OBJECT-GROUP
--    OBJECTS {
--        tnNetworkPolicyRowStatus,
--        tnNetworkPolicyScope,
--        tnNetworkPolicyDescription,
--        tnNetworkPolicyIngressDefaultActionFC,
--        tnNetworkPolicyIngressDefaultActionProfile,
--        tnNetworkPolicyEgressRemark,
--        tnNetworkPolicyLastChanged,
--        tnNetworkPolicyIngressLerUseDscp,
--        tnNetworkPolicyEgressRemarkDscp,
--        tnNetworkPolicyTableLastChanged,
--        tnNetworkIngressDSCPRowStatus,
--        tnNetworkIngressDSCPFC,
--        tnNetworkIngressDSCPProfile,
--        tnNetworkIngressDSCPLastChanged,
--        tnNetworkIngressDSCPTableLastChanged,
--        tnNetworkIngressDot1pRowStatus,
--        tnNetworkIngressDot1pFC,
--        tnNetworkIngressDot1pProfile,
--        tnNetworkIngressDot1pLastChanged,
--        tnNetworkIngressDot1pTableLastChanged,
--        tnNetworkIngressLSPEXPRowStatus,
--        tnNetworkIngressLSPEXPFC,
--        tnNetworkIngressLSPEXPProfile,
--        tnNetworkIngressLSPEXPLastChanged,
--        tnNetworkIngressLSPEXPTableLastChanged,
--        tnNetworkEgressFCDSCPInProfile,
--        tnNetworkEgressFCDSCPOutProfile,
--        tnNetworkEgressFCLspExpInProfile,
--        tnNetworkEgressFCLspExpOutProfile,
--        tnNetworkEgressFCDot1pInProfile,
--        tnNetworkEgressFCDot1pOutProfile,
--        tnNetworkEgressFCLastChanged,
--        tnNetworkEgressFCForceDEValue,
--        tnNetworkEgressFCDEMark,
--        tnNetworkEgressFCTableLastChanged,
--        tnNetworkQueuePolicyRowStatus,
--        tnNetworkQueuePolicyDescription,
--        tnNetworkQueuePolicyLastChanged,
--        tnNetworkQueuePolicyTableLastChanged,
--        tnNetworkQueueRowStatus,
--        tnNetworkQueuePoolName,
--        tnNetworkQueueParent,
--        tnNetworkQueueLevel,
--        tnNetworkQueueWeight,
--        tnNetworkQueueCIRLevel,
--        tnNetworkQueueCIRWeight,
--        tnNetworkQueueMCast,
--        tnNetworkQueueExpedite,
--        tnNetworkQueueCIR,
--        tnNetworkQueuePIR,
--        tnNetworkQueueCBS,
--        tnNetworkQueueMBS,
--        tnNetworkQueueHiPrioOnly,
--        tnNetworkQueueLastChanged,
--        tnNetworkQueueUsePortParent,
--        tnNetworkQueuePortLvl,
--        tnNetworkQueuePortWght,
--        tnNetworkQueuePortCIRLvl,
--        tnNetworkQueuePortCIRWght,
--        tnNetworkQueuePortAvgOverhead,
--        tnNetworkQueuePIRAdaptation,       
--        tnNetworkQueueCIRAdaptation,
--        tnNetworkQueueTableLastChanged,
--        tnNetworkQueueFCRowStatus,
--        tnNetworkQueueFC,
--        tnNetworkQueueFCMCast,
--        tnNetworkQueueFCLastChanged,
--        tnNetworkQueueFCTableLastChanged
--    }
--    STATUS      current
--    DESCRIPTION
--        "The group of objects supporting management of Network QoS policies
--         on Nokia 7x50 SR series systems."
--    ::= { tnQosGroups 35 }

-- tnQosHsmdaV7v0Group OBJECT-GROUP
--    OBJECTS {
--        tnHsmdaSchedulerPlcyRowStatus,
--        tnHsmdaSchedulerPlcyDescription,
--        tnHsmdaSchedulerPlcyMaxRate,
--        tnHsmdaSchedulerPlcyLvl1Rate,
--        tnHsmdaSchedulerPlcyLvl1GrpId,
--        tnHsmdaSchedulerPlcyLvl1WgtInGrp,
--        tnHsmdaSchedulerPlcyLvl2Rate,
--        tnHsmdaSchedulerPlcyLvl2GrpId,
--        tnHsmdaSchedulerPlcyLvl2WgtInGrp,
--        tnHsmdaSchedulerPlcyLvl3Rate,
--        tnHsmdaSchedulerPlcyLvl3GrpId,
--        tnHsmdaSchedulerPlcyLvl3WgtInGrp,
--        tnHsmdaSchedulerPlcyLvl4Rate,
--        tnHsmdaSchedulerPlcyLvl4GrpId,
--        tnHsmdaSchedulerPlcyLvl4WgtInGrp,
--        tnHsmdaSchedulerPlcyLvl5Rate,
--        tnHsmdaSchedulerPlcyLvl5GrpId,
--        tnHsmdaSchedulerPlcyLvl5WgtInGrp,
--        tnHsmdaSchedulerPlcyLvl6Rate,
--        tnHsmdaSchedulerPlcyLvl6GrpId,
--        tnHsmdaSchedulerPlcyLvl6WgtInGrp,
--        tnHsmdaSchedulerPlcyLvl7Rate,
--        tnHsmdaSchedulerPlcyLvl7GrpId,
--        tnHsmdaSchedulerPlcyLvl7WgtInGrp,
--        tnHsmdaSchedulerPlcyLvl8Rate,
--        tnHsmdaSchedulerPlcyLvl8GrpId,
--        tnHsmdaSchedulerPlcyLvl8WgtInGrp,
--        tnHsmdaSchedulerPlcyLastChanged,
--        tnHsmdaSchedulerPlcyGrp1Rate,
--        tnHsmdaSchedulerPlcyGrp2Rate,
--        tnSapEgressFCHsmdaQueue,
--        tnSapEgressFCDot1PHsmdaProfile,
--        tnSapEgressHsmdaQueueRowStatus,
--        tnSapEgressHsmdaQueueCIRAdaptn,
--        tnSapEgressHsmdaQueuePIRAdaptn,
--        tnSapEgressHsmdaQueueAdminPIR,
--        tnSapEgressHsmdaQueueAdminCIR,
--        tnSapEgressHsmdaQueueSlopePolicy,
--        tnSapEgressHsmdaQueueLastChanged,
--        tnSapIngressHsmdaPacketOffset,
--        tnSapIngressDefFCHsmdaCntrOvr,
--        tnSapIngressDot1pHsmdaCntrOvr,
--        tnSapIngressDSCPHsmdaCntrOvr,
--        tnSapIngressFCHsmdaQueue,
--        tnSapIngressFCHsmdaMCastQueue,
--        tnSapIngressFCHsmdaBCastQueue,
--        tnSapIngressPrecHsmdaCntrOvr,
--        tnSapIngressHsmdaQueueRowStatus,
--        tnSapIngressHsmdaQueueLastChanged,
--        tnSapIngressHsmdaQueueCIRAdaptn,
--        tnSapIngressHsmdaQueuePIRAdaptn,
--        tnSapIngressHsmdaQueueAdminPIR,
--        tnSapIngressHsmdaQueueAdminCIR,
--        tnSapIngressHsmdaQueueSlopePolicy,
--        tnSapIngressHsmdaQueuePoliced,
--        tnHsmdaPoolPolicyRowStatus,
--        tnHsmdaPoolLastChanged,
--        tnHsmdaPoolDescription,
--        tnHsmdaPoolSystemReserve,
--        tnHsmdaPoolRoot1AllocWeight,
--        tnHsmdaPoolRoot2AllocWeight,
--        tnHsmdaPoolRoot3AllocWeight,
--        tnHsmdaPoolRoot4AllocWeight,
--        tnHsmdaPoolRoot5AllocWeight,
--        tnHsmdaPoolRoot6AllocWeight,
--        tnHsmdaPoolRoot7AllocWeight,
--        tnHsmdaPoolRoot8AllocWeight,
--        tnHsmdaPoolClass1Parent,
--        tnHsmdaPoolClass1AllocPercent,
--        tnHsmdaPoolClass2Parent,
--        tnHsmdaPoolClass2AllocPercent,
--        tnHsmdaPoolClass3Parent,
--        tnHsmdaPoolClass3AllocPercent,
--        tnHsmdaPoolClass4Parent,
--        tnHsmdaPoolClass4AllocPercent,
--        tnHsmdaPoolClass5Parent,
--        tnHsmdaPoolClass5AllocPercent,
--        tnHsmdaPoolClass6Parent,
--        tnHsmdaPoolClass6AllocPercent,
--        tnHsmdaPoolClass7Parent,
--        tnHsmdaPoolClass7AllocPercent,
--        tnHsmdaPoolClass8Parent,
--        tnHsmdaPoolClass8AllocPercent,
--        tnHsmdaSlopePolicyRowStatus,
--        tnHsmdaSlopeLastChanged,
--        tnHsmdaSlopeDescription,
--        tnHsmdaSlopeQueueMbs,
--        tnHsmdaSlopeHiAdminStatus,
--        tnHsmdaSlopeHiStartDepth,
--        tnHsmdaSlopeHiMaxDepth,
--        tnHsmdaSlopeHiMaxProbability,
--        tnHsmdaSlopeLoAdminStatus,
--        tnHsmdaSlopeLoStartDepth,
--        tnHsmdaSlopeLoMaxDepth,
--        tnHsmdaSlopeLoMaxProbability,
--        tnSapIngrHsmdaQueueTblLastChngd,
--        tnSapEgrHsmdaQueueTblLastChngd,
--        tnHsmdaSchedPlcyTblLastChngd,
--        tnHsmdaSchedPlcyGrpTblLastChngd,
--        tnHsmdaPoolPlcyTblLastChngd,
--        tnHsmdaSlopePolicyTableLastChanged,
--        tnSapIngressIPCritHsmdaCntrOvr,
--        tnSapEgressDSCPRowStatus,
--        tnSapEgressDSCPLastChanged,
--        tnSapEgressDSCPHsmdaCntrOverride,
--        tnSapEgressPrecRowStatus,
--        tnSapEgressPrecLastChanged,
--        tnSapEgressPrecHsmdaCntrOverride,
--        tnSapEgrIPCritRowStatus,
--        tnSapEgrIPCritLastChanged,
--        tnSapEgrIPCritDescription,
--        tnSapEgrIPCritActionHsmdaCntrOvr,
--        tnSapEgrIPCritSourceIpAddrType,
--        tnSapEgrIPCritSourceIpAddr,
--        tnSapEgrIPCritSourceIpMask,
--        tnSapEgrIPCritDestIpAddrType,
--        tnSapEgrIPCritDestIpAddr,
--        tnSapEgrIPCritDestIpMask,
--        tnSapEgrIPCritProtocol,
--        tnSapEgrIPCritSourcePortValue1,
--        tnSapEgrIPCritSourcePortValue2,
--        tnSapEgrIPCritSourcePortOperator,
--        tnSapEgrIPCritDestPortValue1,
--        tnSapEgrIPCritDestPortValue2,
--        tnSapEgrIPCritDestPortOperator,
--        tnSapEgrIPCritDSCP,
--        tnSapEgrIPCritFragment,
--        tnSapEgressMatchCriteria,
--        tnSapEgressHsmdaPacketOffset,
--        tnSapEgrIPCritActionFC,
--        tnSapEgrIPCritActionProfile,
--        tnSapEgressDSCPfc,
--        tnSapEgressDSCPprofile,
--        tnSapEgressPrecFC,
--        tnSapEgressPrecProfile
--   }
--    STATUS      current
--    DESCRIPTION
--        "The group of objects supporting management of QoS policies 
--         for QMDA MDAs on Nokia 7x50 SR series systems release 7.0."
--    ::= { tnQosGroups 36 }

-- tnQosSapAtmV7v0Group OBJECT-GROUP
--     OBJECTS {
--         tnSapIngressMacCriteriaAtmVci
--     }
--     STATUS      current
--     DESCRIPTION
--         "The group of objects supporting management of SAP ATM related
--          QoS policies for Nokia 7x50 SR series systems release 7.0."
--     ::= { tnQosGroups 37 }
    
-- tnQosMcFrIngrGroup OBJECT-GROUP
--    OBJECTS {
--        tnMcFrIngrProfDescription,
--        tnMcFrIngrProfLastChanged,
--        tnMcFrIngrProfRowStatus,
--        tnMcFrIngrProfTableLastChanged,
--        tnMcFrIngrClassReassemblyTmout,
--        tnMcFrIngrClassLastChanged,
--        tnMcFrIngrClassTableLastChanged
--    }
--    STATUS      current
--    DESCRIPTION
--        "The group of objects for the multi-class Fr ingress information on
--         Nokia 7x50 SR series systems."
--    ::= { tnQosGroups 38 }

-- tnQosMcFrEgrGroup OBJECT-GROUP
--    OBJECTS {
--        tnMcFrEgrProfDescription,
--        tnMcFrEgrProfLastChanged,
--        tnMcFrEgrProfRowStatus,       
--        tnMcFrEgrProfTableLastChanged,
--        tnMcFrEgrClassMir,
--        tnMcFrEgrClassWeight,
--        tnMcFrEgrClassMaxSize,
--        tnMcFrEgrClassLastChanged,        
--        tnMcFrEgrClassTableLastChanged
--    }
--    STATUS      current
--    DESCRIPTION
--        "The group of objects for the multi-class Fr egress information on
--         Nokia 7x50 SR series systems."
--    ::= { tnQosGroups 39 }
--    
-- tnQosSapEgrQWredGroup OBJECT-GROUP
--    OBJECTS {
--        tnSapEgressQueueXPWredQ,
--        tnSapEgressQueueXPWredQSlope,
--        tnQosEgrQueueXPWredQ,
--        tnQosEgrQueueXPWredQSlope
--    }
--    STATUS      current
--    DESCRIPTION
--        "The group of objects for the WRED specific SAP egress queue
--        information on Nokia 7x50 SR series systems."
--    ::= { tnQosGroups 40 }
--
-- tnQosNotificationsGroup NOTIFICATION-GROUP
--     NOTIFICATIONS {
--         xxxx
--      }
--     STATUS current
--     DESCRIPTION
--         "the group of notifications providing for xxxx"
--     ::= { tnQosGroups X }
--


END
