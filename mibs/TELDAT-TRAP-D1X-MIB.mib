-- file automatically created


TELDAT-TRAP-D1X-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


d1xTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the D1X event subsystem."
    REVISION "201401200930Z"
    DESCRIPTION "Initial implementation"
        ::= { telEventTraps 213 }


d1xEventsGroup	OBJECT IDENTIFIER	::= { d1xTrapsMIB 1 }

d1xNotifications	OBJECT IDENTIFIER	::= { d1xTrapsMIB 2 }
d1xNotificationsPrefix	OBJECT IDENTIFIER	::= { d1xNotifications 0 }

d1xEventObjects1 OBJECT-IDENTITY
    STATUS current
    DESCRIPTION
        "Event D1X.1
        Timers state machine transition."
    ::= { d1xEventsGroup 1 }

d1x1_state_machine OBJECT-TYPE
    SYNTAX DisplayString
    MAX-ACCESS accessible-for-notify
    STATUS current
    DESCRIPTION
        "Parameter 'state_machine' in event D1X.1"
    ::= { d1xEventObjects1 1 }

d1x1_state OBJECT-TYPE
    SYNTAX DisplayString
    MAX-ACCESS accessible-for-notify
    STATUS current
    DESCRIPTION
        "Parameter 'state' in event D1X.1"
    ::= { d1xEventObjects1 2 }

d1x1_interface OBJECT-TYPE
    SYNTAX DisplayString
    MAX-ACCESS accessible-for-notify
    STATUS current
    DESCRIPTION
        "Parameter 'interface' in event D1X.1"
    ::= { d1xEventObjects1 3 }

d1x1_port_number OBJECT-TYPE
    SYNTAX Integer32
    MAX-ACCESS accessible-for-notify
    STATUS current
    DESCRIPTION
        "Parameter 'port_number' in event D1X.1"
    ::= { d1xEventObjects1 4 }

d1xEventObjects2 OBJECT-IDENTITY
    STATUS current
    DESCRIPTION
        "Event D1X.2
        Authenticator PAE state machine transition."
    ::= { d1xEventsGroup 2 }

d1x2_state_machine OBJECT-TYPE
    SYNTAX DisplayString
    MAX-ACCESS accessible-for-notify
    STATUS current
    DESCRIPTION
        "Parameter 'state_machine' in event D1X.2"
    ::= { d1xEventObjects2 1 }

d1x2_state OBJECT-TYPE
    SYNTAX DisplayString
    MAX-ACCESS accessible-for-notify
    STATUS current
    DESCRIPTION
        "Parameter 'state' in event D1X.2"
    ::= { d1xEventObjects2 2 }

d1x2_interface OBJECT-TYPE
    SYNTAX DisplayString
    MAX-ACCESS accessible-for-notify
    STATUS current
    DESCRIPTION
        "Parameter 'interface' in event D1X.2"
    ::= { d1xEventObjects2 3 }

d1x2_port_number OBJECT-TYPE
    SYNTAX Integer32
    MAX-ACCESS accessible-for-notify
    STATUS current
    DESCRIPTION
        "Parameter 'port_number' in event D1X.2"
    ::= { d1xEventObjects2 4 }

d1xEventObjects3 OBJECT-IDENTITY
    STATUS current
    DESCRIPTION
        "Event D1X.3
        Authenticator Key Transmit state machine transition."
    ::= { d1xEventsGroup 3 }

d1x3_state_machine OBJECT-TYPE
    SYNTAX DisplayString
    MAX-ACCESS accessible-for-notify
    STATUS current
    DESCRIPTION
        "Parameter 'state_machine' in event D1X.3"
    ::= { d1xEventObjects3 1 }

d1x3_state OBJECT-TYPE
    SYNTAX DisplayString
    MAX-ACCESS accessible-for-notify
    STATUS current
    DESCRIPTION
        "Parameter 'state' in event D1X.3"
    ::= { d1xEventObjects3 2 }

d1x3_interface OBJECT-TYPE
    SYNTAX DisplayString
    MAX-ACCESS accessible-for-notify
    STATUS current
    DESCRIPTION
        "Parameter 'interface' in event D1X.3"
    ::= { d1xEventObjects3 3 }

d1x3_port_number OBJECT-TYPE
    SYNTAX Integer32
    MAX-ACCESS accessible-for-notify
    STATUS current
    DESCRIPTION
        "Parameter 'port_number' in event D1X.3"
    ::= { d1xEventObjects3 4 }

d1xEventObjects4 OBJECT-IDENTITY
    STATUS current
    DESCRIPTION
        "Event D1X.4
        Key Receive state machine transition."
    ::= { d1xEventsGroup 4 }

d1x4_state_machine OBJECT-TYPE
    SYNTAX DisplayString
    MAX-ACCESS accessible-for-notify
    STATUS current
    DESCRIPTION
        "Parameter 'state_machine' in event D1X.4"
    ::= { d1xEventObjects4 1 }

d1x4_state OBJECT-TYPE
    SYNTAX DisplayString
    MAX-ACCESS accessible-for-notify
    STATUS current
    DESCRIPTION
        "Parameter 'state' in event D1X.4"
    ::= { d1xEventObjects4 2 }

d1x4_interface OBJECT-TYPE
    SYNTAX DisplayString
    MAX-ACCESS accessible-for-notify
    STATUS current
    DESCRIPTION
        "Parameter 'interface' in event D1X.4"
    ::= { d1xEventObjects4 3 }

d1x4_port_number OBJECT-TYPE
    SYNTAX Integer32
    MAX-ACCESS accessible-for-notify
    STATUS current
    DESCRIPTION
        "Parameter 'port_number' in event D1X.4"
    ::= { d1xEventObjects4 4 }

d1xEventObjects5 OBJECT-IDENTITY
    STATUS current
    DESCRIPTION
        "Event D1X.5
        Reauthentication Timer state machine transition."
    ::= { d1xEventsGroup 5 }

d1x5_state_machine OBJECT-TYPE
    SYNTAX DisplayString
    MAX-ACCESS accessible-for-notify
    STATUS current
    DESCRIPTION
        "Parameter 'state_machine' in event D1X.5"
    ::= { d1xEventObjects5 1 }

d1x5_state OBJECT-TYPE
    SYNTAX DisplayString
    MAX-ACCESS accessible-for-notify
    STATUS current
    DESCRIPTION
        "Parameter 'state' in event D1X.5"
    ::= { d1xEventObjects5 2 }

d1x5_interface OBJECT-TYPE
    SYNTAX DisplayString
    MAX-ACCESS accessible-for-notify
    STATUS current
    DESCRIPTION
        "Parameter 'interface' in event D1X.5"
    ::= { d1xEventObjects5 3 }

d1x5_port_number OBJECT-TYPE
    SYNTAX Integer32
    MAX-ACCESS accessible-for-notify
    STATUS current
    DESCRIPTION
        "Parameter 'port_number' in event D1X.5"
    ::= { d1xEventObjects5 4 }

d1xEventObjects6 OBJECT-IDENTITY
    STATUS current
    DESCRIPTION
        "Event D1X.6
        Backend Authentication state machine transition."
    ::= { d1xEventsGroup 6 }

d1x6_state_machine OBJECT-TYPE
    SYNTAX DisplayString
    MAX-ACCESS accessible-for-notify
    STATUS current
    DESCRIPTION
        "Parameter 'state_machine' in event D1X.6"
    ::= { d1xEventObjects6 1 }

d1x6_state OBJECT-TYPE
    SYNTAX DisplayString
    MAX-ACCESS accessible-for-notify
    STATUS current
    DESCRIPTION
        "Parameter 'state' in event D1X.6"
    ::= { d1xEventObjects6 2 }

d1x6_interface OBJECT-TYPE
    SYNTAX DisplayString
    MAX-ACCESS accessible-for-notify
    STATUS current
    DESCRIPTION
        "Parameter 'interface' in event D1X.6"
    ::= { d1xEventObjects6 3 }

d1x6_port_number OBJECT-TYPE
    SYNTAX Integer32
    MAX-ACCESS accessible-for-notify
    STATUS current
    DESCRIPTION
        "Parameter 'port_number' in event D1X.6"
    ::= { d1xEventObjects6 4 }

d1xEventObjects7 OBJECT-IDENTITY
    STATUS current
    DESCRIPTION
        "Event D1X.7
        Controlled Directions state machine transition."
    ::= { d1xEventsGroup 7 }

d1x7_state_machine OBJECT-TYPE
    SYNTAX DisplayString
    MAX-ACCESS accessible-for-notify
    STATUS current
    DESCRIPTION
        "Parameter 'state_machine' in event D1X.7"
    ::= { d1xEventObjects7 1 }

d1x7_state OBJECT-TYPE
    SYNTAX DisplayString
    MAX-ACCESS accessible-for-notify
    STATUS current
    DESCRIPTION
        "Parameter 'state' in event D1X.7"
    ::= { d1xEventObjects7 2 }

d1x7_interface OBJECT-TYPE
    SYNTAX DisplayString
    MAX-ACCESS accessible-for-notify
    STATUS current
    DESCRIPTION
        "Parameter 'interface' in event D1X.7"
    ::= { d1xEventObjects7 3 }

d1x7_port_number OBJECT-TYPE
    SYNTAX Integer32
    MAX-ACCESS accessible-for-notify
    STATUS current
    DESCRIPTION
        "Parameter 'port_number' in event D1X.7"
    ::= { d1xEventObjects7 4 }

d1xEventObjects8 OBJECT-IDENTITY
    STATUS current
    DESCRIPTION
        "Event D1X.8
        A packet was discarded because the queue of pending EAPOL packets
        to process is too long. This means the number of received EAPOL packets
        is so high that they cannot be processed."
    ::= { d1xEventsGroup 8 }

d1x8_eapol_queue OBJECT-TYPE
    SYNTAX DisplayString
    MAX-ACCESS accessible-for-notify
    STATUS current
    DESCRIPTION
        "Parameter 'eapol_queue' in event D1X.8"
    ::= { d1xEventObjects8 1 }

d1x8_interface OBJECT-TYPE
    SYNTAX DisplayString
    MAX-ACCESS accessible-for-notify
    STATUS current
    DESCRIPTION
        "Parameter 'interface' in event D1X.8"
    ::= { d1xEventObjects8 2 }

d1xEventObjects9 OBJECT-IDENTITY
    STATUS current
    DESCRIPTION
        "Event D1X.9
        An EAPOL packet of the type indicated has just arrived for processing."
    ::= { d1xEventsGroup 9 }

d1x9_eapol_name OBJECT-TYPE
    SYNTAX DisplayString
    MAX-ACCESS accessible-for-notify
    STATUS current
    DESCRIPTION
        "Parameter 'eapol_name' in event D1X.9"
    ::= { d1xEventObjects9 1 }

d1x9_type_string OBJECT-TYPE
    SYNTAX DisplayString
    MAX-ACCESS accessible-for-notify
    STATUS current
    DESCRIPTION
        "Parameter 'type_string' in event D1X.9"
    ::= { d1xEventObjects9 2 }

d1x9_version OBJECT-TYPE
    SYNTAX Integer32
    MAX-ACCESS accessible-for-notify
    STATUS current
    DESCRIPTION
        "Parameter 'version' in event D1X.9"
    ::= { d1xEventObjects9 3 }

d1x9_length OBJECT-TYPE
    SYNTAX Integer32
    MAX-ACCESS accessible-for-notify
    STATUS current
    DESCRIPTION
        "Parameter 'length' in event D1X.9"
    ::= { d1xEventObjects9 4 }

d1x9_source_address OBJECT-TYPE
    SYNTAX DisplayString
    MAX-ACCESS accessible-for-notify
    STATUS current
    DESCRIPTION
        "Parameter 'source_address' in event D1X.9"
    ::= { d1xEventObjects9 5 }

d1x9_destination_address OBJECT-TYPE
    SYNTAX DisplayString
    MAX-ACCESS accessible-for-notify
    STATUS current
    DESCRIPTION
        "Parameter 'destination_address' in event D1X.9"
    ::= { d1xEventObjects9 6 }

d1x9_interface OBJECT-TYPE
    SYNTAX DisplayString
    MAX-ACCESS accessible-for-notify
    STATUS current
    DESCRIPTION
        "Parameter 'interface' in event D1X.9"
    ::= { d1xEventObjects9 7 }

d1x9_port_id OBJECT-TYPE
    SYNTAX Integer32
    MAX-ACCESS accessible-for-notify
    STATUS current
    DESCRIPTION
        "Parameter 'port_id' in event D1X.9"
    ::= { d1xEventObjects9 8 }

d1xEventObjects10 OBJECT-IDENTITY
    STATUS current
    DESCRIPTION
        "Event D1X.10
        An EAPOL packet of the type indicated has just been sent."
    ::= { d1xEventsGroup 10 }

d1x10_eapol_name OBJECT-TYPE
    SYNTAX DisplayString
    MAX-ACCESS accessible-for-notify
    STATUS current
    DESCRIPTION
        "Parameter 'eapol_name' in event D1X.10"
    ::= { d1xEventObjects10 1 }

d1x10_type_string OBJECT-TYPE
    SYNTAX DisplayString
    MAX-ACCESS accessible-for-notify
    STATUS current
    DESCRIPTION
        "Parameter 'type_string' in event D1X.10"
    ::= { d1xEventObjects10 2 }

d1x10_version OBJECT-TYPE
    SYNTAX Integer32
    MAX-ACCESS accessible-for-notify
    STATUS current
    DESCRIPTION
        "Parameter 'version' in event D1X.10"
    ::= { d1xEventObjects10 3 }

d1x10_length OBJECT-TYPE
    SYNTAX Integer32
    MAX-ACCESS accessible-for-notify
    STATUS current
    DESCRIPTION
        "Parameter 'length' in event D1X.10"
    ::= { d1xEventObjects10 4 }

d1x10_destination_address OBJECT-TYPE
    SYNTAX DisplayString
    MAX-ACCESS accessible-for-notify
    STATUS current
    DESCRIPTION
        "Parameter 'destination_address' in event D1X.10"
    ::= { d1xEventObjects10 5 }

d1x10_interface OBJECT-TYPE
    SYNTAX DisplayString
    MAX-ACCESS accessible-for-notify
    STATUS current
    DESCRIPTION
        "Parameter 'interface' in event D1X.10"
    ::= { d1xEventObjects10 6 }

d1x10_port_id OBJECT-TYPE
    SYNTAX Integer32
    MAX-ACCESS accessible-for-notify
    STATUS current
    DESCRIPTION
        "Parameter 'port_id' in event D1X.10"
    ::= { d1xEventObjects10 7 }

d1xEventObjects11 OBJECT-IDENTITY
    STATUS current
    DESCRIPTION
        "Event D1X.11
        A packet was not send because of errors in the outgoing interface."
    ::= { d1xEventsGroup 11 }

d1x11_eapol_name OBJECT-TYPE
    SYNTAX DisplayString
    MAX-ACCESS accessible-for-notify
    STATUS current
    DESCRIPTION
        "Parameter 'eapol_name' in event D1X.11"
    ::= { d1xEventObjects11 1 }

d1x11_interface OBJECT-TYPE
    SYNTAX DisplayString
    MAX-ACCESS accessible-for-notify
    STATUS current
    DESCRIPTION
        "Parameter 'interface' in event D1X.11"
    ::= { d1xEventObjects11 2 }

d1x11_port_id OBJECT-TYPE
    SYNTAX Integer32
    MAX-ACCESS accessible-for-notify
    STATUS current
    DESCRIPTION
        "Parameter 'port_id' in event D1X.11"
    ::= { d1xEventObjects11 3 }

d1xEventObjects12 OBJECT-IDENTITY
    STATUS current
    DESCRIPTION
        "Event D1X.12
        An EAPOL packet was discarded because the destination MAC address does
        not match neither the PAE group address nor the specific MAC address of
        the PAE."
    ::= { d1xEventsGroup 12 }

d1x12_dest_mac OBJECT-TYPE
    SYNTAX DisplayString
    MAX-ACCESS accessible-for-notify
    STATUS current
    DESCRIPTION
        "Parameter 'dest_mac' in event D1X.12"
    ::= { d1xEventObjects12 1 }

d1x12_interface OBJECT-TYPE
    SYNTAX DisplayString
    MAX-ACCESS accessible-for-notify
    STATUS current
    DESCRIPTION
        "Parameter 'interface' in event D1X.12"
    ::= { d1xEventObjects12 2 }

d1x12_port_id OBJECT-TYPE
    SYNTAX Integer32
    MAX-ACCESS accessible-for-notify
    STATUS current
    DESCRIPTION
        "Parameter 'port_id' in event D1X.12"
    ::= { d1xEventObjects12 3 }

d1xEventObjects13 OBJECT-IDENTITY
    STATUS current
    DESCRIPTION
        "Event D1X.13
        An EAPOL packet was discarded because the packet type was none of the
        values EAP-Packet, EAPOL-Start, EAPOL-Logoff, EAPOL-Key or
        EAPOL-Encapsulated-ASF-Alert."
    ::= { d1xEventsGroup 13 }

d1x13_type OBJECT-TYPE
    SYNTAX Integer32
    MAX-ACCESS accessible-for-notify
    STATUS current
    DESCRIPTION
        "Parameter 'type' in event D1X.13"
    ::= { d1xEventObjects13 1 }

d1x13_interface OBJECT-TYPE
    SYNTAX DisplayString
    MAX-ACCESS accessible-for-notify
    STATUS current
    DESCRIPTION
        "Parameter 'interface' in event D1X.13"
    ::= { d1xEventObjects13 2 }

d1x13_port_id OBJECT-TYPE
    SYNTAX Integer32
    MAX-ACCESS accessible-for-notify
    STATUS current
    DESCRIPTION
        "Parameter 'port_id' in event D1X.13"
    ::= { d1xEventObjects13 3 }

d1xEventObjects14 OBJECT-IDENTITY
    STATUS current
    DESCRIPTION
        "Event D1X.14
        The 802.1X port status has been set as a result of the operation of
        the 802.1X state machines."
    ::= { d1xEventsGroup 14 }

d1x14_status OBJECT-TYPE
    SYNTAX DisplayString
    MAX-ACCESS accessible-for-notify
    STATUS current
    DESCRIPTION
        "Parameter 'status' in event D1X.14"
    ::= { d1xEventObjects14 1 }

d1x14_port_number OBJECT-TYPE
    SYNTAX Integer32
    MAX-ACCESS accessible-for-notify
    STATUS current
    DESCRIPTION
        "Parameter 'port_number' in event D1X.14"
    ::= { d1xEventObjects14 2 }

d1x14_interface OBJECT-TYPE
    SYNTAX DisplayString
    MAX-ACCESS accessible-for-notify
    STATUS current
    DESCRIPTION
        "Parameter 'interface' in event D1X.14"
    ::= { d1xEventObjects14 3 }

d1xEventObjects15 OBJECT-IDENTITY
    STATUS current
    DESCRIPTION
        "Event D1X.15
        A received packet is discarded because the 802.1X port has not been
        authenticated yet."
    ::= { d1xEventsGroup 15 }

d1x15_source_Ethernet_address OBJECT-TYPE
    SYNTAX DisplayString
    MAX-ACCESS accessible-for-notify
    STATUS current
    DESCRIPTION
        "Parameter 'source_Ethernet_address' in event D1X.15"
    ::= { d1xEventObjects15 1 }

d1x15_destination_Ethernet_address OBJECT-TYPE
    SYNTAX DisplayString
    MAX-ACCESS accessible-for-notify
    STATUS current
    DESCRIPTION
        "Parameter 'destination_Ethernet_address' in event D1X.15"
    ::= { d1xEventObjects15 2 }

d1x15_protocol OBJECT-TYPE
    SYNTAX Integer32
    MAX-ACCESS accessible-for-notify
    STATUS current
    DESCRIPTION
        "Parameter 'protocol' in event D1X.15"
    ::= { d1xEventObjects15 3 }

d1x15_interface OBJECT-TYPE
    SYNTAX DisplayString
    MAX-ACCESS accessible-for-notify
    STATUS current
    DESCRIPTION
        "Parameter 'interface' in event D1X.15"
    ::= { d1xEventObjects15 4 }

d1x15_port_id OBJECT-TYPE
    SYNTAX Integer32
    MAX-ACCESS accessible-for-notify
    STATUS current
    DESCRIPTION
        "Parameter 'port_id' in event D1X.15"
    ::= { d1xEventObjects15 5 }

d1xEventObjects16 OBJECT-IDENTITY
    STATUS current
    DESCRIPTION
        "Event D1X.16
        A packet is not transmitted because the 802.1X port has not been
        authenticated yet and the controlled directions is set to both."
    ::= { d1xEventsGroup 16 }

d1x16_interface OBJECT-TYPE
    SYNTAX DisplayString
    MAX-ACCESS accessible-for-notify
    STATUS current
    DESCRIPTION
        "Parameter 'interface' in event D1X.16"
    ::= { d1xEventObjects16 1 }

d1x16_port_id OBJECT-TYPE
    SYNTAX Integer32
    MAX-ACCESS accessible-for-notify
    STATUS current
    DESCRIPTION
        "Parameter 'port_id' in event D1X.16"
    ::= { d1xEventObjects16 2 }

d1xEventObjects17 OBJECT-IDENTITY
    STATUS current
    DESCRIPTION
        "Event D1X.17
        An EAPOL packet was discarded because the destination address is a WLAN
        interface with PSK configured (not using 802.1X authentication)."
    ::= { d1xEventsGroup 17 }

d1x17_interface OBJECT-TYPE
    SYNTAX DisplayString
    MAX-ACCESS accessible-for-notify
    STATUS current
    DESCRIPTION
        "Parameter 'interface' in event D1X.17"
    ::= { d1xEventObjects17 1 }

d1xEventObjects18 OBJECT-IDENTITY
    STATUS current
    DESCRIPTION
        "Event D1X.18
        An EAPOL Success packet has just been sent."
    ::= { d1xEventsGroup 18 }

d1x18_destination_address OBJECT-TYPE
    SYNTAX DisplayString
    MAX-ACCESS accessible-for-notify
    STATUS current
    DESCRIPTION
        "Parameter 'destination_address' in event D1X.18"
    ::= { d1xEventObjects18 1 }

d1x18_interface OBJECT-TYPE
    SYNTAX DisplayString
    MAX-ACCESS accessible-for-notify
    STATUS current
    DESCRIPTION
        "Parameter 'interface' in event D1X.18"
    ::= { d1xEventObjects18 2 }

d1x18_port_id OBJECT-TYPE
    SYNTAX Integer32
    MAX-ACCESS accessible-for-notify
    STATUS current
    DESCRIPTION
        "Parameter 'port_id' in event D1X.18"
    ::= { d1xEventObjects18 3 }

d1xEventObjects19 OBJECT-IDENTITY
    STATUS current
    DESCRIPTION
        "Event D1X.19
        An EAPOL Failure packet has just been sent."
    ::= { d1xEventsGroup 19 }

d1x19_destination_address OBJECT-TYPE
    SYNTAX DisplayString
    MAX-ACCESS accessible-for-notify
    STATUS current
    DESCRIPTION
        "Parameter 'destination_address' in event D1X.19"
    ::= { d1xEventObjects19 1 }

d1x19_interface OBJECT-TYPE
    SYNTAX DisplayString
    MAX-ACCESS accessible-for-notify
    STATUS current
    DESCRIPTION
        "Parameter 'interface' in event D1X.19"
    ::= { d1xEventObjects19 2 }

d1x19_port_id OBJECT-TYPE
    SYNTAX Integer32
    MAX-ACCESS accessible-for-notify
    STATUS current
    DESCRIPTION
        "Parameter 'port_id' in event D1X.19"
    ::= { d1xEventObjects19 3 }

d1xEventObjects20 OBJECT-IDENTITY
    STATUS current
    DESCRIPTION
        "Event D1X.20
        Supplicant PAE state machine transition."
    ::= { d1xEventsGroup 20 }

d1x20_state_machine OBJECT-TYPE
    SYNTAX DisplayString
    MAX-ACCESS accessible-for-notify
    STATUS current
    DESCRIPTION
        "Parameter 'state_machine' in event D1X.20"
    ::= { d1xEventObjects20 1 }

d1x20_state OBJECT-TYPE
    SYNTAX DisplayString
    MAX-ACCESS accessible-for-notify
    STATUS current
    DESCRIPTION
        "Parameter 'state' in event D1X.20"
    ::= { d1xEventObjects20 2 }

d1x20_interface OBJECT-TYPE
    SYNTAX DisplayString
    MAX-ACCESS accessible-for-notify
    STATUS current
    DESCRIPTION
        "Parameter 'interface' in event D1X.20"
    ::= { d1xEventObjects20 3 }

d1x20_port_number OBJECT-TYPE
    SYNTAX Integer32
    MAX-ACCESS accessible-for-notify
    STATUS current
    DESCRIPTION
        "Parameter 'port_number' in event D1X.20"
    ::= { d1xEventObjects20 4 }

d1xEventObjects21 OBJECT-IDENTITY
    STATUS current
    DESCRIPTION
        "Event D1X.21
        Supplicant Backend state machine transition."
    ::= { d1xEventsGroup 21 }

d1x21_state_machine OBJECT-TYPE
    SYNTAX DisplayString
    MAX-ACCESS accessible-for-notify
    STATUS current
    DESCRIPTION
        "Parameter 'state_machine' in event D1X.21"
    ::= { d1xEventObjects21 1 }

d1x21_state OBJECT-TYPE
    SYNTAX DisplayString
    MAX-ACCESS accessible-for-notify
    STATUS current
    DESCRIPTION
        "Parameter 'state' in event D1X.21"
    ::= { d1xEventObjects21 2 }

d1x21_interface OBJECT-TYPE
    SYNTAX DisplayString
    MAX-ACCESS accessible-for-notify
    STATUS current
    DESCRIPTION
        "Parameter 'interface' in event D1X.21"
    ::= { d1xEventObjects21 3 }

d1x21_port_number OBJECT-TYPE
    SYNTAX Integer32
    MAX-ACCESS accessible-for-notify
    STATUS current
    DESCRIPTION
        "Parameter 'port_number' in event D1X.21"
    ::= { d1xEventObjects21 4 }

d1xEventObjects22 OBJECT-IDENTITY
    STATUS current
    DESCRIPTION
        "Event D1X.22
        EAP state machine transition."
    ::= { d1xEventsGroup 22 }

d1x22_state_machine OBJECT-TYPE
    SYNTAX DisplayString
    MAX-ACCESS accessible-for-notify
    STATUS current
    DESCRIPTION
        "Parameter 'state_machine' in event D1X.22"
    ::= { d1xEventObjects22 1 }

d1x22_state OBJECT-TYPE
    SYNTAX DisplayString
    MAX-ACCESS accessible-for-notify
    STATUS current
    DESCRIPTION
        "Parameter 'state' in event D1X.22"
    ::= { d1xEventObjects22 2 }

d1x22_interface OBJECT-TYPE
    SYNTAX DisplayString
    MAX-ACCESS accessible-for-notify
    STATUS current
    DESCRIPTION
        "Parameter 'interface' in event D1X.22"
    ::= { d1xEventObjects22 3 }

d1x22_port_number OBJECT-TYPE
    SYNTAX Integer32
    MAX-ACCESS accessible-for-notify
    STATUS current
    DESCRIPTION
        "Parameter 'port_number' in event D1X.22"
    ::= { d1xEventObjects22 4 }

d1xEventObjects23 OBJECT-IDENTITY
    STATUS current
    DESCRIPTION
        "Event D1X.23
        Supplicant Key Receive state machine transition."
    ::= { d1xEventsGroup 23 }

d1x23_state_machine OBJECT-TYPE
    SYNTAX DisplayString
    MAX-ACCESS accessible-for-notify
    STATUS current
    DESCRIPTION
        "Parameter 'state_machine' in event D1X.23"
    ::= { d1xEventObjects23 1 }

d1x23_state OBJECT-TYPE
    SYNTAX DisplayString
    MAX-ACCESS accessible-for-notify
    STATUS current
    DESCRIPTION
        "Parameter 'state' in event D1X.23"
    ::= { d1xEventObjects23 2 }

d1x23_interface OBJECT-TYPE
    SYNTAX DisplayString
    MAX-ACCESS accessible-for-notify
    STATUS current
    DESCRIPTION
        "Parameter 'interface' in event D1X.23"
    ::= { d1xEventObjects23 3 }

d1x23_port_number OBJECT-TYPE
    SYNTAX Integer32
    MAX-ACCESS accessible-for-notify
    STATUS current
    DESCRIPTION
        "Parameter 'port_number' in event D1X.23"
    ::= { d1xEventObjects23 4 }

d1xEventObjects24 OBJECT-IDENTITY
    STATUS current
    DESCRIPTION
        "Event D1X.24
        Supplicant EAPOL Authentication Success."
    ::= { d1xEventsGroup 24 }

d1x24_interface OBJECT-TYPE
    SYNTAX DisplayString
    MAX-ACCESS accessible-for-notify
    STATUS current
    DESCRIPTION
        "Parameter 'interface' in event D1X.24"
    ::= { d1xEventObjects24 1 }

d1x24_port_id OBJECT-TYPE
    SYNTAX Integer32
    MAX-ACCESS accessible-for-notify
    STATUS current
    DESCRIPTION
        "Parameter 'port_id' in event D1X.24"
    ::= { d1xEventObjects24 2 }

d1xEventObjects25 OBJECT-IDENTITY
    STATUS current
    DESCRIPTION
        "Event D1X.25
        Supplicant EAPOL Authentication Failure."
    ::= { d1xEventsGroup 25 }

d1x25_interface OBJECT-TYPE
    SYNTAX DisplayString
    MAX-ACCESS accessible-for-notify
    STATUS current
    DESCRIPTION
        "Parameter 'interface' in event D1X.25"
    ::= { d1xEventObjects25 1 }

d1x25_port_id OBJECT-TYPE
    SYNTAX Integer32
    MAX-ACCESS accessible-for-notify
    STATUS current
    DESCRIPTION
        "Parameter 'port_id' in event D1X.25"
    ::= { d1xEventObjects25 2 }

d1xEventObjects26 OBJECT-IDENTITY
    STATUS current
    DESCRIPTION
        "Event D1X.26
        Dot1x debug traces."
    ::= { d1xEventsGroup 26 }

d1x26_text OBJECT-TYPE
    SYNTAX DisplayString
    MAX-ACCESS accessible-for-notify
    STATUS current
    DESCRIPTION
        "Parameter 'text' in event D1X.26"
    ::= { d1xEventObjects26 1 }

d1xEventObjects27 OBJECT-IDENTITY
    STATUS current
    DESCRIPTION
        "Event D1X.27
        The received EAPOL packet was discarded because an error ocurred while
        processing it."
    ::= { d1xEventsGroup 27 }

d1x27_error_string OBJECT-TYPE
    SYNTAX DisplayString
    MAX-ACCESS accessible-for-notify
    STATUS current
    DESCRIPTION
        "Parameter 'error_string' in event D1X.27"
    ::= { d1xEventObjects27 1 }


d1xNotification1 NOTIFICATION-TYPE
    OBJECTS { 
              d1x1_state_machine, 
              d1x1_state,
              d1x1_interface,
              d1x1_port_number 
            }
    STATUS current
    DESCRIPTION
        "Notification of Event D1X.1

        Message: 'State Machine $1 entered state $2, ifc $3 port $4'

        Parameters list:
              $1: d1x1_state_machine
              $2: d1x1_state
              $3: d1x1_interface
              $4: d1x1_port_number

        Timers state machine transition."
    ::= { d1xNotificationsPrefix 1 }

d1xNotification2 NOTIFICATION-TYPE
    OBJECTS { 
              d1x2_state_machine, 
              d1x2_state,
              d1x2_interface,
              d1x2_port_number 
            }
    STATUS current
    DESCRIPTION
        "Notification of Event D1X.2

        Message: 'State Machine $1 entered state $2, ifc $3 port $4'

        Parameters list:
              $1: d1x2_state_machine
              $2: d1x2_state
              $3: d1x2_interface
              $4: d1x2_port_number

        Authenticator PAE state machine transition."
    ::= { d1xNotificationsPrefix 2 }

d1xNotification3 NOTIFICATION-TYPE
    OBJECTS { 
              d1x3_state_machine, 
              d1x3_state,
              d1x3_interface,
              d1x3_port_number 
            }
    STATUS current
    DESCRIPTION
        "Notification of Event D1X.3

        Message: 'State Machine $1 entered state $2, ifc $3 port $4'

        Parameters list:
              $1: d1x3_state_machine
              $2: d1x3_state
              $3: d1x3_interface
              $4: d1x3_port_number

        Authenticator Key Transmit state machine transition."
    ::= { d1xNotificationsPrefix 3 }

d1xNotification4 NOTIFICATION-TYPE
    OBJECTS { 
              d1x4_state_machine, 
              d1x4_state,
              d1x4_interface,
              d1x4_port_number 
            }
    STATUS current
    DESCRIPTION
        "Notification of Event D1X.4

        Message: 'State Machine $1 entered state $2, ifc $3 port $4'

        Parameters list:
              $1: d1x4_state_machine
              $2: d1x4_state
              $3: d1x4_interface
              $4: d1x4_port_number

        Key Receive state machine transition."
    ::= { d1xNotificationsPrefix 4 }

d1xNotification5 NOTIFICATION-TYPE
    OBJECTS { 
              d1x5_state_machine, 
              d1x5_state,
              d1x5_interface,
              d1x5_port_number 
            }
    STATUS current
    DESCRIPTION
        "Notification of Event D1X.5

        Message: 'State Machine $1 entered state $2, ifc $3 port $4'

        Parameters list:
              $1: d1x5_state_machine
              $2: d1x5_state
              $3: d1x5_interface
              $4: d1x5_port_number

        Reauthentication Timer state machine transition."
    ::= { d1xNotificationsPrefix 5 }

d1xNotification6 NOTIFICATION-TYPE
    OBJECTS { 
              d1x6_state_machine, 
              d1x6_state,
              d1x6_interface,
              d1x6_port_number 
            }
    STATUS current
    DESCRIPTION
        "Notification of Event D1X.6

        Message: 'State Machine $1 entered state $2, ifc $3 port $4'

        Parameters list:
              $1: d1x6_state_machine
              $2: d1x6_state
              $3: d1x6_interface
              $4: d1x6_port_number

        Backend Authentication state machine transition."
    ::= { d1xNotificationsPrefix 6 }

d1xNotification7 NOTIFICATION-TYPE
    OBJECTS { 
              d1x7_state_machine, 
              d1x7_state,
              d1x7_interface,
              d1x7_port_number 
            }
    STATUS current
    DESCRIPTION
        "Notification of Event D1X.7

        Message: 'State Machine $1 entered state $2, ifc $3 port $4'

        Parameters list:
              $1: d1x7_state_machine
              $2: d1x7_state
              $3: d1x7_interface
              $4: d1x7_port_number

        Controlled Directions state machine transition."
    ::= { d1xNotificationsPrefix 7 }

d1xNotification8 NOTIFICATION-TYPE
    OBJECTS { 
              d1x8_eapol_queue, 
              d1x8_interface 
            }
    STATUS current
    DESCRIPTION
        "Notification of Event D1X.8

        Message: '$1 Queue overflow on interface $2'

        Parameters list:
              $1: d1x8_eapol_queue
              $2: d1x8_interface

        A packet was discarded because the queue of pending EAPOL packets
        to process is too long. This means the number of received EAPOL packets
        is so high that they cannot be processed."
    ::= { d1xNotificationsPrefix 8 }

d1xNotification9 NOTIFICATION-TYPE
    OBJECTS { 
              d1x9_eapol_name, 
              d1x9_type_string,
              d1x9_version,
              d1x9_length,
              d1x9_source_address,
              d1x9_destination_address,
              d1x9_interface,
              d1x9_port_id 
            }
    STATUS current
    DESCRIPTION
        "Notification of Event D1X.9

        Message: 'Received $1 $2 Packet version $3, length $4, src $5 -> dst $6, on interface $7 port $8'

        Parameters list:
              $1: d1x9_eapol_name
              $2: d1x9_type_string
              $3: d1x9_version
              $4: d1x9_length
              $5: d1x9_source_address
              $6: d1x9_destination_address
              $7: d1x9_interface
              $8: d1x9_port_id

        An EAPOL packet of the type indicated has just arrived for processing."
    ::= { d1xNotificationsPrefix 9 }

d1xNotification10 NOTIFICATION-TYPE
    OBJECTS { 
              d1x10_eapol_name, 
              d1x10_type_string,
              d1x10_version,
              d1x10_length,
              d1x10_destination_address,
              d1x10_interface,
              d1x10_port_id 
            }
    STATUS current
    DESCRIPTION
        "Notification of Event D1X.10

        Message: 'Transmitted $1 $2 Packet version $3, length $4, -> dst=$5, on interface $6 port $7'

        Parameters list:
              $1: d1x10_eapol_name
              $2: d1x10_type_string
              $3: d1x10_version
              $4: d1x10_length
              $5: d1x10_destination_address
              $6: d1x10_interface
              $7: d1x10_port_id

        An EAPOL packet of the type indicated has just been sent."
    ::= { d1xNotificationsPrefix 10 }

d1xNotification11 NOTIFICATION-TYPE
    OBJECTS { 
              d1x11_eapol_name, 
              d1x11_interface,
              d1x11_port_id 
            }
    STATUS current
    DESCRIPTION
        "Notification of Event D1X.11

        Message: 'error sending $1 packet on interface $2 port $3'

        Parameters list:
              $1: d1x11_eapol_name
              $2: d1x11_interface
              $3: d1x11_port_id

        A packet was not send because of errors in the outgoing interface."
    ::= { d1xNotificationsPrefix 11 }

d1xNotification12 NOTIFICATION-TYPE
    OBJECTS { 
              d1x12_dest_mac, 
              d1x12_interface,
              d1x12_port_id 
            }
    STATUS current
    DESCRIPTION
        "Notification of Event D1X.12

        Message: 'EAPOL packet discarded, unknown destination mac address $1 on interface $2 port $3'

        Parameters list:
              $1: d1x12_dest_mac
              $2: d1x12_interface
              $3: d1x12_port_id

        An EAPOL packet was discarded because the destination MAC address does
        not match neither the PAE group address nor the specific MAC address of
        the PAE."
    ::= { d1xNotificationsPrefix 12 }

d1xNotification13 NOTIFICATION-TYPE
    OBJECTS { 
              d1x13_type, 
              d1x13_interface,
              d1x13_port_id 
            }
    STATUS current
    DESCRIPTION
        "Notification of Event D1X.13

        Message: 'EAPOL packet discarded, unknown type $1 on interface $2 port $3'

        Parameters list:
              $1: d1x13_type
              $2: d1x13_interface
              $3: d1x13_port_id

        An EAPOL packet was discarded because the packet type was none of the
        values EAP-Packet, EAPOL-Start, EAPOL-Logoff, EAPOL-Key or
        EAPOL-Encapsulated-ASF-Alert."
    ::= { d1xNotificationsPrefix 13 }

d1xNotification14 NOTIFICATION-TYPE
    OBJECTS { 
              d1x14_status, 
              d1x14_port_number,
              d1x14_interface 
            }
    STATUS current
    DESCRIPTION
        "Notification of Event D1X.14

        Message: 'Port status set to $1, port $2 on interface $3'

        Parameters list:
              $1: d1x14_status
              $2: d1x14_port_number
              $3: d1x14_interface

        The 802.1X port status has been set as a result of the operation of
        the 802.1X state machines."
    ::= { d1xNotificationsPrefix 14 }

d1xNotification15 NOTIFICATION-TYPE
    OBJECTS { 
              d1x15_source_Ethernet_address, 
              d1x15_destination_Ethernet_address,
              d1x15_protocol,
              d1x15_interface,
              d1x15_port_id 
            }
    STATUS current
    DESCRIPTION
        "Notification of Event D1X.15

        Message: 'Packet received $1 -> $2  prt $3 discarded, 802.1X port not authenticated interface $4 port $5'

        Parameters list:
              $1: d1x15_source_Ethernet_address
              $2: d1x15_destination_Ethernet_address
              $3: d1x15_protocol
              $4: d1x15_interface
              $5: d1x15_port_id

        A received packet is discarded because the 802.1X port has not been
        authenticated yet."
    ::= { d1xNotificationsPrefix 15 }

d1xNotification16 NOTIFICATION-TYPE
    OBJECTS { 
              d1x16_interface, 
              d1x16_port_id 
            }
    STATUS current
    DESCRIPTION
        "Notification of Event D1X.16

        Message: 'Packet transmission discarded, 802.1X port not authenticated interface $1 port $2'

        Parameters list:
              $1: d1x16_interface
              $2: d1x16_port_id

        A packet is not transmitted because the 802.1X port has not been
        authenticated yet and the controlled directions is set to both."
    ::= { d1xNotificationsPrefix 16 }

d1xNotification17 NOTIFICATION-TYPE
    OBJECTS { 
              d1x17_interface 
            }
    STATUS current
    DESCRIPTION
        "Notification of Event D1X.17

        Message: 'EAPOL packet discarded, dot11i PSK configured on interface $1'

        Parameters list:
              $1: d1x17_interface

        An EAPOL packet was discarded because the destination address is a WLAN
        interface with PSK configured (not using 802.1X authentication)."
    ::= { d1xNotificationsPrefix 17 }

d1xNotification18 NOTIFICATION-TYPE
    OBJECTS { 
              d1x18_destination_address, 
              d1x18_interface,
              d1x18_port_id 
            }
    STATUS current
    DESCRIPTION
        "Notification of Event D1X.18

        Message: 'Authentication Success MAC $1, on interface $2 port $3'

        Parameters list:
              $1: d1x18_destination_address
              $2: d1x18_interface
              $3: d1x18_port_id

        An EAPOL Success packet has just been sent."
    ::= { d1xNotificationsPrefix 18 }

d1xNotification19 NOTIFICATION-TYPE
    OBJECTS { 
              d1x19_destination_address, 
              d1x19_interface,
              d1x19_port_id 
            }
    STATUS current
    DESCRIPTION
        "Notification of Event D1X.19

        Message: 'Authentication Failure MAC $1, on interface $2 port $3'

        Parameters list:
              $1: d1x19_destination_address
              $2: d1x19_interface
              $3: d1x19_port_id

        An EAPOL Failure packet has just been sent."
    ::= { d1xNotificationsPrefix 19 }

d1xNotification20 NOTIFICATION-TYPE
    OBJECTS { 
              d1x20_state_machine, 
              d1x20_state,
              d1x20_interface,
              d1x20_port_number 
            }
    STATUS current
    DESCRIPTION
        "Notification of Event D1X.20

        Message: 'State Machine $1 entered state $2, ifc $3 port $4'

        Parameters list:
              $1: d1x20_state_machine
              $2: d1x20_state
              $3: d1x20_interface
              $4: d1x20_port_number

        Supplicant PAE state machine transition."
    ::= { d1xNotificationsPrefix 20 }

d1xNotification21 NOTIFICATION-TYPE
    OBJECTS { 
              d1x21_state_machine, 
              d1x21_state,
              d1x21_interface,
              d1x21_port_number 
            }
    STATUS current
    DESCRIPTION
        "Notification of Event D1X.21

        Message: 'State Machine $1 entered state $2, ifc $3 port $4'

        Parameters list:
              $1: d1x21_state_machine
              $2: d1x21_state
              $3: d1x21_interface
              $4: d1x21_port_number

        Supplicant Backend state machine transition."
    ::= { d1xNotificationsPrefix 21 }

d1xNotification22 NOTIFICATION-TYPE
    OBJECTS { 
              d1x22_state_machine, 
              d1x22_state,
              d1x22_interface,
              d1x22_port_number 
            }
    STATUS current
    DESCRIPTION
        "Notification of Event D1X.22

        Message: 'State Machine $1 entered state $2, ifc $3 port $4'

        Parameters list:
              $1: d1x22_state_machine
              $2: d1x22_state
              $3: d1x22_interface
              $4: d1x22_port_number

        EAP state machine transition."
    ::= { d1xNotificationsPrefix 22 }

d1xNotification23 NOTIFICATION-TYPE
    OBJECTS { 
              d1x23_state_machine, 
              d1x23_state,
              d1x23_interface,
              d1x23_port_number 
            }
    STATUS current
    DESCRIPTION
        "Notification of Event D1X.23

        Message: 'State Machine $1 entered state $2, ifc $3 port $4'

        Parameters list:
              $1: d1x23_state_machine
              $2: d1x23_state
              $3: d1x23_interface
              $4: d1x23_port_number

        Supplicant Key Receive state machine transition."
    ::= { d1xNotificationsPrefix 23 }

d1xNotification24 NOTIFICATION-TYPE
    OBJECTS { 
              d1x24_interface, 
              d1x24_port_id 
            }
    STATUS current
    DESCRIPTION
        "Notification of Event D1X.24

        Message: 'Supplicant Authentication Success, on interface $1 port $2'

        Parameters list:
              $1: d1x24_interface
              $2: d1x24_port_id

        Supplicant EAPOL Authentication Success."
    ::= { d1xNotificationsPrefix 24 }

d1xNotification25 NOTIFICATION-TYPE
    OBJECTS { 
              d1x25_interface, 
              d1x25_port_id 
            }
    STATUS current
    DESCRIPTION
        "Notification of Event D1X.25

        Message: 'Supplicant Authentication Failure, on interface $1 port $2'

        Parameters list:
              $1: d1x25_interface
              $2: d1x25_port_id

        Supplicant EAPOL Authentication Failure."
    ::= { d1xNotificationsPrefix 25 }

d1xNotification26 NOTIFICATION-TYPE
    OBJECTS { 
              d1x26_text 
            }
    STATUS current
    DESCRIPTION
        "Notification of Event D1X.26

        Message: '$1'

        Parameters list:
              $1: d1x26_text

        Dot1x debug traces."
    ::= { d1xNotificationsPrefix 26 }

d1xNotification27 NOTIFICATION-TYPE
    OBJECTS { 
              d1x27_error_string 
            }
    STATUS current
    DESCRIPTION
        "Notification of Event D1X.27

        Message: 'Received EAPOL packet discarded ($1)'

        Parameters list:
              $1: d1x27_error_string

        The received EAPOL packet was discarded because an error ocurred while
        processing it."
    ::= { d1xNotificationsPrefix 27 }


END
