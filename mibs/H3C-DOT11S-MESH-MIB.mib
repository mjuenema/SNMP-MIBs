-- =============================================================================
-- Copyright (C) 2008 by Hangzhou H3C Technologies Co., Ltd. All rights reserved.
--
-- Description:
--   The file defines a MIB to provide MESH configuration information.
-- Reference:
-- Version: V1.0
-- History:
--   V1.0 2008-07-08 Initial version, created by ChangHuifeng
-- =============================================================================
H3C-DOT11S-MESH-MIB DEFINITIONS ::= BEGIN

IMPORTS
        TruthValue,
        MacAddress,
        RowStatus
    FROM SNMPv2-TC
        MODULE-IDENTITY,
        OBJECT-TYPE,
        Integer32,
        Unsigned32
    FROM SNMPv2-SMI
        h3cDot11, H3cDot11RadioElementIndex, h3cDot11APElementIndex
    FROM H3C-DOT11-REF-MIB;

h3cDot11sMesh MODULE-IDENTITY
    LAST-UPDATED "200807081800Z"        -- July 8, 2008 at 18:00 GMT
    ORGANIZATION
        "Hangzhou H3C Technologies Co., Ltd."
    CONTACT-INFO
        "Platform Team Hangzhou H3C Technologies Co., Ltd.
         Hai-Dian District Beijing P.R. China
         Http://www.h3c.com
         Zip:100085"
    DESCRIPTION
        "The file defines a MIB to provide MESH configuration information.

        GLOSSARY

        IEEE 802.11
        Standard to encourage interoperability among
        wireless networking equipment.

        Access point (AP)
        Transmitter/receiver (transceiver) device
        that commonly connects and transports data
        between a wireless network and a wired network.

        Access control (AC)
        To control and manage multi-APs, it will bridge
        wireless and wired network.

        Fat AP
        Applied in the home, SOHO and so on, and it could
        work independently without help from AC.

        Fit AP
        Applied in the enterprise environment, it will work
        under the control and management from AC.

        BSS
        IEEE 802.11 Basic Service Set (Radio Cell).  The
        BSS of an AP comprises of the stations directly
        associating with the AP.

        Radio
        The chip set to receive and send wireless signal.

        Mesh
        A network consisting of two or more mesh points
        which communicate with each other via mesh services.

        Mesh Point (MP)
        An IEEE 802.11 entity that contains an IEEE 802.11-conformant
        medium access control (MAC) and physical layer (PHY) interface
        to the wireless medium (WM) that supports mesh services.

        Mesh Access Point (MAP)
        A mesh point that is collocated with one or more access points.

        Mesh Portal Point (MPP)
        A mesh point that is collocated with one or more portals.

        Mesh Link
        A link between two MPs."

    REVISION "200807081800Z"        -- July 8, 2008 at 18:00 GMT
    DESCRIPTION
        "The initial revision of this MIB module."
    ::= { h3cDot11 11 }

-- *****************************************************************************
-- *  Major sections
-- *****************************************************************************

h3cDot11sConfigGroup OBJECT IDENTIFIER  ::= { h3cDot11sMesh 1 }
--  Dot11s Configuration Group has the following children:
--  h3cDot11sMeshGlobalPara             ::= { h3cDot11sConfigGroup 1 }
--  h3cDot11sMeshPflTable               ::= { h3cDot11sConfigGroup 2 }
--  h3cDot11sMpPlcyTable                ::= { h3cDot11sConfigGroup 3 }
--  h3cDot11sMlspCfgTable               ::= { h3cDot11sConfigGroup 4 }
--  h3cDot11sRadioCfgTable              ::= { h3cDot11sConfigGroup 5 }
--  h3cDot11sAPCfgTable                 ::= { h3cDot11sConfigGroup 6 }

h3cDot11sWDSConfigGroup OBJECT IDENTIFIER ::= { h3cDot11sMesh 2 }
--  Dot11s WDS Configuration Group has the following children:
--  h3cDot11sWDSPeerMacTable         ::= { h3cDot11sWDSConfigGroup 1 }

h3cDot11sMeshStatusGroup OBJECT IDENTIFIER ::= { h3cDot11sMesh 3 }
--  Dot11s Mesh Status Group has the following children:
--  h3cDot11sMeshLinkStatusTable    ::= { h3cDot11sMeshStatusGroup 1 }

-- *****************************************************************************
-- *  h3cDot11sMeshGlobalPara Definition
-- *****************************************************************************
h3cDot11sMeshGlobalPara OBJECT IDENTIFIER  ::= { h3cDot11sConfigGroup 1 }

h3cDot11sMeshMkdID OBJECT-TYPE
    SYNTAX      MacAddress
    MAX-ACCESS  read-write
    STATUS      current
    DESCRIPTION
        "This object represents the mesh key distributor identifier (MKD-ID).
        If the MKD-ID is not configured, the value is '00:00:00:00:00:00'."
    ::= { h3cDot11sMeshGlobalPara 1 }

-- *****************************************************************************
-- * End of h3cDot11sMeshGlobalPara Definition
-- *****************************************************************************
-- *****************************************************************************
-- *  h3cDot11sMeshPflTable Definition
-- *****************************************************************************
h3cDot11sMeshPflTable OBJECT-TYPE
    SYNTAX      SEQUENCE OF H3cDot11sMeshPflEntry
    MAX-ACCESS  not-accessible
    STATUS      current
    DESCRIPTION
        "This table is used to configure mesh profile.
        A mesh profile is created and mapped to a MP so that
        it can provide mesh services to other MPs which have the same
        mesh ID.
        When the mesh profile is enabled, all of the object in this table
        can not be modified except h3cDot11sMeshPflEnable.
        The mesh profile can not be deleted when it is bound with the radio."
    ::= { h3cDot11sConfigGroup 2 }

h3cDot11sMeshPflEntry OBJECT-TYPE
    SYNTAX      H3cDot11sMeshPflEntry
    MAX-ACCESS  not-accessible
    STATUS      current
    DESCRIPTION
        "Each entry contains information of a mesh profile."
    INDEX
        {
            h3cDot11sMeshPflIndex
        }
    ::= { h3cDot11sMeshPflTable 1 }

H3cDot11sMeshPflEntry ::= SEQUENCE
    {
        h3cDot11sMeshPflIndex         Integer32,
        h3cDot11sMeshPflMeshID        OCTET STRING,
        h3cDot11sMeshPflBindIntNum    Integer32,
        h3cDot11sMeshPflKeepAlive     Integer32,
        h3cDot11sMeshPflBackhaulRate  Integer32,
        h3cDot11sMeshMkdServEnable    TruthValue,
        h3cDot11sMeshPflEnable        TruthValue,
        h3cDot11sMeshPflRowStatus     RowStatus
    }

h3cDot11sMeshPflIndex OBJECT-TYPE
    SYNTAX      Integer32
    MAX-ACCESS  not-accessible
    STATUS      current
    DESCRIPTION
        "This object represents the index of the mesh profile."
    ::= { h3cDot11sMeshPflEntry 1 }

h3cDot11sMeshPflMeshID OBJECT-TYPE
    SYNTAX      OCTET STRING (SIZE (0..32))
    MAX-ACCESS  read-create
    STATUS      current
    DESCRIPTION
        "This object represents the mesh ID of the mesh profile.
        The string length of this object is zero when the mesh ID is not
        configured.  If the mesh ID is not configured, h3cDot11sMeshPflEnable
        can not be set to 'true'."
    ::= { h3cDot11sMeshPflEntry 2 }

h3cDot11sMeshPflBindIntNum OBJECT-TYPE
    SYNTAX      Integer32
    MAX-ACCESS  read-create
    STATUS      current
    DESCRIPTION
        "This object represents the specified mesh interface number
        binding to the mesh profile.
        If the value is set to -1, the binding will be removed.
        If the mesh interface is not specified, the value of
        h3cDot11sMeshPflEnable can not be set to 'true'."
    DEFVAL      { -1 }
    ::= { h3cDot11sMeshPflEntry 3 }

h3cDot11sMeshPflKeepAlive OBJECT-TYPE
    SYNTAX      Integer32(1..1800)
    UNITS       "second"
    MAX-ACCESS  read-create
    STATUS      current
    DESCRIPTION
        "This object represents the mesh link keep-alive interval."
    ::= { h3cDot11sMeshPflEntry 4 }

h3cDot11sMeshPflBackhaulRate OBJECT-TYPE
    SYNTAX      Integer32
    UNITS       "Kbps"
    MAX-ACCESS  read-create
    STATUS      current
    DESCRIPTION
        "This object represents the link backhaul rate."
    ::= { h3cDot11sMeshPflEntry 5 }

h3cDot11sMeshMkdServEnable OBJECT-TYPE
    SYNTAX      TruthValue
    MAX-ACCESS  read-create
    STATUS      current
    DESCRIPTION
        "This object indicates whether the mesh key distributor (MKD)
        service for the mesh profile is enabled.
        'true': The MKD service for the mesh profile is enabled.
        'false': The MKD service for the mesh profile is disabled."
    DEFVAL      { false }
    ::= { h3cDot11sMeshPflEntry 6 }

h3cDot11sMeshPflEnable OBJECT-TYPE
    SYNTAX      TruthValue
    MAX-ACCESS  read-create
    STATUS      current
    DESCRIPTION
        "This object indicates whether the mesh profile is enabled.
        'true': The mesh profile is enabled.
        'false': The mesh profile is disabled."
    DEFVAL      { false }
    ::= { h3cDot11sMeshPflEntry 7 }

h3cDot11sMeshPflRowStatus OBJECT-TYPE
    SYNTAX      RowStatus
    MAX-ACCESS  read-create
    STATUS      current
    DESCRIPTION
        "The status of this table entry."
    ::= { h3cDot11sMeshPflEntry 8 }

-- *****************************************************************************
-- * End of h3cDot11sMeshPflTable Definition
-- *****************************************************************************
-- *****************************************************************************
-- *  h3cDot11sMpPlcyTable Definition
-- *****************************************************************************
h3cDot11sMpPlcyTable OBJECT-TYPE
    SYNTAX      SEQUENCE OF H3cDot11sMpPlcyEntry
    MAX-ACCESS  not-accessible
    STATUS      current
    DESCRIPTION
        "This table is used to configure MP policy.
        There is 'default_mp_plcy' on system by default and its index is 1.
        The 'default_mp_plcy' can not be deleted or modified.
        The MP policy can not be deleted when it is applied to a radio.
        It can not be modified when it is applied to an enabled radio."
    ::= { h3cDot11sConfigGroup 3 }

h3cDot11sMpPlcyEntry OBJECT-TYPE
    SYNTAX      H3cDot11sMpPlcyEntry
    MAX-ACCESS  not-accessible
    STATUS      current
    DESCRIPTION
        "Each entry contains information of a MP policy."
    INDEX
        {
            h3cDot11sMpPlcyIndex
        }
    ::= { h3cDot11sMpPlcyTable 1 }

H3cDot11sMpPlcyEntry ::= SEQUENCE
    {
        h3cDot11sMpPlcyIndex          Integer32,
        h3cDot11sMpPlcyName           OCTET STRING,
        h3cDot11sMpPlcyInitEnable     TruthValue,
        h3cDot11sMlspEnable           TruthValue,
        h3cDot11sProbReqInterval      Integer32,
        h3cDot11sRoleAuthEnable       TruthValue,
        h3cDot11sLinkHoldRSSI         Integer32,
        h3cDot11sLinkHoldTime         Integer32,
        h3cDot11sSwitchMargin         Integer32,
        h3cDot11sLinkSaturationRSSI   Integer32,
        h3cDot11sLinkRateMode         INTEGER,
        h3cDot11sMaxLinkNum           Integer32,
        h3cDot11sMpPlcyRowStatus      RowStatus
    }

h3cDot11sMpPlcyIndex OBJECT-TYPE
    SYNTAX      Integer32
    MAX-ACCESS  not-accessible
    STATUS      current
    DESCRIPTION
        "This object represents the MP policy index."
    ::= { h3cDot11sMpPlcyEntry 1 }

h3cDot11sMpPlcyName OBJECT-TYPE
    SYNTAX      OCTET STRING (SIZE (1..15))
    MAX-ACCESS  read-create
    STATUS      current
    DESCRIPTION
        "This object represents the MP policy name.
        MP policy can not be created with name 'a', 'al', 'all' or
        'default_mp_plcy'.
        Modification is not supported."
    ::= { h3cDot11sMpPlcyEntry 2 }

h3cDot11sMpPlcyInitEnable OBJECT-TYPE
    SYNTAX      TruthValue
    MAX-ACCESS  read-create
    STATUS      current
    DESCRIPTION
        "This object indicates whether the link initiation for
        the MP policy is enabled.
        'true': The link initiation for the MP policy is enabled.
        'false': The link initiation for the MP policy is disabled."
    DEFVAL      { true }
    ::= { h3cDot11sMpPlcyEntry 3 }

h3cDot11sMlspEnable OBJECT-TYPE
    SYNTAX      TruthValue
    MAX-ACCESS  read-create
    STATUS      current
    DESCRIPTION
        "This object indicates whether the mesh link switch protocol (MLSP)
        is enabled.
        'true': MLSP is enabled.
        'false': MLSP is disabled."
    DEFVAL      { false }
    ::= { h3cDot11sMpPlcyEntry 4 }

h3cDot11sProbReqInterval OBJECT-TYPE
    SYNTAX      Integer32
    UNITS       "millisecond"
    MAX-ACCESS  read-create
    STATUS      current
    DESCRIPTION
        "This object represents the probe request interval."
    ::= { h3cDot11sMpPlcyEntry 5 }

h3cDot11sRoleAuthEnable OBJECT-TYPE
    SYNTAX      TruthValue
    MAX-ACCESS  read-create
    STATUS      current
    DESCRIPTION
        "This object indicates whether the device can play as the role
        of an authenticator."
    DEFVAL      { true }
    ::= { h3cDot11sMpPlcyEntry 6 }

h3cDot11sLinkHoldRSSI OBJECT-TYPE
    SYNTAX      Integer32(5..100)
    UNITS       "dBm"
    MAX-ACCESS  read-create
    STATUS      current
    DESCRIPTION
        "This object represents the link-hold
        receive signal strength indicator (RSSI)."
    ::= { h3cDot11sMpPlcyEntry 7 }

h3cDot11sLinkHoldTime OBJECT-TYPE
    SYNTAX      Integer32(1000..20000)
    UNITS       "millisecond"
    MAX-ACCESS  read-create
    STATUS      current
    DESCRIPTION
        "This object represents the link-hold time."
    ::= { h3cDot11sMpPlcyEntry 8 }

h3cDot11sSwitchMargin OBJECT-TYPE
    SYNTAX      Integer32(1..100)
    UNITS       "dBm"
    MAX-ACCESS  read-create
    STATUS      current
    DESCRIPTION
        "This object represents the link-switch margin."
    ::= { h3cDot11sMpPlcyEntry 9 }

h3cDot11sLinkSaturationRSSI OBJECT-TYPE
    SYNTAX      Integer32(30..150)
    UNITS       "dBm"
    MAX-ACCESS  read-create
    STATUS      current
    DESCRIPTION
        "This object represents the link saturation
        receive signal strength indicator (RSSI)."
    ::= { h3cDot11sMpPlcyEntry 10 }

h3cDot11sLinkRateMode OBJECT-TYPE
    SYNTAX      INTEGER
        {
            fixed(1),
            realtime(2)
        }
    MAX-ACCESS  read-create
    STATUS      current
    DESCRIPTION
        "This object represents the rate mode of the mesh link."
    DEFVAL      { fixed }
    ::= { h3cDot11sMpPlcyEntry 11 }

h3cDot11sMaxLinkNum OBJECT-TYPE
    SYNTAX      Integer32
    MAX-ACCESS  read-create
    STATUS      current
    DESCRIPTION
        "This object represents the maximum number of the mesh link."
    ::= { h3cDot11sMpPlcyEntry 12 }

h3cDot11sMpPlcyRowStatus OBJECT-TYPE
    SYNTAX      RowStatus
    MAX-ACCESS  read-create
    STATUS      current
    DESCRIPTION
        "The status of this table entry."
    ::= { h3cDot11sMpPlcyEntry 13 }

-- *****************************************************************************
-- * End of h3cDot11sMpPlcyTable Definition
-- *****************************************************************************
-- *****************************************************************************
-- *  h3cDot11sMlspCfgTable Definition
-- *****************************************************************************
h3cDot11sMlspCfgTable OBJECT-TYPE
    SYNTAX      SEQUENCE OF H3cDot11sMlspCfgEntry
    MAX-ACCESS  not-accessible
    STATUS      current
    DESCRIPTION
        "This table is used to configure MLSP proxy MAC address.
        Only if the specified MP policy is modifiable and the MLSP
        is enabled, the row of this table can be created and deleted.
        The row of this table can not be modified."
    ::= { h3cDot11sConfigGroup 4 }

h3cDot11sMlspCfgEntry OBJECT-TYPE
    SYNTAX      H3cDot11sMlspCfgEntry
    MAX-ACCESS  not-accessible
    STATUS      current
    DESCRIPTION
        "Each entry contains information of MLSP proxy MAC address."
    INDEX
        {
            h3cDot11sMpPlcyIndex,
            h3cDot11sMlspProxyIndex
        }
    ::= { h3cDot11sMlspCfgTable 1 }

H3cDot11sMlspCfgEntry ::= SEQUENCE
    {
        h3cDot11sMlspProxyIndex       Integer32,
        h3cDot11sMlspProxyMac         MacAddress,
        h3cDot11sMlspRowStatus        RowStatus
    }

h3cDot11sMlspProxyIndex OBJECT-TYPE
    SYNTAX      Integer32
    MAX-ACCESS  not-accessible
    STATUS      current
    DESCRIPTION
        "This object represents the MLSP proxy MAC address index."
    ::= { h3cDot11sMlspCfgEntry 1 }

h3cDot11sMlspProxyMac OBJECT-TYPE
    SYNTAX      MacAddress
    MAX-ACCESS  read-create
    STATUS      current
    DESCRIPTION
        "This object represents the MLSP proxy MAC address."
    ::= { h3cDot11sMlspCfgEntry 2 }

h3cDot11sMlspRowStatus OBJECT-TYPE
    SYNTAX      RowStatus
    MAX-ACCESS  read-create
    STATUS      current
    DESCRIPTION
        "The status of this table entry."
    ::= { h3cDot11sMlspCfgEntry 3 }

-- *****************************************************************************
-- * End of h3cDot11sMlspCfgTable Definition
-- *****************************************************************************
-- *****************************************************************************
-- *  h3cDot11sRadioCfgTable Definition
-- *****************************************************************************
h3cDot11sRadioCfgTable OBJECT-TYPE
    SYNTAX      SEQUENCE OF H3cDot11sRadioCfgEntry
    MAX-ACCESS  not-accessible
    STATUS      current
    DESCRIPTION
        "This table is used to configure mesh to the specified radio."
    ::= { h3cDot11sConfigGroup 5 }

h3cDot11sRadioCfgEntry OBJECT-TYPE
    SYNTAX      H3cDot11sRadioCfgEntry
    MAX-ACCESS  not-accessible
    STATUS      current
    DESCRIPTION
        "Each entry contains mesh configure information
        of the specified radio."
    INDEX
        {
            h3cDot11sCfgRadioIndex
        }
    ::= { h3cDot11sRadioCfgTable 1 }

H3cDot11sRadioCfgEntry ::= SEQUENCE
    {
        h3cDot11sCfgRadioIndex        H3cDot11RadioElementIndex,
        h3cDot11sMeshPflMap           Integer32,
        h3cDot11sMpPlcyMap            Integer32
    }

h3cDot11sCfgRadioIndex OBJECT-TYPE
    SYNTAX      H3cDot11RadioElementIndex
    MAX-ACCESS  not-accessible
    STATUS      current
    DESCRIPTION
        "Represents index of the radio."
    ::= { h3cDot11sRadioCfgEntry 1 }

h3cDot11sMeshPflMap OBJECT-TYPE
    SYNTAX      Integer32
    MAX-ACCESS  read-write
    STATUS      current
    DESCRIPTION
        "This object represents the number of the mesh profile mapped to
        the specified radio.  The value is zero when the radio is not
        binding mesh profile."
    DEFVAL      { 0 }
    ::= { h3cDot11sRadioCfgEntry 2 }

h3cDot11sMpPlcyMap OBJECT-TYPE
    SYNTAX      Integer32
    MAX-ACCESS  read-write
    STATUS      current
    DESCRIPTION
        "This object represents the index of the MP policy mapped to the
        specified radio.  The MP policy is 'default_mp_plcy' when the radio
        is not binding user-defined MP policy.
        The index of 'default_mp_plcy' is 1.
        This object can not be modified when the radio is enabled."
    DEFVAL      { 1 }
    ::= { h3cDot11sRadioCfgEntry 3 }

-- *****************************************************************************
-- * End of h3cDot11sRadioCfgTable Definition
-- *****************************************************************************
-- *****************************************************************************
-- *  h3cDot11sAPCfgTable Definition
-- *****************************************************************************
h3cDot11sAPCfgTable OBJECT-TYPE
    SYNTAX      SEQUENCE OF H3cDot11sAPCfgEntry
    MAX-ACCESS  not-accessible
    STATUS      current
    DESCRIPTION
        "This table is used to configure mesh to the specified AP."
    ::= { h3cDot11sConfigGroup 6 }

h3cDot11sAPCfgEntry OBJECT-TYPE
    SYNTAX      H3cDot11sAPCfgEntry
    MAX-ACCESS  not-accessible
    STATUS      current
    DESCRIPTION
        "Each entry contains mesh configure information
        of the specified AP."
    INDEX
        {
            h3cDot11APElementIndex
        }
    ::= { h3cDot11sAPCfgTable 1 }

H3cDot11sAPCfgEntry ::= SEQUENCE
    {
        h3cDot11sPortalEnable         TruthValue
    }

h3cDot11sPortalEnable OBJECT-TYPE
    SYNTAX      TruthValue
    MAX-ACCESS  read-write
    STATUS      current
    DESCRIPTION
        "This object indicates whether the portal service is enabled.
        'true': The portal service is enabled.
        'false': The portal service is disabled."
    DEFVAL      { false }
    ::= { h3cDot11sAPCfgEntry 1 }

-- *****************************************************************************
-- * End of h3cDot11sAPCfgTable Definition
-- *****************************************************************************
-- *****************************************************************************
-- *  h3cDot11sWDSPeerMacTable Definition
-- *****************************************************************************
h3cDot11sWDSPeerMacTable OBJECT-TYPE
    SYNTAX      SEQUENCE OF H3cDot11sWDSPeerMacEntry
    MAX-ACCESS  not-accessible
    STATUS      current
    DESCRIPTION
        "This table is used to configure wireless distribution system (WDS).
        The row of this table can not be modified."
    ::= { h3cDot11sWDSConfigGroup 1 }

h3cDot11sWDSPeerMacEntry OBJECT-TYPE
    SYNTAX      H3cDot11sWDSPeerMacEntry
    MAX-ACCESS  not-accessible
    STATUS      current
    DESCRIPTION
        "Each entry contains information of WDS."
    INDEX
        {
            h3cDot11sCfgRadioIndex,
            h3cDot11sWDSPeerMacIndex
        }
    ::= { h3cDot11sWDSPeerMacTable 1 }

H3cDot11sWDSPeerMacEntry ::= SEQUENCE
    {
        h3cDot11sWDSPeerMacIndex      Integer32,
        h3cDot11sWDSPeerMacAddrss     MacAddress,
        h3cDot11sWDSPeerMacRowStatus  RowStatus
    }

h3cDot11sWDSPeerMacIndex OBJECT-TYPE
    SYNTAX      Integer32
    MAX-ACCESS  not-accessible
    STATUS      current
    DESCRIPTION
        "This object represents the peer MAC address index."
    ::= { h3cDot11sWDSPeerMacEntry 1 }

h3cDot11sWDSPeerMacAddrss OBJECT-TYPE
    SYNTAX      MacAddress
    MAX-ACCESS  read-create
    STATUS      current
    DESCRIPTION
        "This object represents the peer MAC address."
    ::= { h3cDot11sWDSPeerMacEntry 2 }

h3cDot11sWDSPeerMacRowStatus OBJECT-TYPE
    SYNTAX      RowStatus
    MAX-ACCESS  read-create
    STATUS      current
    DESCRIPTION
        "The status of this table entry."
    ::= { h3cDot11sWDSPeerMacEntry 3 }

-- *****************************************************************************
-- * End of h3cDot11sWDSPeerMacTable Definition
-- *****************************************************************************
-- *****************************************************************************
-- *  h3cDot11sMeshLinkStatusTable Definition
-- *****************************************************************************
h3cDot11sMeshLinkStatusTable OBJECT-TYPE
    SYNTAX      SEQUENCE OF H3cDot11sMeshLinkStatusEntry
    MAX-ACCESS  not-accessible
    STATUS      current
    DESCRIPTION
        "This table is used to represent the status of mesh link."
    ::= { h3cDot11sMeshStatusGroup 1 }

h3cDot11sMeshLinkStatusEntry OBJECT-TYPE
    SYNTAX      H3cDot11sMeshLinkStatusEntry
    MAX-ACCESS  not-accessible
    STATUS      current
    DESCRIPTION
        "Each entry contains status information of mesh link."
    INDEX
        {
            h3cDot11sMeshLinkIfIndex
        }
    ::= { h3cDot11sMeshLinkStatusTable 1 }

H3cDot11sMeshLinkStatusEntry ::= SEQUENCE
    {
        h3cDot11sMeshLinkIfIndex        Unsigned32,
        h3cDot11sMeshLinkName           OCTET STRING,
        h3cDot11sMeshLinkBSSID          MacAddress,
        h3cDot11sMeshLinkPeerMac        MacAddress,
        h3cDot11sMeshLinkExistDuration  Integer32
    }

h3cDot11sMeshLinkIfIndex OBJECT-TYPE
    SYNTAX      Unsigned32
    MAX-ACCESS  not-accessible
    STATUS      current
    DESCRIPTION
        "This object represents the interface index of the mesh link."
    ::= { h3cDot11sMeshLinkStatusEntry 1 }

h3cDot11sMeshLinkName OBJECT-TYPE
    SYNTAX      OCTET STRING
    MAX-ACCESS  read-only
    STATUS      current
    DESCRIPTION
        "This object represents the name of the mesh link."
    ::= { h3cDot11sMeshLinkStatusEntry 2 }

h3cDot11sMeshLinkBSSID OBJECT-TYPE
    SYNTAX      MacAddress
    MAX-ACCESS  read-only
    STATUS      current
    DESCRIPTION
        "This object represents the BSS ID of the mesh link."
    ::= { h3cDot11sMeshLinkStatusEntry 3 }

h3cDot11sMeshLinkPeerMac OBJECT-TYPE
    SYNTAX      MacAddress
    MAX-ACCESS  read-only
    STATUS      current
    DESCRIPTION
        "This object represents the peer MAC address of the mesh link."
    ::= { h3cDot11sMeshLinkStatusEntry 4 }

h3cDot11sMeshLinkExistDuration OBJECT-TYPE
    SYNTAX      Integer32
    UNITS       "second"
    MAX-ACCESS  read-only
    STATUS      current
    DESCRIPTION
        "This object represents the time for which the link has been up."
    ::= { h3cDot11sMeshLinkStatusEntry 5 }

-- *****************************************************************************
-- * End of h3cDot11sMeshLinkStatusTable Definition
-- *****************************************************************************
END
