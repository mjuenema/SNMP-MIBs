-- file automatically created


TELDAT-TRAP-UDAF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


udafTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the UDAF event subsystem."
    REVISION "201401200930Z"
    DESCRIPTION "Initial implementation"
        ::= { telEventTraps 143 }


udafEventsGroup	OBJECT IDENTIFIER	::= { udafTrapsMIB 1 }

udafNotifications	OBJECT IDENTIFIER	::= { udafTrapsMIB 2 }
udafNotificationsPrefix	OBJECT IDENTIFIER	::= { udafNotifications 0 }

udafEventObjects1 OBJECT-IDENTITY
    STATUS current
    DESCRIPTION
        "Event UDAF.1
        Data has been received from POS."
    ::= { udafEventsGroup 1 }

udaf1_bytes_number OBJECT-TYPE
    SYNTAX Integer32
    MAX-ACCESS accessible-for-notify
    STATUS current
    DESCRIPTION
        "Parameter 'bytes_number' in event UDAF.1"
    ::= { udafEventObjects1 1 }

udaf1_interface OBJECT-TYPE
    SYNTAX DisplayString
    MAX-ACCESS accessible-for-notify
    STATUS current
    DESCRIPTION
        "Parameter 'interface' in event UDAF.1"
    ::= { udafEventObjects1 2 }

udafEventObjects2 OBJECT-IDENTITY
    STATUS current
    DESCRIPTION
        "Event UDAF.2
        An ACK control character has been received from POS."
    ::= { udafEventsGroup 2 }

udaf2_interface OBJECT-TYPE
    SYNTAX DisplayString
    MAX-ACCESS accessible-for-notify
    STATUS current
    DESCRIPTION
        "Parameter 'interface' in event UDAF.2"
    ::= { udafEventObjects2 1 }

udaf2_state OBJECT-TYPE
    SYNTAX Integer32
    MAX-ACCESS accessible-for-notify
    STATUS current
    DESCRIPTION
        "Parameter 'state' in event UDAF.2"
    ::= { udafEventObjects2 2 }

udafEventObjects3 OBJECT-IDENTITY
    STATUS current
    DESCRIPTION
        "Event UDAF.3
        An EOT control character has been received from POS."
    ::= { udafEventsGroup 3 }

udaf3_interface OBJECT-TYPE
    SYNTAX DisplayString
    MAX-ACCESS accessible-for-notify
    STATUS current
    DESCRIPTION
        "Parameter 'interface' in event UDAF.3"
    ::= { udafEventObjects3 1 }

udaf3_state OBJECT-TYPE
    SYNTAX Integer32
    MAX-ACCESS accessible-for-notify
    STATUS current
    DESCRIPTION
        "Parameter 'state' in event UDAF.3"
    ::= { udafEventObjects3 2 }

udafEventObjects4 OBJECT-IDENTITY
    STATUS current
    DESCRIPTION
        "Event UDAF.4
        A NAK control character has been received from POS."
    ::= { udafEventsGroup 4 }

udaf4_interface OBJECT-TYPE
    SYNTAX DisplayString
    MAX-ACCESS accessible-for-notify
    STATUS current
    DESCRIPTION
        "Parameter 'interface' in event UDAF.4"
    ::= { udafEventObjects4 1 }

udaf4_state OBJECT-TYPE
    SYNTAX Integer32
    MAX-ACCESS accessible-for-notify
    STATUS current
    DESCRIPTION
        "Parameter 'state' in event UDAF.4"
    ::= { udafEventObjects4 2 }

udafEventObjects5 OBJECT-IDENTITY
    STATUS current
    DESCRIPTION
        "Event UDAF.5
        A block with parity error has been received from POS."
    ::= { udafEventsGroup 5 }

udaf5_interface OBJECT-TYPE
    SYNTAX DisplayString
    MAX-ACCESS accessible-for-notify
    STATUS current
    DESCRIPTION
        "Parameter 'interface' in event UDAF.5"
    ::= { udafEventObjects5 1 }

udafEventObjects6 OBJECT-IDENTITY
    STATUS current
    DESCRIPTION
        "Event UDAF.6
        An ACK control character has been transmitted to POS."
    ::= { udafEventsGroup 6 }

udaf6_interface OBJECT-TYPE
    SYNTAX DisplayString
    MAX-ACCESS accessible-for-notify
    STATUS current
    DESCRIPTION
        "Parameter 'interface' in event UDAF.6"
    ::= { udafEventObjects6 1 }

udaf6_state OBJECT-TYPE
    SYNTAX Integer32
    MAX-ACCESS accessible-for-notify
    STATUS current
    DESCRIPTION
        "Parameter 'state' in event UDAF.6"
    ::= { udafEventObjects6 2 }

udafEventObjects7 OBJECT-IDENTITY
    STATUS current
    DESCRIPTION
        "Event UDAF.7
        An EOT control character has been transmitted to POS."
    ::= { udafEventsGroup 7 }

udaf7_interface OBJECT-TYPE
    SYNTAX DisplayString
    MAX-ACCESS accessible-for-notify
    STATUS current
    DESCRIPTION
        "Parameter 'interface' in event UDAF.7"
    ::= { udafEventObjects7 1 }

udaf7_state OBJECT-TYPE
    SYNTAX Integer32
    MAX-ACCESS accessible-for-notify
    STATUS current
    DESCRIPTION
        "Parameter 'state' in event UDAF.7"
    ::= { udafEventObjects7 2 }

udafEventObjects8 OBJECT-IDENTITY
    STATUS current
    DESCRIPTION
        "Event UDAF.8
        A NAK control character has been transmitted to POS."
    ::= { udafEventsGroup 8 }

udaf8_interface OBJECT-TYPE
    SYNTAX DisplayString
    MAX-ACCESS accessible-for-notify
    STATUS current
    DESCRIPTION
        "Parameter 'interface' in event UDAF.8"
    ::= { udafEventObjects8 1 }

udaf8_state OBJECT-TYPE
    SYNTAX Integer32
    MAX-ACCESS accessible-for-notify
    STATUS current
    DESCRIPTION
        "Parameter 'state' in event UDAF.8"
    ::= { udafEventObjects8 2 }

udafEventObjects9 OBJECT-IDENTITY
    STATUS current
    DESCRIPTION
        "Event UDAF.9
        An S message was expected and it has not been received properly."
    ::= { udafEventsGroup 9 }

udaf9_interface OBJECT-TYPE
    SYNTAX DisplayString
    MAX-ACCESS accessible-for-notify
    STATUS current
    DESCRIPTION
        "Parameter 'interface' in event UDAF.9"
    ::= { udafEventObjects9 1 }

udafEventObjects10 OBJECT-IDENTITY
    STATUS current
    DESCRIPTION
        "Event UDAF.10
        NA received from POS is not included in configuration profile list."
    ::= { udafEventsGroup 10 }

udaf10_na OBJECT-TYPE
    SYNTAX DisplayString
    MAX-ACCESS accessible-for-notify
    STATUS current
    DESCRIPTION
        "Parameter 'na' in event UDAF.10"
    ::= { udafEventObjects10 1 }

udaf10_interface OBJECT-TYPE
    SYNTAX DisplayString
    MAX-ACCESS accessible-for-notify
    STATUS current
    DESCRIPTION
        "Parameter 'interface' in event UDAF.10"
    ::= { udafEventObjects10 2 }

udafEventObjects11 OBJECT-IDENTITY
    STATUS current
    DESCRIPTION
        "Event UDAF.11
        The specified NA is trying the connection against IP Host and P port,
        using the specified transport protocol."
    ::= { udafEventsGroup 11 }

udaf11_na OBJECT-TYPE
    SYNTAX DisplayString
    MAX-ACCESS accessible-for-notify
    STATUS current
    DESCRIPTION
        "Parameter 'na' in event UDAF.11"
    ::= { udafEventObjects11 1 }

udaf11_transport OBJECT-TYPE
    SYNTAX DisplayString
    MAX-ACCESS accessible-for-notify
    STATUS current
    DESCRIPTION
        "Parameter 'transport' in event UDAF.11"
    ::= { udafEventObjects11 2 }

udaf11_ip_host_address OBJECT-TYPE
    SYNTAX IpAddress
    MAX-ACCESS accessible-for-notify
    STATUS current
    DESCRIPTION
        "Parameter 'ip_host_address' in event UDAF.11"
    ::= { udafEventObjects11 3 }

udaf11_port OBJECT-TYPE
    SYNTAX Integer32
    MAX-ACCESS accessible-for-notify
    STATUS current
    DESCRIPTION
        "Parameter 'port' in event UDAF.11"
    ::= { udafEventObjects11 4 }

udaf11_interface OBJECT-TYPE
    SYNTAX DisplayString
    MAX-ACCESS accessible-for-notify
    STATUS current
    DESCRIPTION
        "Parameter 'interface' in event UDAF.11"
    ::= { udafEventObjects11 5 }

udafEventObjects12 OBJECT-IDENTITY
    STATUS current
    DESCRIPTION
        "Event UDAF.12
        The connection against Host has failed."
    ::= { udafEventsGroup 12 }

udaf12_interface OBJECT-TYPE
    SYNTAX DisplayString
    MAX-ACCESS accessible-for-notify
    STATUS current
    DESCRIPTION
        "Parameter 'interface' in event UDAF.12"
    ::= { udafEventObjects12 1 }

udafEventObjects13 OBJECT-IDENTITY
    STATUS current
    DESCRIPTION
        "Event UDAF.13
        The transaction has been completed successfully."
    ::= { udafEventsGroup 13 }

udaf13_interface OBJECT-TYPE
    SYNTAX DisplayString
    MAX-ACCESS accessible-for-notify
    STATUS current
    DESCRIPTION
        "Parameter 'interface' in event UDAF.13"
    ::= { udafEventObjects13 1 }

udafEventObjects14 OBJECT-IDENTITY
    STATUS current
    DESCRIPTION
        "Event UDAF.14
        Trying to send message to Host."
    ::= { udafEventsGroup 14 }

udaf14_message_type OBJECT-TYPE
    SYNTAX DisplayString
    MAX-ACCESS accessible-for-notify
    STATUS current
    DESCRIPTION
        "Parameter 'message_type' in event UDAF.14"
    ::= { udafEventObjects14 1 }

udaf14_bytes_number OBJECT-TYPE
    SYNTAX Integer32
    MAX-ACCESS accessible-for-notify
    STATUS current
    DESCRIPTION
        "Parameter 'bytes_number' in event UDAF.14"
    ::= { udafEventObjects14 2 }

udaf14_interface OBJECT-TYPE
    SYNTAX DisplayString
    MAX-ACCESS accessible-for-notify
    STATUS current
    DESCRIPTION
        "Parameter 'interface' in event UDAF.14"
    ::= { udafEventObjects14 3 }

udafEventObjects15 OBJECT-IDENTITY
    STATUS current
    DESCRIPTION
        "Event UDAF.15
        A TRMTP message has been received."
    ::= { udafEventsGroup 15 }

udaf15_message_type OBJECT-TYPE
    SYNTAX DisplayString
    MAX-ACCESS accessible-for-notify
    STATUS current
    DESCRIPTION
        "Parameter 'message_type' in event UDAF.15"
    ::= { udafEventObjects15 1 }

udaf15_bytes_number OBJECT-TYPE
    SYNTAX Integer32
    MAX-ACCESS accessible-for-notify
    STATUS current
    DESCRIPTION
        "Parameter 'bytes_number' in event UDAF.15"
    ::= { udafEventObjects15 2 }

udaf15_interface OBJECT-TYPE
    SYNTAX DisplayString
    MAX-ACCESS accessible-for-notify
    STATUS current
    DESCRIPTION
        "Parameter 'interface' in event UDAF.15"
    ::= { udafEventObjects15 3 }

udaf15_state OBJECT-TYPE
    SYNTAX Integer32
    MAX-ACCESS accessible-for-notify
    STATUS current
    DESCRIPTION
        "Parameter 'state' in event UDAF.15"
    ::= { udafEventObjects15 4 }

udafEventObjects16 OBJECT-IDENTITY
    STATUS current
    DESCRIPTION
        "Event UDAF.16
        Trying TRMTP message retransmission."
    ::= { udafEventsGroup 16 }

udaf16_interface OBJECT-TYPE
    SYNTAX DisplayString
    MAX-ACCESS accessible-for-notify
    STATUS current
    DESCRIPTION
        "Parameter 'interface' in event UDAF.16"
    ::= { udafEventObjects16 1 }

udafEventObjects17 OBJECT-IDENTITY
    STATUS current
    DESCRIPTION
        "Event UDAF.17
        Trying retransmission to POS."
    ::= { udafEventsGroup 17 }

udaf17_interface OBJECT-TYPE
    SYNTAX DisplayString
    MAX-ACCESS accessible-for-notify
    STATUS current
    DESCRIPTION
        "Parameter 'interface' in event UDAF.17"
    ::= { udafEventObjects17 1 }

udafEventObjects18 OBJECT-IDENTITY
    STATUS current
    DESCRIPTION
        "Event UDAF.18
        A certain error was found."
    ::= { udafEventsGroup 18 }

udaf18_error_message OBJECT-TYPE
    SYNTAX DisplayString
    MAX-ACCESS accessible-for-notify
    STATUS current
    DESCRIPTION
        "Parameter 'error_message' in event UDAF.18"
    ::= { udafEventObjects18 1 }

udaf18_interface OBJECT-TYPE
    SYNTAX DisplayString
    MAX-ACCESS accessible-for-notify
    STATUS current
    DESCRIPTION
        "Parameter 'interface' in event UDAF.18"
    ::= { udafEventObjects18 2 }

udaf18_state OBJECT-TYPE
    SYNTAX Integer32
    MAX-ACCESS accessible-for-notify
    STATUS current
    DESCRIPTION
        "Parameter 'state' in event UDAF.18"
    ::= { udafEventObjects18 3 }

udafEventObjects19 OBJECT-IDENTITY
    STATUS current
    DESCRIPTION
        "Event UDAF.19
        A message from HOST has been received."
    ::= { udafEventsGroup 19 }

udaf19_message_type OBJECT-TYPE
    SYNTAX DisplayString
    MAX-ACCESS accessible-for-notify
    STATUS current
    DESCRIPTION
        "Parameter 'message_type' in event UDAF.19"
    ::= { udafEventObjects19 1 }

udaf19_bytes_number OBJECT-TYPE
    SYNTAX Integer32
    MAX-ACCESS accessible-for-notify
    STATUS current
    DESCRIPTION
        "Parameter 'bytes_number' in event UDAF.19"
    ::= { udafEventObjects19 2 }

udaf19_interface OBJECT-TYPE
    SYNTAX DisplayString
    MAX-ACCESS accessible-for-notify
    STATUS current
    DESCRIPTION
        "Parameter 'interface' in event UDAF.19"
    ::= { udafEventObjects19 3 }

udaf19_state OBJECT-TYPE
    SYNTAX Integer32
    MAX-ACCESS accessible-for-notify
    STATUS current
    DESCRIPTION
        "Parameter 'state' in event UDAF.19"
    ::= { udafEventObjects19 4 }

udafEventObjects20 OBJECT-IDENTITY
    STATUS current
    DESCRIPTION
        "Event UDAF.20
        A TCP packet has been received."
    ::= { udafEventsGroup 20 }

udaf20_message_type OBJECT-TYPE
    SYNTAX DisplayString
    MAX-ACCESS accessible-for-notify
    STATUS current
    DESCRIPTION
        "Parameter 'message_type' in event UDAF.20"
    ::= { udafEventObjects20 1 }

udaf20_bytes_number OBJECT-TYPE
    SYNTAX Integer32
    MAX-ACCESS accessible-for-notify
    STATUS current
    DESCRIPTION
        "Parameter 'bytes_number' in event UDAF.20"
    ::= { udafEventObjects20 2 }

udaf20_interface OBJECT-TYPE
    SYNTAX DisplayString
    MAX-ACCESS accessible-for-notify
    STATUS current
    DESCRIPTION
        "Parameter 'interface' in event UDAF.20"
    ::= { udafEventObjects20 3 }

udaf20_state OBJECT-TYPE
    SYNTAX Integer32
    MAX-ACCESS accessible-for-notify
    STATUS current
    DESCRIPTION
        "Parameter 'state' in event UDAF.20"
    ::= { udafEventObjects20 4 }

udafEventObjects21 OBJECT-IDENTITY
    STATUS current
    DESCRIPTION
        "Event UDAF.21
        The TCP session has been closed."
    ::= { udafEventsGroup 21 }

udaf21_interface OBJECT-TYPE
    SYNTAX DisplayString
    MAX-ACCESS accessible-for-notify
    STATUS current
    DESCRIPTION
        "Parameter 'interface' in event UDAF.21"
    ::= { udafEventObjects21 1 }

udaf21_state OBJECT-TYPE
    SYNTAX Integer32
    MAX-ACCESS accessible-for-notify
    STATUS current
    DESCRIPTION
        "Parameter 'state' in event UDAF.21"
    ::= { udafEventObjects21 2 }

udafEventObjects22 OBJECT-IDENTITY
    STATUS current
    DESCRIPTION
        "Event UDAF.22
        The TCP session has been closed by the remote HOST."
    ::= { udafEventsGroup 22 }

udaf22_interface OBJECT-TYPE
    SYNTAX DisplayString
    MAX-ACCESS accessible-for-notify
    STATUS current
    DESCRIPTION
        "Parameter 'interface' in event UDAF.22"
    ::= { udafEventObjects22 1 }

udaf22_state OBJECT-TYPE
    SYNTAX Integer32
    MAX-ACCESS accessible-for-notify
    STATUS current
    DESCRIPTION
        "Parameter 'state' in event UDAF.22"
    ::= { udafEventObjects22 2 }

udafEventObjects23 OBJECT-IDENTITY
    STATUS current
    DESCRIPTION
        "Event UDAF.23
        A TCP session has been opened by the remote HOST."
    ::= { udafEventsGroup 23 }

udaf23_interface OBJECT-TYPE
    SYNTAX DisplayString
    MAX-ACCESS accessible-for-notify
    STATUS current
    DESCRIPTION
        "Parameter 'interface' in event UDAF.23"
    ::= { udafEventObjects23 1 }

udaf23_state OBJECT-TYPE
    SYNTAX Integer32
    MAX-ACCESS accessible-for-notify
    STATUS current
    DESCRIPTION
        "Parameter 'state' in event UDAF.23"
    ::= { udafEventObjects23 2 }

udafEventObjects24 OBJECT-IDENTITY
    STATUS current
    DESCRIPTION
        "Event UDAF.24
        A message has been transmitted to POS."
    ::= { udafEventsGroup 24 }

udaf24_message_type OBJECT-TYPE
    SYNTAX DisplayString
    MAX-ACCESS accessible-for-notify
    STATUS current
    DESCRIPTION
        "Parameter 'message_type' in event UDAF.24"
    ::= { udafEventObjects24 1 }

udaf24_bytes_number OBJECT-TYPE
    SYNTAX Integer32
    MAX-ACCESS accessible-for-notify
    STATUS current
    DESCRIPTION
        "Parameter 'bytes_number' in event UDAF.24"
    ::= { udafEventObjects24 2 }

udaf24_interface OBJECT-TYPE
    SYNTAX DisplayString
    MAX-ACCESS accessible-for-notify
    STATUS current
    DESCRIPTION
        "Parameter 'interface' in event UDAF.24"
    ::= { udafEventObjects24 3 }

udaf24_state OBJECT-TYPE
    SYNTAX Integer32
    MAX-ACCESS accessible-for-notify
    STATUS current
    DESCRIPTION
        "Parameter 'state' in event UDAF.24"
    ::= { udafEventObjects24 4 }

udafEventObjects25 OBJECT-IDENTITY
    STATUS current
    DESCRIPTION
        "Event UDAF.25
        One OK message has been received from POS."
    ::= { udafEventsGroup 25 }

udaf25_message_type OBJECT-TYPE
    SYNTAX DisplayString
    MAX-ACCESS accessible-for-notify
    STATUS current
    DESCRIPTION
        "Parameter 'message_type' in event UDAF.25"
    ::= { udafEventObjects25 1 }

udaf25_bytes_number OBJECT-TYPE
    SYNTAX Integer32
    MAX-ACCESS accessible-for-notify
    STATUS current
    DESCRIPTION
        "Parameter 'bytes_number' in event UDAF.25"
    ::= { udafEventObjects25 2 }

udaf25_interface OBJECT-TYPE
    SYNTAX DisplayString
    MAX-ACCESS accessible-for-notify
    STATUS current
    DESCRIPTION
        "Parameter 'interface' in event UDAF.25"
    ::= { udafEventObjects25 3 }

udaf25_state OBJECT-TYPE
    SYNTAX Integer32
    MAX-ACCESS accessible-for-notify
    STATUS current
    DESCRIPTION
        "Parameter 'state' in event UDAF.25"
    ::= { udafEventObjects25 4 }

udafEventObjects26 OBJECT-IDENTITY
    STATUS current
    DESCRIPTION
        "Event UDAF.26
        One Bad message has been received from POS."
    ::= { udafEventsGroup 26 }

udaf26_interface OBJECT-TYPE
    SYNTAX DisplayString
    MAX-ACCESS accessible-for-notify
    STATUS current
    DESCRIPTION
        "Parameter 'interface' in event UDAF.26"
    ::= { udafEventObjects26 1 }

udaf26_state OBJECT-TYPE
    SYNTAX Integer32
    MAX-ACCESS accessible-for-notify
    STATUS current
    DESCRIPTION
        "Parameter 'state' in event UDAF.26"
    ::= { udafEventObjects26 2 }

udafEventObjects27 OBJECT-IDENTITY
    STATUS current
    DESCRIPTION
        "Event UDAF.27
        A change ON/OFF has been detected in Serial Control Signal Input."
    ::= { udafEventsGroup 27 }

udaf27_new_on_off_status OBJECT-TYPE
    SYNTAX DisplayString
    MAX-ACCESS accessible-for-notify
    STATUS current
    DESCRIPTION
        "Parameter 'new_on_off_status' in event UDAF.27"
    ::= { udafEventObjects27 1 }

udaf27_interface OBJECT-TYPE
    SYNTAX DisplayString
    MAX-ACCESS accessible-for-notify
    STATUS current
    DESCRIPTION
        "Parameter 'interface' in event UDAF.27"
    ::= { udafEventObjects27 2 }

udaf27_state OBJECT-TYPE
    SYNTAX Integer32
    MAX-ACCESS accessible-for-notify
    STATUS current
    DESCRIPTION
        "Parameter 'state' in event UDAF.27"
    ::= { udafEventObjects27 3 }

udafEventObjects28 OBJECT-IDENTITY
    STATUS current
    DESCRIPTION
        "Event UDAF.28
        An ENQ control character has been transmitted to POS."
    ::= { udafEventsGroup 28 }

udaf28_interface OBJECT-TYPE
    SYNTAX DisplayString
    MAX-ACCESS accessible-for-notify
    STATUS current
    DESCRIPTION
        "Parameter 'interface' in event UDAF.28"
    ::= { udafEventObjects28 1 }

udaf28_state OBJECT-TYPE
    SYNTAX Integer32
    MAX-ACCESS accessible-for-notify
    STATUS current
    DESCRIPTION
        "Parameter 'state' in event UDAF.28"
    ::= { udafEventObjects28 2 }

udafEventObjects29 OBJECT-IDENTITY
    STATUS current
    DESCRIPTION
        "Event UDAF.29
        Timeout has occur waiting data from POS."
    ::= { udafEventsGroup 29 }

udaf29_interface OBJECT-TYPE
    SYNTAX DisplayString
    MAX-ACCESS accessible-for-notify
    STATUS current
    DESCRIPTION
        "Parameter 'interface' in event UDAF.29"
    ::= { udafEventObjects29 1 }

udaf29_state OBJECT-TYPE
    SYNTAX Integer32
    MAX-ACCESS accessible-for-notify
    STATUS current
    DESCRIPTION
        "Parameter 'state' in event UDAF.29"
    ::= { udafEventObjects29 2 }

udafEventObjects30 OBJECT-IDENTITY
    STATUS current
    DESCRIPTION
        "Event UDAF.30
        Trying to send a Release message to X25 Gateway."
    ::= { udafEventsGroup 30 }

udaf30_interface OBJECT-TYPE
    SYNTAX DisplayString
    MAX-ACCESS accessible-for-notify
    STATUS current
    DESCRIPTION
        "Parameter 'interface' in event UDAF.30"
    ::= { udafEventObjects30 1 }

udaf30_state OBJECT-TYPE
    SYNTAX Integer32
    MAX-ACCESS accessible-for-notify
    STATUS current
    DESCRIPTION
        "Parameter 'state' in event UDAF.30"
    ::= { udafEventObjects30 2 }

udafEventObjects31 OBJECT-IDENTITY
    STATUS current
    DESCRIPTION
        "Event UDAF.31
        A message from POS has been received."
    ::= { udafEventsGroup 31 }

udaf31_message_type OBJECT-TYPE
    SYNTAX DisplayString
    MAX-ACCESS accessible-for-notify
    STATUS current
    DESCRIPTION
        "Parameter 'message_type' in event UDAF.31"
    ::= { udafEventObjects31 1 }

udaf31_interface OBJECT-TYPE
    SYNTAX DisplayString
    MAX-ACCESS accessible-for-notify
    STATUS current
    DESCRIPTION
        "Parameter 'interface' in event UDAF.31"
    ::= { udafEventObjects31 2 }

udaf31_state OBJECT-TYPE
    SYNTAX Integer32
    MAX-ACCESS accessible-for-notify
    STATUS current
    DESCRIPTION
        "Parameter 'state' in event UDAF.31"
    ::= { udafEventObjects31 3 }

udafEventObjects32 OBJECT-IDENTITY
    STATUS current
    DESCRIPTION
        "Event UDAF.32
        A packet was lost, due to TCP Tx overrun error."
    ::= { udafEventsGroup 32 }

udaf32_interface OBJECT-TYPE
    SYNTAX DisplayString
    MAX-ACCESS accessible-for-notify
    STATUS current
    DESCRIPTION
        "Parameter 'interface' in event UDAF.32"
    ::= { udafEventObjects32 1 }

udaf32_state OBJECT-TYPE
    SYNTAX Integer32
    MAX-ACCESS accessible-for-notify
    STATUS current
    DESCRIPTION
        "Parameter 'state' in event UDAF.32"
    ::= { udafEventObjects32 2 }

udafEventObjects33 OBJECT-IDENTITY
    STATUS current
    DESCRIPTION
        "Event UDAF.33
        Transaction against the destination whose NA and IP address are shown
        went wrong because of the indicated cause."
    ::= { udafEventsGroup 33 }

udaf33_na OBJECT-TYPE
    SYNTAX DisplayString
    MAX-ACCESS accessible-for-notify
    STATUS current
    DESCRIPTION
        "Parameter 'na' in event UDAF.33"
    ::= { udafEventObjects33 1 }

udaf33_ip_host_address OBJECT-TYPE
    SYNTAX IpAddress
    MAX-ACCESS accessible-for-notify
    STATUS current
    DESCRIPTION
        "Parameter 'ip_host_address' in event UDAF.33"
    ::= { udafEventObjects33 2 }

udaf33_cause OBJECT-TYPE
    SYNTAX Integer32
    MAX-ACCESS accessible-for-notify
    STATUS current
    DESCRIPTION
        "Parameter 'cause' in event UDAF.33"
    ::= { udafEventObjects33 3 }

udaf33_interface OBJECT-TYPE
    SYNTAX DisplayString
    MAX-ACCESS accessible-for-notify
    STATUS current
    DESCRIPTION
        "Parameter 'interface' in event UDAF.33"
    ::= { udafEventObjects33 4 }

udafEventObjects34 OBJECT-IDENTITY
    STATUS current
    DESCRIPTION
        "Event UDAF.34
        Transmission process is busy at new transaction start."
    ::= { udafEventsGroup 34 }

udaf34_interface OBJECT-TYPE
    SYNTAX DisplayString
    MAX-ACCESS accessible-for-notify
    STATUS current
    DESCRIPTION
        "Parameter 'interface' in event UDAF.34"
    ::= { udafEventObjects34 1 }

udaf34_state OBJECT-TYPE
    SYNTAX Integer32
    MAX-ACCESS accessible-for-notify
    STATUS current
    DESCRIPTION
        "Parameter 'state' in event UDAF.34"
    ::= { udafEventObjects34 2 }

udafEventObjects35 OBJECT-IDENTITY
    STATUS current
    DESCRIPTION
        "Event UDAF.35
        The TCP session has been closed due to inactivity timeout."
    ::= { udafEventsGroup 35 }

udaf35_interface OBJECT-TYPE
    SYNTAX DisplayString
    MAX-ACCESS accessible-for-notify
    STATUS current
    DESCRIPTION
        "Parameter 'interface' in event UDAF.35"
    ::= { udafEventObjects35 1 }

udaf35_state OBJECT-TYPE
    SYNTAX Integer32
    MAX-ACCESS accessible-for-notify
    STATUS current
    DESCRIPTION
        "Parameter 'state' in event UDAF.35"
    ::= { udafEventObjects35 2 }

udafEventObjects36 OBJECT-IDENTITY
    STATUS current
    DESCRIPTION
        "Event UDAF.36
        Data is received from POS, but the service is suspended by operator."
    ::= { udafEventsGroup 36 }

udaf36_bytes_number OBJECT-TYPE
    SYNTAX Integer32
    MAX-ACCESS accessible-for-notify
    STATUS current
    DESCRIPTION
        "Parameter 'bytes_number' in event UDAF.36"
    ::= { udafEventObjects36 1 }

udaf36_interface OBJECT-TYPE
    SYNTAX DisplayString
    MAX-ACCESS accessible-for-notify
    STATUS current
    DESCRIPTION
        "Parameter 'interface' in event UDAF.36"
    ::= { udafEventObjects36 2 }

udafEventObjects37 OBJECT-IDENTITY
    STATUS current
    DESCRIPTION
        "Event UDAF.37
        PAD has established X.25 connection with HOST."
    ::= { udafEventsGroup 37 }

udaf37_interface OBJECT-TYPE
    SYNTAX DisplayString
    MAX-ACCESS accessible-for-notify
    STATUS current
    DESCRIPTION
        "Parameter 'interface' in event UDAF.37"
    ::= { udafEventObjects37 1 }

udaf37_state OBJECT-TYPE
    SYNTAX Integer32
    MAX-ACCESS accessible-for-notify
    STATUS current
    DESCRIPTION
        "Parameter 'state' in event UDAF.37"
    ::= { udafEventObjects37 2 }

udafEventObjects38 OBJECT-IDENTITY
    STATUS current
    DESCRIPTION
        "Event UDAF.38
        Timeout has occur waiting data from HOST."
    ::= { udafEventsGroup 38 }

udaf38_interface OBJECT-TYPE
    SYNTAX DisplayString
    MAX-ACCESS accessible-for-notify
    STATUS current
    DESCRIPTION
        "Parameter 'interface' in event UDAF.38"
    ::= { udafEventObjects38 1 }

udaf38_state OBJECT-TYPE
    SYNTAX Integer32
    MAX-ACCESS accessible-for-notify
    STATUS current
    DESCRIPTION
        "Parameter 'state' in event UDAF.38"
    ::= { udafEventObjects38 2 }

udafEventObjects39 OBJECT-IDENTITY
    STATUS current
    DESCRIPTION
        "Event UDAF.39
        Release message was received from X25 Gateway."
    ::= { udafEventsGroup 39 }

udaf39_interface OBJECT-TYPE
    SYNTAX DisplayString
    MAX-ACCESS accessible-for-notify
    STATUS current
    DESCRIPTION
        "Parameter 'interface' in event UDAF.39"
    ::= { udafEventObjects39 1 }

udaf39_state OBJECT-TYPE
    SYNTAX Integer32
    MAX-ACCESS accessible-for-notify
    STATUS current
    DESCRIPTION
        "Parameter 'state' in event UDAF.39"
    ::= { udafEventObjects39 2 }

udafEventObjects40 OBJECT-IDENTITY
    STATUS current
    DESCRIPTION
        "Event UDAF.40
        A change ON/OFF has been made in Serial Control Signal Output."
    ::= { udafEventsGroup 40 }

udaf40_new_on_off_status OBJECT-TYPE
    SYNTAX DisplayString
    MAX-ACCESS accessible-for-notify
    STATUS current
    DESCRIPTION
        "Parameter 'new_on_off_status' in event UDAF.40"
    ::= { udafEventObjects40 1 }

udaf40_interface OBJECT-TYPE
    SYNTAX DisplayString
    MAX-ACCESS accessible-for-notify
    STATUS current
    DESCRIPTION
        "Parameter 'interface' in event UDAF.40"
    ::= { udafEventObjects40 2 }

udaf40_state OBJECT-TYPE
    SYNTAX Integer32
    MAX-ACCESS accessible-for-notify
    STATUS current
    DESCRIPTION
        "Parameter 'state' in event UDAF.40"
    ::= { udafEventObjects40 3 }

udafEventObjects41 OBJECT-IDENTITY
    STATUS current
    DESCRIPTION
        "Event UDAF.41
        A message (whose type is shown) has been transmitted to Host."
    ::= { udafEventsGroup 41 }

udaf41_message_type OBJECT-TYPE
    SYNTAX DisplayString
    MAX-ACCESS accessible-for-notify
    STATUS current
    DESCRIPTION
        "Parameter 'message_type' in event UDAF.41"
    ::= { udafEventObjects41 1 }

udaf41_bytes_number OBJECT-TYPE
    SYNTAX Integer32
    MAX-ACCESS accessible-for-notify
    STATUS current
    DESCRIPTION
        "Parameter 'bytes_number' in event UDAF.41"
    ::= { udafEventObjects41 2 }

udaf41_interface OBJECT-TYPE
    SYNTAX DisplayString
    MAX-ACCESS accessible-for-notify
    STATUS current
    DESCRIPTION
        "Parameter 'interface' in event UDAF.41"
    ::= { udafEventObjects41 3 }

udaf41_state OBJECT-TYPE
    SYNTAX Integer32
    MAX-ACCESS accessible-for-notify
    STATUS current
    DESCRIPTION
        "Parameter 'state' in event UDAF.41"
    ::= { udafEventObjects41 4 }


udafNotification1 NOTIFICATION-TYPE
    OBJECTS { 
              udaf1_bytes_number, 
              udaf1_interface 
            }
    STATUS current
    DESCRIPTION
        "Notification of Event UDAF.1

        Message: 'Rx Data from POS, $1 bytes, interface $2'

        Parameters list:
              $1: udaf1_bytes_number
              $2: udaf1_interface

        Data has been received from POS."
    ::= { udafNotificationsPrefix 1 }

udafNotification2 NOTIFICATION-TYPE
    OBJECTS { 
              udaf2_interface, 
              udaf2_state 
            }
    STATUS current
    DESCRIPTION
        "Notification of Event UDAF.2

        Message: 'Rx ACK control character from POS, interface $1, state $2'

        Parameters list:
              $1: udaf2_interface
              $2: udaf2_state

        An ACK control character has been received from POS."
    ::= { udafNotificationsPrefix 2 }

udafNotification3 NOTIFICATION-TYPE
    OBJECTS { 
              udaf3_interface, 
              udaf3_state 
            }
    STATUS current
    DESCRIPTION
        "Notification of Event UDAF.3

        Message: 'Rx EOT control character from POS, interface $1, state $2'

        Parameters list:
              $1: udaf3_interface
              $2: udaf3_state

        An EOT control character has been received from POS."
    ::= { udafNotificationsPrefix 3 }

udafNotification4 NOTIFICATION-TYPE
    OBJECTS { 
              udaf4_interface, 
              udaf4_state 
            }
    STATUS current
    DESCRIPTION
        "Notification of Event UDAF.4

        Message: 'Rx NAK control character from POS, interface $1, state $2'

        Parameters list:
              $1: udaf4_interface
              $2: udaf4_state

        A NAK control character has been received from POS."
    ::= { udafNotificationsPrefix 4 }

udafNotification5 NOTIFICATION-TYPE
    OBJECTS { 
              udaf5_interface 
            }
    STATUS current
    DESCRIPTION
        "Notification of Event UDAF.5

        Message: 'A block with LRC/CRC error has been received from POS, interface $1'

        Parameters list:
              $1: udaf5_interface

        A block with parity error has been received from POS."
    ::= { udafNotificationsPrefix 5 }

udafNotification6 NOTIFICATION-TYPE
    OBJECTS { 
              udaf6_interface, 
              udaf6_state 
            }
    STATUS current
    DESCRIPTION
        "Notification of Event UDAF.6

        Message: 'Tx ACK control character to POS, interface $1, state $2'

        Parameters list:
              $1: udaf6_interface
              $2: udaf6_state

        An ACK control character has been transmitted to POS."
    ::= { udafNotificationsPrefix 6 }

udafNotification7 NOTIFICATION-TYPE
    OBJECTS { 
              udaf7_interface, 
              udaf7_state 
            }
    STATUS current
    DESCRIPTION
        "Notification of Event UDAF.7

        Message: 'Tx EOT control character to POS, interface $1, state $2'

        Parameters list:
              $1: udaf7_interface
              $2: udaf7_state

        An EOT control character has been transmitted to POS."
    ::= { udafNotificationsPrefix 7 }

udafNotification8 NOTIFICATION-TYPE
    OBJECTS { 
              udaf8_interface, 
              udaf8_state 
            }
    STATUS current
    DESCRIPTION
        "Notification of Event UDAF.8

        Message: 'Tx NAK control character to POS, interface $1, state $2'

        Parameters list:
              $1: udaf8_interface
              $2: udaf8_state

        A NAK control character has been transmitted to POS."
    ::= { udafNotificationsPrefix 8 }

udafNotification9 NOTIFICATION-TYPE
    OBJECTS { 
              udaf9_interface 
            }
    STATUS current
    DESCRIPTION
        "Notification of Event UDAF.9

        Message: 'An S message was expected and it has not been received properly. Interface $1'

        Parameters list:
              $1: udaf9_interface

        An S message was expected and it has not been received properly."
    ::= { udafNotificationsPrefix 9 }

udafNotification10 NOTIFICATION-TYPE
    OBJECTS { 
              udaf10_na, 
              udaf10_interface 
            }
    STATUS current
    DESCRIPTION
        "Notification of Event UDAF.10

        Message: 'NA $1 received from POS is not included in configuration profile list. Interface $2'

        Parameters list:
              $1: udaf10_na
              $2: udaf10_interface

        NA received from POS is not included in configuration profile list."
    ::= { udafNotificationsPrefix 10 }

udafNotification11 NOTIFICATION-TYPE
    OBJECTS { 
              udaf11_na, 
              udaf11_transport,
              udaf11_ip_host_address,
              udaf11_port,
              udaf11_interface 
            }
    STATUS current
    DESCRIPTION
        "Notification of Event UDAF.11

        Message: 'NA $1 is trying the connection $2, against IP $3 Host, Port $4, Interface $5'

        Parameters list:
              $1: udaf11_na
              $2: udaf11_transport
              $3: udaf11_ip_host_address
              $4: udaf11_port
              $5: udaf11_interface

        The specified NA is trying the connection against IP Host and P port,
        using the specified transport protocol."
    ::= { udafNotificationsPrefix 11 }

udafNotification12 NOTIFICATION-TYPE
    OBJECTS { 
              udaf12_interface 
            }
    STATUS current
    DESCRIPTION
        "Notification of Event UDAF.12

        Message: 'The connection against Host has failed. Interface $1'

        Parameters list:
              $1: udaf12_interface

        The connection against Host has failed."
    ::= { udafNotificationsPrefix 12 }

udafNotification13 NOTIFICATION-TYPE
    OBJECTS { 
              udaf13_interface 
            }
    STATUS current
    DESCRIPTION
        "Notification of Event UDAF.13

        Message: 'The transaction has been completed successfully. Interface $1'

        Parameters list:
              $1: udaf13_interface

        The transaction has been completed successfully."
    ::= { udafNotificationsPrefix 13 }

udafNotification14 NOTIFICATION-TYPE
    OBJECTS { 
              udaf14_message_type, 
              udaf14_bytes_number,
              udaf14_interface 
            }
    STATUS current
    DESCRIPTION
        "Notification of Event UDAF.14

        Message: 'Trying to send $1 message to Host with $2 bytes. Interface $3'

        Parameters list:
              $1: udaf14_message_type
              $2: udaf14_bytes_number
              $3: udaf14_interface

        Trying to send message to Host."
    ::= { udafNotificationsPrefix 14 }

udafNotification15 NOTIFICATION-TYPE
    OBJECTS { 
              udaf15_message_type, 
              udaf15_bytes_number,
              udaf15_interface,
              udaf15_state 
            }
    STATUS current
    DESCRIPTION
        "Notification of Event UDAF.15

        Message: 'A TRMTP Message of $1 type has been received, $2 bytes. Interface $3, state $4'

        Parameters list:
              $1: udaf15_message_type
              $2: udaf15_bytes_number
              $3: udaf15_interface
              $4: udaf15_state

        A TRMTP message has been received."
    ::= { udafNotificationsPrefix 15 }

udafNotification16 NOTIFICATION-TYPE
    OBJECTS { 
              udaf16_interface 
            }
    STATUS current
    DESCRIPTION
        "Notification of Event UDAF.16

        Message: 'Trying TRMTP message Retransmission. Interface $1'

        Parameters list:
              $1: udaf16_interface

        Trying TRMTP message retransmission."
    ::= { udafNotificationsPrefix 16 }

udafNotification17 NOTIFICATION-TYPE
    OBJECTS { 
              udaf17_interface 
            }
    STATUS current
    DESCRIPTION
        "Notification of Event UDAF.17

        Message: 'Trying retransmission to POS. Interface $1'

        Parameters list:
              $1: udaf17_interface

        Trying retransmission to POS."
    ::= { udafNotificationsPrefix 17 }

udafNotification18 NOTIFICATION-TYPE
    OBJECTS { 
              udaf18_error_message, 
              udaf18_interface,
              udaf18_state 
            }
    STATUS current
    DESCRIPTION
        "Notification of Event UDAF.18

        Message: 'An Error $1 was found. Interface $2, state $3'

        Parameters list:
              $1: udaf18_error_message
              $2: udaf18_interface
              $3: udaf18_state

        A certain error was found."
    ::= { udafNotificationsPrefix 18 }

udafNotification19 NOTIFICATION-TYPE
    OBJECTS { 
              udaf19_message_type, 
              udaf19_bytes_number,
              udaf19_interface,
              udaf19_state 
            }
    STATUS current
    DESCRIPTION
        "Notification of Event UDAF.19

        Message: 'A message from HOST of $1 type has been received, $2 bytes. Interface $3, state $4'

        Parameters list:
              $1: udaf19_message_type
              $2: udaf19_bytes_number
              $3: udaf19_interface
              $4: udaf19_state

        A message from HOST has been received."
    ::= { udafNotificationsPrefix 19 }

udafNotification20 NOTIFICATION-TYPE
    OBJECTS { 
              udaf20_message_type, 
              udaf20_bytes_number,
              udaf20_interface,
              udaf20_state 
            }
    STATUS current
    DESCRIPTION
        "Notification of Event UDAF.20

        Message: 'A TCP Packet of $1 type has been received, $2 bytes. Interface $3, state $4'

        Parameters list:
              $1: udaf20_message_type
              $2: udaf20_bytes_number
              $3: udaf20_interface
              $4: udaf20_state

        A TCP packet has been received."
    ::= { udafNotificationsPrefix 20 }

udafNotification21 NOTIFICATION-TYPE
    OBJECTS { 
              udaf21_interface, 
              udaf21_state 
            }
    STATUS current
    DESCRIPTION
        "Notification of Event UDAF.21

        Message: 'The TCP session has been closed. Interface $1, state $2'

        Parameters list:
              $1: udaf21_interface
              $2: udaf21_state

        The TCP session has been closed."
    ::= { udafNotificationsPrefix 21 }

udafNotification22 NOTIFICATION-TYPE
    OBJECTS { 
              udaf22_interface, 
              udaf22_state 
            }
    STATUS current
    DESCRIPTION
        "Notification of Event UDAF.22

        Message: 'The TCP session has been closed by the remote HOST. Interface $1, state $2'

        Parameters list:
              $1: udaf22_interface
              $2: udaf22_state

        The TCP session has been closed by the remote HOST."
    ::= { udafNotificationsPrefix 22 }

udafNotification23 NOTIFICATION-TYPE
    OBJECTS { 
              udaf23_interface, 
              udaf23_state 
            }
    STATUS current
    DESCRIPTION
        "Notification of Event UDAF.23

        Message: 'The TCP session has been opened by the remote HOST. Interface $1, state $2'

        Parameters list:
              $1: udaf23_interface
              $2: udaf23_state

        A TCP session has been opened by the remote HOST."
    ::= { udafNotificationsPrefix 23 }

udafNotification24 NOTIFICATION-TYPE
    OBJECTS { 
              udaf24_message_type, 
              udaf24_bytes_number,
              udaf24_interface,
              udaf24_state 
            }
    STATUS current
    DESCRIPTION
        "Notification of Event UDAF.24

        Message: 'Tx $1 Message to POS, $2 bytes, interface $3 state $4'

        Parameters list:
              $1: udaf24_message_type
              $2: udaf24_bytes_number
              $3: udaf24_interface
              $4: udaf24_state

        A message has been transmitted to POS."
    ::= { udafNotificationsPrefix 24 }

udafNotification25 NOTIFICATION-TYPE
    OBJECTS { 
              udaf25_message_type, 
              udaf25_bytes_number,
              udaf25_interface,
              udaf25_state 
            }
    STATUS current
    DESCRIPTION
        "Notification of Event UDAF.25

        Message: 'Rx $1 Message from POS, $2 bytes, interface $3, state $4'

        Parameters list:
              $1: udaf25_message_type
              $2: udaf25_bytes_number
              $3: udaf25_interface
              $4: udaf25_state

        One OK message has been received from POS."
    ::= { udafNotificationsPrefix 25 }

udafNotification26 NOTIFICATION-TYPE
    OBJECTS { 
              udaf26_interface, 
              udaf26_state 
            }
    STATUS current
    DESCRIPTION
        "Notification of Event UDAF.26

        Message: 'Rx Bad Message from POS, interface $1, state $2'

        Parameters list:
              $1: udaf26_interface
              $2: udaf26_state

        One Bad message has been received from POS."
    ::= { udafNotificationsPrefix 26 }

udafNotification27 NOTIFICATION-TYPE
    OBJECTS { 
              udaf27_new_on_off_status, 
              udaf27_interface,
              udaf27_state 
            }
    STATUS current
    DESCRIPTION
        "Notification of Event UDAF.27

        Message: 'Serial Control Signal Input change to $1, interface $2, state $3'

        Parameters list:
              $1: udaf27_new_on_off_status
              $2: udaf27_interface
              $3: udaf27_state

        A change ON/OFF has been detected in Serial Control Signal Input."
    ::= { udafNotificationsPrefix 27 }

udafNotification28 NOTIFICATION-TYPE
    OBJECTS { 
              udaf28_interface, 
              udaf28_state 
            }
    STATUS current
    DESCRIPTION
        "Notification of Event UDAF.28

        Message: 'Tx ENQ control character to POS, interface $1, state $2'

        Parameters list:
              $1: udaf28_interface
              $2: udaf28_state

        An ENQ control character has been transmitted to POS."
    ::= { udafNotificationsPrefix 28 }

udafNotification29 NOTIFICATION-TYPE
    OBJECTS { 
              udaf29_interface, 
              udaf29_state 
            }
    STATUS current
    DESCRIPTION
        "Notification of Event UDAF.29

        Message: 'Timeout waiting data from POS, interface $1, state $2'

        Parameters list:
              $1: udaf29_interface
              $2: udaf29_state

        Timeout has occur waiting data from POS."
    ::= { udafNotificationsPrefix 29 }

udafNotification30 NOTIFICATION-TYPE
    OBJECTS { 
              udaf30_interface, 
              udaf30_state 
            }
    STATUS current
    DESCRIPTION
        "Notification of Event UDAF.30

        Message: 'Trying to send a Release message to X25 Gateway. Interface $1, state $2'

        Parameters list:
              $1: udaf30_interface
              $2: udaf30_state

        Trying to send a Release message to X25 Gateway."
    ::= { udafNotificationsPrefix 30 }

udafNotification31 NOTIFICATION-TYPE
    OBJECTS { 
              udaf31_message_type, 
              udaf31_interface,
              udaf31_state 
            }
    STATUS current
    DESCRIPTION
        "Notification of Event UDAF.31

        Message: 'A message from POS of $1 type has been received. Interface $2, state $3'

        Parameters list:
              $1: udaf31_message_type
              $2: udaf31_interface
              $3: udaf31_state

        A message from POS has been received."
    ::= { udafNotificationsPrefix 31 }

udafNotification32 NOTIFICATION-TYPE
    OBJECTS { 
              udaf32_interface, 
              udaf32_state 
            }
    STATUS current
    DESCRIPTION
        "Notification of Event UDAF.32

        Message: 'Packet lost due to TCP Tx overrun error. Interface $1, state $2'

        Parameters list:
              $1: udaf32_interface
              $2: udaf32_state

        A packet was lost, due to TCP Tx overrun error."
    ::= { udafNotificationsPrefix 32 }

udafNotification33 NOTIFICATION-TYPE
    OBJECTS { 
              udaf33_na, 
              udaf33_ip_host_address,
              udaf33_cause,
              udaf33_interface 
            }
    STATUS current
    DESCRIPTION
        "Notification of Event UDAF.33

        Message: 'The transaction has been wrong, against NA $1, IP $2, Cause $3, Interface $4'

        Parameters list:
              $1: udaf33_na
              $2: udaf33_ip_host_address
              $3: udaf33_cause
              $4: udaf33_interface

        Transaction against the destination whose NA and IP address are shown
        went wrong because of the indicated cause."
    ::= { udafNotificationsPrefix 33 }

udafNotification34 NOTIFICATION-TYPE
    OBJECTS { 
              udaf34_interface, 
              udaf34_state 
            }
    STATUS current
    DESCRIPTION
        "Notification of Event UDAF.34

        Message: 'Transmission process busy at transaction start. Interface $1, state $2'

        Parameters list:
              $1: udaf34_interface
              $2: udaf34_state

        Transmission process is busy at new transaction start."
    ::= { udafNotificationsPrefix 34 }

udafNotification35 NOTIFICATION-TYPE
    OBJECTS { 
              udaf35_interface, 
              udaf35_state 
            }
    STATUS current
    DESCRIPTION
        "Notification of Event UDAF.35

        Message: 'The TCP session has been closed due to inactivity timeout. Interface $1, state $2'

        Parameters list:
              $1: udaf35_interface
              $2: udaf35_state

        The TCP session has been closed due to inactivity timeout."
    ::= { udafNotificationsPrefix 35 }

udafNotification36 NOTIFICATION-TYPE
    OBJECTS { 
              udaf36_bytes_number, 
              udaf36_interface 
            }
    STATUS current
    DESCRIPTION
        "Notification of Event UDAF.36

        Message: 'Service is suspended when Rx Data from POS. $1 bytes, interface $2'

        Parameters list:
              $1: udaf36_bytes_number
              $2: udaf36_interface

        Data is received from POS, but the service is suspended by operator."
    ::= { udafNotificationsPrefix 36 }

udafNotification37 NOTIFICATION-TYPE
    OBJECTS { 
              udaf37_interface, 
              udaf37_state 
            }
    STATUS current
    DESCRIPTION
        "Notification of Event UDAF.37

        Message: 'Connection has been established with HOST. Interface $1, state $2'

        Parameters list:
              $1: udaf37_interface
              $2: udaf37_state

        PAD has established X.25 connection with HOST."
    ::= { udafNotificationsPrefix 37 }

udafNotification38 NOTIFICATION-TYPE
    OBJECTS { 
              udaf38_interface, 
              udaf38_state 
            }
    STATUS current
    DESCRIPTION
        "Notification of Event UDAF.38

        Message: 'Timeout waiting data from HOST, interface $1, state $2'

        Parameters list:
              $1: udaf38_interface
              $2: udaf38_state

        Timeout has occur waiting data from HOST."
    ::= { udafNotificationsPrefix 38 }

udafNotification39 NOTIFICATION-TYPE
    OBJECTS { 
              udaf39_interface, 
              udaf39_state 
            }
    STATUS current
    DESCRIPTION
        "Notification of Event UDAF.39

        Message: 'Release message was received from X25 Gateway. Interface $1, state $2'

        Parameters list:
              $1: udaf39_interface
              $2: udaf39_state

        Release message was received from X25 Gateway."
    ::= { udafNotificationsPrefix 39 }

udafNotification40 NOTIFICATION-TYPE
    OBJECTS { 
              udaf40_new_on_off_status, 
              udaf40_interface,
              udaf40_state 
            }
    STATUS current
    DESCRIPTION
        "Notification of Event UDAF.40

        Message: 'Serial Control Signal Output change to $1, interface $2, state $3'

        Parameters list:
              $1: udaf40_new_on_off_status
              $2: udaf40_interface
              $3: udaf40_state

        A change ON/OFF has been made in Serial Control Signal Output."
    ::= { udafNotificationsPrefix 40 }

udafNotification41 NOTIFICATION-TYPE
    OBJECTS { 
              udaf41_message_type, 
              udaf41_bytes_number,
              udaf41_interface,
              udaf41_state 
            }
    STATUS current
    DESCRIPTION
        "Notification of Event UDAF.41

        Message: 'Tx $1 Message to Host, $2 bytes, interface $3, state $4'

        Parameters list:
              $1: udaf41_message_type
              $2: udaf41_bytes_number
              $3: udaf41_interface
              $4: udaf41_state

        A message (whose type is shown) has been transmitted to Host."
    ::= { udafNotificationsPrefix 41 }


END
