-- file automatically created


TELDAT-TRAP-ARLY-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


arlyTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ARLY event subsystem."
    REVISION "201401200930Z"
    DESCRIPTION "Initial implementation"
        ::= { telEventTraps 202 }


arlyEventsGroup	OBJECT IDENTIFIER	::= { arlyTrapsMIB 1 }

arlyNotifications	OBJECT IDENTIFIER	::= { arlyTrapsMIB 2 }
arlyNotificationsPrefix	OBJECT IDENTIFIER	::= { arlyNotifications 0 }

arlyEventObjects1 OBJECT-IDENTITY
    STATUS current
    DESCRIPTION
        "Event ARLY.1
        Data has been received from UDP."
    ::= { arlyEventsGroup 1 }

arly1_size OBJECT-TYPE
    SYNTAX Integer32
    MAX-ACCESS accessible-for-notify
    STATUS current
    DESCRIPTION
        "Parameter 'size' in event ARLY.1"
    ::= { arlyEventObjects1 1 }

arlyEventObjects2 OBJECT-IDENTITY
    STATUS current
    DESCRIPTION
        "Event ARLY.2
        Data has been sent to UDP."
    ::= { arlyEventsGroup 2 }

arly2_size OBJECT-TYPE
    SYNTAX Integer32
    MAX-ACCESS accessible-for-notify
    STATUS current
    DESCRIPTION
        "Parameter 'size' in event ARLY.2"
    ::= { arlyEventObjects2 1 }

arlyEventObjects3 OBJECT-IDENTITY
    STATUS current
    DESCRIPTION
        "Event ARLY.3
        Reports an IP address monitor message."
    ::= { arlyEventsGroup 3 }

arly3_message OBJECT-TYPE
    SYNTAX DisplayString
    MAX-ACCESS accessible-for-notify
    STATUS current
    DESCRIPTION
        "Parameter 'message' in event ARLY.3"
    ::= { arlyEventObjects3 1 }

arlyEventObjects4 OBJECT-IDENTITY
    STATUS current
    DESCRIPTION
        "Event ARLY.4
        Data has been received from ARLY serial line interface."
    ::= { arlyEventsGroup 4 }

arly4_data OBJECT-TYPE
    SYNTAX DisplayString
    MAX-ACCESS accessible-for-notify
    STATUS current
    DESCRIPTION
        "Parameter 'data' in event ARLY.4"
    ::= { arlyEventObjects4 1 }

arlyEventObjects5 OBJECT-IDENTITY
    STATUS current
    DESCRIPTION
        "Event ARLY.5
        Data has been sent to ARLY interface serial line."
    ::= { arlyEventsGroup 5 }

arly5_data OBJECT-TYPE
    SYNTAX DisplayString
    MAX-ACCESS accessible-for-notify
    STATUS current
    DESCRIPTION
        "Parameter 'data' in event ARLY.5"
    ::= { arlyEventObjects5 1 }

arlyEventObjects6 OBJECT-IDENTITY
    STATUS current
    DESCRIPTION
        "Event ARLY.6
        Alarm receiver emulation software has detected some error and
        this is reported."
    ::= { arlyEventsGroup 6 }

arly6_message OBJECT-TYPE
    SYNTAX DisplayString
    MAX-ACCESS accessible-for-notify
    STATUS current
    DESCRIPTION
        "Parameter 'message' in event ARLY.6"
    ::= { arlyEventObjects6 1 }

arlyEventObjects7 OBJECT-IDENTITY
    STATUS current
    DESCRIPTION
        "Event ARLY.7
        A remote registration saved"
    ::= { arlyEventsGroup 7 }

arly7_data OBJECT-TYPE
    SYNTAX DisplayString
    MAX-ACCESS accessible-for-notify
    STATUS current
    DESCRIPTION
        "Parameter 'data' in event ARLY.7"
    ::= { arlyEventObjects7 1 }

arlyEventObjects8 OBJECT-IDENTITY
    STATUS current
    DESCRIPTION
        "Event ARLY.8
        Alarm receiver emulation software receives an event in
        the reported state."
    ::= { arlyEventsGroup 8 }

arly8_state OBJECT-TYPE
    SYNTAX Integer32
    MAX-ACCESS accessible-for-notify
    STATUS current
    DESCRIPTION
        "Parameter 'state' in event ARLY.8"
    ::= { arlyEventObjects8 1 }

arly8_event OBJECT-TYPE
    SYNTAX Integer32
    MAX-ACCESS accessible-for-notify
    STATUS current
    DESCRIPTION
        "Parameter 'event' in event ARLY.8"
    ::= { arlyEventObjects8 2 }

arlyEventObjects9 OBJECT-IDENTITY
    STATUS current
    DESCRIPTION
        "Event ARLY.9
        Alarm receiver emulation software receives a timeout event in
        the reported state."
    ::= { arlyEventsGroup 9 }

arly9_state OBJECT-TYPE
    SYNTAX Integer32
    MAX-ACCESS accessible-for-notify
    STATUS current
    DESCRIPTION
        "Parameter 'state' in event ARLY.9"
    ::= { arlyEventObjects9 1 }

arlyEventObjects12 OBJECT-IDENTITY
    STATUS current
    DESCRIPTION
        "Event ARLY.12
        Received a contact frame from the specified MIP's account."
    ::= { arlyEventsGroup 12 }

arly12_account OBJECT-TYPE
    SYNTAX Integer32
    MAX-ACCESS accessible-for-notify
    STATUS current
    DESCRIPTION
        "Parameter 'account' in event ARLY.12"
    ::= { arlyEventObjects12 1 }

arlyEventObjects13 OBJECT-IDENTITY
    STATUS current
    DESCRIPTION
        "Event ARLY.13
        Received a keep-alive frame from the specified MIP's account."
    ::= { arlyEventsGroup 13 }

arly13_account OBJECT-TYPE
    SYNTAX Integer32
    MAX-ACCESS accessible-for-notify
    STATUS current
    DESCRIPTION
        "Parameter 'account' in event ARLY.13"
    ::= { arlyEventObjects13 1 }

arlyEventObjects14 OBJECT-IDENTITY
    STATUS current
    DESCRIPTION
        "Event ARLY.14
        Supervision timer expired for the specified account. MIP is considered
        lost. An alarm is reported to Automation Software."
    ::= { arlyEventsGroup 14 }

arly14_account OBJECT-TYPE
    SYNTAX Integer32
    MAX-ACCESS accessible-for-notify
    STATUS current
    DESCRIPTION
        "Parameter 'account' in event ARLY.14"
    ::= { arlyEventObjects14 1 }

arlyEventObjects15 OBJECT-IDENTITY
    STATUS current
    DESCRIPTION
        "Event ARLY.15
        A wrong remote supervision frame has been received from the specified
        MIP's account."
    ::= { arlyEventsGroup 15 }

arly15_message OBJECT-TYPE
    SYNTAX DisplayString
    MAX-ACCESS accessible-for-notify
    STATUS current
    DESCRIPTION
        "Parameter 'message' in event ARLY.15"
    ::= { arlyEventObjects15 1 }

arly15_account OBJECT-TYPE
    SYNTAX Integer32
    MAX-ACCESS accessible-for-notify
    STATUS current
    DESCRIPTION
        "Parameter 'account' in event ARLY.15"
    ::= { arlyEventObjects15 2 }

arlyEventObjects16 OBJECT-IDENTITY
    STATUS current
    DESCRIPTION
        "Event ARLY.16
        An alarm frame has been received from the specified MIP's account."
    ::= { arlyEventsGroup 16 }

arly16_account OBJECT-TYPE
    SYNTAX Integer32
    MAX-ACCESS accessible-for-notify
    STATUS current
    DESCRIPTION
        "Parameter 'account' in event ARLY.16"
    ::= { arlyEventObjects16 1 }

arlyEventObjects17 OBJECT-IDENTITY
    STATUS current
    DESCRIPTION
        "Event ARLY.17
        A wrong alarm frame has been received from the specified MIP's account."
    ::= { arlyEventsGroup 17 }

arly17_account OBJECT-TYPE
    SYNTAX Integer32
    MAX-ACCESS accessible-for-notify
    STATUS current
    DESCRIPTION
        "Parameter 'account' in event ARLY.17"
    ::= { arlyEventObjects17 1 }

arly17_error OBJECT-TYPE
    SYNTAX Integer32
    MAX-ACCESS accessible-for-notify
    STATUS current
    DESCRIPTION
        "Parameter 'error' in event ARLY.17"
    ::= { arlyEventObjects17 2 }

arlyEventObjects18 OBJECT-IDENTITY
    STATUS current
    DESCRIPTION
        "Event ARLY.18
        An alarm is lost due to lack of free buffers to store it.
        The alarm is lost."
    ::= { arlyEventsGroup 18 }

arly18_account OBJECT-TYPE
    SYNTAX Integer32
    MAX-ACCESS accessible-for-notify
    STATUS current
    DESCRIPTION
        "Parameter 'account' in event ARLY.18"
    ::= { arlyEventObjects18 1 }

arlyEventObjects19 OBJECT-IDENTITY
    STATUS current
    DESCRIPTION
        "Event ARLY.19
        A received alarm is saved for further rely to the automation software.
        Number of free buffers is reported."
    ::= { arlyEventsGroup 19 }

arly19_buffers OBJECT-TYPE
    SYNTAX Integer32
    MAX-ACCESS accessible-for-notify
    STATUS current
    DESCRIPTION
        "Parameter 'buffers' in event ARLY.19"
    ::= { arlyEventObjects19 1 }

arlyEventObjects20 OBJECT-IDENTITY
    STATUS current
    DESCRIPTION
        "Event ARLY.20
        An alarm is deleted because has been sent to the automation software."
    ::= { arlyEventsGroup 20 }

arly20_buffers OBJECT-TYPE
    SYNTAX Integer32
    MAX-ACCESS accessible-for-notify
    STATUS current
    DESCRIPTION
        "Parameter 'buffers' in event ARLY.20"
    ::= { arlyEventObjects20 1 }

arlyEventObjects22 OBJECT-IDENTITY
    STATUS current
    DESCRIPTION
        "Event ARLY.22
        A TRMTP frame has been received."
    ::= { arlyEventsGroup 22 }

arly22_data OBJECT-TYPE
    SYNTAX DisplayString
    MAX-ACCESS accessible-for-notify
    STATUS current
    DESCRIPTION
        "Parameter 'data' in event ARLY.22"
    ::= { arlyEventObjects22 1 }

arlyEventObjects23 OBJECT-IDENTITY
    STATUS current
    DESCRIPTION
        "Event ARLY.23
        A TRMTP frame has been sent."
    ::= { arlyEventsGroup 23 }

arly23_data OBJECT-TYPE
    SYNTAX DisplayString
    MAX-ACCESS accessible-for-notify
    STATUS current
    DESCRIPTION
        "Parameter 'data' in event ARLY.23"
    ::= { arlyEventObjects23 1 }

arlyEventObjects24 OBJECT-IDENTITY
    STATUS current
    DESCRIPTION
        "Event ARLY.24
        A remote registration frame has been received from the specified MIP's
        account. The frame has been successfully decoded with the specified
        installer password."
    ::= { arlyEventsGroup 24 }

arly24_account OBJECT-TYPE
    SYNTAX Integer32
    MAX-ACCESS accessible-for-notify
    STATUS current
    DESCRIPTION
        "Parameter 'account' in event ARLY.24"
    ::= { arlyEventObjects24 1 }

arly24_password OBJECT-TYPE
    SYNTAX DisplayString
    MAX-ACCESS accessible-for-notify
    STATUS current
    DESCRIPTION
        "Parameter 'password' in event ARLY.24"
    ::= { arlyEventObjects24 2 }

arlyEventObjects25 OBJECT-IDENTITY
    STATUS current
    DESCRIPTION
        "Event ARLY.25
        Reports events related to remote configuration of the specified
        MIP's account."
    ::= { arlyEventsGroup 25 }

arly25_account OBJECT-TYPE
    SYNTAX Integer32
    MAX-ACCESS accessible-for-notify
    STATUS current
    DESCRIPTION
        "Parameter 'account' in event ARLY.25"
    ::= { arlyEventObjects25 1 }

arly25_message OBJECT-TYPE
    SYNTAX DisplayString
    MAX-ACCESS accessible-for-notify
    STATUS current
    DESCRIPTION
        "Parameter 'message' in event ARLY.25"
    ::= { arlyEventObjects25 2 }

arlyEventObjects26 OBJECT-IDENTITY
    STATUS current
    DESCRIPTION
        "Event ARLY.26
        An error has been detected and reported."
    ::= { arlyEventsGroup 26 }

arly26_message OBJECT-TYPE
    SYNTAX DisplayString
    MAX-ACCESS accessible-for-notify
    STATUS current
    DESCRIPTION
        "Parameter 'message' in event ARLY.26"
    ::= { arlyEventObjects26 1 }

arlyEventObjects27 OBJECT-IDENTITY
    STATUS current
    DESCRIPTION
        "Event ARLY.27
        The polling has failed."
    ::= { arlyEventsGroup 27 }

arly27_ip1 OBJECT-TYPE
    SYNTAX Integer32
    MAX-ACCESS accessible-for-notify
    STATUS current
    DESCRIPTION
        "Parameter 'ip1' in event ARLY.27"
    ::= { arlyEventObjects27 1 }

arly27_ip2 OBJECT-TYPE
    SYNTAX Integer32
    MAX-ACCESS accessible-for-notify
    STATUS current
    DESCRIPTION
        "Parameter 'ip2' in event ARLY.27"
    ::= { arlyEventObjects27 2 }

arly27_ip3 OBJECT-TYPE
    SYNTAX Integer32
    MAX-ACCESS accessible-for-notify
    STATUS current
    DESCRIPTION
        "Parameter 'ip3' in event ARLY.27"
    ::= { arlyEventObjects27 3 }

arly27_ip4 OBJECT-TYPE
    SYNTAX Integer32
    MAX-ACCESS accessible-for-notify
    STATUS current
    DESCRIPTION
        "Parameter 'ip4' in event ARLY.27"
    ::= { arlyEventObjects27 4 }

arlyEventObjects28 OBJECT-IDENTITY
    STATUS current
    DESCRIPTION
        "Event ARLY.28
        New retry packet."
    ::= { arlyEventsGroup 28 }

arly28_pack OBJECT-TYPE
    SYNTAX Integer32
    MAX-ACCESS accessible-for-notify
    STATUS current
    DESCRIPTION
        "Parameter 'pack' in event ARLY.28"
    ::= { arlyEventObjects28 1 }

arlyEventObjects29 OBJECT-IDENTITY
    STATUS current
    DESCRIPTION
        "Event ARLY.29
        The main VisorAlarm is reachable."
    ::= { arlyEventsGroup 29 }

arly29_ip1 OBJECT-TYPE
    SYNTAX Integer32
    MAX-ACCESS accessible-for-notify
    STATUS current
    DESCRIPTION
        "Parameter 'ip1' in event ARLY.29"
    ::= { arlyEventObjects29 1 }

arly29_ip2 OBJECT-TYPE
    SYNTAX Integer32
    MAX-ACCESS accessible-for-notify
    STATUS current
    DESCRIPTION
        "Parameter 'ip2' in event ARLY.29"
    ::= { arlyEventObjects29 2 }

arly29_ip3 OBJECT-TYPE
    SYNTAX Integer32
    MAX-ACCESS accessible-for-notify
    STATUS current
    DESCRIPTION
        "Parameter 'ip3' in event ARLY.29"
    ::= { arlyEventObjects29 3 }

arly29_ip4 OBJECT-TYPE
    SYNTAX Integer32
    MAX-ACCESS accessible-for-notify
    STATUS current
    DESCRIPTION
        "Parameter 'ip4' in event ARLY.29"
    ::= { arlyEventObjects29 4 }

arlyEventObjects30 OBJECT-IDENTITY
    STATUS current
    DESCRIPTION
        "Event ARLY.30
        Polling between main station to secondary one."
    ::= { arlyEventsGroup 30 }

arly30_ip1 OBJECT-TYPE
    SYNTAX Integer32
    MAX-ACCESS accessible-for-notify
    STATUS current
    DESCRIPTION
        "Parameter 'ip1' in event ARLY.30"
    ::= { arlyEventObjects30 1 }

arly30_ip2 OBJECT-TYPE
    SYNTAX Integer32
    MAX-ACCESS accessible-for-notify
    STATUS current
    DESCRIPTION
        "Parameter 'ip2' in event ARLY.30"
    ::= { arlyEventObjects30 2 }

arly30_ip3 OBJECT-TYPE
    SYNTAX Integer32
    MAX-ACCESS accessible-for-notify
    STATUS current
    DESCRIPTION
        "Parameter 'ip3' in event ARLY.30"
    ::= { arlyEventObjects30 3 }

arly30_ip4 OBJECT-TYPE
    SYNTAX Integer32
    MAX-ACCESS accessible-for-notify
    STATUS current
    DESCRIPTION
        "Parameter 'ip4' in event ARLY.30"
    ::= { arlyEventObjects30 4 }

arlyEventObjects31 OBJECT-IDENTITY
    STATUS current
    DESCRIPTION
        "Event ARLY.31
        Polling between main station to secondary one."
    ::= { arlyEventsGroup 31 }

arly31_action OBJECT-TYPE
    SYNTAX DisplayString
    MAX-ACCESS accessible-for-notify
    STATUS current
    DESCRIPTION
        "Parameter 'action' in event ARLY.31"
    ::= { arlyEventObjects31 1 }

arly31_ip1 OBJECT-TYPE
    SYNTAX Integer32
    MAX-ACCESS accessible-for-notify
    STATUS current
    DESCRIPTION
        "Parameter 'ip1' in event ARLY.31"
    ::= { arlyEventObjects31 2 }

arly31_ip2 OBJECT-TYPE
    SYNTAX Integer32
    MAX-ACCESS accessible-for-notify
    STATUS current
    DESCRIPTION
        "Parameter 'ip2' in event ARLY.31"
    ::= { arlyEventObjects31 3 }

arly31_ip3 OBJECT-TYPE
    SYNTAX Integer32
    MAX-ACCESS accessible-for-notify
    STATUS current
    DESCRIPTION
        "Parameter 'ip3' in event ARLY.31"
    ::= { arlyEventObjects31 4 }

arly31_ip4 OBJECT-TYPE
    SYNTAX Integer32
    MAX-ACCESS accessible-for-notify
    STATUS current
    DESCRIPTION
        "Parameter 'ip4' in event ARLY.31"
    ::= { arlyEventObjects31 5 }

arlyEventObjects32 OBJECT-IDENTITY
    STATUS current
    DESCRIPTION
        "Event ARLY.32
        Report the events of the sync-config protocol in the
        MASTER VisorALARM"
    ::= { arlyEventsGroup 32 }

arly32_data OBJECT-TYPE
    SYNTAX DisplayString
    MAX-ACCESS accessible-for-notify
    STATUS current
    DESCRIPTION
        "Parameter 'data' in event ARLY.32"
    ::= { arlyEventObjects32 1 }

arlyEventObjects33 OBJECT-IDENTITY
    STATUS current
    DESCRIPTION
        "Event ARLY.33
        Report the events of the sync-config protocol in the
        SLAVE VisorALARM"
    ::= { arlyEventsGroup 33 }

arly33_data OBJECT-TYPE
    SYNTAX DisplayString
    MAX-ACCESS accessible-for-notify
    STATUS current
    DESCRIPTION
        "Parameter 'data' in event ARLY.33"
    ::= { arlyEventObjects33 1 }

arlyEventObjects34 OBJECT-IDENTITY
    STATUS current
    DESCRIPTION
        "Event ARLY.34
        Report a change in the state of the MAIN VisorAlarm"
    ::= { arlyEventsGroup 34 }

arly34_data OBJECT-TYPE
    SYNTAX DisplayString
    MAX-ACCESS accessible-for-notify
    STATUS current
    DESCRIPTION
        "Parameter 'data' in event ARLY.34"
    ::= { arlyEventObjects34 1 }

arlyEventObjects35 OBJECT-IDENTITY
    STATUS current
    DESCRIPTION
        "Event ARLY.35
        Report a change in the state of the BACKUP VisorAlarm"
    ::= { arlyEventsGroup 35 }

arly35_data OBJECT-TYPE
    SYNTAX DisplayString
    MAX-ACCESS accessible-for-notify
    STATUS current
    DESCRIPTION
        "Parameter 'data' in event ARLY.35"
    ::= { arlyEventObjects35 1 }

arlyEventObjects36 OBJECT-IDENTITY
    STATUS current
    DESCRIPTION
        "Event ARLY.36
        Report an event in relation to failover of MIP"
    ::= { arlyEventsGroup 36 }

arly36_str OBJECT-TYPE
    SYNTAX DisplayString
    MAX-ACCESS accessible-for-notify
    STATUS current
    DESCRIPTION
        "Parameter 'str' in event ARLY.36"
    ::= { arlyEventObjects36 1 }

arly36_data OBJECT-TYPE
    SYNTAX Integer32
    MAX-ACCESS accessible-for-notify
    STATUS current
    DESCRIPTION
        "Parameter 'data' in event ARLY.36"
    ::= { arlyEventObjects36 2 }

arlyEventObjects37 OBJECT-IDENTITY
    STATUS current
    DESCRIPTION
        "Event ARLY.37
        Report an event for the amount of alarms stored
        without being processed by the automation software"
    ::= { arlyEventsGroup 37 }

arly37_str OBJECT-TYPE
    SYNTAX DisplayString
    MAX-ACCESS accessible-for-notify
    STATUS current
    DESCRIPTION
        "Parameter 'str' in event ARLY.37"
    ::= { arlyEventObjects37 1 }

arlyEventObjects39 OBJECT-IDENTITY
    STATUS current
    DESCRIPTION
        "Event ARLY.39
        Data with an unknown protocol field has been received from UDP."
    ::= { arlyEventsGroup 39 }

arly39_protocol OBJECT-TYPE
    SYNTAX Integer32
    MAX-ACCESS accessible-for-notify
    STATUS current
    DESCRIPTION
        "Parameter 'protocol' in event ARLY.39"
    ::= { arlyEventObjects39 1 }

arly39_size OBJECT-TYPE
    SYNTAX Integer32
    MAX-ACCESS accessible-for-notify
    STATUS current
    DESCRIPTION
        "Parameter 'size' in event ARLY.39"
    ::= { arlyEventObjects39 2 }

arlyEventObjects40 OBJECT-IDENTITY
    STATUS current
    DESCRIPTION
        "Event ARLY.40
        An alarm frame has been received from an unknown account."
    ::= { arlyEventsGroup 40 }

arly40_account OBJECT-TYPE
    SYNTAX Integer32
    MAX-ACCESS accessible-for-notify
    STATUS current
    DESCRIPTION
        "Parameter 'account' in event ARLY.40"
    ::= { arlyEventObjects40 1 }

arlyEventObjects41 OBJECT-IDENTITY
    STATUS current
    DESCRIPTION
        "Event ARLY.41
        An alarm frame has been received with a bad sequence number
        from the specified MIP's account."
    ::= { arlyEventsGroup 41 }

arly41_account OBJECT-TYPE
    SYNTAX Integer32
    MAX-ACCESS accessible-for-notify
    STATUS current
    DESCRIPTION
        "Parameter 'account' in event ARLY.41"
    ::= { arlyEventObjects41 1 }

arlyEventObjects42 OBJECT-IDENTITY
    STATUS current
    DESCRIPTION
        "Event ARLY.42
        A UPDWNP packet is sent to a MIPX."
    ::= { arlyEventsGroup 42 }

arly42_size OBJECT-TYPE
    SYNTAX Integer32
    MAX-ACCESS accessible-for-notify
    STATUS current
    DESCRIPTION
        "Parameter 'size' in event ARLY.42"
    ::= { arlyEventObjects42 1 }

arly42_seq OBJECT-TYPE
    SYNTAX Integer32
    MAX-ACCESS accessible-for-notify
    STATUS current
    DESCRIPTION
        "Parameter 'seq' in event ARLY.42"
    ::= { arlyEventObjects42 2 }

arly42_queue OBJECT-TYPE
    SYNTAX Integer32
    MAX-ACCESS accessible-for-notify
    STATUS current
    DESCRIPTION
        "Parameter 'queue' in event ARLY.42"
    ::= { arlyEventObjects42 3 }

arlyEventObjects43 OBJECT-IDENTITY
    STATUS current
    DESCRIPTION
        "Event ARLY.43
        A UPDWNP packet is received from MIPX."
    ::= { arlyEventsGroup 43 }

arly43_size OBJECT-TYPE
    SYNTAX Integer32
    MAX-ACCESS accessible-for-notify
    STATUS current
    DESCRIPTION
        "Parameter 'size' in event ARLY.43"
    ::= { arlyEventObjects43 1 }

arly43_seq OBJECT-TYPE
    SYNTAX Integer32
    MAX-ACCESS accessible-for-notify
    STATUS current
    DESCRIPTION
        "Parameter 'seq' in event ARLY.43"
    ::= { arlyEventObjects43 2 }

arly43_queue OBJECT-TYPE
    SYNTAX Integer32
    MAX-ACCESS accessible-for-notify
    STATUS current
    DESCRIPTION
        "Parameter 'queue' in event ARLY.43"
    ::= { arlyEventObjects43 3 }

arlyEventObjects44 OBJECT-IDENTITY
    STATUS current
    DESCRIPTION
        "Event ARLY.44
        An error UPDWNP packet is received from MIPX."
    ::= { arlyEventsGroup 44 }

arly44_cause OBJECT-TYPE
    SYNTAX DisplayString
    MAX-ACCESS accessible-for-notify
    STATUS current
    DESCRIPTION
        "Parameter 'cause' in event ARLY.44"
    ::= { arlyEventObjects44 1 }

arly44_queue OBJECT-TYPE
    SYNTAX Integer32
    MAX-ACCESS accessible-for-notify
    STATUS current
    DESCRIPTION
        "Parameter 'queue' in event ARLY.44"
    ::= { arlyEventObjects44 2 }

arlyEventObjects45 OBJECT-IDENTITY
    STATUS current
    DESCRIPTION
        "Event ARLY.45
        An ACK UPDWNP packet is received from MIPX."
    ::= { arlyEventsGroup 45 }

arly45_seq OBJECT-TYPE
    SYNTAX Integer32
    MAX-ACCESS accessible-for-notify
    STATUS current
    DESCRIPTION
        "Parameter 'seq' in event ARLY.45"
    ::= { arlyEventObjects45 1 }

arly45_queue OBJECT-TYPE
    SYNTAX Integer32
    MAX-ACCESS accessible-for-notify
    STATUS current
    DESCRIPTION
        "Parameter 'queue' in event ARLY.45"
    ::= { arlyEventObjects45 2 }

arlyEventObjects46 OBJECT-IDENTITY
    STATUS current
    DESCRIPTION
        "Event ARLY.46
        An ACK UPDWNP packet is sent from MIPX."
    ::= { arlyEventsGroup 46 }

arly46_seq OBJECT-TYPE
    SYNTAX Integer32
    MAX-ACCESS accessible-for-notify
    STATUS current
    DESCRIPTION
        "Parameter 'seq' in event ARLY.46"
    ::= { arlyEventObjects46 1 }

arly46_queue OBJECT-TYPE
    SYNTAX Integer32
    MAX-ACCESS accessible-for-notify
    STATUS current
    DESCRIPTION
        "Parameter 'queue' in event ARLY.46"
    ::= { arlyEventObjects46 2 }

arlyEventObjects47 OBJECT-IDENTITY
    STATUS current
    DESCRIPTION
        "Event ARLY.47
        Middleware UPDWNP."
    ::= { arlyEventsGroup 47 }

arly47_accn OBJECT-TYPE
    SYNTAX Integer32
    MAX-ACCESS accessible-for-notify
    STATUS current
    DESCRIPTION
        "Parameter 'accn' in event ARLY.47"
    ::= { arlyEventObjects47 1 }

arly47_str OBJECT-TYPE
    SYNTAX DisplayString
    MAX-ACCESS accessible-for-notify
    STATUS current
    DESCRIPTION
        "Parameter 'str' in event ARLY.47"
    ::= { arlyEventObjects47 2 }

arlyEventObjects48 OBJECT-IDENTITY
    STATUS current
    DESCRIPTION
        "Event ARLY.48
        Middleware UPDWNP error."
    ::= { arlyEventsGroup 48 }

arly48_str OBJECT-TYPE
    SYNTAX DisplayString
    MAX-ACCESS accessible-for-notify
    STATUS current
    DESCRIPTION
        "Parameter 'str' in event ARLY.48"
    ::= { arlyEventObjects48 1 }

arlyEventObjects49 OBJECT-IDENTITY
    STATUS current
    DESCRIPTION
        "Event ARLY.49
        TVRP changes to a new state."
    ::= { arlyEventsGroup 49 }

arly49_str OBJECT-TYPE
    SYNTAX DisplayString
    MAX-ACCESS accessible-for-notify
    STATUS current
    DESCRIPTION
        "Parameter 'str' in event ARLY.49"
    ::= { arlyEventObjects49 1 }

arlyEventObjects50 OBJECT-IDENTITY
    STATUS current
    DESCRIPTION
        "Event ARLY.50
        The TVRP active member wants to share its configuration."
    ::= { arlyEventsGroup 50 }

arly50_id OBJECT-TYPE
    SYNTAX Integer32
    MAX-ACCESS accessible-for-notify
    STATUS current
    DESCRIPTION
        "Parameter 'id' in event ARLY.50"
    ::= { arlyEventObjects50 1 }

arlyEventObjects51 OBJECT-IDENTITY
    STATUS current
    DESCRIPTION
        "Event ARLY.51
        A TVRP group member has been deleted."
    ::= { arlyEventsGroup 51 }

arly51_id OBJECT-TYPE
    SYNTAX Integer32
    MAX-ACCESS accessible-for-notify
    STATUS current
    DESCRIPTION
        "Parameter 'id' in event ARLY.51"
    ::= { arlyEventObjects51 1 }

arlyEventObjects52 OBJECT-IDENTITY
    STATUS current
    DESCRIPTION
        "Event ARLY.52
        A TVRP group member has been added."
    ::= { arlyEventsGroup 52 }

arly52_id OBJECT-TYPE
    SYNTAX Integer32
    MAX-ACCESS accessible-for-notify
    STATUS current
    DESCRIPTION
        "Parameter 'id' in event ARLY.52"
    ::= { arlyEventObjects52 1 }

arlyEventObjects53 OBJECT-IDENTITY
    STATUS current
    DESCRIPTION
        "Event ARLY.53
        Generic system information."
    ::= { arlyEventsGroup 53 }

arly53_message OBJECT-TYPE
    SYNTAX DisplayString
    MAX-ACCESS accessible-for-notify
    STATUS current
    DESCRIPTION
        "Parameter 'message' in event ARLY.53"
    ::= { arlyEventObjects53 1 }

arlyEventObjects54 OBJECT-IDENTITY
    STATUS current
    DESCRIPTION
        "Event ARLY.54
        An ALARM packet has been received."
    ::= { arlyEventsGroup 54 }

arly54_seq OBJECT-TYPE
    SYNTAX Integer32
    MAX-ACCESS accessible-for-notify
    STATUS current
    DESCRIPTION
        "Parameter 'seq' in event ARLY.54"
    ::= { arlyEventObjects54 1 }

arly54_ip OBJECT-TYPE
    SYNTAX IpAddress
    MAX-ACCESS accessible-for-notify
    STATUS current
    DESCRIPTION
        "Parameter 'ip' in event ARLY.54"
    ::= { arlyEventObjects54 2 }

arlyEventObjects55 OBJECT-IDENTITY
    STATUS current
    DESCRIPTION
        "Event ARLY.55
        A SIA block has been received."
    ::= { arlyEventsGroup 55 }

arly55_block OBJECT-TYPE
    SYNTAX DisplayString
    MAX-ACCESS accessible-for-notify
    STATUS current
    DESCRIPTION
        "Parameter 'block' in event ARLY.55"
    ::= { arlyEventObjects55 1 }

arly55_len OBJECT-TYPE
    SYNTAX Integer32
    MAX-ACCESS accessible-for-notify
    STATUS current
    DESCRIPTION
        "Parameter 'len' in event ARLY.55"
    ::= { arlyEventObjects55 2 }

arly55_ack OBJECT-TYPE
    SYNTAX Integer32
    MAX-ACCESS accessible-for-notify
    STATUS current
    DESCRIPTION
        "Parameter 'ack' in event ARLY.55"
    ::= { arlyEventObjects55 3 }

arly55_data OBJECT-TYPE
    SYNTAX DisplayString
    MAX-ACCESS accessible-for-notify
    STATUS current
    DESCRIPTION
        "Parameter 'data' in event ARLY.55"
    ::= { arlyEventObjects55 4 }

arly55_ip OBJECT-TYPE
    SYNTAX IpAddress
    MAX-ACCESS accessible-for-notify
    STATUS current
    DESCRIPTION
        "Parameter 'ip' in event ARLY.55"
    ::= { arlyEventObjects55 5 }

arlyEventObjects56 OBJECT-IDENTITY
    STATUS current
    DESCRIPTION
        "Event ARLY.56
        A POLL packet has been sent."
    ::= { arlyEventsGroup 56 }

arly56_acc OBJECT-TYPE
    SYNTAX Integer32
    MAX-ACCESS accessible-for-notify
    STATUS current
    DESCRIPTION
        "Parameter 'acc' in event ARLY.56"
    ::= { arlyEventObjects56 1 }

arlyEventObjects57 OBJECT-IDENTITY
    STATUS current
    DESCRIPTION
        "Event ARLY.57
        A POLL-ACK packet has been received."
    ::= { arlyEventsGroup 57 }

arly57_acc OBJECT-TYPE
    SYNTAX Integer32
    MAX-ACCESS accessible-for-notify
    STATUS current
    DESCRIPTION
        "Parameter 'acc' in event ARLY.57"
    ::= { arlyEventObjects57 1 }

arlyEventObjects58 OBJECT-IDENTITY
    STATUS current
    DESCRIPTION
        "Event ARLY.58
        A SPRVSN-REQ packet has been received."
    ::= { arlyEventsGroup 58 }

arly58_path OBJECT-TYPE
    SYNTAX Integer32
    MAX-ACCESS accessible-for-notify
    STATUS current
    DESCRIPTION
        "Parameter 'path' in event ARLY.58"
    ::= { arlyEventObjects58 1 }

arly58_acc OBJECT-TYPE
    SYNTAX Integer32
    MAX-ACCESS accessible-for-notify
    STATUS current
    DESCRIPTION
        "Parameter 'acc' in event ARLY.58"
    ::= { arlyEventObjects58 2 }

arlyEventObjects59 OBJECT-IDENTITY
    STATUS current
    DESCRIPTION
        "Event ARLY.59
        A SPRVSN-RSP packet has been sent."
    ::= { arlyEventsGroup 59 }

arly59_path OBJECT-TYPE
    SYNTAX Integer32
    MAX-ACCESS accessible-for-notify
    STATUS current
    DESCRIPTION
        "Parameter 'path' in event ARLY.59"
    ::= { arlyEventObjects59 1 }

arly59_acc OBJECT-TYPE
    SYNTAX Integer32
    MAX-ACCESS accessible-for-notify
    STATUS current
    DESCRIPTION
        "Parameter 'acc' in event ARLY.59"
    ::= { arlyEventObjects59 2 }

arlyEventObjects60 OBJECT-IDENTITY
    STATUS current
    DESCRIPTION
        "Event ARLY.60
        A ENC packet has been received."
    ::= { arlyEventsGroup 60 }

arly60_encrypt OBJECT-TYPE
    SYNTAX Integer32
    MAX-ACCESS accessible-for-notify
    STATUS current
    DESCRIPTION
        "Parameter 'encrypt' in event ARLY.60"
    ::= { arlyEventObjects60 1 }

arly60_pub_key OBJECT-TYPE
    SYNTAX Integer32
    MAX-ACCESS accessible-for-notify
    STATUS current
    DESCRIPTION
        "Parameter 'pub_key' in event ARLY.60"
    ::= { arlyEventObjects60 2 }

arly60_pri_key OBJECT-TYPE
    SYNTAX Integer32
    MAX-ACCESS accessible-for-notify
    STATUS current
    DESCRIPTION
        "Parameter 'pri_key' in event ARLY.60"
    ::= { arlyEventObjects60 3 }

arly60_ip OBJECT-TYPE
    SYNTAX IpAddress
    MAX-ACCESS accessible-for-notify
    STATUS current
    DESCRIPTION
        "Parameter 'ip' in event ARLY.60"
    ::= { arlyEventObjects60 4 }

arlyEventObjects61 OBJECT-IDENTITY
    STATUS current
    DESCRIPTION
        "Event ARLY.61
        A ENC packet has been sent."
    ::= { arlyEventsGroup 61 }

arly61_encrypt OBJECT-TYPE
    SYNTAX Integer32
    MAX-ACCESS accessible-for-notify
    STATUS current
    DESCRIPTION
        "Parameter 'encrypt' in event ARLY.61"
    ::= { arlyEventObjects61 1 }

arly61_pri_key OBJECT-TYPE
    SYNTAX Integer32
    MAX-ACCESS accessible-for-notify
    STATUS current
    DESCRIPTION
        "Parameter 'pri_key' in event ARLY.61"
    ::= { arlyEventObjects61 2 }

arly61_ip OBJECT-TYPE
    SYNTAX IpAddress
    MAX-ACCESS accessible-for-notify
    STATUS current
    DESCRIPTION
        "Parameter 'ip' in event ARLY.61"
    ::= { arlyEventObjects61 3 }

arlyEventObjects62 OBJECT-IDENTITY
    STATUS current
    DESCRIPTION
        "Event ARLY.62
        A PPKCOM packet has been sent."
    ::= { arlyEventsGroup 62 }

arly62_ip OBJECT-TYPE
    SYNTAX IpAddress
    MAX-ACCESS accessible-for-notify
    STATUS current
    DESCRIPTION
        "Parameter 'ip' in event ARLY.62"
    ::= { arlyEventObjects62 1 }

arlyEventObjects63 OBJECT-IDENTITY
    STATUS current
    DESCRIPTION
        "Event ARLY.63
        A PPKREP packet has been received."
    ::= { arlyEventsGroup 63 }

arly63_ip OBJECT-TYPE
    SYNTAX IpAddress
    MAX-ACCESS accessible-for-notify
    STATUS current
    DESCRIPTION
        "Parameter 'ip' in event ARLY.63"
    ::= { arlyEventObjects63 1 }


arlyNotification1 NOTIFICATION-TYPE
    OBJECTS { 
              arly1_size 
            }
    STATUS current
    DESCRIPTION
        "Notification of Event ARLY.1

        Message: 'Data received from UDP. Size: $1'

        Parameters list:
              $1: arly1_size

        Data has been received from UDP."
    ::= { arlyNotificationsPrefix 1 }

arlyNotification2 NOTIFICATION-TYPE
    OBJECTS { 
              arly2_size 
            }
    STATUS current
    DESCRIPTION
        "Notification of Event ARLY.2

        Message: 'Data sent to UDP. Size: $1'

        Parameters list:
              $1: arly2_size

        Data has been sent to UDP."
    ::= { arlyNotificationsPrefix 2 }

arlyNotification3 NOTIFICATION-TYPE
    OBJECTS { 
              arly3_message 
            }
    STATUS current
    DESCRIPTION
        "Notification of Event ARLY.3

        Message: 'IP Address monitor. Message: $1'

        Parameters list:
              $1: arly3_message

        Reports an IP address monitor message."
    ::= { arlyNotificationsPrefix 3 }

arlyNotification4 NOTIFICATION-TYPE
    OBJECTS { 
              arly4_data 
            }
    STATUS current
    DESCRIPTION
        "Notification of Event ARLY.4

        Message: 'Data received from serial line. Data: $1'

        Parameters list:
              $1: arly4_data

        Data has been received from ARLY serial line interface."
    ::= { arlyNotificationsPrefix 4 }

arlyNotification5 NOTIFICATION-TYPE
    OBJECTS { 
              arly5_data 
            }
    STATUS current
    DESCRIPTION
        "Notification of Event ARLY.5

        Message: 'Data sent to serial line. Data: $1'

        Parameters list:
              $1: arly5_data

        Data has been sent to ARLY interface serial line."
    ::= { arlyNotificationsPrefix 5 }

arlyNotification6 NOTIFICATION-TYPE
    OBJECTS { 
              arly6_message 
            }
    STATUS current
    DESCRIPTION
        "Notification of Event ARLY.6

        Message: 'Serial Line protocol error. Message: $1'

        Parameters list:
              $1: arly6_message

        Alarm receiver emulation software has detected some error and
        this is reported."
    ::= { arlyNotificationsPrefix 6 }

arlyNotification7 NOTIFICATION-TYPE
    OBJECTS { 
              arly7_data 
            }
    STATUS current
    DESCRIPTION
        "Notification of Event ARLY.7

        Message: 'REMOTE REGISTER. $1'

        Parameters list:
              $1: arly7_data

        A remote registration saved"
    ::= { arlyNotificationsPrefix 7 }

arlyNotification8 NOTIFICATION-TYPE
    OBJECTS { 
              arly8_state, 
              arly8_event 
            }
    STATUS current
    DESCRIPTION
        "Notification of Event ARLY.8

        Message: 'FMS in state $1 receives event $2'

        Parameters list:
              $1: arly8_state
              $2: arly8_event

        Alarm receiver emulation software receives an event in
        the reported state."
    ::= { arlyNotificationsPrefix 8 }

arlyNotification9 NOTIFICATION-TYPE
    OBJECTS { 
              arly9_state 
            }
    STATUS current
    DESCRIPTION
        "Notification of Event ARLY.9

        Message: 'FMS receive a timeout event in state $1'

        Parameters list:
              $1: arly9_state

        Alarm receiver emulation software receives a timeout event in
        the reported state."
    ::= { arlyNotificationsPrefix 9 }

arlyNotification10 NOTIFICATION-TYPE
    STATUS current
    DESCRIPTION
        "Notification of Event ARLY.10

        Message: 'REMOTE SERVICE. Rx frame'

        A remote service frame has been received."
    ::= { arlyNotificationsPrefix 10 }

arlyNotification11 NOTIFICATION-TYPE
    STATUS current
    DESCRIPTION
        "Notification of Event ARLY.11

        Message: 'REMOTE SERVICE. Rx error frame'

        The remote service frame received is wrong."
    ::= { arlyNotificationsPrefix 11 }

arlyNotification12 NOTIFICATION-TYPE
    OBJECTS { 
              arly12_account 
            }
    STATUS current
    DESCRIPTION
        "Notification of Event ARLY.12

        Message: 'REMOTE SUPERVISION. Account $1 contacted'

        Parameters list:
              $1: arly12_account

        Received a contact frame from the specified MIP's account."
    ::= { arlyNotificationsPrefix 12 }

arlyNotification13 NOTIFICATION-TYPE
    OBJECTS { 
              arly13_account 
            }
    STATUS current
    DESCRIPTION
        "Notification of Event ARLY.13

        Message: 'REMOTE SUPERVISION. Account $1 is alive'

        Parameters list:
              $1: arly13_account

        Received a keep-alive frame from the specified MIP's account."
    ::= { arlyNotificationsPrefix 13 }

arlyNotification14 NOTIFICATION-TYPE
    OBJECTS { 
              arly14_account 
            }
    STATUS current
    DESCRIPTION
        "Notification of Event ARLY.14

        Message: 'REMOTE SUPERVISION. Supervision timer expired for account $1'

        Parameters list:
              $1: arly14_account

        Supervision timer expired for the specified account. MIP is considered
        lost. An alarm is reported to Automation Software."
    ::= { arlyNotificationsPrefix 14 }

arlyNotification15 NOTIFICATION-TYPE
    OBJECTS { 
              arly15_message, 
              arly15_account 
            }
    STATUS current
    DESCRIPTION
        "Notification of Event ARLY.15

        Message: 'REMOTE SUPERVISION. Received a wrong frame $1 from account $2'

        Parameters list:
              $1: arly15_message
              $2: arly15_account

        A wrong remote supervision frame has been received from the specified
        MIP's account."
    ::= { arlyNotificationsPrefix 15 }

arlyNotification16 NOTIFICATION-TYPE
    OBJECTS { 
              arly16_account 
            }
    STATUS current
    DESCRIPTION
        "Notification of Event ARLY.16

        Message: 'ALARM. Alarm received from account $1'

        Parameters list:
              $1: arly16_account

        An alarm frame has been received from the specified MIP's account."
    ::= { arlyNotificationsPrefix 16 }

arlyNotification17 NOTIFICATION-TYPE
    OBJECTS { 
              arly17_account, 
              arly17_error 
            }
    STATUS current
    DESCRIPTION
        "Notification of Event ARLY.17

        Message: 'ALARM. Wrong alarm received from account $1, error $2'

        Parameters list:
              $1: arly17_account
              $2: arly17_error

        A wrong alarm frame has been received from the specified MIP's account."
    ::= { arlyNotificationsPrefix 17 }

arlyNotification18 NOTIFICATION-TYPE
    OBJECTS { 
              arly18_account 
            }
    STATUS current
    DESCRIPTION
        "Notification of Event ARLY.18

        Message: 'ALARM. Alarm from account $1 lost due to lack of buffer'

        Parameters list:
              $1: arly18_account

        An alarm is lost due to lack of free buffers to store it.
        The alarm is lost."
    ::= { arlyNotificationsPrefix 18 }

arlyNotification19 NOTIFICATION-TYPE
    OBJECTS { 
              arly19_buffers 
            }
    STATUS current
    DESCRIPTION
        "Notification of Event ARLY.19

        Message: 'ALARM STORAGE. Alarm saved, $1 buffers free'

        Parameters list:
              $1: arly19_buffers

        A received alarm is saved for further rely to the automation software.
        Number of free buffers is reported."
    ::= { arlyNotificationsPrefix 19 }

arlyNotification20 NOTIFICATION-TYPE
    OBJECTS { 
              arly20_buffers 
            }
    STATUS current
    DESCRIPTION
        "Notification of Event ARLY.20

        Message: 'ALARM STORAGE. Alarm deleted, $1 buffers free'

        Parameters list:
              $1: arly20_buffers

        An alarm is deleted because has been sent to the automation software."
    ::= { arlyNotificationsPrefix 20 }

arlyNotification21 NOTIFICATION-TYPE
    STATUS current
    DESCRIPTION
        "Notification of Event ARLY.21

        Message: 'ALARM STORAGE. No free buffer available'

        A buffer has been requested to store an incoming alarm but there is no
        free buffer an this event is reported."
    ::= { arlyNotificationsPrefix 21 }

arlyNotification22 NOTIFICATION-TYPE
    OBJECTS { 
              arly22_data 
            }
    STATUS current
    DESCRIPTION
        "Notification of Event ARLY.22

        Message: 'TMRTP. Received frame. Data $1'

        Parameters list:
              $1: arly22_data

        A TRMTP frame has been received."
    ::= { arlyNotificationsPrefix 22 }

arlyNotification23 NOTIFICATION-TYPE
    OBJECTS { 
              arly23_data 
            }
    STATUS current
    DESCRIPTION
        "Notification of Event ARLY.23

        Message: 'TMRTP. Transmit frame. Data $1'

        Parameters list:
              $1: arly23_data

        A TRMTP frame has been sent."
    ::= { arlyNotificationsPrefix 23 }

arlyNotification24 NOTIFICATION-TYPE
    OBJECTS { 
              arly24_account, 
              arly24_password 
            }
    STATUS current
    DESCRIPTION
        "Notification of Event ARLY.24

        Message: 'REMOTE REGISTER. Received frame from account $1, installer password $2'

        Parameters list:
              $1: arly24_account
              $2: arly24_password

        A remote registration frame has been received from the specified MIP's
        account. The frame has been successfully decoded with the specified
        installer password."
    ::= { arlyNotificationsPrefix 24 }

arlyNotification25 NOTIFICATION-TYPE
    OBJECTS { 
              arly25_account, 
              arly25_message 
            }
    STATUS current
    DESCRIPTION
        "Notification of Event ARLY.25

        Message: 'REMOTE CONFIG. Account $1 message: $2'

        Parameters list:
              $1: arly25_account
              $2: arly25_message

        Reports events related to remote configuration of the specified
        MIP's account."
    ::= { arlyNotificationsPrefix 25 }

arlyNotification26 NOTIFICATION-TYPE
    OBJECTS { 
              arly26_message 
            }
    STATUS current
    DESCRIPTION
        "Notification of Event ARLY.26

        Message: 'ERROR: $1'

        Parameters list:
              $1: arly26_message

        An error has been detected and reported."
    ::= { arlyNotificationsPrefix 26 }

arlyNotification27 NOTIFICATION-TYPE
    OBJECTS { 
              arly27_ip1, 
              arly27_ip2,
              arly27_ip3,
              arly27_ip4 
            }
    STATUS current
    DESCRIPTION
        "Notification of Event ARLY.27

        Message: 'Polling Fail. Main address $1.$2.$3.$4'

        Parameters list:
              $1: arly27_ip1
              $2: arly27_ip2
              $3: arly27_ip3
              $4: arly27_ip4

        The polling has failed."
    ::= { arlyNotificationsPrefix 27 }

arlyNotification28 NOTIFICATION-TYPE
    OBJECTS { 
              arly28_pack 
            }
    STATUS current
    DESCRIPTION
        "Notification of Event ARLY.28

        Message: 'New retry packet $1'

        Parameters list:
              $1: arly28_pack

        New retry packet."
    ::= { arlyNotificationsPrefix 28 }

arlyNotification29 NOTIFICATION-TYPE
    OBJECTS { 
              arly29_ip1, 
              arly29_ip2,
              arly29_ip3,
              arly29_ip4 
            }
    STATUS current
    DESCRIPTION
        "Notification of Event ARLY.29

        Message: 'The main VisorAlarm $1.$2.$3.$4 is reachable'

        Parameters list:
              $1: arly29_ip1
              $2: arly29_ip2
              $3: arly29_ip3
              $4: arly29_ip4

        The main VisorAlarm is reachable."
    ::= { arlyNotificationsPrefix 29 }

arlyNotification30 NOTIFICATION-TYPE
    OBJECTS { 
              arly30_ip1, 
              arly30_ip2,
              arly30_ip3,
              arly30_ip4 
            }
    STATUS current
    DESCRIPTION
        "Notification of Event ARLY.30

        Message: 'Send poll to $1.$2.$3.$4'

        Parameters list:
              $1: arly30_ip1
              $2: arly30_ip2
              $3: arly30_ip3
              $4: arly30_ip4

        Polling between main station to secondary one."
    ::= { arlyNotificationsPrefix 30 }

arlyNotification31 NOTIFICATION-TYPE
    OBJECTS { 
              arly31_action, 
              arly31_ip1,
              arly31_ip2,
              arly31_ip3,
              arly31_ip4 
            }
    STATUS current
    DESCRIPTION
        "Notification of Event ARLY.31

        Message: 'Send response $1 to $2.$3.$4.$5'

        Parameters list:
              $1: arly31_action
              $2: arly31_ip1
              $3: arly31_ip2
              $4: arly31_ip3
              $5: arly31_ip4

        Polling between main station to secondary one."
    ::= { arlyNotificationsPrefix 31 }

arlyNotification32 NOTIFICATION-TYPE
    OBJECTS { 
              arly32_data 
            }
    STATUS current
    DESCRIPTION
        "Notification of Event ARLY.32

        Message: 'Sync configuration MASTER sync: $1'

        Parameters list:
              $1: arly32_data

        Report the events of the sync-config protocol in the
        MASTER VisorALARM"
    ::= { arlyNotificationsPrefix 32 }

arlyNotification33 NOTIFICATION-TYPE
    OBJECTS { 
              arly33_data 
            }
    STATUS current
    DESCRIPTION
        "Notification of Event ARLY.33

        Message: 'Sync configuration slave SLAVE sync: $1'

        Parameters list:
              $1: arly33_data

        Report the events of the sync-config protocol in the
        SLAVE VisorALARM"
    ::= { arlyNotificationsPrefix 33 }

arlyNotification34 NOTIFICATION-TYPE
    OBJECTS { 
              arly34_data 
            }
    STATUS current
    DESCRIPTION
        "Notification of Event ARLY.34

        Message: 'Change MAIN state: $1'

        Parameters list:
              $1: arly34_data

        Report a change in the state of the MAIN VisorAlarm"
    ::= { arlyNotificationsPrefix 34 }

arlyNotification35 NOTIFICATION-TYPE
    OBJECTS { 
              arly35_data 
            }
    STATUS current
    DESCRIPTION
        "Notification of Event ARLY.35

        Message: 'Change BCK state: $1'

        Parameters list:
              $1: arly35_data

        Report a change in the state of the BACKUP VisorAlarm"
    ::= { arlyNotificationsPrefix 35 }

arlyNotification36 NOTIFICATION-TYPE
    OBJECTS { 
              arly36_str, 
              arly36_data 
            }
    STATUS current
    DESCRIPTION
        "Notification of Event ARLY.36

        Message: '$1 accnt $2'

        Parameters list:
              $1: arly36_str
              $2: arly36_data

        Report an event in relation to failover of MIP"
    ::= { arlyNotificationsPrefix 36 }

arlyNotification37 NOTIFICATION-TYPE
    OBJECTS { 
              arly37_str 
            }
    STATUS current
    DESCRIPTION
        "Notification of Event ARLY.37

        Message: '$1'

        Parameters list:
              $1: arly37_str

        Report an event for the amount of alarms stored
        without being processed by the automation software"
    ::= { arlyNotificationsPrefix 37 }

arlyNotification38 NOTIFICATION-TYPE
    STATUS current
    DESCRIPTION
        "Notification of Event ARLY.38

        Message: 'CPE REMOTE SERVICE. Rx frame'

        A CPE remote service frame has been received."
    ::= { arlyNotificationsPrefix 38 }

arlyNotification39 NOTIFICATION-TYPE
    OBJECTS { 
              arly39_protocol, 
              arly39_size 
            }
    STATUS current
    DESCRIPTION
        "Notification of Event ARLY.39

        Message: 'Data received from UDP for unknown protocol $1, Size $2'

        Parameters list:
              $1: arly39_protocol
              $2: arly39_size

        Data with an unknown protocol field has been received from UDP."
    ::= { arlyNotificationsPrefix 39 }

arlyNotification40 NOTIFICATION-TYPE
    OBJECTS { 
              arly40_account 
            }
    STATUS current
    DESCRIPTION
        "Notification of Event ARLY.40

        Message: 'ALARM. Alarm received from not registered account $1'

        Parameters list:
              $1: arly40_account

        An alarm frame has been received from an unknown account."
    ::= { arlyNotificationsPrefix 40 }

arlyNotification41 NOTIFICATION-TYPE
    OBJECTS { 
              arly41_account 
            }
    STATUS current
    DESCRIPTION
        "Notification of Event ARLY.41

        Message: 'ALARM. Alarm received with a bad sequence number, account $1'

        Parameters list:
              $1: arly41_account

        An alarm frame has been received with a bad sequence number
        from the specified MIP's account."
    ::= { arlyNotificationsPrefix 41 }

arlyNotification42 NOTIFICATION-TYPE
    OBJECTS { 
              arly42_size, 
              arly42_seq,
              arly42_queue 
            }
    STATUS current
    DESCRIPTION
        "Notification of Event ARLY.42

        Message: 'UPDWNP. Transmition data length $1 seq $2 Q $3'

        Parameters list:
              $1: arly42_size
              $2: arly42_seq
              $3: arly42_queue

        A UPDWNP packet is sent to a MIPX."
    ::= { arlyNotificationsPrefix 42 }

arlyNotification43 NOTIFICATION-TYPE
    OBJECTS { 
              arly43_size, 
              arly43_seq,
              arly43_queue 
            }
    STATUS current
    DESCRIPTION
        "Notification of Event ARLY.43

        Message: 'UPDWNP. Reception data length $1 seq $2 Q $3'

        Parameters list:
              $1: arly43_size
              $2: arly43_seq
              $3: arly43_queue

        A UPDWNP packet is received from MIPX."
    ::= { arlyNotificationsPrefix 43 }

arlyNotification44 NOTIFICATION-TYPE
    OBJECTS { 
              arly44_cause, 
              arly44_queue 
            }
    STATUS current
    DESCRIPTION
        "Notification of Event ARLY.44

        Message: 'UPDWNP. Error on protocol, cause $1 Q $2'

        Parameters list:
              $1: arly44_cause
              $2: arly44_queue

        An error UPDWNP packet is received from MIPX."
    ::= { arlyNotificationsPrefix 44 }

arlyNotification45 NOTIFICATION-TYPE
    OBJECTS { 
              arly45_seq, 
              arly45_queue 
            }
    STATUS current
    DESCRIPTION
        "Notification of Event ARLY.45

        Message: 'UPDWNP. Reception of a ACK packet seq $1 Q $2'

        Parameters list:
              $1: arly45_seq
              $2: arly45_queue

        An ACK UPDWNP packet is received from MIPX."
    ::= { arlyNotificationsPrefix 45 }

arlyNotification46 NOTIFICATION-TYPE
    OBJECTS { 
              arly46_seq, 
              arly46_queue 
            }
    STATUS current
    DESCRIPTION
        "Notification of Event ARLY.46

        Message: 'UPDWNP. Transmision of a ACK packet seq: $1 Q $2'

        Parameters list:
              $1: arly46_seq
              $2: arly46_queue

        An ACK UPDWNP packet is sent from MIPX."
    ::= { arlyNotificationsPrefix 46 }

arlyNotification47 NOTIFICATION-TYPE
    OBJECTS { 
              arly47_accn, 
              arly47_str 
            }
    STATUS current
    DESCRIPTION
        "Notification of Event ARLY.47

        Message: 'MW account $1 $2'

        Parameters list:
              $1: arly47_accn
              $2: arly47_str

        Middleware UPDWNP."
    ::= { arlyNotificationsPrefix 47 }

arlyNotification48 NOTIFICATION-TYPE
    OBJECTS { 
              arly48_str 
            }
    STATUS current
    DESCRIPTION
        "Notification of Event ARLY.48

        Message: 'MW. Error $1'

        Parameters list:
              $1: arly48_str

        Middleware UPDWNP error."
    ::= { arlyNotificationsPrefix 48 }

arlyNotification49 NOTIFICATION-TYPE
    OBJECTS { 
              arly49_str 
            }
    STATUS current
    DESCRIPTION
        "Notification of Event ARLY.49

        Message: 'TVRP State: $1'

        Parameters list:
              $1: arly49_str

        TVRP changes to a new state."
    ::= { arlyNotificationsPrefix 49 }

arlyNotification50 NOTIFICATION-TYPE
    OBJECTS { 
              arly50_id 
            }
    STATUS current
    DESCRIPTION
        "Notification of Event ARLY.50

        Message: 'TVRP Syncronization order for group member $1'

        Parameters list:
              $1: arly50_id

        The TVRP active member wants to share its configuration."
    ::= { arlyNotificationsPrefix 50 }

arlyNotification51 NOTIFICATION-TYPE
    OBJECTS { 
              arly51_id 
            }
    STATUS current
    DESCRIPTION
        "Notification of Event ARLY.51

        Message: 'TVRP Delete id $1'

        Parameters list:
              $1: arly51_id

        A TVRP group member has been deleted."
    ::= { arlyNotificationsPrefix 51 }

arlyNotification52 NOTIFICATION-TYPE
    OBJECTS { 
              arly52_id 
            }
    STATUS current
    DESCRIPTION
        "Notification of Event ARLY.52

        Message: 'TVRP Add id $1'

        Parameters list:
              $1: arly52_id

        A TVRP group member has been added."
    ::= { arlyNotificationsPrefix 52 }

arlyNotification53 NOTIFICATION-TYPE
    OBJECTS { 
              arly53_message 
            }
    STATUS current
    DESCRIPTION
        "Notification of Event ARLY.53

        Message: '$1'

        Parameters list:
              $1: arly53_message

        Generic system information."
    ::= { arlyNotificationsPrefix 53 }

arlyNotification54 NOTIFICATION-TYPE
    OBJECTS { 
              arly54_seq, 
              arly54_ip 
            }
    STATUS current
    DESCRIPTION
        "Notification of Event ARLY.54

        Message: 'MDX Received ALARM packet with sequence number $1 from ip address $2'

        Parameters list:
              $1: arly54_seq
              $2: arly54_ip

        An ALARM packet has been received."
    ::= { arlyNotificationsPrefix 54 }

arlyNotification55 NOTIFICATION-TYPE
    OBJECTS { 
              arly55_block, 
              arly55_len,
              arly55_ack,
              arly55_data,
              arly55_ip 
            }
    STATUS current
    DESCRIPTION
        "Notification of Event ARLY.55

        Message: 'MDX Received SIA block $1: length=$2, acknowledgment=$3, data=$4 from $5'

        Parameters list:
              $1: arly55_block
              $2: arly55_len
              $3: arly55_ack
              $4: arly55_data
              $5: arly55_ip

        A SIA block has been received."
    ::= { arlyNotificationsPrefix 55 }

arlyNotification56 NOTIFICATION-TYPE
    OBJECTS { 
              arly56_acc 
            }
    STATUS current
    DESCRIPTION
        "Notification of Event ARLY.56

        Message: 'MDX Sent POLL packet to account $1'

        Parameters list:
              $1: arly56_acc

        A POLL packet has been sent."
    ::= { arlyNotificationsPrefix 56 }

arlyNotification57 NOTIFICATION-TYPE
    OBJECTS { 
              arly57_acc 
            }
    STATUS current
    DESCRIPTION
        "Notification of Event ARLY.57

        Message: 'MDX Received POLL-ACK packet from account $1'

        Parameters list:
              $1: arly57_acc

        A POLL-ACK packet has been received."
    ::= { arlyNotificationsPrefix 57 }

arlyNotification58 NOTIFICATION-TYPE
    OBJECTS { 
              arly58_path, 
              arly58_acc 
            }
    STATUS current
    DESCRIPTION
        "Notification of Event ARLY.58

        Message: 'MDX Received SUPERVISION-REQUEST packet from path $1, account $2'

        Parameters list:
              $1: arly58_path
              $2: arly58_acc

        A SPRVSN-REQ packet has been received."
    ::= { arlyNotificationsPrefix 58 }

arlyNotification59 NOTIFICATION-TYPE
    OBJECTS { 
              arly59_path, 
              arly59_acc 
            }
    STATUS current
    DESCRIPTION
        "Notification of Event ARLY.59

        Message: 'MDX Sent SUPERVISION-RESPONSE packet for path $1, account $2'

        Parameters list:
              $1: arly59_path
              $2: arly59_acc

        A SPRVSN-RSP packet has been sent."
    ::= { arlyNotificationsPrefix 59 }

arlyNotification60 NOTIFICATION-TYPE
    OBJECTS { 
              arly60_encrypt, 
              arly60_pub_key,
              arly60_pri_key,
              arly60_ip 
            }
    STATUS current
    DESCRIPTION
        "Notification of Event ARLY.60

        Message: 'MDX Received ENC packet. Encryption required=$1. Public key=$2, Private key=$3, IP Address=$4'

        Parameters list:
              $1: arly60_encrypt
              $2: arly60_pub_key
              $3: arly60_pri_key
              $4: arly60_ip

        A ENC packet has been received."
    ::= { arlyNotificationsPrefix 60 }

arlyNotification61 NOTIFICATION-TYPE
    OBJECTS { 
              arly61_encrypt, 
              arly61_pri_key,
              arly61_ip 
            }
    STATUS current
    DESCRIPTION
        "Notification of Event ARLY.61

        Message: 'MDX Sent ENC packet. Encryption required=$1, Private key=$2, IP Address=$3'

        Parameters list:
              $1: arly61_encrypt
              $2: arly61_pri_key
              $3: arly61_ip

        A ENC packet has been sent."
    ::= { arlyNotificationsPrefix 61 }

arlyNotification62 NOTIFICATION-TYPE
    OBJECTS { 
              arly62_ip 
            }
    STATUS current
    DESCRIPTION
        "Notification of Event ARLY.62

        Message: 'MDX Sent PPKCOM packet. IP Address: $1'

        Parameters list:
              $1: arly62_ip

        A PPKCOM packet has been sent."
    ::= { arlyNotificationsPrefix 62 }

arlyNotification63 NOTIFICATION-TYPE
    OBJECTS { 
              arly63_ip 
            }
    STATUS current
    DESCRIPTION
        "Notification of Event ARLY.63

        Message: 'MDX Received PPKREP packet. IP Address: $1'

        Parameters list:
              $1: arly63_ip

        A PPKREP packet has been received."
    ::= { arlyNotificationsPrefix 63 }


END
