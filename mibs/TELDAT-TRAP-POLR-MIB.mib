-- file automatically created


TELDAT-TRAP-POLR-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


polrTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the POLR event subsystem."
    REVISION "201401200930Z"
    DESCRIPTION "Initial implementation"
        ::= { telEventTraps 162 }


polrEventsGroup	OBJECT IDENTIFIER	::= { polrTrapsMIB 1 }

polrNotifications	OBJECT IDENTIFIER	::= { polrTrapsMIB 2 }
polrNotificationsPrefix	OBJECT IDENTIFIER	::= { polrNotifications 0 }

polrEventObjects1 OBJECT-IDENTITY
    STATUS current
    DESCRIPTION
        "Event POLR.1
        A packet was generated from specified address for specified address.
        Packet length and protocol are also shown. This packet will be tested
        for policy routing."
    ::= { polrEventsGroup 1 }

polr1_srcaddr OBJECT-TYPE
    SYNTAX IpAddress
    MAX-ACCESS accessible-for-notify
    STATUS current
    DESCRIPTION
        "Parameter 'srcaddr' in event POLR.1"
    ::= { polrEventObjects1 1 }

polr1_dstaddr OBJECT-TYPE
    SYNTAX IpAddress
    MAX-ACCESS accessible-for-notify
    STATUS current
    DESCRIPTION
        "Parameter 'dstaddr' in event POLR.1"
    ::= { polrEventObjects1 2 }

polr1_length OBJECT-TYPE
    SYNTAX Integer32
    MAX-ACCESS accessible-for-notify
    STATUS current
    DESCRIPTION
        "Parameter 'length' in event POLR.1"
    ::= { polrEventObjects1 3 }

polr1_protocol OBJECT-TYPE
    SYNTAX Integer32
    MAX-ACCESS accessible-for-notify
    STATUS current
    DESCRIPTION
        "Parameter 'protocol' in event POLR.1"
    ::= { polrEventObjects1 4 }

polrEventObjects2 OBJECT-IDENTITY
    STATUS current
    DESCRIPTION
        "Event POLR.2
        A packet was received from specified address for specified address, on
        specified interface. Packet length and protocol are also shown. This
        packet will be tested for policy routing."
    ::= { polrEventsGroup 2 }

polr2_srcaddr OBJECT-TYPE
    SYNTAX IpAddress
    MAX-ACCESS accessible-for-notify
    STATUS current
    DESCRIPTION
        "Parameter 'srcaddr' in event POLR.2"
    ::= { polrEventObjects2 1 }

polr2_dstaddr OBJECT-TYPE
    SYNTAX IpAddress
    MAX-ACCESS accessible-for-notify
    STATUS current
    DESCRIPTION
        "Parameter 'dstaddr' in event POLR.2"
    ::= { polrEventObjects2 2 }

polr2_length OBJECT-TYPE
    SYNTAX Integer32
    MAX-ACCESS accessible-for-notify
    STATUS current
    DESCRIPTION
        "Parameter 'length' in event POLR.2"
    ::= { polrEventObjects2 3 }

polr2_protocol OBJECT-TYPE
    SYNTAX Integer32
    MAX-ACCESS accessible-for-notify
    STATUS current
    DESCRIPTION
        "Parameter 'protocol' in event POLR.2"
    ::= { polrEventObjects2 4 }

polr2_interface OBJECT-TYPE
    SYNTAX DisplayString
    MAX-ACCESS accessible-for-notify
    STATUS current
    DESCRIPTION
        "Parameter 'interface' in event POLR.2"
    ::= { polrEventObjects2 5 }

polrEventObjects4 OBJECT-IDENTITY
    STATUS current
    DESCRIPTION
        "Event POLR.4
        No route map associated to specified interface."
    ::= { polrEventsGroup 4 }

polr4_interface OBJECT-TYPE
    SYNTAX DisplayString
    MAX-ACCESS accessible-for-notify
    STATUS current
    DESCRIPTION
        "Parameter 'interface' in event POLR.4"
    ::= { polrEventObjects4 1 }

polrEventObjects5 OBJECT-IDENTITY
    STATUS current
    DESCRIPTION
        "Event POLR.5
        A packet was generated from specified address for specified address.
        Packet length and protocol are also shown. This packet did not match the
        specified route map."
    ::= { polrEventsGroup 5 }

polr5_srcaddr OBJECT-TYPE
    SYNTAX IpAddress
    MAX-ACCESS accessible-for-notify
    STATUS current
    DESCRIPTION
        "Parameter 'srcaddr' in event POLR.5"
    ::= { polrEventObjects5 1 }

polr5_dstaddr OBJECT-TYPE
    SYNTAX IpAddress
    MAX-ACCESS accessible-for-notify
    STATUS current
    DESCRIPTION
        "Parameter 'dstaddr' in event POLR.5"
    ::= { polrEventObjects5 2 }

polr5_length OBJECT-TYPE
    SYNTAX Integer32
    MAX-ACCESS accessible-for-notify
    STATUS current
    DESCRIPTION
        "Parameter 'length' in event POLR.5"
    ::= { polrEventObjects5 3 }

polr5_protocol OBJECT-TYPE
    SYNTAX Integer32
    MAX-ACCESS accessible-for-notify
    STATUS current
    DESCRIPTION
        "Parameter 'protocol' in event POLR.5"
    ::= { polrEventObjects5 4 }

polr5_routemap OBJECT-TYPE
    SYNTAX DisplayString
    MAX-ACCESS accessible-for-notify
    STATUS current
    DESCRIPTION
        "Parameter 'routemap' in event POLR.5"
    ::= { polrEventObjects5 5 }

polrEventObjects6 OBJECT-IDENTITY
    STATUS current
    DESCRIPTION
        "Event POLR.6
        A packet was received from specified address for specified address, on
        specified interface. Packet length and protocol are also shown. This
        packet did not match the specified route map."
    ::= { polrEventsGroup 6 }

polr6_srcaddr OBJECT-TYPE
    SYNTAX IpAddress
    MAX-ACCESS accessible-for-notify
    STATUS current
    DESCRIPTION
        "Parameter 'srcaddr' in event POLR.6"
    ::= { polrEventObjects6 1 }

polr6_dstaddr OBJECT-TYPE
    SYNTAX IpAddress
    MAX-ACCESS accessible-for-notify
    STATUS current
    DESCRIPTION
        "Parameter 'dstaddr' in event POLR.6"
    ::= { polrEventObjects6 2 }

polr6_length OBJECT-TYPE
    SYNTAX Integer32
    MAX-ACCESS accessible-for-notify
    STATUS current
    DESCRIPTION
        "Parameter 'length' in event POLR.6"
    ::= { polrEventObjects6 3 }

polr6_protocol OBJECT-TYPE
    SYNTAX Integer32
    MAX-ACCESS accessible-for-notify
    STATUS current
    DESCRIPTION
        "Parameter 'protocol' in event POLR.6"
    ::= { polrEventObjects6 4 }

polr6_interface OBJECT-TYPE
    SYNTAX DisplayString
    MAX-ACCESS accessible-for-notify
    STATUS current
    DESCRIPTION
        "Parameter 'interface' in event POLR.6"
    ::= { polrEventObjects6 5 }

polr6_routemap OBJECT-TYPE
    SYNTAX DisplayString
    MAX-ACCESS accessible-for-notify
    STATUS current
    DESCRIPTION
        "Parameter 'routemap' in event POLR.6"
    ::= { polrEventObjects6 6 }

polrEventObjects7 OBJECT-IDENTITY
    STATUS current
    DESCRIPTION
        "Event POLR.7
        A packet was generated from specified address for specified address.
        Packet length and protocol are also shown. This packet did match the
        specified entry of the specified route map."
    ::= { polrEventsGroup 7 }

polr7_srcaddr OBJECT-TYPE
    SYNTAX IpAddress
    MAX-ACCESS accessible-for-notify
    STATUS current
    DESCRIPTION
        "Parameter 'srcaddr' in event POLR.7"
    ::= { polrEventObjects7 1 }

polr7_dstaddr OBJECT-TYPE
    SYNTAX IpAddress
    MAX-ACCESS accessible-for-notify
    STATUS current
    DESCRIPTION
        "Parameter 'dstaddr' in event POLR.7"
    ::= { polrEventObjects7 2 }

polr7_length OBJECT-TYPE
    SYNTAX Integer32
    MAX-ACCESS accessible-for-notify
    STATUS current
    DESCRIPTION
        "Parameter 'length' in event POLR.7"
    ::= { polrEventObjects7 3 }

polr7_protocol OBJECT-TYPE
    SYNTAX Integer32
    MAX-ACCESS accessible-for-notify
    STATUS current
    DESCRIPTION
        "Parameter 'protocol' in event POLR.7"
    ::= { polrEventObjects7 4 }

polr7_routemap OBJECT-TYPE
    SYNTAX DisplayString
    MAX-ACCESS accessible-for-notify
    STATUS current
    DESCRIPTION
        "Parameter 'routemap' in event POLR.7"
    ::= { polrEventObjects7 5 }

polr7_entrynumber OBJECT-TYPE
    SYNTAX Integer32
    MAX-ACCESS accessible-for-notify
    STATUS current
    DESCRIPTION
        "Parameter 'entrynumber' in event POLR.7"
    ::= { polrEventObjects7 6 }

polrEventObjects8 OBJECT-IDENTITY
    STATUS current
    DESCRIPTION
        "Event POLR.8
        A packet was received from specified address for specified address, on
        specified interface. Packet length and protocol are also shown. This
        packet did match the specified entry of the specified route map."
    ::= { polrEventsGroup 8 }

polr8_srcaddr OBJECT-TYPE
    SYNTAX IpAddress
    MAX-ACCESS accessible-for-notify
    STATUS current
    DESCRIPTION
        "Parameter 'srcaddr' in event POLR.8"
    ::= { polrEventObjects8 1 }

polr8_dstaddr OBJECT-TYPE
    SYNTAX IpAddress
    MAX-ACCESS accessible-for-notify
    STATUS current
    DESCRIPTION
        "Parameter 'dstaddr' in event POLR.8"
    ::= { polrEventObjects8 2 }

polr8_length OBJECT-TYPE
    SYNTAX Integer32
    MAX-ACCESS accessible-for-notify
    STATUS current
    DESCRIPTION
        "Parameter 'length' in event POLR.8"
    ::= { polrEventObjects8 3 }

polr8_protocol OBJECT-TYPE
    SYNTAX Integer32
    MAX-ACCESS accessible-for-notify
    STATUS current
    DESCRIPTION
        "Parameter 'protocol' in event POLR.8"
    ::= { polrEventObjects8 4 }

polr8_interface OBJECT-TYPE
    SYNTAX DisplayString
    MAX-ACCESS accessible-for-notify
    STATUS current
    DESCRIPTION
        "Parameter 'interface' in event POLR.8"
    ::= { polrEventObjects8 5 }

polr8_routemap OBJECT-TYPE
    SYNTAX DisplayString
    MAX-ACCESS accessible-for-notify
    STATUS current
    DESCRIPTION
        "Parameter 'routemap' in event POLR.8"
    ::= { polrEventObjects8 6 }

polr8_entrynumber OBJECT-TYPE
    SYNTAX Integer32
    MAX-ACCESS accessible-for-notify
    STATUS current
    DESCRIPTION
        "Parameter 'entrynumber' in event POLR.8"
    ::= { polrEventObjects8 7 }

polrEventObjects9 OBJECT-IDENTITY
    STATUS current
    DESCRIPTION
        "Event POLR.9
        A packet was received from specified address for specified address. The
        tos field was changed from oldtos to newtos."
    ::= { polrEventsGroup 9 }

polr9_srcaddr OBJECT-TYPE
    SYNTAX IpAddress
    MAX-ACCESS accessible-for-notify
    STATUS current
    DESCRIPTION
        "Parameter 'srcaddr' in event POLR.9"
    ::= { polrEventObjects9 1 }

polr9_dstaddr OBJECT-TYPE
    SYNTAX IpAddress
    MAX-ACCESS accessible-for-notify
    STATUS current
    DESCRIPTION
        "Parameter 'dstaddr' in event POLR.9"
    ::= { polrEventObjects9 2 }

polr9_oldtos OBJECT-TYPE
    SYNTAX Integer32
    MAX-ACCESS accessible-for-notify
    STATUS current
    DESCRIPTION
        "Parameter 'oldtos' in event POLR.9"
    ::= { polrEventObjects9 3 }

polr9_newtos OBJECT-TYPE
    SYNTAX Integer32
    MAX-ACCESS accessible-for-notify
    STATUS current
    DESCRIPTION
        "Parameter 'newtos' in event POLR.9"
    ::= { polrEventObjects9 4 }

polrEventObjects10 OBJECT-IDENTITY
    STATUS current
    DESCRIPTION
        "Event POLR.10
        A packet was received from specified address for specified address. The
        next hop is set to the specified interface."
    ::= { polrEventsGroup 10 }

polr10_srcaddr OBJECT-TYPE
    SYNTAX IpAddress
    MAX-ACCESS accessible-for-notify
    STATUS current
    DESCRIPTION
        "Parameter 'srcaddr' in event POLR.10"
    ::= { polrEventObjects10 1 }

polr10_dstaddr OBJECT-TYPE
    SYNTAX IpAddress
    MAX-ACCESS accessible-for-notify
    STATUS current
    DESCRIPTION
        "Parameter 'dstaddr' in event POLR.10"
    ::= { polrEventObjects10 2 }

polr10_interface OBJECT-TYPE
    SYNTAX DisplayString
    MAX-ACCESS accessible-for-notify
    STATUS current
    DESCRIPTION
        "Parameter 'interface' in event POLR.10"
    ::= { polrEventObjects10 3 }

polrEventObjects11 OBJECT-IDENTITY
    STATUS current
    DESCRIPTION
        "Event POLR.11
        A packet was received from specified address for specified address. The
        next hop is set to the specified address."
    ::= { polrEventsGroup 11 }

polr11_srcaddr OBJECT-TYPE
    SYNTAX IpAddress
    MAX-ACCESS accessible-for-notify
    STATUS current
    DESCRIPTION
        "Parameter 'srcaddr' in event POLR.11"
    ::= { polrEventObjects11 1 }

polr11_dstaddr OBJECT-TYPE
    SYNTAX IpAddress
    MAX-ACCESS accessible-for-notify
    STATUS current
    DESCRIPTION
        "Parameter 'dstaddr' in event POLR.11"
    ::= { polrEventObjects11 2 }

polr11_nexthop OBJECT-TYPE
    SYNTAX IpAddress
    MAX-ACCESS accessible-for-notify
    STATUS current
    DESCRIPTION
        "Parameter 'nexthop' in event POLR.11"
    ::= { polrEventObjects11 3 }

polrEventObjects12 OBJECT-IDENTITY
    STATUS current
    DESCRIPTION
        "Event POLR.12
        A packet was received from specified address for specified address. The
        packet is forwarded based on routing table rather than policy routing."
    ::= { polrEventsGroup 12 }

polr12_srcaddr OBJECT-TYPE
    SYNTAX IpAddress
    MAX-ACCESS accessible-for-notify
    STATUS current
    DESCRIPTION
        "Parameter 'srcaddr' in event POLR.12"
    ::= { polrEventObjects12 1 }

polr12_dstaddr OBJECT-TYPE
    SYNTAX IpAddress
    MAX-ACCESS accessible-for-notify
    STATUS current
    DESCRIPTION
        "Parameter 'dstaddr' in event POLR.12"
    ::= { polrEventObjects12 2 }

polrEventObjects13 OBJECT-IDENTITY
    STATUS current
    DESCRIPTION
        "Event POLR.13
        A packet was received from specified address for specified address. The
        default next hop is set to the specified interface."
    ::= { polrEventsGroup 13 }

polr13_srcaddr OBJECT-TYPE
    SYNTAX IpAddress
    MAX-ACCESS accessible-for-notify
    STATUS current
    DESCRIPTION
        "Parameter 'srcaddr' in event POLR.13"
    ::= { polrEventObjects13 1 }

polr13_dstaddr OBJECT-TYPE
    SYNTAX IpAddress
    MAX-ACCESS accessible-for-notify
    STATUS current
    DESCRIPTION
        "Parameter 'dstaddr' in event POLR.13"
    ::= { polrEventObjects13 2 }

polr13_interface OBJECT-TYPE
    SYNTAX DisplayString
    MAX-ACCESS accessible-for-notify
    STATUS current
    DESCRIPTION
        "Parameter 'interface' in event POLR.13"
    ::= { polrEventObjects13 3 }

polrEventObjects14 OBJECT-IDENTITY
    STATUS current
    DESCRIPTION
        "Event POLR.14
        A packet was received from specified address for specified address. The
        default next hop is set to the specified address."
    ::= { polrEventsGroup 14 }

polr14_srcaddr OBJECT-TYPE
    SYNTAX IpAddress
    MAX-ACCESS accessible-for-notify
    STATUS current
    DESCRIPTION
        "Parameter 'srcaddr' in event POLR.14"
    ::= { polrEventObjects14 1 }

polr14_dstaddr OBJECT-TYPE
    SYNTAX IpAddress
    MAX-ACCESS accessible-for-notify
    STATUS current
    DESCRIPTION
        "Parameter 'dstaddr' in event POLR.14"
    ::= { polrEventObjects14 2 }

polr14_nexthop OBJECT-TYPE
    SYNTAX IpAddress
    MAX-ACCESS accessible-for-notify
    STATUS current
    DESCRIPTION
        "Parameter 'nexthop' in event POLR.14"
    ::= { polrEventObjects14 3 }

polrEventObjects15 OBJECT-IDENTITY
    STATUS current
    DESCRIPTION
        "Event POLR.15
        A packet was received from specified address for specified address. No
        specific route was found for this packet, therefore default routing is
        performed."
    ::= { polrEventsGroup 15 }

polr15_srcaddr OBJECT-TYPE
    SYNTAX IpAddress
    MAX-ACCESS accessible-for-notify
    STATUS current
    DESCRIPTION
        "Parameter 'srcaddr' in event POLR.15"
    ::= { polrEventObjects15 1 }

polr15_dstaddr OBJECT-TYPE
    SYNTAX IpAddress
    MAX-ACCESS accessible-for-notify
    STATUS current
    DESCRIPTION
        "Parameter 'dstaddr' in event POLR.15"
    ::= { polrEventObjects15 2 }

polrEventObjects16 OBJECT-IDENTITY
    STATUS current
    DESCRIPTION
        "Event POLR.16
        A packet was received from specified address for specified address. The
        DF bit was changed from oldDF to newDF."
    ::= { polrEventsGroup 16 }

polr16_srcaddr OBJECT-TYPE
    SYNTAX IpAddress
    MAX-ACCESS accessible-for-notify
    STATUS current
    DESCRIPTION
        "Parameter 'srcaddr' in event POLR.16"
    ::= { polrEventObjects16 1 }

polr16_dstaddr OBJECT-TYPE
    SYNTAX IpAddress
    MAX-ACCESS accessible-for-notify
    STATUS current
    DESCRIPTION
        "Parameter 'dstaddr' in event POLR.16"
    ::= { polrEventObjects16 2 }

polr16_oldDF OBJECT-TYPE
    SYNTAX Integer32
    MAX-ACCESS accessible-for-notify
    STATUS current
    DESCRIPTION
        "Parameter 'oldDF' in event POLR.16"
    ::= { polrEventObjects16 3 }

polr16_newDF OBJECT-TYPE
    SYNTAX Integer32
    MAX-ACCESS accessible-for-notify
    STATUS current
    DESCRIPTION
        "Parameter 'newDF' in event POLR.16"
    ::= { polrEventObjects16 4 }

polrEventObjects17 OBJECT-IDENTITY
    STATUS current
    DESCRIPTION
        "Event POLR.17
        A packet was received from specified address for specified address. The
        packet will be processed locally."
    ::= { polrEventsGroup 17 }

polr17_srcaddr OBJECT-TYPE
    SYNTAX IpAddress
    MAX-ACCESS accessible-for-notify
    STATUS current
    DESCRIPTION
        "Parameter 'srcaddr' in event POLR.17"
    ::= { polrEventObjects17 1 }

polr17_dstaddr OBJECT-TYPE
    SYNTAX IpAddress
    MAX-ACCESS accessible-for-notify
    STATUS current
    DESCRIPTION
        "Parameter 'dstaddr' in event POLR.17"
    ::= { polrEventObjects17 2 }

polrEventObjects18 OBJECT-IDENTITY
    STATUS current
    DESCRIPTION
        "Event POLR.18
        A packet was received from specified address for specified address. The
        packet will be processed locally by default."
    ::= { polrEventsGroup 18 }

polr18_srcaddr OBJECT-TYPE
    SYNTAX IpAddress
    MAX-ACCESS accessible-for-notify
    STATUS current
    DESCRIPTION
        "Parameter 'srcaddr' in event POLR.18"
    ::= { polrEventObjects18 1 }

polr18_dstaddr OBJECT-TYPE
    SYNTAX IpAddress
    MAX-ACCESS accessible-for-notify
    STATUS current
    DESCRIPTION
        "Parameter 'dstaddr' in event POLR.18"
    ::= { polrEventObjects18 2 }

polrEventObjects19 OBJECT-IDENTITY
    STATUS current
    DESCRIPTION
        "Event POLR.19
        A packet was received from specified address for specified address. Its
        label value was changed from oldvalue to newvalue."
    ::= { polrEventsGroup 19 }

polr19_srcaddr OBJECT-TYPE
    SYNTAX IpAddress
    MAX-ACCESS accessible-for-notify
    STATUS current
    DESCRIPTION
        "Parameter 'srcaddr' in event POLR.19"
    ::= { polrEventObjects19 1 }

polr19_dstaddr OBJECT-TYPE
    SYNTAX IpAddress
    MAX-ACCESS accessible-for-notify
    STATUS current
    DESCRIPTION
        "Parameter 'dstaddr' in event POLR.19"
    ::= { polrEventObjects19 2 }

polr19_oldlabel OBJECT-TYPE
    SYNTAX Integer32
    MAX-ACCESS accessible-for-notify
    STATUS current
    DESCRIPTION
        "Parameter 'oldlabel' in event POLR.19"
    ::= { polrEventObjects19 3 }

polr19_newlabel OBJECT-TYPE
    SYNTAX Integer32
    MAX-ACCESS accessible-for-notify
    STATUS current
    DESCRIPTION
        "Parameter 'newlabel' in event POLR.19"
    ::= { polrEventObjects19 4 }

polrEventObjects20 OBJECT-IDENTITY
    STATUS current
    DESCRIPTION
        "Event POLR.20
        A packet was received from specified address for specified address. The
        AFS session mark was changed from oldmark to newmark."
    ::= { polrEventsGroup 20 }

polr20_srcaddr OBJECT-TYPE
    SYNTAX IpAddress
    MAX-ACCESS accessible-for-notify
    STATUS current
    DESCRIPTION
        "Parameter 'srcaddr' in event POLR.20"
    ::= { polrEventObjects20 1 }

polr20_dstaddr OBJECT-TYPE
    SYNTAX IpAddress
    MAX-ACCESS accessible-for-notify
    STATUS current
    DESCRIPTION
        "Parameter 'dstaddr' in event POLR.20"
    ::= { polrEventObjects20 2 }

polr20_oldmark OBJECT-TYPE
    SYNTAX Integer32
    MAX-ACCESS accessible-for-notify
    STATUS current
    DESCRIPTION
        "Parameter 'oldmark' in event POLR.20"
    ::= { polrEventObjects20 3 }

polr20_newmark OBJECT-TYPE
    SYNTAX Integer32
    MAX-ACCESS accessible-for-notify
    STATUS current
    DESCRIPTION
        "Parameter 'newmark' in event POLR.20"
    ::= { polrEventObjects20 4 }


polrNotification1 NOTIFICATION-TYPE
    OBJECTS { 
              polr1_srcaddr, 
              polr1_dstaddr,
              polr1_length,
              polr1_protocol 
            }
    STATUS current
    DESCRIPTION
        "Notification of Event POLR.1

        Message: 'test local packet from $1 for $2 of length $3 protocol $4'

        Parameters list:
              $1: polr1_srcaddr
              $2: polr1_dstaddr
              $3: polr1_length
              $4: polr1_protocol

        A packet was generated from specified address for specified address.
        Packet length and protocol are also shown. This packet will be tested
        for policy routing."
    ::= { polrNotificationsPrefix 1 }

polrNotification2 NOTIFICATION-TYPE
    OBJECTS { 
              polr2_srcaddr, 
              polr2_dstaddr,
              polr2_length,
              polr2_protocol,
              polr2_interface 
            }
    STATUS current
    DESCRIPTION
        "Notification of Event POLR.2

        Message: 'test packet from $1 for $2 of length $3 protocol $4 from interface $5'

        Parameters list:
              $1: polr2_srcaddr
              $2: polr2_dstaddr
              $3: polr2_length
              $4: polr2_protocol
              $5: polr2_interface

        A packet was received from specified address for specified address, on
        specified interface. Packet length and protocol are also shown. This
        packet will be tested for policy routing."
    ::= { polrNotificationsPrefix 2 }

polrNotification3 NOTIFICATION-TYPE
    STATUS current
    DESCRIPTION
        "Notification of Event POLR.3

        Message: 'local policy routing disabled'

        No route map associated to locally generated packets."
    ::= { polrNotificationsPrefix 3 }

polrNotification4 NOTIFICATION-TYPE
    OBJECTS { 
              polr4_interface 
            }
    STATUS current
    DESCRIPTION
        "Notification of Event POLR.4

        Message: 'policy routing disabled on interface $1'

        Parameters list:
              $1: polr4_interface

        No route map associated to specified interface."
    ::= { polrNotificationsPrefix 4 }

polrNotification5 NOTIFICATION-TYPE
    OBJECTS { 
              polr5_srcaddr, 
              polr5_dstaddr,
              polr5_length,
              polr5_protocol,
              polr5_routemap 
            }
    STATUS current
    DESCRIPTION
        "Notification of Event POLR.5

        Message: 'missed local packet from $1 for $2 of length $3 protocol $4 with route map $5'

        Parameters list:
              $1: polr5_srcaddr
              $2: polr5_dstaddr
              $3: polr5_length
              $4: polr5_protocol
              $5: polr5_routemap

        A packet was generated from specified address for specified address.
        Packet length and protocol are also shown. This packet did not match the
        specified route map."
    ::= { polrNotificationsPrefix 5 }

polrNotification6 NOTIFICATION-TYPE
    OBJECTS { 
              polr6_srcaddr, 
              polr6_dstaddr,
              polr6_length,
              polr6_protocol,
              polr6_interface,
              polr6_routemap 
            }
    STATUS current
    DESCRIPTION
        "Notification of Event POLR.6

        Message: 'missed packet from $1 for $2 of length $3 protocol $4 interface $5 with route map $6'

        Parameters list:
              $1: polr6_srcaddr
              $2: polr6_dstaddr
              $3: polr6_length
              $4: polr6_protocol
              $5: polr6_interface
              $6: polr6_routemap

        A packet was received from specified address for specified address, on
        specified interface. Packet length and protocol are also shown. This
        packet did not match the specified route map."
    ::= { polrNotificationsPrefix 6 }

polrNotification7 NOTIFICATION-TYPE
    OBJECTS { 
              polr7_srcaddr, 
              polr7_dstaddr,
              polr7_length,
              polr7_protocol,
              polr7_routemap,
              polr7_entrynumber 
            }
    STATUS current
    DESCRIPTION
        "Notification of Event POLR.7

        Message: 'match of local packet from $1 for $2 of length $3 protocol $4 with route map $5 entry $6'

        Parameters list:
              $1: polr7_srcaddr
              $2: polr7_dstaddr
              $3: polr7_length
              $4: polr7_protocol
              $5: polr7_routemap
              $6: polr7_entrynumber

        A packet was generated from specified address for specified address.
        Packet length and protocol are also shown. This packet did match the
        specified entry of the specified route map."
    ::= { polrNotificationsPrefix 7 }

polrNotification8 NOTIFICATION-TYPE
    OBJECTS { 
              polr8_srcaddr, 
              polr8_dstaddr,
              polr8_length,
              polr8_protocol,
              polr8_interface,
              polr8_routemap,
              polr8_entrynumber 
            }
    STATUS current
    DESCRIPTION
        "Notification of Event POLR.8

        Message: 'match of packet from $1 for $2 of length $3 protocol $4 interface $5 with route map $6 entry $7'

        Parameters list:
              $1: polr8_srcaddr
              $2: polr8_dstaddr
              $3: polr8_length
              $4: polr8_protocol
              $5: polr8_interface
              $6: polr8_routemap
              $7: polr8_entrynumber

        A packet was received from specified address for specified address, on
        specified interface. Packet length and protocol are also shown. This
        packet did match the specified entry of the specified route map."
    ::= { polrNotificationsPrefix 8 }

polrNotification9 NOTIFICATION-TYPE
    OBJECTS { 
              polr9_srcaddr, 
              polr9_dstaddr,
              polr9_oldtos,
              polr9_newtos 
            }
    STATUS current
    DESCRIPTION
        "Notification of Event POLR.9

        Message: 'set packet from $1 for $2 field tos changed from 0x$3 to 0x$4'

        Parameters list:
              $1: polr9_srcaddr
              $2: polr9_dstaddr
              $3: polr9_oldtos
              $4: polr9_newtos

        A packet was received from specified address for specified address. The
        tos field was changed from oldtos to newtos."
    ::= { polrNotificationsPrefix 9 }

polrNotification10 NOTIFICATION-TYPE
    OBJECTS { 
              polr10_srcaddr, 
              polr10_dstaddr,
              polr10_interface 
            }
    STATUS current
    DESCRIPTION
        "Notification of Event POLR.10

        Message: 'set packet from $1 for $2 next hop interface $3'

        Parameters list:
              $1: polr10_srcaddr
              $2: polr10_dstaddr
              $3: polr10_interface

        A packet was received from specified address for specified address. The
        next hop is set to the specified interface."
    ::= { polrNotificationsPrefix 10 }

polrNotification11 NOTIFICATION-TYPE
    OBJECTS { 
              polr11_srcaddr, 
              polr11_dstaddr,
              polr11_nexthop 
            }
    STATUS current
    DESCRIPTION
        "Notification of Event POLR.11

        Message: 'set packet from $1 for $2 next hop $3'

        Parameters list:
              $1: polr11_srcaddr
              $2: polr11_dstaddr
              $3: polr11_nexthop

        A packet was received from specified address for specified address. The
        next hop is set to the specified address."
    ::= { polrNotificationsPrefix 11 }

polrNotification12 NOTIFICATION-TYPE
    OBJECTS { 
              polr12_srcaddr, 
              polr12_dstaddr 
            }
    STATUS current
    DESCRIPTION
        "Notification of Event POLR.12

        Message: 'forward packet from $1 for $2 with routing table'

        Parameters list:
              $1: polr12_srcaddr
              $2: polr12_dstaddr

        A packet was received from specified address for specified address. The
        packet is forwarded based on routing table rather than policy routing."
    ::= { polrNotificationsPrefix 12 }

polrNotification13 NOTIFICATION-TYPE
    OBJECTS { 
              polr13_srcaddr, 
              polr13_dstaddr,
              polr13_interface 
            }
    STATUS current
    DESCRIPTION
        "Notification of Event POLR.13

        Message: 'set packet from $1 for $2 default next hop interface $3'

        Parameters list:
              $1: polr13_srcaddr
              $2: polr13_dstaddr
              $3: polr13_interface

        A packet was received from specified address for specified address. The
        default next hop is set to the specified interface."
    ::= { polrNotificationsPrefix 13 }

polrNotification14 NOTIFICATION-TYPE
    OBJECTS { 
              polr14_srcaddr, 
              polr14_dstaddr,
              polr14_nexthop 
            }
    STATUS current
    DESCRIPTION
        "Notification of Event POLR.14

        Message: 'set packet from $1 for $2 default next hop $3'

        Parameters list:
              $1: polr14_srcaddr
              $2: polr14_dstaddr
              $3: polr14_nexthop

        A packet was received from specified address for specified address. The
        default next hop is set to the specified address."
    ::= { polrNotificationsPrefix 14 }

polrNotification15 NOTIFICATION-TYPE
    OBJECTS { 
              polr15_srcaddr, 
              polr15_dstaddr 
            }
    STATUS current
    DESCRIPTION
        "Notification of Event POLR.15

        Message: 'default routing for packet from $1 for $2'

        Parameters list:
              $1: polr15_srcaddr
              $2: polr15_dstaddr

        A packet was received from specified address for specified address. No
        specific route was found for this packet, therefore default routing is
        performed."
    ::= { polrNotificationsPrefix 15 }

polrNotification16 NOTIFICATION-TYPE
    OBJECTS { 
              polr16_srcaddr, 
              polr16_dstaddr,
              polr16_oldDF,
              polr16_newDF 
            }
    STATUS current
    DESCRIPTION
        "Notification of Event POLR.16

        Message: 'set packet from $1 for $2 DF bit changed from $3 to $4'

        Parameters list:
              $1: polr16_srcaddr
              $2: polr16_dstaddr
              $3: polr16_oldDF
              $4: polr16_newDF

        A packet was received from specified address for specified address. The
        DF bit was changed from oldDF to newDF."
    ::= { polrNotificationsPrefix 16 }

polrNotification17 NOTIFICATION-TYPE
    OBJECTS { 
              polr17_srcaddr, 
              polr17_dstaddr 
            }
    STATUS current
    DESCRIPTION
        "Notification of Event POLR.17

        Message: 'packet from $1 for $2 will be processed locally'

        Parameters list:
              $1: polr17_srcaddr
              $2: polr17_dstaddr

        A packet was received from specified address for specified address. The
        packet will be processed locally."
    ::= { polrNotificationsPrefix 17 }

polrNotification18 NOTIFICATION-TYPE
    OBJECTS { 
              polr18_srcaddr, 
              polr18_dstaddr 
            }
    STATUS current
    DESCRIPTION
        "Notification of Event POLR.18

        Message: 'packet from $1 for $2 will be processed locally by default'

        Parameters list:
              $1: polr18_srcaddr
              $2: polr18_dstaddr

        A packet was received from specified address for specified address. The
        packet will be processed locally by default."
    ::= { polrNotificationsPrefix 18 }

polrNotification19 NOTIFICATION-TYPE
    OBJECTS { 
              polr19_srcaddr, 
              polr19_dstaddr,
              polr19_oldlabel,
              polr19_newlabel 
            }
    STATUS current
    DESCRIPTION
        "Notification of Event POLR.19

        Message: 'set packet from $1 for $2 field label changed from $3 to $4'

        Parameters list:
              $1: polr19_srcaddr
              $2: polr19_dstaddr
              $3: polr19_oldlabel
              $4: polr19_newlabel

        A packet was received from specified address for specified address. Its
        label value was changed from oldvalue to newvalue."
    ::= { polrNotificationsPrefix 19 }

polrNotification20 NOTIFICATION-TYPE
    OBJECTS { 
              polr20_srcaddr, 
              polr20_dstaddr,
              polr20_oldmark,
              polr20_newmark 
            }
    STATUS current
    DESCRIPTION
        "Notification of Event POLR.20

        Message: 'set packet from $1 for $2 AFS session mark changed from $3 to $4'

        Parameters list:
              $1: polr20_srcaddr
              $2: polr20_dstaddr
              $3: polr20_oldmark
              $4: polr20_newmark

        A packet was received from specified address for specified address. The
        AFS session mark was changed from oldmark to newmark."
    ::= { polrNotificationsPrefix 20 }


END
