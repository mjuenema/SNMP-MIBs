-- ==================================================================
--  Copyright © 1999 - 2008 Siemens Enterprise Communications
--
--  All Rights Reserved.
--
--  Reproduction of this document is authorized on condition that
--  this copyright notice is included.
--
--  This MIB document embodies proprietary intellectual property. 
--  of Siemens Network Convergence LLC, which retains all title and
--  ownership in this MIB, including any revisions.
--
--  This module will be extended, as required.
--
--  Siemens Network Convergence LLC reserves the right to make 
--  changes in specification and other information contained in this 
--  document without prior notice. The reader should consult 
--  Siemens Network Convergence LLC to determine whether any such
--  changes have been made.
--
--  Copyright © 1999 - 2008 Siemens Enterprise Communications
-- ==================================================================

-- ***********************************************************************
-- Revision History
--  08/31/99      Mangping Chang      initial code
--  01/31/00      Mangping Chang      Unisphere renaming
--  04/04/00      Mangping Chang      MIB review meeting update 
--  07/18/00      Mangping Chang      Add Statistics Counters
--  08/10/00      Vidya S. Pandey     removed all the traps
--  02/20/02      Mangping Chang      Add more statistics Counters
--  04/04/02      Mangping Chang      Added description for supported 
--                                    variant for each counter.
--  05/23/02      Mangping Chang      Updated description for C release
--  07/23/02      Mangping Chang      Changed timer max value to 2147483647
--  12/17/02      Mangping Chang      Removed SIPT performance data and
--                                    regroup all the statistics counters 
--  05/08/03      Polly Yu            Updated copyright text
--  06/10/03      Mangping Chang      Added SipT call type counters
--  11/16/05      Magnping Chang      Modified the range for CDR timeout timer 
--  10/24/06      Mangping Chang      Depreciated usSrxUceAnswerTimeout
--  12/12/06      Carlos Gregorio     Removed OMAP references for R12 - FRN2271 - Decommission PRI
--  04/10/08      C. Chatzidimitriou  FRN3208. Cleanup of MIBS 
--  06/12/2008    C. Chatzidimitriou  Updated MIB to be fully compatible with SNMPv2 
-- ***********************************************************************

US-SRX-UCE-MIB DEFINITIONS ::= BEGIN

IMPORTS
    MODULE-IDENTITY, OBJECT-TYPE, Counter32
        FROM SNMPv2-SMI
    surpassRtp
	FROM SURPASS-RTP-MIB
    hiq8000Admin
        FROM SURPASS-RTP-ADMIN-MIB;

--########################################################
-- SRX Universal Call Engine  MIB MODULE                 #
--########################################################

usSrxUce MODULE-IDENTITY
    LAST-UPDATED "200806111500Z"
    ORGANIZATION "Siemens Network Convergence LLC"
    CONTACT-INFO " "
    DESCRIPTION
        " SRX Universal Call Engine MIB module. " 
        
    REVISION "200806111500Z"    
    DESCRIPTION
            "Updated the MIB to be fully compatible with SNMPv2"

    ::= { hiq8000Admin 1 }

--####################
-- OBJECT IDENTIFIER #
--####################

usSrxUceObjects              OBJECT IDENTIFIER      ::= { usSrxUce 1 } 

usSrxUcePerformData          OBJECT IDENTIFIER      ::= { usSrxUceObjects 1 }

usSrxUcePerfGeneral          OBJECT IDENTIFIER      ::= {usSrxUcePerformData 1 } 

usSrxUcePerfSipCalls         OBJECT IDENTIFIER      ::= {usSrxUcePerformData 2 }

-- *****************************************************************
-- UCE Performance  Data
-- Every statistics counter will be shared by all instances of the
-- UCE process.
-- *****************************************************************
--
-- UCE statistics counters of Completed and Aborted Calls 

usSrxUceIncomingHalfCallsCounter     OBJECT-TYPE
    SYNTAX      Counter32
    MAX-ACCESS  read-only
    STATUS      current
    DESCRIPTION
        " This object refers to the total number of incoming half  
          calls. "
    ::= { usSrxUcePerfGeneral 1  }

usSrxUceForwardReleaseCounter     OBJECT-TYPE
    SYNTAX      Counter32
    MAX-ACCESS  read-only
    STATUS      current
    DESCRIPTION
        " This object refers to the total number of forward Release  
          calls. "
    ::= { usSrxUcePerfGeneral 2  }

usSrxUceOutgoingHalfCallsCounter     OBJECT-TYPE
    SYNTAX      Counter32
    MAX-ACCESS  read-only
    STATUS      current
    DESCRIPTION
        " This object refers to the total number of outgoing half  
          calls. "
    ::= { usSrxUcePerfGeneral 3  }

usSrxUceCallsReachAddrCompleteCounter     OBJECT-TYPE
    SYNTAX      Counter32
    MAX-ACCESS  read-only
    STATUS      current
    DESCRIPTION
        " This object refers to the total number of calls reaching 
          address completion. "
    ::= { usSrxUcePerfGeneral 4  }

usSrxUceCallsReachAnswerCounter     OBJECT-TYPE
    SYNTAX      Counter32
    MAX-ACCESS  read-only
    STATUS      current
    DESCRIPTION
        " This object refers to the total number of calls reaching  
          answering. "
    ::= { usSrxUcePerfGeneral 5  }

usSrxUceBackwardReleaseCounter     OBJECT-TYPE
    SYNTAX      Counter32
    MAX-ACCESS  read-only
    STATUS      current
    DESCRIPTION
        " This object refers to the total number of backward release  
          calls. "
    ::= { usSrxUcePerfGeneral 6  }

usSrxUceTotalReleaseCounter     OBJECT-TYPE
    SYNTAX      Counter32
    MAX-ACCESS  read-only
    STATUS      current
    DESCRIPTION
        " This object refers to the total number of total release
          calls."
    ::= { usSrxUcePerfGeneral 7 }

usSrxUceAbortForUnavailableResourcesCounter     OBJECT-TYPE
    SYNTAX      Counter32
    MAX-ACCESS  read-only
    STATUS      current
    DESCRIPTION
        " This object refers to the total number of abort calls
          caused by unavailable resources."
    ::= { usSrxUcePerfGeneral 8 }

usSrxUceAbortForNoRouteAvailableCounter     OBJECT-TYPE
    SYNTAX      Counter32
    MAX-ACCESS  read-only
    STATUS      current
    DESCRIPTION
         " This object refers to the total number of abort calls
           caused by no route availabe ."
    ::= { usSrxUcePerfGeneral 9 }

usSrxUceAbortForNoTrunkAvailableCounter     OBJECT-TYPE
    SYNTAX      Counter32
    MAX-ACCESS  read-only
    STATUS      current
    DESCRIPTION
        " This object refers to the total number of abort calls
          caused by no trunk availabe."
    ::= { usSrxUcePerfGeneral 10 }

usSrxUceAbortForGatewayResourceUnavailableCounter     OBJECT-TYPE
    SYNTAX      Counter32
    MAX-ACCESS  read-only
    STATUS      current
    DESCRIPTION
        " This object refers to the total number of abort calls
          caused by gateway resources unavailable."
    ::= { usSrxUcePerfGeneral 11 }

usSrxUceAbortForCodecUnavailableCounter     OBJECT-TYPE
    SYNTAX      Counter32
    MAX-ACCESS  read-only
    STATUS      current
    DESCRIPTION
        " This object refers to the total number of abort calls
          caused by codec unavailable."
    ::= { usSrxUcePerfGeneral 12 }

usSrxUceAbortForAuthFailCounter     OBJECT-TYPE
    SYNTAX      Counter32
    MAX-ACCESS  read-only
    STATUS      current
    DESCRIPTION
        " This object refers to the total number of abort calls
          caused by authorization failure."
    ::= { usSrxUcePerfGeneral 13 }

usSrxUceAbortForMiscErrorCounter     OBJECT-TYPE
    SYNTAX      Counter32
    MAX-ACCESS  read-only
    STATUS      current
    DESCRIPTION
        " This object refers to the total number of abort calls
          because of other misc error."
    ::= { usSrxUcePerfGeneral 14 }

usSrxUceTermToTreatmentCounter     OBJECT-TYPE
    SYNTAX      Counter32
    MAX-ACCESS  read-only
    STATUS      current
    DESCRIPTION
        " This object refers to the total number of terminated
          calls to treatment. "
    ::= { usSrxUcePerfGeneral 15 }

-- *****************************************************************
-- UCE Performance  Data
-- Sip to other Signal Managers interworking calls statistics data
-- *****************************************************************

usSrxUceSipToMgcpCounter     OBJECT-TYPE
    SYNTAX      Counter32
    MAX-ACCESS  read-only
    STATUS      current
    DESCRIPTION
        " This object refers to the total number of Sip to Mgcp calls."
    ::= { usSrxUcePerfSipCalls 1 }


usSrxUceSipToSipCounter     OBJECT-TYPE
    SYNTAX      Counter32
    MAX-ACCESS  read-only
    STATUS      current
    DESCRIPTION
        " This object refers to the total number of Sip to Sip calls."
    ::= { usSrxUcePerfSipCalls 2 }

END
