TROPIC-SHELF-MIB DEFINITIONS ::= BEGIN

-- (c) Copyright 2016 Nokia.  All rights reserved.
-- This software is the confidential and proprietary property of
-- Nokia and may only be used in accordance with the
-- terms of the license agreement provided with this software.

 IMPORTS
      SnmpAdminString                         FROM SNMP-FRAMEWORK-MIB
      OBJECT-TYPE, MODULE-IDENTITY,
      Unsigned32, Integer32                   FROM SNMPv2-SMI
      MODULE-COMPLIANCE, OBJECT-GROUP         FROM SNMPv2-CONF
      TEXTUAL-CONVENTION,
      TruthValue                              FROM SNMPv2-TC
      TropicShelfIndexType,
      TropicCardCLEI,
      TropicCardManufacturingPartNumber,
      TropicCardSerialNumber,
      TropicLEDColorType,
      TropicLEDStateType,
      TnCommand,
      AluWdmWtClkValues,
      TnRackSize                              FROM TROPIC-TC
      tnShelfModules, tnShelfMIB              FROM TROPIC-GLOBAL-REG;

  tnShelfMibModule MODULE-IDENTITY
      LAST-UPDATED    "201606031200Z"
      ORGANIZATION    "Nokia"
      CONTACT-INFO    "Nokia
                       Postal: 600 March Rd.
                       Kanata, Ontario
                       Canada K2K 2E6

                       Phone: +1 613 591 3600
                       Fax:   +1 613 591 3680"

      DESCRIPTION "The shelf MIB for Nokia network elements."

      REVISION    "200802161200Z"
      DESCRIPTION "1) Updated the description for the shelf MIB.
                   2) Added the expected amps shelf attribute."

      REVISION    "200803061200Z"
      DESCRIPTION "Changed the expected amps shelf attribute SYNTAX
                   from Unsigned32 to an enumerated integer."

      REVISION    "200804051200Z"
      DESCRIPTION "Changed tnShelfInhibitLossComms to tnShelfIsUnmanaged."

      REVISION    "200805291200Z"
      DESCRIPTION "1) Added tnShelfSerialNumber.
                   2) Added tnShelfAINS."

      REVISION    "200806051200Z"
      DESCRIPTION "Added tnShelfInhibitAutoSwitching."

      REVISION    "200904271200Z"
      DESCRIPTION "Updated the description for tnShelfSerialNumber to
                   include ITLB."

      REVISION    "200905191200Z"
      DESCRIPTION "Added tnShelfStatusLEDColor and tnShelfStatusLEDState."

      REVISION    "200906071200Z"
      DESCRIPTION "Added TropicLEDColorType and TropicLEDStateType to
                   IMPORTS list."

      REVISION    "200907151200Z"
      DESCRIPTION "Added amps20(4) to tnShelfExpectedAmps."

      REVISION    "200909091200Z"
      DESCRIPTION "Added auto(5) to tnShelfExpectedAmps."

      REVISION    "200909151200Z"
      DESCRIPTION "Made auto(5) the default for tnShelfExpectedAmps."

      REVISION    "200912111200Z"
      DESCRIPTION "Added tnShelfWTMode."

      REVISION    "201006041200Z"
      DESCRIPTION "Added tnShelfRiDataTable for PSS4."

      REVISION    "201006281200Z"
      DESCRIPTION "Added the following to tnShelfExpectedAmps:
                   amps35(6)
                   amps5(7)
                   amps7(8)."

      REVISION    "201009131200Z"
      DESCRIPTION "Added the following to tnShelfExpectedAmps:
                   amps100(9)
                   amps150(10)."

      REVISION    "201010041200Z"
      DESCRIPTION "1) Added the following to tnShelfExpectedAmps:
                      amps60(11).
                   2) Updated description of tnShelfExpectedAmps per new
                      requirements."

      REVISION    "201010121200Z"
      DESCRIPTION "Added the following to tnShelfExpectedAmps for PSS64:
                   amps275(12)."

      REVISION    "201012161200Z"
      DESCRIPTION "Added the following to tnShelfTable:
                   tnShelfMateMt0cReadyToProtect
                   tnShelfActivityMt0cSwitch."

      REVISION    "201102061200Z"
      DESCRIPTION "Added the following to tnShelfExpectedAmps:
                   amps2x50(13)
                   amps2x60(14)
                   amps3x60(15)."

      REVISION    "201104071200Z"
      DESCRIPTION "Added the following to tnShelfExpectedAmps:
                   amps20dot6(16)
                   amps8dot5(17)
                   amps3dot7(18)."

      REVISION    "201202061200Z"
      DESCRIPTION "Added the following to tnShelfExpectedAmps:
                   ampsMix(19)."

      REVISION    "201202231200Z"
      DESCRIPTION "Added the following to tnShelfTable:
                   tnShelfExpectedPfa
                   tnShelfExpectedPfb."

      REVISION    "201203291200Z"
      DESCRIPTION "Added the following to tnShelfExpectedAmps:
                   amps4dot1(20)."

      REVISION    "201209061200Z"
      DESCRIPTION "Added the following to tnShelfTable:
                   tnShelfHighVoltageThreshold
                   tnShelfLowVoltageThreshold
                   tnShelfVoltageThresholdTol."

      REVISION    "201209251200Z"
      DESCRIPTION "1) Added the following to tnShelfExpectedAmps:
                      ampsNa(21),
                      to
                      amps320(23).
                   2) Added the following to tnShelfTable:
                      tnShelfExpectedVolts."

      REVISION    "201212141200Z"
      DESCRIPTION "Added the following to tnShelfTable:
                   tnShelfMatrixSize."

      REVISION    "201304291200Z"
      DESCRIPTION "Updated range and DESCRIPTIONs of the following:
                   tnShelfHighVoltageThreshold
                   tnShelfLowVoltageThreshold
                   tnShelfVoltageThresholdTol."

      REVISION    "201305211200Z"
      DESCRIPTION "Marked the following as obsolete:
                   tnShelfEvents."

      REVISION    "201308071200Z"
      DESCRIPTION "Added the following to tnShelfTable:
                   tnShelfVoltageFloor."

      REVISION    "201309061200Z"
      DESCRIPTION "Added the following to tnShelfTable:
                   tnShelfCalculatedLoad."

      REVISION    "201311141200Z"
      DESCRIPTION "Marked the following as obsolete:
                   tnShelfInhibitAutoSwitching."

      REVISION    "201312151200Z"
      DESCRIPTION "Added the following to tnShelfTable:
                   tnShelfClkSwitch."

      REVISION    "201402261200Z"
      DESCRIPTION "Added DEFVAL to attributes."

      REVISION    "201407251200Z"
      DESCRIPTION "Added the following to tnShelfTable:
                   tnShelfExpectedVoltsAC
                   tnShelfHighVoltageThresholdAC
                   tnShelfLowVoltageThresholdAC
                   tnShelfVoltageFloorAC
                   tnShelfExternalAcPower
                   tnShelfLoadWarningThreshold
                   tnShelfTimingSwitch."

      REVISION    "201409121200Z"
      DESCRIPTION "1) Added the following to tnShelfTable:
                      tnShelfCalculatedLoadAC
                      tnShelfPowerCapacity
                      tnShelfRemainingPowerCapacity.
                   2) Added the following to tnShelfExpectedAmps:
                      amps65(24).
                   3) Added the following to AluWdmExpectedAmpPF:
                      ampsdc30(5)
                      ampsac7(6)."

      REVISION    "201506041200Z"
      DESCRIPTION "Updated the DEFVAL of following MIB:
                   tnShelfLoadWarningThreshold."  

      REVISION    "201507311200Z"
      DESCRIPTION "Added the following from tnShelfTable:
                   tnShelfLockout."

      REVISION    "201508061200Z"
      DESCRIPTION "Renamed amps65 to amps63 in tnShelfExpectedAmps"

      REVISION    "201508251200Z"
      DESCRIPTION "Added the following from tnShelfTable:
                   tnShelfFilterMonitorStatus,
                   tnShelfFilterInspectionInterval,
                   tnShelfFilterStartDate."

      REVISION    "201509301200Z"
      DESCRIPTION "Added the following from tnShelfTable:
                   tnShelfAlmProfName."

      REVISION    "201510201200Z"
      DESCRIPTION "Changed the UNITS of following from volts to 1/100 volts:
                   tnShelfVoltageFloor,
                   tnShelfVoltageFloorAC."

      REVISION    "201512071200Z"
      DESCRIPTION "Added the following from tnShelfTable:
                   tnShelfBranchPowerCap1,
                   tnShelfBranchPowerCap2,
                   tnShelfBranchPowerCap3,
                   tnShelfBranchPowerCap4,
                   tnShelfBranchPowerCap5,
                   tnShelfBranchPowerCap6,
                   tnShelfBranchRemainingPwrCap1,
                   tnShelfBranchRemainingPwrCap2,
                   tnShelfBranchRemainingPwrCap3,
                   tnShelfBranchRemainingPwrCap4,
                   tnShelfBranchRemainingPwrCap5,
                   tnShelfBranchRemainingPwrCap6."

      REVISION    "201512241200Z"
      DESCRIPTION "Moved the following Fabric MIB attributes from tnFabricCardTable 
                   to tnShelfTable:
                   tnShelfFabricEQPStatus,
                   tnShelfFabricActivityState,
                   tnShelfFabricFailures,
                   tnShelfFabricUsage,
                   tnShelfFabricEqpsLEDColor,
                   tnShelfFabricReadyToProtect."

      REVISION    "201602011200Z"
      DESCRIPTION "1) Added the following from tnShelfTable:
                      tnShelfRackType.
                   2) Added the following to tnShelfFabricFailures:
                      latchOpen(6)."

      REVISION    "201605061200Z"
      DESCRIPTION "1) Added the following from tnShelfTable:
                      tnShelfInventoryAction.
                   2) Changed the UNITS of following from watts to 1/10 watts:
                      tnShelfBranchPowerCap1,
                      tnShelfBranchPowerCap2,
                      tnShelfBranchPowerCap3,
                      tnShelfBranchPowerCap4,
                      tnShelfBranchPowerCap5,
                      tnShelfBranchPowerCap6,
                      tnShelfBranchRemainingPwrCap1,
                      tnShelfBranchRemainingPwrCap2,
                      tnShelfBranchRemainingPwrCap3,
                      tnShelfBranchRemainingPwrCap4,
                      tnShelfBranchRemainingPwrCap5,
                      tnShelfBranchRemainingPwrCap6."

      REVISION    "201606031200Z"
      DESCRIPTION "Changed the SYNTAX of tnShelfBranchRemainingPwrCap[1-6]:
                   From Unsigned32 to Integer32."

      ::= { tnShelfModules 1 }

  tnShelfConf        OBJECT IDENTIFIER ::= { tnShelfMIB 1 }
  tnShelfGroups      OBJECT IDENTIFIER ::= { tnShelfConf 1 }
  tnShelfCompliances OBJECT IDENTIFIER ::= { tnShelfConf 2 }
  tnShelfObjs        OBJECT IDENTIFIER ::= { tnShelfMIB 2 }
  tnShelfBasics      OBJECT IDENTIFIER ::= { tnShelfObjs 1 }
--  obsolete
--  tnShelfEvents      OBJECT IDENTIFIER ::= { tnShelfMIB 3 }

--------------------------------------------------------------------------------
-- Type Definitions
--------------------------------------------------------------------------------
    AluWdmExpectedAmpPF ::= TEXTUAL-CONVENTION
        STATUS         current
        DESCRIPTION    "The expectedamps for PF card located in slot 2
                        or 3 when the expectedamps is mix."
        SYNTAX         INTEGER {
                         amps3dot7(1),
                         amps4dot1(2),
                         amps8dot5(3),
                         amps20dot6(4),
                         ampsdc30(5),
                         ampsac7(6),
                         na(7)
                       }

--------------------------------------------------------------------------------
-- Generic Shelf Table
--------------------------------------------------------------------------------
    tnShelfTable OBJECT-TYPE
        SYNTAX         SEQUENCE OF TnShelfEntry
        MAX-ACCESS     not-accessible
        STATUS         current
        DESCRIPTION    ""
        ::= { tnShelfBasics 1 }

    tnShelfEntry OBJECT-TYPE
        SYNTAX         TnShelfEntry
        MAX-ACCESS     not-accessible
        STATUS         current
        DESCRIPTION    ""
        INDEX { tnShelfIndex }
        ::= { tnShelfTable 1 }

    TnShelfEntry ::=
        SEQUENCE {
            tnShelfIndex                   TropicShelfIndexType,
            tnShelfName                    SnmpAdminString,
            tnShelfDescr                   SnmpAdminString,
            tnShelfSerialNum               Integer32,
            tnShelfProgrammedType          OBJECT IDENTIFIER,
            tnShelfPresentType             OBJECT IDENTIFIER,
            tnShelfActivitySwitch          TnCommand,
            tnShelfLampTest                TnCommand,
            tnShelfMateCCReadyToProtect    TruthValue,
            tnShelfIsUnmanaged             TruthValue,
            tnShelfExpectedAmps            INTEGER,
            tnShelfSerialNumber            SnmpAdminString,
            tnShelfAINS                    TruthValue,
--            obsolete
--            tnShelfInhibitAutoSwitching    TruthValue,
            tnShelfStatusLEDColor          TropicLEDColorType,
            tnShelfStatusLEDState          TropicLEDStateType,
            tnShelfWTMode                  TruthValue,
            tnShelfActivityMt0cSwitch      TnCommand,
            tnShelfMateMt0cReadyToProtect  TruthValue,
            tnShelfExpectedPfa             AluWdmExpectedAmpPF,
            tnShelfExpectedPfb             AluWdmExpectedAmpPF,
            tnShelfHighVoltageThreshold    Unsigned32,
            tnShelfLowVoltageThreshold     Unsigned32,
            tnShelfVoltageThresholdTol     Unsigned32,
            tnShelfExpectedVolts           INTEGER,
            tnShelfMatrixSize              INTEGER,
            tnShelfVoltageFloor            Unsigned32,
            tnShelfCalculatedLoad          Unsigned32,
            tnShelfClkSwitch               AluWdmWtClkValues,
            tnShelfExpectedVoltsAC         INTEGER,
            tnShelfHighVoltageThresholdAC  Unsigned32,
            tnShelfLowVoltageThresholdAC   Unsigned32,
            tnShelfVoltageFloorAC          Unsigned32,
            tnShelfExternalAcPower         Unsigned32,
            tnShelfLoadWarningThreshold    Unsigned32,
            tnShelfTimingSwitch            INTEGER,
            tnShelfCalculatedLoadAC        Unsigned32,
            tnShelfPowerCapacity           Unsigned32, 
            tnShelfRemainingPowerCapacity  Integer32,
	          tnShelfLockout		             INTEGER,
            tnShelfFilterMonitorStatus     TruthValue,
            tnShelfFilterInspectionInterval Unsigned32,
            tnShelfFilterStartDate         Unsigned32,
            tnShelfAlmProfName             OCTET STRING,
            tnShelfBranchPowerCap1         Unsigned32,
            tnShelfBranchPowerCap2         Unsigned32,
            tnShelfBranchPowerCap3         Unsigned32,
            tnShelfBranchPowerCap4         Unsigned32,
            tnShelfBranchPowerCap5         Unsigned32,
            tnShelfBranchPowerCap6         Unsigned32,
            tnShelfBranchRemainingPwrCap1  Integer32,
            tnShelfBranchRemainingPwrCap2  Integer32,
            tnShelfBranchRemainingPwrCap3  Integer32,
            tnShelfBranchRemainingPwrCap4  Integer32,
            tnShelfBranchRemainingPwrCap5  Integer32,
            tnShelfBranchRemainingPwrCap6  Integer32,
            tnShelfFabricEQPStatus         INTEGER,
            tnShelfFabricActivityState     INTEGER,
            tnShelfFabricFailures          INTEGER,
            tnShelfFabricUsage             INTEGER,
            tnShelfFabricEqpsLEDColor      OCTET STRING,
            tnShelfFabricReadyToProtect    INTEGER,
            tnShelfRackType                TnRackSize,
            tnShelfInventoryAction         INTEGER
        }

    tnShelfIndex OBJECT-TYPE
        SYNTAX         TropicShelfIndexType
        MAX-ACCESS     not-accessible
        STATUS         current
        DESCRIPTION    ""
        ::= { tnShelfEntry 1 }

    tnShelfName OBJECT-TYPE
        SYNTAX         SnmpAdminString (SIZE(0..31))
        MAX-ACCESS     read-create
        STATUS         current
        DESCRIPTION    "Shelf name (an abbreviated description)."
        DEFVAL         { "" }
        ::= { tnShelfEntry 2 }

    tnShelfDescr OBJECT-TYPE
        SYNTAX         SnmpAdminString (SIZE(0..255))
        MAX-ACCESS     read-create
        STATUS         current
        DESCRIPTION    "Shelf description."
        DEFVAL         { "" }
        ::= { tnShelfEntry 3 }

    tnShelfSerialNum OBJECT-TYPE
        SYNTAX         Integer32
        MAX-ACCESS     read-create
        STATUS         current
        DESCRIPTION    "Shelf serial number.  Applicable to the 1696R."
        ::= { tnShelfEntry 4 }

    tnShelfProgrammedType OBJECT-TYPE
        SYNTAX         OBJECT IDENTIFIER
        MAX-ACCESS     read-create
        STATUS         current
        DESCRIPTION    "Type of shelf provisioned."
        DEFVAL         { tropicEmptyCard }
        ::= { tnShelfEntry 5 }

    tnShelfPresentType OBJECT-TYPE
        SYNTAX         OBJECT IDENTIFIER
        MAX-ACCESS     read-only
        STATUS         current
        DESCRIPTION    "Actual shelf present."
        DEFVAL         { tropicEmptyCard }
        ::= { tnShelfEntry 6 }

    tnShelfActivitySwitch OBJECT-TYPE
        SYNTAX         TnCommand
        MAX-ACCESS     read-create
        STATUS         current
        DESCRIPTION    "Perform an activity switch on this shelf.  When
                        read, this object returns noCmd."
        DEFVAL         { noCmd }
        ::= { tnShelfEntry 7 }

    tnShelfLampTest OBJECT-TYPE
        SYNTAX         TnCommand
        MAX-ACCESS     read-create
        STATUS         current
        DESCRIPTION    "Perform a lamp test on the shelf.  When read,
                        this object returns noCmd."
        DEFVAL         { noCmd }
        ::= { tnShelfEntry 8 }

    tnShelfMateCCReadyToProtect OBJECT-TYPE
        SYNTAX         TruthValue
        MAX-ACCESS     read-only
        STATUS         current
        DESCRIPTION    ""
        ::= { tnShelfEntry 9 }

    tnShelfIsUnmanaged OBJECT-TYPE
        SYNTAX         TruthValue
        MAX-ACCESS     read-create
        STATUS         current
        DESCRIPTION    "Indicates a shelf is not being managed.  This is
                        set to true for shelves that have no managed
                        inventory."
        DEFVAL         { false }
        ::= { tnShelfEntry 10 }

    tnShelfExpectedAmps OBJECT-TYPE
        SYNTAX         INTEGER {
                         amps30(1),
                         amps50(2),
                         amps70(3),
                         amps20(4),
                         auto(5),
                         amps35(6),
                         amps5(7),
                         amps7(8),
                         amps100(9),
                         amps150(10),
                         amps60(11),
                         amps275(12),
                         amps2x50(13),
                         amps2x60(14),
                         amps3x60(15),
                         amps20dot6(16),
                         amps8dot5(17),
                         amps3dot7(18),
                         ampsMix(19),
                         amps4dot1(20),
                         ampsNa(21),
                         amps3x50(22),
                         amps320(23),
                         amps63(24)
                       }
        MAX-ACCESS     read-create
        STATUS         current
        DESCRIPTION    "This attribute is associated with shelf
                        pre-provisioning, and defines a single value for
                        the shelf which applies to both PSFs.  The value
                        can be edited by the network manager.  A mismatch
                        alarm will be generated against any PSF that does
                        not agree with the value of this attribute.  An
                        excess load alarm will be raised against any
                        inserted circuit pack which cannot be provided
                        power without exceeding the actual or provisioned
                        shelf amperage (whichever is less).  Auto means
                        when the shelf is equipped, the EC reads the id of
                        the two power filters and takes the value (they
                        should both be the same, but just in case) of the
                        smaller one as the shelf power capacity.

                        Current configurable values:
                        PSS4:   3.7, 8.5, 20.6.
                        PSS32:  auto, 20, 30, 50, 60, 70.
                        PSS16:  auto, 20, 35.
                        PSS36:  If only PFC power filter is supported, this
                                  attribute is read-only, with the value 150.
                                If both PFC and PFB50 power filters are
                                  supported, this attribute is provisionable
                                  with values auto, 100, 150.
                        PSS64:  275."
        DEFVAL         { auto }
        ::= { tnShelfEntry 11 }

    tnShelfSerialNumber OBJECT-TYPE
        SYNTAX         SnmpAdminString (SIZE(0..16))
        MAX-ACCESS     read-create
        STATUS         current
        DESCRIPTION    "Applicable to the 1830 PSS-32 DCM, SFD44 and ITLB
                        shelves."
        DEFVAL         { "" }
        ::= { tnShelfEntry 12 }

    tnShelfAINS OBJECT-TYPE
        SYNTAX         TruthValue
        MAX-ACCESS     read-create
        STATUS         current
        DESCRIPTION    "Applicable to the 1830 PSS-32."
        DEFVAL         { false }
        ::= { tnShelfEntry 13 }

--    obsolete
--    tnShelfInhibitAutoSwitching OBJECT-TYPE ::= { tnShelfEntry 14 }

    tnShelfStatusLEDColor OBJECT-TYPE
        SYNTAX         TropicLEDColorType
        MAX-ACCESS     read-only
        STATUS         current
        DESCRIPTION    "The color of the shelf status LED."
        ::= { tnShelfEntry 15 }

    tnShelfStatusLEDState OBJECT-TYPE
        SYNTAX         TropicLEDStateType
        MAX-ACCESS     read-only
        STATUS         current
        DESCRIPTION    "The state of the shelf status LED."
        ::= { tnShelfEntry 16 }

    tnShelfWTMode OBJECT-TYPE
        SYNTAX         TruthValue
        MAX-ACCESS     read-create
        STATUS         current
        DESCRIPTION    "The Shelf WT Mode."
        DEFVAL         { true }
        ::= { tnShelfEntry 17 }

    tnShelfActivityMt0cSwitch OBJECT-TYPE
        SYNTAX         TnCommand
        MAX-ACCESS     read-create
        STATUS         current
        DESCRIPTION    "Perform an activity switch on the MT0C.  When
                        read, this object returns noCmd."
        DEFVAL         { noCmd }
        ::= { tnShelfEntry 18 }

    tnShelfMateMt0cReadyToProtect OBJECT-TYPE
        SYNTAX         TruthValue
        MAX-ACCESS     read-only
        STATUS         current
        DESCRIPTION    ""
        ::= { tnShelfEntry 19 }

    tnShelfExpectedPfa OBJECT-TYPE
        SYNTAX         AluWdmExpectedAmpPF
        MAX-ACCESS     read-create
        STATUS         current
        DESCRIPTION    "The expectedamps for PF card located in slot 2
                        when the expectedamps is mix."
        DEFVAL         { amps3dot7 }
        ::= { tnShelfEntry 20 }

    tnShelfExpectedPfb OBJECT-TYPE
        SYNTAX         AluWdmExpectedAmpPF
        MAX-ACCESS     read-create
        STATUS         current
        DESCRIPTION    "The expectedamps for PF card located in slot 3
                        when the expectedamps is mix."
        DEFVAL         { amps8dot5 }
        ::= { tnShelfEntry 21 }

    tnShelfHighVoltageThreshold OBJECT-TYPE
        SYNTAX         Unsigned32 (0..8500)
        UNITS          "1/100 volts"
        MAX-ACCESS     read-create
        STATUS         current
        DESCRIPTION    "Shelf high voltage threshold.  Default is depending
                        on value of tnShelfExpectedVolts:
                          v48 - 5700
                          v60 - 7200.

                        Current configurable values: 0 to 8500, in
                        increments of 50."
        ::= { tnShelfEntry 22 }

    tnShelfLowVoltageThreshold OBJECT-TYPE
        SYNTAX         Unsigned32 (0..8500)
        UNITS          "1/100 volts"
        MAX-ACCESS     read-create
        STATUS         current
        DESCRIPTION    "Shelf low voltage threshold.  Default is depending
                        on value of tnShelfExpectedVolts:
                          v48 - 4050
                          v60 - 5000.

                        Current configurable values: 0 to 8500, in
                        increments of 50."
        ::= { tnShelfEntry 23 }

    tnShelfVoltageThresholdTol OBJECT-TYPE
        SYNTAX         Unsigned32 (100..500)
        UNITS          "1/100 volts"
        MAX-ACCESS     read-create
        STATUS         current
        DESCRIPTION    "Shelf voltage threshold tolerance.

                        Current configurable values: 100 to 500, in
                        increments of 100."
        DEFVAL         { 200 }
        ::= { tnShelfEntry 24 }

    tnShelfExpectedVolts OBJECT-TYPE
        SYNTAX         INTEGER {
                         v48(1),
                         v60(2)
                       }
        MAX-ACCESS     read-create
        STATUS         current
        DESCRIPTION    "Nominal voltage for the shelf.
                          v48 - The input supply voltage is nominally -48 V dc.
                          v60 - The input supply voltage is nominally -60 V dc.
                        This has the effect of setting the voltage alarms
                        to the ends of the standard operating range for
                        the specified input supply voltage."
        DEFVAL         { v48 }
        ::= { tnShelfEntry 25 }

    tnShelfMatrixSize OBJECT-TYPE
        SYNTAX         INTEGER {
                         notApplicable(1),
                         ms1dot2T(2),
                         ms1dot9T(3)
                       }
        MAX-ACCESS     read-create
        STATUS         current
        DESCRIPTION    "The matrix size of the shelf.
                          notApplicable - Not applicable to this shelf.
                          ms1dot2T      - 1.2T shelf.
                          ms1dot9T      - 1.9T shelf.

                        Sets are not supported."
        DEFVAL         { notApplicable }
        ::= { tnShelfEntry 26 }

    tnShelfVoltageFloor OBJECT-TYPE
        SYNTAX         Unsigned32 (3900..7200)
        UNITS          "1/100 volts"
        MAX-ACCESS     read-create
        STATUS         current
        DESCRIPTION    "Shelf voltage floor.

                        Current configurable range: 3900 to 7200."
        DEFVAL         { 3900 }
        ::= { tnShelfEntry 27 }

    tnShelfCalculatedLoad OBJECT-TYPE
        SYNTAX         Unsigned32
        UNITS          "mA"
        MAX-ACCESS     read-only
        STATUS         current
        DESCRIPTION    "This attribute shall be calculated by adding
                        the pre-defined maximum power consumption of
                        each plugged in or pre-provisioned card and
                        then dividing the sum by tnShelfVoltageFloor."
        ::= { tnShelfEntry 28 }

    tnShelfClkSwitch   OBJECT-TYPE
        SYNTAX         AluWdmWtClkValues
        MAX-ACCESS     read-create
        STATUS         current
        DESCRIPTION    "Clock Switch on shelf level."
        DEFVAL         { wtClkAuto }
        ::= { tnShelfEntry 29 }

    tnShelfExpectedVoltsAC OBJECT-TYPE
        SYNTAX         INTEGER {
                         v110(1),
                         v220(2)
                       }
        MAX-ACCESS     read-create
        STATUS         current
        DESCRIPTION    "Nominal AC voltage for the shelf.
                        v110 - The input supply voltage is nominally
                                -110 V ac.
                        v220 - The input supply voltage is nominally
                                -220 V ac.

                        This has the effect of setting the voltage
                        alarms to the ends of the standard operating
                        range for the specified input supply voltage."
        DEFVAL         { v110 }
        ::= { tnShelfEntry 30 }

    tnShelfHighVoltageThresholdAC OBJECT-TYPE
        SYNTAX         Unsigned32 (9000..26400)
        UNITS          "1/100 volts"
        MAX-ACCESS     read-create
        STATUS         current
        DESCRIPTION    "Shelf high ac voltage threshold.  Default is
                        depending on value of tnShelfExpectedVoltsAC:
                        v110 - 12000.
                        v220 - 24000.

                        Current configurable values: 9000 to 26400,
                        in increments of 50."
        ::= { tnShelfEntry 31 }

  tnShelfLowVoltageThresholdAC OBJECT-TYPE
        SYNTAX         Unsigned32 (9000..26400)
        UNITS          "1/100 volts"
        MAX-ACCESS     read-create
        STATUS         current
        DESCRIPTION    "Shelf low ac voltage threshold.  Default is
                        depending on value of tnShelfExpectedVoltsAC:
                        v110 - 10000.
                        v220 - 20000.

                        Current configurable values: 9000 to 26400,
                        in increments of 50."
        ::= { tnShelfEntry 32 }

    tnShelfVoltageFloorAC OBJECT-TYPE
        SYNTAX         Unsigned32 (9000..26400)
        UNITS          "1/100 volts"
        MAX-ACCESS     read-create
        STATUS         current
        DESCRIPTION    "Shelf ac voltage floor.

                        Current configurable range: 9000 to 26400."
        DEFVAL         { 10000 }
        ::= { tnShelfEntry 33 }

    tnShelfExternalAcPower   OBJECT-TYPE
        SYNTAX         Unsigned32
        UNITS          "1/10 watt"
        MAX-ACCESS     read-create
        STATUS         current
        DESCRIPTION    "The power of the external AC power box."
        DEFVAL         { 0 }
        ::= { tnShelfEntry 34 }

  tnShelfLoadWarningThreshold   OBJECT-TYPE
        SYNTAX         Unsigned32 (500..1000)
        MAX-ACCESS     read-create
        STATUS         current
        DESCRIPTION    "Shelf load warning threshold."
        DEFVAL         { 1000 }
        ::= { tnShelfEntry 35 }

    tnShelfTimingSwitch   OBJECT-TYPE
        SYNTAX         INTEGER {
                         timingSwitchAuto(1),
                         timingSwitchA(2),
                         timingSwitchB(3)
                       }
        MAX-ACCESS     read-create
        STATUS         current
        DESCRIPTION    "System Timing Switch on shelf level."
        DEFVAL         { timingSwitchAuto }
        ::= { tnShelfEntry 36 }
   
    tnShelfCalculatedLoadAC OBJECT-TYPE
        SYNTAX         Unsigned32
        UNITS          "mA"
        MAX-ACCESS     read-only
        STATUS         current
        DESCRIPTION    "This attribute shall be calculated by adding
                        the pre-defined maximum power consumption of
                        each plugged in or pre-provisioned card and
                        then dividing the sum by tnShelfVoltageFloor."
        DEFVAL         { 0 }
        ::= { tnShelfEntry 37 }

    tnShelfPowerCapacity OBJECT-TYPE
        SYNTAX         Unsigned32
        UNITS          "1/10 watt"
        MAX-ACCESS     read-only
        STATUS         current
        DESCRIPTION    "Shelf Power Capacity."
        DEFVAL         { 0 }
        ::= { tnShelfEntry 38 }

    tnShelfRemainingPowerCapacity OBJECT-TYPE
        SYNTAX         Integer32
        UNITS          "1/10 watt"
        MAX-ACCESS     read-only
        STATUS         current
        DESCRIPTION    "Shelf Remaining Power Capacity."
        DEFVAL         { 0 }
        ::= { tnShelfEntry 39 }

     tnShelfLockout OBJECT-TYPE
          SYNTAX         INTEGER {
                          fab07(1),
                          fab08(2),
                          fab09(3),
                          clear(4)
                         }
          MAX-ACCESS     read-create
          STATUS         current
          DESCRIPTION    "FABRIC card lockout status."
          DEFVAL         { clear }
          ::= { tnShelfEntry 40 }

    tnShelfFilterMonitorStatus OBJECT-TYPE
        SYNTAX         TruthValue
        MAX-ACCESS     read-create
        STATUS         current
        DESCRIPTION    "Filter maintenance status."
        DEFVAL         { false }
        ::= { tnShelfEntry 41 }
    
  tnShelfFilterInspectionInterval OBJECT-TYPE
        SYNTAX         Unsigned32 (1..104)
        MAX-ACCESS     read-create
        STATUS         current
        DESCRIPTION    "Filter inspection interval time in weeks."
        DEFVAL         { 26 }
        ::= { tnShelfEntry 42 }
    
  tnShelfFilterStartDate OBJECT-TYPE
        SYNTAX         Unsigned32
        MAX-ACCESS     read-create
        STATUS         current
        DESCRIPTION    "Filter inspection start date."
        DEFVAL         { 426770689 }
        ::= { tnShelfEntry 43 }

  tnShelfAlmProfName OBJECT-TYPE
        SYNTAX         OCTET STRING
        MAX-ACCESS     read-create
        STATUS         current
        DESCRIPTION    ""
        ::= { tnShelfEntry 44 }

    tnShelfBranchPowerCap1 OBJECT-TYPE
        SYNTAX         Unsigned32
        UNITS          "1/10 watt"
        MAX-ACCESS     read-create 
        STATUS         current
        DESCRIPTION    " "
        DEFVAL         { 0 }
        ::= { tnShelfEntry 45 }
    
    tnShelfBranchPowerCap2 OBJECT-TYPE
        SYNTAX         Unsigned32
        UNITS          "1/10 watt"
        MAX-ACCESS     read-create
        STATUS         current
        DESCRIPTION    " "
        DEFVAL         { 0 }
        ::= { tnShelfEntry 46 }
    
    tnShelfBranchPowerCap3 OBJECT-TYPE
        SYNTAX         Unsigned32
        UNITS          "1/10 watt"
        MAX-ACCESS     read-create
        STATUS         current
        DESCRIPTION    " "
        DEFVAL         { 0 }
        ::= { tnShelfEntry 47 }
    
    tnShelfBranchPowerCap4 OBJECT-TYPE
        SYNTAX         Unsigned32
        UNITS          "1/10 watt"
        MAX-ACCESS     read-create
        STATUS         current
        DESCRIPTION    " "
        DEFVAL         { 0 }
        ::= { tnShelfEntry 48 }
    
    tnShelfBranchPowerCap5 OBJECT-TYPE
        SYNTAX         Unsigned32
        UNITS          "1/10 watt"
        MAX-ACCESS     read-create
        STATUS         current
        DESCRIPTION    " "
        DEFVAL         { 0 }
        ::= { tnShelfEntry 49 }
    
    tnShelfBranchPowerCap6 OBJECT-TYPE
        SYNTAX         Unsigned32
        UNITS          "1/10 watt"
        MAX-ACCESS     read-create
        STATUS         current
        DESCRIPTION    " "
        DEFVAL         { 0 }
        ::= { tnShelfEntry 50 }
    
    tnShelfBranchRemainingPwrCap1 OBJECT-TYPE
        SYNTAX         Integer32 
        UNITS          "1/10 watt"
        MAX-ACCESS     read-create
        STATUS         current
        DESCRIPTION    " "
        DEFVAL         { 0 }
        ::= { tnShelfEntry 51 }
    
    tnShelfBranchRemainingPwrCap2 OBJECT-TYPE
        SYNTAX         Integer32 
        UNITS          "1/10 watt"
        MAX-ACCESS     read-create
        STATUS         current
        DESCRIPTION    " "
        DEFVAL         { 0 }
        ::= { tnShelfEntry 52 }
    
    tnShelfBranchRemainingPwrCap3 OBJECT-TYPE
        SYNTAX         Integer32 
        UNITS          "1/10 watt"
        MAX-ACCESS     read-create
        STATUS         current
        DESCRIPTION    " "
        DEFVAL         { 0 }
        ::= { tnShelfEntry 53 }
    
    tnShelfBranchRemainingPwrCap4 OBJECT-TYPE
        SYNTAX         Integer32 
        UNITS          "1/10 watt"
        MAX-ACCESS     read-create
        STATUS         current
        DESCRIPTION    " "
        DEFVAL         { 0 }
        ::= { tnShelfEntry 54 }
    
    tnShelfBranchRemainingPwrCap5 OBJECT-TYPE
        SYNTAX         Integer32 
        UNITS          "1/10 watt"
        MAX-ACCESS     read-create
        STATUS         current
        DESCRIPTION    " "
        DEFVAL         { 0 }
        ::= { tnShelfEntry 55 }
    
    tnShelfBranchRemainingPwrCap6 OBJECT-TYPE
        SYNTAX         Integer32 
        UNITS          "1/10 watt"
        MAX-ACCESS     read-create
        STATUS         current
        DESCRIPTION    " "
        DEFVAL         { 0 }
        ::= { tnShelfEntry 56 }

   tnShelfFabricEQPStatus OBJECT-TYPE
       SYNTAX         INTEGER {
                     available(1),
                     notAvailable(2),
                     inUse(3),
                     trafficImpaired(4),
                     allTrafficLost(5)
                    }
       MAX-ACCESS     read-only
       STATUS         current
       DESCRIPTION    "Fabric location status."
       ::= { tnShelfEntry 57 }

   tnShelfFabricActivityState OBJECT-TYPE
       SYNTAX         INTEGER {
                        inUse(1),
                        notInUse(2),
                        lockedOut(3),
                        loButInUse(4)
                      }
       MAX-ACCESS     read-only
       STATUS         current
       DESCRIPTION    "Fabric activity states."
       ::= { tnShelfEntry 58 }

    tnShelfFabricFailures OBJECT-TYPE
        SYNTAX         INTEGER {
                        none(1),
                        tSIFail(2),
                        linkFail(3),
                        cardFail(4),
                        cardRemoved(5),
                        latchOpen(6)
                       }
        MAX-ACCESS     read-only
        STATUS         current
        DESCRIPTION    "Fabric failure mode."
        ::= { tnShelfEntry 59 }

    tnShelfFabricUsage OBJECT-TYPE
        SYNTAX         INTEGER {
                          inUse(1),
                          notInUse(2)
                       }
        MAX-ACCESS     read-only
        STATUS         current
        DESCRIPTION    "Fabric Usage status."
        ::= { tnShelfEntry 60 }

    tnShelfFabricEqpsLEDColor OBJECT-TYPE
        SYNTAX         OCTET STRING 
        MAX-ACCESS     read-only
        STATUS         current
        DESCRIPTION    "The color of the CRU EQPS status LED."
        ::= { tnShelfEntry 61 }

    tnShelfFabricReadyToProtect OBJECT-TYPE
        SYNTAX         INTEGER {
                          yes(1),
                          partially(2),
                          no(3),
                          invalid(4)
                       }
        MAX-ACCESS     read-only
        STATUS         current
        DESCRIPTION    "Fabric ready to protect status."
        ::= { tnShelfEntry 62 }

    tnShelfRackType OBJECT-TYPE
        SYNTAX        TnRackSize
        MAX-ACCESS    read-create
        STATUS        current
        DESCRIPTION   "Shelf rack size"
        DEFVAL        { inch19 }
        ::= { tnShelfEntry 63 }

    tnShelfInventoryAction OBJECT-TYPE
        SYNTAX         INTEGER {
                          unInitialized(1),
                          toDb(2),
                          toHw(3),
                          ready(4),
                          fail(5)
                       }
        MAX-ACCESS     read-create
        STATUS         current
        DESCRIPTION    "Copies the shelf Remote Inventory information from the shelf 
                        inventory HW into the database or from database to the shelf 
                        inventory HW."
        DEFVAL        { unInitialized }
        ::= { tnShelfEntry 64 }

--------------------------------------------------------------------------------
-- Generic Shelf Scalars
--------------------------------------------------------------------------------
    tnShelfTotal OBJECT-TYPE
        SYNTAX         Integer32
        MAX-ACCESS     read-only
        STATUS         current
        DESCRIPTION    "The total number of shelves allocated on a
                        1696R/1830 ROADM NE."
        ::= { tnShelfBasics 2 }

--------------------------------------------------------------------------------
-- PSS4 Shelf RI Data Table
--------------------------------------------------------------------------------
    tnShelfRiDataTable OBJECT-TYPE
        SYNTAX         SEQUENCE OF TnShelfRiDataEntry
        MAX-ACCESS     not-accessible
        STATUS         current
        DESCRIPTION    "Applicable to PSS4."
        ::= { tnShelfBasics 3 }

    tnShelfRiDataEntry OBJECT-TYPE
        SYNTAX         TnShelfRiDataEntry
        MAX-ACCESS     not-accessible
        STATUS         current
        DESCRIPTION    ""
        INDEX { tnShelfIndex }
        ::= { tnShelfRiDataTable 1 }

    TnShelfRiDataEntry ::=
        SEQUENCE {
            tnShelfRiCompanyID                SnmpAdminString,
            tnShelfRiMnemonic                 SnmpAdminString,
            tnShelfRiCLEI                     TropicCardCLEI,
            tnShelfRiManufacturingPartNumber  TropicCardManufacturingPartNumber,
            tnShelfRiSWPartNum                SnmpAdminString,
            tnShelfRiFactoryID                SnmpAdminString,
            tnShelfRiSerialNumber             TropicCardSerialNumber,
            tnShelfRiDate                     SnmpAdminString,
            tnShelfRiExtraData                SnmpAdminString
        }

    tnShelfRiCompanyID OBJECT-TYPE
        SYNTAX         SnmpAdminString
        MAX-ACCESS     read-only
        STATUS         current
        DESCRIPTION    ""
        DEFVAL         { "" }
        ::= { tnShelfRiDataEntry 1 }

    tnShelfRiMnemonic OBJECT-TYPE
        SYNTAX         SnmpAdminString
        MAX-ACCESS     read-only
        STATUS         current
        DESCRIPTION    ""
        DEFVAL         { "" }
        ::= { tnShelfRiDataEntry 2 }

    tnShelfRiCLEI OBJECT-TYPE
        SYNTAX         TropicCardCLEI
        MAX-ACCESS     read-only
        STATUS         current
        DESCRIPTION    ""
        DEFVAL         { "" }
        ::= { tnShelfRiDataEntry 3 }

    tnShelfRiManufacturingPartNumber OBJECT-TYPE
        SYNTAX         TropicCardManufacturingPartNumber
        MAX-ACCESS     read-only
        STATUS         current
        DESCRIPTION    ""
        DEFVAL         { "" }
        ::= { tnShelfRiDataEntry 4 }

    tnShelfRiSWPartNum OBJECT-TYPE
        SYNTAX         SnmpAdminString
        MAX-ACCESS     read-only
        STATUS         current
        DESCRIPTION    ""
        DEFVAL         { "" }
        ::= { tnShelfRiDataEntry 5 }

    tnShelfRiFactoryID OBJECT-TYPE
        SYNTAX         SnmpAdminString
        MAX-ACCESS     read-only
        STATUS         current
        DESCRIPTION    ""
        DEFVAL         { "" }
        ::= { tnShelfRiDataEntry 6 }

    tnShelfRiSerialNumber OBJECT-TYPE
        SYNTAX         TropicCardSerialNumber
        MAX-ACCESS     read-only
        STATUS         current
        DESCRIPTION    ""
        DEFVAL         { "" }
        ::= { tnShelfRiDataEntry 7 }

    tnShelfRiDate OBJECT-TYPE
        SYNTAX         SnmpAdminString
        MAX-ACCESS     read-only
        STATUS         current
        DESCRIPTION    ""
        DEFVAL         { "" }
        ::= { tnShelfRiDataEntry 8 }

    tnShelfRiExtraData OBJECT-TYPE
        SYNTAX         SnmpAdminString
        MAX-ACCESS     read-only
        STATUS         current
        DESCRIPTION    ""
        DEFVAL         { "" }
        ::= { tnShelfRiDataEntry 9 }

--------------------------------------------------------------------------------
-- Conformance Group Definitions
--------------------------------------------------------------------------------
    tnShelfGroup OBJECT-GROUP
        OBJECTS {
            tnShelfName,
            tnShelfDescr,
            tnShelfSerialNum,
            tnShelfProgrammedType,
            tnShelfPresentType,
            tnShelfActivitySwitch,
            tnShelfLampTest,
            tnShelfMateCCReadyToProtect,
            tnShelfIsUnmanaged,
            tnShelfExpectedAmps,
            tnShelfSerialNumber,
            tnShelfAINS,
--            obsolete
--            tnShelfInhibitAutoSwitching,
            tnShelfStatusLEDColor,
            tnShelfStatusLEDState,
            tnShelfWTMode,
            tnShelfActivityMt0cSwitch,
            tnShelfMateMt0cReadyToProtect,
            tnShelfExpectedPfa,
            tnShelfExpectedPfb,
            tnShelfHighVoltageThreshold,
            tnShelfLowVoltageThreshold,
            tnShelfVoltageThresholdTol,
            tnShelfExpectedVolts,
            tnShelfMatrixSize,
            tnShelfVoltageFloor,
            tnShelfCalculatedLoad,
            tnShelfClkSwitch,
            tnShelfExpectedVoltsAC,
            tnShelfHighVoltageThresholdAC,
            tnShelfLowVoltageThresholdAC,
            tnShelfVoltageFloorAC,
            tnShelfExternalAcPower,
            tnShelfLoadWarningThreshold,
            tnShelfTimingSwitch,
            tnShelfCalculatedLoadAC,
            tnShelfPowerCapacity,
            tnShelfRemainingPowerCapacity,
	          tnShelfLockout,
            tnShelfFilterMonitorStatus,
            tnShelfFilterInspectionInterval,
            tnShelfFilterStartDate,
            tnShelfAlmProfName,
            tnShelfBranchPowerCap1,
            tnShelfBranchPowerCap2,
            tnShelfBranchPowerCap3,
            tnShelfBranchPowerCap4,
            tnShelfBranchPowerCap5,
            tnShelfBranchPowerCap6,
            tnShelfBranchRemainingPwrCap1,
            tnShelfBranchRemainingPwrCap2,
            tnShelfBranchRemainingPwrCap3,
            tnShelfBranchRemainingPwrCap4,
            tnShelfBranchRemainingPwrCap5,
            tnShelfBranchRemainingPwrCap6,
            tnShelfFabricEQPStatus,
            tnShelfFabricActivityState,
            tnShelfFabricFailures,
            tnShelfFabricUsage,
            tnShelfFabricEqpsLEDColor,
            tnShelfFabricReadyToProtect,
            tnShelfRackType,
            tnShelfInventoryAction
        }
        STATUS         current
        DESCRIPTION    ""
        ::= { tnShelfGroups 1 }

    tnShelfScalarsGroup OBJECT-GROUP
        OBJECTS {
            tnShelfTotal
        }
        STATUS         current
        DESCRIPTION    ""
        ::= { tnShelfGroups 2 }

    tnShelfRiDataGroup OBJECT-GROUP
        OBJECTS {
            tnShelfRiCompanyID,
            tnShelfRiMnemonic,
            tnShelfRiCLEI,
            tnShelfRiManufacturingPartNumber,
            tnShelfRiSWPartNum,
            tnShelfRiFactoryID,
            tnShelfRiSerialNumber,
            tnShelfRiDate,
            tnShelfRiExtraData
        }
        STATUS         current
        DESCRIPTION    ""
        ::= { tnShelfGroups 3 }

--------------------------------------------------------------------------------
-- Compliance Statements (mandatory)
--------------------------------------------------------------------------------
    tnShelfCompliance MODULE-COMPLIANCE
        STATUS         current
        DESCRIPTION    ""
        MODULE
        MANDATORY-GROUPS {
            tnShelfGroup,
            tnShelfScalarsGroup,
            tnShelfRiDataGroup
        }
        ::= { tnShelfCompliances 1 }

END -- DEFINITION OF TROPIC-SLOT-MIB
