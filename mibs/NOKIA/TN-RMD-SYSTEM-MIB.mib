TN-RMD-SYSTEM-MIB DEFINITIONS ::= BEGIN

-- (c) Copyright 2016 Nokia.  All rights reserved.
-- This software is the confidential and proprietary property of
-- Nokia and may only be used in accordance with the
-- terms of the license agreement provided with this software.

IMPORTS
      SnmpAdminString                         FROM SNMP-FRAMEWORK-MIB
      MODULE-IDENTITY, OBJECT-TYPE,
      Unsigned32, Integer32                   FROM SNMPv2-SMI
      DateAndTime, MacAddress,
      RowStatus, TruthValue                   FROM SNMPv2-TC
      VlanId                                  FROM IEEE8021-CFM-MIB
      TnRmdAccessIfIndex, TnRmdItemCode,
      TnRmdOui, TnRmdVersion,
      TnRmdPcp, TnRmdTpid                     FROM TN-RMD-TC-MIB
      TItemDescription,
      TmnxPortID, TmnxEncapVal                FROM TN-TC-MIB
      tnSysSwitchId                           FROM TROPIC-SYSTEM-MIB
      tnRmdObjs, tnRmdMIBModules              FROM TROPIC-GLOBAL-REG;

tnRmdSystemMibModule MODULE-IDENTITY
    LAST-UPDATED    "201404100000Z"
    ORGANIZATION    "Nokia"
    CONTACT-INFO    "Nokia
                     Postal: 600 March Rd.
                     Kanata, Ontario
                     Canada K2K 2E6

                     Phone: +1 613 591 3600
                     Fax:   +1 613 591 3680"

    DESCRIPTION
        "System MIB for Remote Managed Devices (RMDs).
         This MIB covers the management of the discovery of RMDs, as
         well as the management of system level RMD data."

    REVISION    "201211280000Z"
    DESCRIPTION "Initial revision."

    REVISION    "201308090000Z"
    DESCRIPTION "Added the following to TnRmdDeviceType:
                 tsopOC3  (3),
                 tsopOC12 (4)."

    REVISION    "201404100000Z"
    DESCRIPTION "1) Marked the following as obsolete:
                    tnRmdSystemInventory.
                 2) Added the following to tnRmdSystemInventoryTable:
                    tnRmdSystemInventoryModuleVendorSerNo
                    tnRmdSystemInventoryModuleVendor
                    tnRmdSystemInventoryWavelength
                    tnRmdSystemInventoryModuleType
                    tnRmdSystemInventoryCLEI
                    tnRmdSystemInventoryUnitPartNum
                    tnRmdSystemInventorySWPartNum
                    tnRmdSystemInventoryFactoryID
                    tnRmdSystemInventoryDate
                    tnRmdSystemInventoryExtraData
                    tnRmdSystemInventoryMaximumCaseTemperature
                    tnRmdSystemInventoryInterchangeabilityMarking
                    tnRmdSystemInventoryAcronymCode
                    tnRmdSystemInventoryCustomerInventoryField."

    ::= { tnRmdMIBModules 4 }


tnRmdSystemObjects  OBJECT IDENTIFIER ::= { tnRmdObjs 4 }


-- =============================================================
-- Textual Conventions
-- =============================================================
TnRmdDeviceType ::= TEXTUAL-CONVENTION
    STATUS current
    DESCRIPTION
        "Indicates the device type.

         efm      : Device type is EFM
         cfm      : Device type is CFM
         cedd     : Device type is Carrier Ethernet Demarcation Device
         tsopOC3  : Device type is Transparent Sdh/Sonet Over Packet with STS-3/STM-1 signal
         tsopOC12 : Device type is Transparent Sdh/Sonet Over Packet with STS-12/STM-4 signal
         unknown  : Device type is not known"
    SYNTAX INTEGER {
              efm      (0),
              cfm      (1),
              cedd     (2),
              tsopOC3  (3),
              tsopOC12 (4),
              unknown  (254)
           }

TnRmdDiscoveryMode ::= TEXTUAL-CONVENTION
    STATUS current
    DESCRIPTION
        "Either represents
           1) how a discovery is performed, or
           2) how an SD replies to discovery requests

         For the applicable above meaning, see the descriptions of
         the objects using this textual convention."
    SYNTAX INTEGER {
           pollAll(0),
           pollGroup(1)
           }

TnRmdNumberOfVlanTags ::= TEXTUAL-CONVENTION
    STATUS current
    DESCRIPTION
        "Number of VLAN Tags used to encapsulate the IDL protocol frames.

         Value 0 implies that no VLAN Tags are used.
         Value 1 implies that only an outer VLAN Tag is used.
         Value 2 implies that both an outer and inner VLAN Tag are used."
    SYNTAX Unsigned32 (0..2)

TnRmdSwImageState ::= TEXTUAL-CONVENTION
    STATUS current
    DESCRIPTION
        "Represents the status of a software image on the RMD."
    SYNTAX INTEGER {
           swImageActive(1),
           swImageInactive(2),
           swImageEmpty(3),
           swImageError(4),
           swImageSoak(5)
           }

TnRmdSystemId ::= TEXTUAL-CONVENTION
    STATUS current
    DESCRIPTION
        "The ID of an RMD."
    SYNTAX Unsigned32 (1..32)

TnRmdSystemLocation ::= TEXTUAL-CONVENTION
    STATUS current
    DESCRIPTION
       "Contains the location of an RMD.
        The set of allowed octet values is RMD type specific."
    SYNTAX OCTET STRING (SIZE(32))

TnRmdSystemManagementMode ::= TEXTUAL-CONVENTION
    STATUS current
    DESCRIPTION
        "Represents the management mode of an RMD."
    SYNTAX INTEGER {
           mgmtModeIntegrated(0),
           mgmtModeStandalone(1),
           mgmtModeNotApplicable(255)
           }

TnRmdSystemName ::= TEXTUAL-CONVENTION
    STATUS current
    DESCRIPTION
       "Contains the name of an RMD.
        The set of allowed octet values is RMD type specific."
    SYNTAX OCTET STRING (SIZE(32))

TnRmdSystemResetType ::= TEXTUAL-CONVENTION
    STATUS current
    DESCRIPTION
        "Represents the type of reset of an RMD.

         An object of this type can be set to the following values :
          resetWarm1 : Non-service affecting soft reset.
          resetWarm2 : Possibly service affecting soft reset.
          resetWarm3 : Service affecting soft reset.
          resetCold  : Hard reset, always affecting.
          noCmd      : Setting to this value has no effect."
    SYNTAX INTEGER {
           resetWarm1(0),
           resetWarm2(1),
           resetWarm3(2),
           resetCold(3),
           noCmd(255)
           }

TnRmdSystemDeviceStatus ::= TEXTUAL-CONVENTION
    STATUS current
    DESCRIPTION
        "Indicates the status of the device.

         Normal: Device is operating as expected
         NDF:    No Device Found
         DNR:    Device Not Reachable
         WDP:    Wrong Device Present
         PWR:    Power Failure
         EQF:    Equipment Fault

         Note: Power Failure can only occur for the cedd."
    SYNTAX INTEGER {
              normal  (1),
              ndf     (2),
              dnr     (3),
              wdp     (4),
              pwr     (5),
              eqf     (6)
           }

TnRmdSystemRmdAccessIfType ::= TEXTUAL-CONVENTION
    STATUS current
    DESCRIPTION
        "Represents the type of logical interfae which the remote
         managed devices are accessed.

         An object of this type can be set to the following values :
           port    : Specifies that a port is to be used to manage RMDs
           sap     : Specifies that SAPs are to be used to manage RMDs."
    SYNTAX INTEGER {
              port    (1),
              sap     (2)
           }


--------------------------------------------------------------------------------
-- RMD System Scalar
--------------------------------------------------------------------------------
tnRmdSystemAttributeTotal OBJECT-TYPE
    SYNTAX      Integer32
    MAX-ACCESS  read-only
    STATUS      current
    DESCRIPTION ""
    ::= { tnRmdSystemObjects 1 }

-- =============================================================
-- tnRmdDiscoverySystemTable
-- =============================================================
tnRmdDiscoverySystemTable OBJECT-TYPE
    SYNTAX      SEQUENCE OF TnRmdDiscoverySystemEntry
    MAX-ACCESS  not-accessible
    STATUS      current
    DESCRIPTION
        "A table containing the parameters used to discover RMDs."
    ::= { tnRmdSystemObjects 2 }

tnRmdDiscoverySystemEntry OBJECT-TYPE
    SYNTAX      TnRmdDiscoverySystemEntry
    MAX-ACCESS  not-accessible
    STATUS      current
    DESCRIPTION
        "An object containing the parameters used to discover RMDs."
    INDEX  { tnSysSwitchId }
    ::= { tnRmdDiscoverySystemTable 1 }

TnRmdDiscoverySystemEntry ::=
    SEQUENCE {
        tnRmdDiscoveryMcMacAddress     MacAddress,
        tnRmdDiscoveryMode             TnRmdDiscoveryMode,
        tnRmdDiscoveryNumberOfVlanTags TnRmdNumberOfVlanTags,
        tnRmdDiscoveryOuterTPID        TnRmdTpid,
        tnRmdDiscoveryOuterVlanId      VlanId,
        tnRmdDiscoveryOuterPCP         TnRmdPcp,
        tnRmdDiscoveryOuterDEI         TruthValue,
        tnRmdDiscoveryInnerTPID        TnRmdTpid,
        tnRmdDiscoveryInnerVlanId      VlanId,
        tnRmdDiscoveryInnerPCP         TnRmdPcp,
        tnRmdDiscoveryInnerDEI         TruthValue,
        tnRmdDiscoveryRmdAccessIf      TnRmdAccessIfIndex,
        tnRmdDiscoveryOui              TnRmdOui
    }

tnRmdDiscoveryMcMacAddress OBJECT-TYPE
    SYNTAX      MacAddress
    MAX-ACCESS  read-create
    STATUS      current
    DESCRIPTION
        "The Multicast MAC Address used to discover RMDs."
    ::= { tnRmdDiscoverySystemEntry 1 }

tnRmdDiscoveryMode OBJECT-TYPE
    SYNTAX      TnRmdDiscoveryMode
    MAX-ACCESS  read-create
    STATUS      current
    DESCRIPTION
        "Determines which devices will reply to the discovery request.
          pollAll   : any RMD will reply
          pollGroup : only RMDs with discovery mode 'group' will reply."
    ::= { tnRmdDiscoverySystemEntry 2 }

tnRmdDiscoveryNumberOfVlanTags OBJECT-TYPE
    SYNTAX      TnRmdNumberOfVlanTags
    MAX-ACCESS  read-create
    STATUS      current
    DESCRIPTION
        "Number of VLAN Tags used to encapsulate the IDL protocol frames."
    ::= { tnRmdDiscoverySystemEntry 3 }

tnRmdDiscoveryOuterTPID OBJECT-TYPE
    SYNTAX      TnRmdTpid
    MAX-ACCESS  read-create
    STATUS      current
    DESCRIPTION
        "The TPID of the outer VLAN Tag in which the IDL protocol
         frames are encapsulated."
    ::= { tnRmdDiscoverySystemEntry 4 }

tnRmdDiscoveryOuterVlanId OBJECT-TYPE
    SYNTAX      VlanId
    MAX-ACCESS  read-create
    STATUS      current
    DESCRIPTION
        "The VLAN-ID of the outer VLAN Tag in which the IDL protocol
         frames are encapsulated."
    ::= { tnRmdDiscoverySystemEntry 5 }

tnRmdDiscoveryOuterPCP OBJECT-TYPE
    SYNTAX      TnRmdPcp
    MAX-ACCESS  read-create
    STATUS      current
    DESCRIPTION
        "The PCP of the outer VLAN Tag in which the IDL protocol
         frames are encapsulated."
    ::= { tnRmdDiscoverySystemEntry 6 }

tnRmdDiscoveryOuterDEI OBJECT-TYPE
    SYNTAX      TruthValue
    MAX-ACCESS  read-create
    STATUS      current
    DESCRIPTION
        "The DEI of the outer VLAN Tag in which the IDL protocol
         frames are encapsulated."
    ::= { tnRmdDiscoverySystemEntry 7 }

tnRmdDiscoveryInnerTPID OBJECT-TYPE
    SYNTAX      TnRmdTpid
    MAX-ACCESS  read-create
    STATUS      current
    DESCRIPTION
        "The TPID of the inner VLAN Tag in which the IDL protocol
         frames are encapsulated."
    ::= { tnRmdDiscoverySystemEntry 8 }

tnRmdDiscoveryInnerVlanId OBJECT-TYPE
    SYNTAX      VlanId
    MAX-ACCESS  read-create
    STATUS      current
    DESCRIPTION
        "The VLAN-ID of the inner VLAN Tag in which the IDL protocol
         frames are encapsulated."
    ::= { tnRmdDiscoverySystemEntry 9 }

tnRmdDiscoveryInnerPCP OBJECT-TYPE
    SYNTAX      TnRmdPcp
    MAX-ACCESS  read-create
    STATUS      current
    DESCRIPTION
        "The PCP of the inner VLAN Tag in which the IDL protocol
         frames are encapsulated."
    ::= { tnRmdDiscoverySystemEntry 10 }

tnRmdDiscoveryInnerDEI OBJECT-TYPE
    SYNTAX      TruthValue
    MAX-ACCESS  read-create
    STATUS      current
    DESCRIPTION
        "The DEI of the inner VLAN Tag in which the IDL protocol
         frames are encapsulated."
    ::= { tnRmdDiscoverySystemEntry 11 }

tnRmdDiscoveryRmdAccessIf OBJECT-TYPE
    SYNTAX      TnRmdAccessIfIndex
    MAX-ACCESS  read-create
    STATUS      current
    DESCRIPTION
        "The access interface on the Agent via which the discovery is performed."
    ::= { tnRmdDiscoverySystemEntry 12 }

tnRmdDiscoveryOui OBJECT-TYPE
    SYNTAX      TnRmdOui
    MAX-ACCESS  read-create
    STATUS      current
    DESCRIPTION
        "The Organization Unique Identifier (OUI) of the RMDs that should
         respond to the discovery request."
    ::= { tnRmdDiscoverySystemEntry 13 }

-- =============================================================
-- tnRmdDiscoverySystemStartTable
-- =============================================================
tnRmdDiscoverySystemStartTable OBJECT-TYPE
    SYNTAX      SEQUENCE OF TnRmdDiscoverySystemStartEntry
    MAX-ACCESS  not-accessible
    STATUS      current
    DESCRIPTION
        "A table used to trigger the discovery of RMDs."
    ::= { tnRmdSystemObjects 3 }

tnRmdDiscoverySystemStartEntry OBJECT-TYPE
    SYNTAX      TnRmdDiscoverySystemStartEntry
    MAX-ACCESS  not-accessible
    STATUS      current
    DESCRIPTION
        "An object used to trigger the discovery of RMDs."
    INDEX  { tnSysSwitchId }
    ::= { tnRmdDiscoverySystemStartTable 1 }

TnRmdDiscoverySystemStartEntry ::=
    SEQUENCE {
        tnRmdDiscoveryStart            TruthValue
    }

tnRmdDiscoveryStart OBJECT-TYPE
    SYNTAX      TruthValue
    MAX-ACCESS  read-create
    STATUS      current
    DESCRIPTION
        "Setting of this object to value 'true' triggers the start of
         a discovery of RMDs. The discovery makes use of the values of
         the following objects :

           - tnRmdDiscoveryMcMacAddress
           - tnRmdDiscoveryMode
           - tnRmdDiscoveryNumberOfVlanTags
           - tnRmdDiscoveryOuterTPID
           - tnRmdDiscoveryOuterVlanId
           - tnRmdDiscoveryOuterPCP
           - tnRmdDiscoveryOuterDEI
           - tnRmdDiscoveryInnerTPID
           - tnRmdDiscoveryInnerVlanId
           - tnRmdDiscoveryInnerPCP
           - tnRmdDiscoveryInnerDEI
           - tnRmdDiscoveryRmdAccessIf
           - tnRmdDiscoveryOui

         Setting of this object to value 'false' has no effect.

         This object is merely used to trigger the start of a discovery,
         and its actual value has no meaning."
    ::= { tnRmdDiscoverySystemStartEntry 1 }

-- =============================================================
-- tnRmdDiscoverySystemClearTable
-- =============================================================
tnRmdDiscoverySystemClearTable OBJECT-TYPE
    SYNTAX      SEQUENCE OF TnRmdDiscoverySystemClearEntry
    MAX-ACCESS  not-accessible
    STATUS      current
    DESCRIPTION
        "A table used to trigger the clearing of entries from table
         tnRmdDiscoveredSystemTable."
    ::= { tnRmdSystemObjects 4 }

tnRmdDiscoverySystemClearEntry OBJECT-TYPE
    SYNTAX      TnRmdDiscoverySystemClearEntry
    MAX-ACCESS  not-accessible
    STATUS      current
    DESCRIPTION
        "An object used to trigger the clearing of entries from table
         tnRmdDiscoveredSystemTable."
    INDEX  { tnSysSwitchId }
    ::= { tnRmdDiscoverySystemClearTable 1 }

TnRmdDiscoverySystemClearEntry ::=
    SEQUENCE {
        tnRmdDiscoveryClear            TruthValue
    }

tnRmdDiscoveryClear OBJECT-TYPE
    SYNTAX      TruthValue
    MAX-ACCESS  read-create
    STATUS      current
    DESCRIPTION
        "Setting of this object to value 'true' triggers the clearing of
         entries from table tnRmdDiscoveredSystemTable.

         The clearing is performed based on the values of a subset of the
         following objects :

           - tnRmdDiscoveryNumberOfVlanTags
           - tnRmdDiscoveryOuterTPID
           - tnRmdDiscoveryOuterVlanId
           - tnRmdDiscoveryOuterPCP
           - tnRmdDiscoveryOuterDEI
           - tnRmdDiscoveryInnerTPID
           - tnRmdDiscoveryInnerVlanId
           - tnRmdDiscoveryInnerPCP
           - tnRmdDiscoveryInnerDEI
           - tnRmdDiscoveryRmdAccessIf
           - tnRmdDiscoveryOui

         The subset of objects used for the clearing is product specific.

         Setting of this object to value 'false' has no effect.

         This object is merely used to trigger the clearing of table
         entries, and its actual value has no meaning."
    ::= { tnRmdDiscoverySystemClearEntry 1 }

-- =============================================================
-- tnRmdDiscoveredSystemTable
-- =============================================================
tnRmdDiscoveredSystemTable OBJECT-TYPE
    SYNTAX      SEQUENCE OF TnRmdDiscoveredSystemEntry
    MAX-ACCESS  not-accessible
    STATUS      current
    DESCRIPTION
        "A table containing the information of all discovered RMDs."
    ::= { tnRmdSystemObjects 5 }

tnRmdDiscoveredSystemEntry OBJECT-TYPE
    SYNTAX      TnRmdDiscoveredSystemEntry
    MAX-ACCESS  not-accessible
    STATUS      current
    DESCRIPTION
        "An object containing the information of a discovered RMD."
    INDEX  { tnSysSwitchId,
             tnRmdDiscoveredSystemRmdAccessIf,
             tnRmdDiscoveredSystemMacAddress }
    ::= { tnRmdDiscoveredSystemTable 1 }

TnRmdDiscoveredSystemEntry ::=
    SEQUENCE {
        tnRmdDiscoveredSystemRmdAccessIf       TnRmdAccessIfIndex,
        tnRmdDiscoveredSystemMacAddress        MacAddress,
        tnRmdDiscoveredSystemDeviceType        TnRmdDeviceType,
        tnRmdDiscoveredSystemMcMacAddress      MacAddress,
        tnRmdDiscoveredSystemNumberOfVlanTags  TnRmdNumberOfVlanTags,
        tnRmdDiscoveredSystemOuterTPID         TnRmdTpid,
        tnRmdDiscoveredSystemOuterVlanId       VlanId,
        tnRmdDiscoveredSystemOuterPCP          TnRmdPcp,
        tnRmdDiscoveredSystemOuterDEI          TruthValue,
        tnRmdDiscoveredSystemInnerTPID         TnRmdTpid,
        tnRmdDiscoveredSystemInnerVlanId       VlanId,
        tnRmdDiscoveredSystemInnerPCP          TnRmdPcp,
        tnRmdDiscoveredSystemInnerDEI          TruthValue,
        tnRmdDiscoveredSystemOui               TnRmdOui
    }

tnRmdDiscoveredSystemRmdAccessIf OBJECT-TYPE
    SYNTAX      TnRmdAccessIfIndex
    MAX-ACCESS  not-accessible
    STATUS      current
    DESCRIPTION
        "The access interface on the Agent via which the discovery of the
         RMD was performed."
    ::= { tnRmdDiscoveredSystemEntry 1 }

tnRmdDiscoveredSystemMacAddress OBJECT-TYPE
    SYNTAX      MacAddress
    MAX-ACCESS  not-accessible
    STATUS      current
    DESCRIPTION
        "The MAC address of the discovered RMD."
    ::= { tnRmdDiscoveredSystemEntry 2 }

tnRmdDiscoveredSystemDeviceType OBJECT-TYPE
    SYNTAX      TnRmdDeviceType
    MAX-ACCESS  read-only
    STATUS      current
    DESCRIPTION
        "The device type of the discovered RMD."
    ::= { tnRmdDiscoveredSystemEntry 3 }

tnRmdDiscoveredSystemMcMacAddress OBJECT-TYPE
    SYNTAX      MacAddress
    MAX-ACCESS  read-only
    STATUS      current
    DESCRIPTION
        "The Multicast MAC address used for the discovery of the RMD."
    ::= { tnRmdDiscoveredSystemEntry 4 }

tnRmdDiscoveredSystemNumberOfVlanTags OBJECT-TYPE
    SYNTAX      TnRmdNumberOfVlanTags
    MAX-ACCESS  read-only
    STATUS      current
    DESCRIPTION
        "Number of VLAN Tags used to encapsulate the IDL protocol frames."
    ::= { tnRmdDiscoveredSystemEntry 5 }

tnRmdDiscoveredSystemOuterTPID OBJECT-TYPE
    SYNTAX      TnRmdTpid
    MAX-ACCESS  read-only
    STATUS      current
    DESCRIPTION
        "The TPID of the outer VLAN Tag in which the IDL protocol
         frames were encapsulated."
    ::= { tnRmdDiscoveredSystemEntry 6 }

tnRmdDiscoveredSystemOuterVlanId OBJECT-TYPE
    SYNTAX      VlanId
    MAX-ACCESS  read-only
    STATUS      current
    DESCRIPTION
        "The VLAN-ID of the outer VLAN Tag in which the IDL protocol
         frames were encapsulated."
    ::= { tnRmdDiscoveredSystemEntry 7 }

tnRmdDiscoveredSystemOuterPCP OBJECT-TYPE
    SYNTAX      TnRmdPcp
    MAX-ACCESS  read-only
    STATUS      current
    DESCRIPTION
        "The PCP of the outer VLAN Tag in which the IDL protocol
         frames were encapsulated."
    ::= { tnRmdDiscoveredSystemEntry 8 }

tnRmdDiscoveredSystemOuterDEI OBJECT-TYPE
    SYNTAX      TruthValue
    MAX-ACCESS  read-only
    STATUS      current
    DESCRIPTION
        "The DEI of the outer VLAN Tag in which the IDL protocol
         frames were encapsulated."
    ::= { tnRmdDiscoveredSystemEntry 9 }

tnRmdDiscoveredSystemInnerTPID OBJECT-TYPE
    SYNTAX      TnRmdTpid
    MAX-ACCESS  read-only
    STATUS      current
    DESCRIPTION
        "The TPID of the inner VLAN Tag in which the IDL protocol
         frames were encapsulated."
    ::= { tnRmdDiscoveredSystemEntry 10 }

tnRmdDiscoveredSystemInnerVlanId OBJECT-TYPE
    SYNTAX      VlanId
    MAX-ACCESS  read-only
    STATUS      current
    DESCRIPTION
        "The VLAN-ID of the inner VLAN Tag in which the IDL protocol
         frames were encapsulated."
    ::= { tnRmdDiscoveredSystemEntry 11 }

tnRmdDiscoveredSystemInnerPCP OBJECT-TYPE
    SYNTAX      TnRmdPcp
    MAX-ACCESS  read-only
    STATUS      current
    DESCRIPTION
        "The PCP of the inner VLAN Tag in which the IDL protocol
         frames were encapsulated."
    ::= { tnRmdDiscoveredSystemEntry 12 }

tnRmdDiscoveredSystemInnerDEI OBJECT-TYPE
    SYNTAX      TruthValue
    MAX-ACCESS  read-only
    STATUS      current
    DESCRIPTION
        "The DEI of the inner VLAN Tag in which the IDL protocol
         frames were encapsulated."
    ::= { tnRmdDiscoveredSystemEntry 13 }

tnRmdDiscoveredSystemOui OBJECT-TYPE
    SYNTAX      TnRmdOui
    MAX-ACCESS  read-only
    STATUS      current
    DESCRIPTION
        "The Organization Unique Identifier used for the
         discovery of the RMD."
    ::= { tnRmdDiscoveredSystemEntry 14 }

-- =============================================================
-- tnRmdSystemTable
-- =============================================================
tnRmdSystemTable OBJECT-TYPE
    SYNTAX      SEQUENCE OF TnRmdSystemEntry
    MAX-ACCESS  not-accessible
    STATUS      current
    DESCRIPTION
        "A table containing system level parameters of all RMDs."
    ::= { tnRmdSystemObjects 6 }

tnRmdSystemEntry OBJECT-TYPE
    SYNTAX      TnRmdSystemEntry
    MAX-ACCESS  not-accessible
    STATUS      current
    DESCRIPTION
        "A list of objects containing system level parameters of an RMD."
    INDEX  { tnSysSwitchId,
             tnRmdSystemId }
    ::= { tnRmdSystemTable 1 }

TnRmdSystemEntry ::=
    SEQUENCE {
        tnRmdSystemId                TnRmdSystemId,
        tnRmdSystemMacAddress        MacAddress,
        tnRmdSystemDeviceType        TnRmdDeviceType,
        tnRmdSystemMcMacAddress      MacAddress,
        tnRmdSystemDiscoveryMode     TnRmdDiscoveryMode,
        tnRmdSystemNumberOfVlanTags  TnRmdNumberOfVlanTags,
        tnRmdSystemOuterTPID         TnRmdTpid,
        tnRmdSystemOuterVlanId       VlanId,
        tnRmdSystemOuterPCP          TnRmdPcp,
        tnRmdSystemOuterDEI          TruthValue,
        tnRmdSystemInnerTPID         TnRmdTpid,
        tnRmdSystemInnerVlanId       VlanId,
        tnRmdSystemInnerPCP          TnRmdPcp,
        tnRmdSystemInnerDEI          TruthValue,
        tnRmdSystemRmdAccessIf       TnRmdAccessIfIndex,
        tnRmdSystemOui               TnRmdOui,
        tnRmdSystemName              TnRmdSystemName,
        tnRmdSystemLocation          TnRmdSystemLocation,
        tnRmdSystemDescription       TItemDescription,
        tnRmdSystemManagementMode    TnRmdSystemManagementMode,
        tnRmdSystemReset             TnRmdSystemResetType,
        tnRmdSystemRowStatus         RowStatus,
        tnRmdSystemDeviceStatus      TnRmdSystemDeviceStatus
    }

tnRmdSystemId OBJECT-TYPE
    SYNTAX      TnRmdSystemId
    MAX-ACCESS  not-accessible
    STATUS      current
    DESCRIPTION
        "The ID of the RMD."
    ::= { tnRmdSystemEntry 1 }

tnRmdSystemMacAddress OBJECT-TYPE
    SYNTAX      MacAddress
    MAX-ACCESS  read-create
    STATUS      current
    DESCRIPTION
        "The MAC address of the RMD
         An all-zero MAC address value represents an 'unknown MAC address'."
    ::= { tnRmdSystemEntry 2 }

tnRmdSystemDeviceType OBJECT-TYPE
    SYNTAX      TnRmdDeviceType
    MAX-ACCESS  read-create
    STATUS      current
    DESCRIPTION
        "The device type of the RMD."
    ::= { tnRmdSystemEntry 3 }

tnRmdSystemMcMacAddress OBJECT-TYPE
    SYNTAX      MacAddress
    MAX-ACCESS  read-create
    STATUS      current
    DESCRIPTION
        "The Multicast MAC address used for the discovery."
    ::= { tnRmdSystemEntry 4 }

tnRmdSystemDiscoveryMode OBJECT-TYPE
    SYNTAX      TnRmdDiscoveryMode
    MAX-ACCESS  read-create
    STATUS      current
    DESCRIPTION
        "The mode of the discovery of the RMD."
    ::= { tnRmdSystemEntry 5 }

tnRmdSystemNumberOfVlanTags OBJECT-TYPE
    SYNTAX      TnRmdNumberOfVlanTags
    MAX-ACCESS  read-create
    STATUS      current
    DESCRIPTION
        "Number of VLAN Tags used to encapsulate the IDL protocol frames."
    ::= { tnRmdSystemEntry 6 }

tnRmdSystemOuterTPID OBJECT-TYPE
    SYNTAX      TnRmdTpid
    MAX-ACCESS  read-create
    STATUS      current
    DESCRIPTION
        "The TPID of the outer VLAN Tag in which the IDL protocol
         frames are encapsulated."
    ::= { tnRmdSystemEntry 7 }

tnRmdSystemOuterVlanId OBJECT-TYPE
    SYNTAX      VlanId
    MAX-ACCESS  read-create
    STATUS      current
    DESCRIPTION
        "The VLAN-ID of the outer VLAN Tag in which the IDL protocol
         frames are encapsulated."
    ::= { tnRmdSystemEntry 8 }

tnRmdSystemOuterPCP OBJECT-TYPE
    SYNTAX      TnRmdPcp
    MAX-ACCESS  read-create
    STATUS      current
    DESCRIPTION
        "The PCP of the outer VLAN Tag in which the IDL protocol
         frames are encapsulated."
    ::= { tnRmdSystemEntry 9 }

tnRmdSystemOuterDEI OBJECT-TYPE
    SYNTAX      TruthValue
    MAX-ACCESS  read-create
    STATUS      current
    DESCRIPTION
        "The DEI of the outer VLAN Tag in which the IDL protocol
         frames are encapsulated."
    ::= { tnRmdSystemEntry 10 }

tnRmdSystemInnerTPID OBJECT-TYPE
    SYNTAX      TnRmdTpid
    MAX-ACCESS  read-create
    STATUS      current
    DESCRIPTION
        "The TPID of the inner VLAN Tag in which the IDL protocol
         frames are encapsulated."
    ::= { tnRmdSystemEntry 11 }

tnRmdSystemInnerVlanId OBJECT-TYPE
    SYNTAX      VlanId
    MAX-ACCESS  read-create
    STATUS      current
    DESCRIPTION
        "The VLAN-ID of the inner VLAN Tag in which the IDL protocol
         frames are encapsulated."
    ::= { tnRmdSystemEntry 12 }

tnRmdSystemInnerPCP OBJECT-TYPE
    SYNTAX      TnRmdPcp
    MAX-ACCESS  read-create
    STATUS      current
    DESCRIPTION
        "The PCP of the inner VLAN Tag in which the IDL protocol
         frames are encapsulated."
    ::= { tnRmdSystemEntry 13 }

tnRmdSystemInnerDEI OBJECT-TYPE
    SYNTAX      TruthValue
    MAX-ACCESS  read-create
    STATUS      current
    DESCRIPTION
        "The DEI of the inner VLAN Tag in which the IDL protocol
         frames are encapsulated."
    ::= { tnRmdSystemEntry 14 }

tnRmdSystemRmdAccessIf OBJECT-TYPE
    SYNTAX      TnRmdAccessIfIndex
    MAX-ACCESS  read-create
    STATUS      current
    DESCRIPTION
        "The access interface via which the management of the RMD is performed."
    ::= { tnRmdSystemEntry 15 }

tnRmdSystemOui OBJECT-TYPE
    SYNTAX      TnRmdOui
    MAX-ACCESS  read-create
    STATUS      current
    DESCRIPTION
        "The Organization Unique Identifier of the RMD."
    ::= { tnRmdSystemEntry 16 }

tnRmdSystemName OBJECT-TYPE
    SYNTAX      TnRmdSystemName
    MAX-ACCESS  read-create
    STATUS      current
    DESCRIPTION
        "The name of the RMD."
    ::= { tnRmdSystemEntry 17 }

tnRmdSystemLocation OBJECT-TYPE
    SYNTAX      TnRmdSystemLocation
    MAX-ACCESS  read-create
    STATUS      current
    DESCRIPTION
        "The location of the RMD."
    ::= { tnRmdSystemEntry 18 }

tnRmdSystemDescription OBJECT-TYPE
    SYNTAX      TItemDescription
    MAX-ACCESS  read-create
    STATUS      current
    DESCRIPTION
        "A description for the RMD."
    ::= { tnRmdSystemEntry 19 }

tnRmdSystemManagementMode OBJECT-TYPE
    SYNTAX      TnRmdSystemManagementMode
    MAX-ACCESS  read-create
    STATUS      current
    DESCRIPTION
        "The management mode of the RMD."
    ::= { tnRmdSystemEntry 20 }

tnRmdSystemReset OBJECT-TYPE
    SYNTAX      TnRmdSystemResetType
    MAX-ACCESS  read-create
    STATUS      current
    DESCRIPTION
        "Setting of this object invokes a reset of the RMD.
         The value to which this object is set determines the type of
         reset that is performed by the RMD.

         This object is merely used to invoke a reset, and its actual
         value has no meaning."
    ::= { tnRmdSystemEntry 21 }

tnRmdSystemRowStatus OBJECT-TYPE
    SYNTAX      RowStatus
    MAX-ACCESS  read-create
    STATUS      current
    DESCRIPTION
        "Used to create, delete or activate an entry in this table."
    ::= { tnRmdSystemEntry 22 }

tnRmdSystemDeviceStatus OBJECT-TYPE
    SYNTAX      TnRmdSystemDeviceStatus
    MAX-ACCESS  read-only
    STATUS      current
    DESCRIPTION
        "Indicates the status of the device.

           Normal: Device is operating as expected
           NDF:    No Device Found
           DNR:    Device Not Reachable
           MDF:    Multiple Devices Found
           WDP:    Wrong Device Present
           Init:   Device is initializing"
    ::= { tnRmdSystemEntry 23 }

-- =============================================================
-- tnRmdSystemInventoryTable
-- =============================================================
tnRmdSystemInventoryTable OBJECT-TYPE
    SYNTAX      SEQUENCE OF TnRmdSystemInventoryEntry
    MAX-ACCESS  not-accessible
    STATUS      current
    DESCRIPTION
        "A table containing the system inventory of all RMDs."
    ::= { tnRmdSystemObjects 7 }

tnRmdSystemInventoryEntry OBJECT-TYPE
    SYNTAX      TnRmdSystemInventoryEntry
    MAX-ACCESS  not-accessible
    STATUS      current
    DESCRIPTION
        "An object containing the system inventory of an RMD."
    INDEX  { tnSysSwitchId,
             tnRmdSystemId }
    ::= { tnRmdSystemInventoryTable 1 }

TnRmdSystemInventoryEntry ::=
    SEQUENCE {
--        obsolete
--        tnRmdSystemInventory                              TnRmdInventory
        tnRmdSystemInventoryModuleVendorSerNo             SnmpAdminString,
        tnRmdSystemInventoryModuleVendor                  SnmpAdminString,
        tnRmdSystemInventoryWavelength                    Unsigned32,
        tnRmdSystemInventoryModuleType                    SnmpAdminString,
        tnRmdSystemInventoryCLEI                          SnmpAdminString,
        tnRmdSystemInventoryUnitPartNum                   SnmpAdminString,
        tnRmdSystemInventorySWPartNum                     SnmpAdminString,
        tnRmdSystemInventoryFactoryID                     SnmpAdminString,
        tnRmdSystemInventoryDate                          SnmpAdminString,
        tnRmdSystemInventoryExtraData                     SnmpAdminString,
        tnRmdSystemInventoryMaximumCaseTemperature        Integer32,
        tnRmdSystemInventoryInterchangeabilityMarking     SnmpAdminString,
        tnRmdSystemInventoryAcronymCode                   SnmpAdminString,
        tnRmdSystemInventoryCustomerInventoryField        SnmpAdminString
    }

-- obsolete
-- tnRmdSystemInventory OBJECT-TYPE ::= { tnRmdSystemInventoryEntry 1 }

tnRmdSystemInventoryModuleVendorSerNo OBJECT-TYPE
    SYNTAX      SnmpAdminString (SIZE(0..18))
    MAX-ACCESS  read-only
    STATUS      current
    DESCRIPTION "Module vendor serial number."
    ::= { tnRmdSystemInventoryEntry 2 }

tnRmdSystemInventoryModuleVendor OBJECT-TYPE
    SYNTAX      SnmpAdminString (SIZE(0..16))
    MAX-ACCESS  read-only
    STATUS      current
    DESCRIPTION "Module vendor."
    ::= { tnRmdSystemInventoryEntry 3 }

tnRmdSystemInventoryWavelength OBJECT-TYPE
    SYNTAX      Unsigned32
    MAX-ACCESS  read-only
    STATUS      current
    DESCRIPTION "wavelength."
    ::= { tnRmdSystemInventoryEntry 4 }

tnRmdSystemInventoryModuleType OBJECT-TYPE
    SYNTAX      SnmpAdminString
    MAX-ACCESS  read-only
    STATUS      current
    DESCRIPTION "Module type."
    ::= { tnRmdSystemInventoryEntry 5 }

tnRmdSystemInventoryCLEI OBJECT-TYPE
    SYNTAX      SnmpAdminString
    MAX-ACCESS  read-only
    STATUS      current
    DESCRIPTION "CLEI."
    ::= { tnRmdSystemInventoryEntry 6 }

tnRmdSystemInventoryUnitPartNum OBJECT-TYPE
    SYNTAX      SnmpAdminString
    MAX-ACCESS  read-only
    STATUS      current
    DESCRIPTION "Unit part number."
    ::= { tnRmdSystemInventoryEntry 7 }

tnRmdSystemInventorySWPartNum OBJECT-TYPE
    SYNTAX      SnmpAdminString
    MAX-ACCESS  read-only
    STATUS      current
    DESCRIPTION "Software part number."
    ::= { tnRmdSystemInventoryEntry 8 }

tnRmdSystemInventoryFactoryID OBJECT-TYPE
    SYNTAX      SnmpAdminString
    MAX-ACCESS  read-only
    STATUS      current
    DESCRIPTION "Factory ID."
    ::= { tnRmdSystemInventoryEntry 9 }

tnRmdSystemInventoryDate OBJECT-TYPE
    SYNTAX      SnmpAdminString
    MAX-ACCESS  read-only
    STATUS      current
    DESCRIPTION "Date."
    ::= { tnRmdSystemInventoryEntry 10 }

tnRmdSystemInventoryExtraData OBJECT-TYPE
    SYNTAX      SnmpAdminString
    MAX-ACCESS  read-only
    STATUS      current
    DESCRIPTION "Extra data."
    ::= { tnRmdSystemInventoryEntry 11 }

tnRmdSystemInventoryMaximumCaseTemperature OBJECT-TYPE
    SYNTAX      Integer32
    MAX-ACCESS  read-only
    STATUS      current
    DESCRIPTION "Maximum case temperature."
    ::= { tnRmdSystemInventoryEntry 12 }

tnRmdSystemInventoryInterchangeabilityMarking OBJECT-TYPE
    SYNTAX      SnmpAdminString (SIZE(0..6))
    MAX-ACCESS  read-only
    STATUS      current
    DESCRIPTION "Interchangeability marking."
    ::= { tnRmdSystemInventoryEntry 13 }

tnRmdSystemInventoryAcronymCode OBJECT-TYPE
    SYNTAX      SnmpAdminString (SIZE(0..12))
    MAX-ACCESS  read-only
    STATUS      current
    DESCRIPTION "Acronym code."
    ::= { tnRmdSystemInventoryEntry 14 }

tnRmdSystemInventoryCustomerInventoryField OBJECT-TYPE
    SYNTAX      SnmpAdminString (SIZE(0..12))
    MAX-ACCESS  read-only
    STATUS      current
    DESCRIPTION "Customer Inventory Field."
    ::= { tnRmdSystemInventoryEntry 15 }

-- =============================================================
-- tnRmdSystemSwImageTable
-- =============================================================
tnRmdSystemSwImageTable OBJECT-TYPE
    SYNTAX      SEQUENCE OF TnRmdSystemSwImageEntry
    MAX-ACCESS  not-accessible
    STATUS      current
    DESCRIPTION
        "A table containing the characteristics of the software images
         of all RMDs."
    ::= { tnRmdSystemObjects 8 }

tnRmdSystemSwImageEntry OBJECT-TYPE
    SYNTAX      TnRmdSystemSwImageEntry
    MAX-ACCESS  not-accessible
    STATUS      current
    DESCRIPTION
        "A list of objects containing the characteristics of a software
         image of an RMD."
    INDEX  { tnSysSwitchId,
             tnRmdSystemId,
             tnRmdSystemSwImageId }
    ::= { tnRmdSystemSwImageTable 1 }

TnRmdSystemSwImageEntry ::=
    SEQUENCE {
        tnRmdSystemSwImageId        Unsigned32,
        tnRmdSystemSwImageState     TnRmdSwImageState,
        tnRmdSystemSwImageVersion   TnRmdVersion,
        tnRmdSystemSwImageDate      DateAndTime,
        tnRmdSystemSwImageItemCode  TnRmdItemCode,
        tnRmdSystemSwImageSize      Unsigned32
    }

tnRmdSystemSwImageId OBJECT-TYPE
    SYNTAX      Unsigned32
    MAX-ACCESS  not-accessible
    STATUS      current
    DESCRIPTION
        "The ID of the software image."
    ::= { tnRmdSystemSwImageEntry 1 }

tnRmdSystemSwImageState OBJECT-TYPE
    SYNTAX      TnRmdSwImageState
    MAX-ACCESS  read-only
    STATUS      current
    DESCRIPTION
        "The status of the software image."
    ::= { tnRmdSystemSwImageEntry 2 }

tnRmdSystemSwImageVersion OBJECT-TYPE
    SYNTAX      TnRmdVersion
    MAX-ACCESS  read-only
    STATUS      current
    DESCRIPTION
        "The version of the software image."
     ::= { tnRmdSystemSwImageEntry 3 }

tnRmdSystemSwImageDate OBJECT-TYPE
    SYNTAX      DateAndTime
    MAX-ACCESS  read-only
    STATUS      current
    DESCRIPTION
        "The release date of the software image."
    ::= { tnRmdSystemSwImageEntry 4 }

tnRmdSystemSwImageItemCode OBJECT-TYPE
    SYNTAX      TnRmdItemCode
    MAX-ACCESS  read-only
    STATUS      current
    DESCRIPTION
        "The item code of the software image."
    ::= { tnRmdSystemSwImageEntry 5 }

tnRmdSystemSwImageSize OBJECT-TYPE
    SYNTAX      Unsigned32
    MAX-ACCESS  read-only
    STATUS      current
    DESCRIPTION
        "The size, in octets, of the software image."
    ::= { tnRmdSystemSwImageEntry 6 }

-- =============================================================
-- tnRmdSystemFwVersionTable
-- =============================================================
tnRmdSystemFwVersionTable OBJECT-TYPE
    SYNTAX      SEQUENCE OF TnRmdSystemFwVersionEntry
    MAX-ACCESS  not-accessible
    STATUS      current
    DESCRIPTION
        "A table containing the firmware and Packet Processor (PP)
         versions of all RMDs."
    ::= { tnRmdSystemObjects 9 }

tnRmdSystemFwVersionEntry OBJECT-TYPE
    SYNTAX      TnRmdSystemFwVersionEntry
    MAX-ACCESS  not-accessible
    STATUS      current
    DESCRIPTION
        "A list of objects containing the firmware and Packet
         Processor (PP) versions of an RMD."
    INDEX  { tnSysSwitchId,
             tnRmdSystemId }
    ::= { tnRmdSystemFwVersionTable 1 }

TnRmdSystemFwVersionEntry ::=
    SEQUENCE {
        tnRmdSystemFirmwareVersion  TnRmdVersion,
        tnRmdSystemPpVersion        TnRmdVersion,
        tnRmdSystemPpNvmVersion     TnRmdVersion
    }

tnRmdSystemFirmwareVersion OBJECT-TYPE
    SYNTAX      TnRmdVersion
    MAX-ACCESS  read-only
    STATUS      current
    DESCRIPTION
        "Version of the firmware."
    ::= { tnRmdSystemFwVersionEntry 1 }

tnRmdSystemPpVersion OBJECT-TYPE
    SYNTAX      TnRmdVersion
    MAX-ACCESS  read-only
    STATUS      current
    DESCRIPTION
        "Version of the Packet Processor."
    ::= { tnRmdSystemFwVersionEntry 2 }

tnRmdSystemPpNvmVersion OBJECT-TYPE
    SYNTAX      TnRmdVersion
    MAX-ACCESS  read-only
    STATUS      current
    DESCRIPTION
        "Version of the Packet Processor in non-volatile memory."
    ::= { tnRmdSystemFwVersionEntry 3 }

-- =============================================================
-- tnRmdSystemIdlTable
-- =============================================================
-- tnRmdSystemIdlTable OBJECT-TYPE
--     SYNTAX      SEQUENCE OF TnRmdSystemIdlEntry
--     MAX-ACCESS  not-accessible
--     STATUS      current
--     DESCRIPTION
--         "A table containing the system-level IDL parameters of all RMDs."
--     ::= { tnRmdSystemObjects 10 }
--
-- tnRmdSystemIdlEntry OBJECT-TYPE
--     SYNTAX      TnRmdSystemIdlEntry
--     MAX-ACCESS  not-accessible
--     STATUS      current
--     DESCRIPTION
--         "A list of objects containing the system-level IDL parameters
--          of an RMD."
--     INDEX  { tnSysSwitchId,
--              tnRmdSystemId }
--     ::= { tnRmdSystemIdlTable 1 }
--
-- TnRmdSystemIdlEntry ::=
--     SEQUENCE {
--         tnRmdSystemIdlMcMacAddress  MacAddress
--     }
--
-- tnRmdSystemIdlMcMacAddress OBJECT-TYPE
--     SYNTAX      MacAddress
--     MAX-ACCESS  read-create
--     STATUS      current
--     DESCRIPTION
--         "The Multicast MAC address to which the IDL aware RMD must listen."
--     ::= { tnRmdSystemIdlEntry 1 }

-- =============================================================
-- tnRmdSystemIdlAcceptableSourceTable
-- =============================================================
-- tnRmdSystemIdlAcceptableSourceTable OBJECT-TYPE
--     SYNTAX      SEQUENCE OF TnRmdSystemIdlAcceptableSourceEntry
--     MAX-ACCESS  not-accessible
--     STATUS      current
--     DESCRIPTION
--         "A table containing the acceptable IDL source list of all RMDs."
--     ::= { tnRmdSystemObjects 11 }
--
-- tnRmdSystemIdlAcceptableSourceEntry OBJECT-TYPE
--     SYNTAX      TnRmdSystemIdlAcceptableSourceEntry
--     MAX-ACCESS  not-accessible
--     STATUS      current
--     DESCRIPTION
--         "A list of objects containing an acceptable IDL source of an RMD."
--     INDEX  { tnSysSwitchId,
--              tnRmdSystemId,
--              tnRmdSystemIdlAccSrcId }
--     ::= { tnRmdSystemIdlAcceptableSourceTable 1 }
--
-- TnRmdSystemIdlAcceptableSourceEntry ::=
--     SEQUENCE {
--         tnRmdSystemIdlAccSrcId                Unsigned32,
--         tnRmdSystemIdlAccSrcMacAddress        MacAddress,
--         tnRmdSystemIdlAccSrcLearn             TruthValue,
--         tnRmdSystemIdlAccSrcNumberOfVlanTags  TnRmdNumberOfVlanTags,
--         tnRmdSystemIdlAccSrcOuterTPID         TnRmdTpid,
--         tnRmdSystemIdlAccSrcOuterVlanId       VlanId,
--         tnRmdSystemIdlAccSrcOuterPCP          TnRmdPcp,
--         tnRmdSystemIdlAccSrcOuterDEI          TruthValue,
--         tnRmdSystemIdlAccSrcInnerTPID         TnRmdTpid,
--         tnRmdSystemIdlAccSrcInnerVlanId       VlanId,
--         tnRmdSystemIdlAccSrcInnerPCP          TnRmdPcp,
--         tnRmdSystemIdlAccSrcInnerDEI          TruthValue,
--         tnRmdSystemIdlAccSrcInterface         InterfaceIndex,
--         tnRmdSystemIdlAccSrcDesignatedMaster  TruthValue,
--         tnRmdSystemIdlAccSrcDiscoveryMode     TnRmdDiscoveryMode,
--         tnRmdSystemIdlAccSrcRowStatus         RowStatus
--     }
--
-- tnRmdSystemIdlAccSrcId OBJECT-TYPE
--     SYNTAX      Unsigned32
--     MAX-ACCESS  not-accessible
--     STATUS      current
--     DESCRIPTION
--         "Identifier of the acceptable source."
--     ::= { tnRmdSystemIdlAcceptableSourceEntry 1 }
--
-- tnRmdSystemIdlAccSrcMacAddress OBJECT-TYPE
--     SYNTAX      MacAddress
--     MAX-ACCESS  read-create
--     STATUS      current
--     DESCRIPTION
--         "The MAC address to which IDL replies are sent."
--     ::= { tnRmdSystemIdlAcceptableSourceEntry 2 }
--
-- tnRmdSystemIdlAccSrcLearn OBJECT-TYPE
--     SYNTAX      TruthValue
--     MAX-ACCESS  read-create
--     STATUS      current
--     DESCRIPTION
--         "Indicates whether learning is enabled."
--     ::= { tnRmdSystemIdlAcceptableSourceEntry 3 }
--
-- tnRmdSystemIdlAccSrcNumberOfVlanTags OBJECT-TYPE
--     SYNTAX      TnRmdNumberOfVlanTags
--     MAX-ACCESS  read-create
--     STATUS      current
--     DESCRIPTION
--         "Number of VLAN Tags used to encapsulate the IDL protocol frames."
--     ::= { tnRmdSystemIdlAcceptableSourceEntry 4 }
--
-- tnRmdSystemIdlAccSrcOuterTPID OBJECT-TYPE
--     SYNTAX      TnRmdTpid
--     MAX-ACCESS  read-create
--     STATUS      current
--     DESCRIPTION
--         "The TPID of the outer VLAN Tag in which the IDL protocol
--          frames are encapsulated."
--     ::= { tnRmdSystemIdlAcceptableSourceEntry 5 }
--
-- tnRmdSystemIdlAccSrcOuterVlanId OBJECT-TYPE
--     SYNTAX      VlanId
--     MAX-ACCESS  read-create
--     STATUS      current
--     DESCRIPTION
--         "The VLAN-ID of the outer VLAN Tag in which the IDL protocol
--          frames are encapsulated."
--     ::= { tnRmdSystemIdlAcceptableSourceEntry 6 }
--
-- tnRmdSystemIdlAccSrcOuterPCP OBJECT-TYPE
--     SYNTAX      TnRmdPcp
--     MAX-ACCESS  read-create
--     STATUS      current
--     DESCRIPTION
--         "The PCP of the outer VLAN Tag in which the IDL protocol
--          frames are encapsulated."
--     ::= { tnRmdSystemIdlAcceptableSourceEntry 7 }
--
-- tnRmdSystemIdlAccSrcOuterDEI OBJECT-TYPE
--     SYNTAX      TruthValue
--     MAX-ACCESS  read-create
--     STATUS      current
--     DESCRIPTION
--         "The DEI of the outer VLAN Tag in which the IDL protocol
--          frames are encapsulated."
--     ::= { tnRmdSystemIdlAcceptableSourceEntry 8 }
--
-- tnRmdSystemIdlAccSrcInnerTPID OBJECT-TYPE
--     SYNTAX      TnRmdTpid
--     MAX-ACCESS  read-create
--     STATUS      current
--     DESCRIPTION
--         "The TPID of the inner VLAN Tag in which the IDL protocol
--          frames are encapsulated."
--     ::= { tnRmdSystemIdlAcceptableSourceEntry 9 }
--
-- tnRmdSystemIdlAccSrcInnerVlanId OBJECT-TYPE
--     SYNTAX      VlanId
--     MAX-ACCESS  read-create
--     STATUS      current
--     DESCRIPTION
--         "The VLAN-ID of the inner VLAN Tag in which the IDL protocol
--          frames are encapsulated."
--     ::= { tnRmdSystemIdlAcceptableSourceEntry 10 }
--
-- tnRmdSystemIdlAccSrcInnerPCP OBJECT-TYPE
--     SYNTAX      TnRmdPcp
--     MAX-ACCESS  read-create
--     STATUS      current
--     DESCRIPTION
--         "The PCP of the inner VLAN Tag in which the IDL protocol
--          frames are encapsulated."
--     ::= { tnRmdSystemIdlAcceptableSourceEntry 11 }
--
-- tnRmdSystemIdlAccSrcInnerDEI OBJECT-TYPE
--     SYNTAX      TruthValue
--     MAX-ACCESS  read-create
--     STATUS      current
--     DESCRIPTION
--         "The DEI of the inner VLAN Tag in which the IDL protocol
--          frames are encapsulated."
--     ::= { tnRmdSystemIdlAcceptableSourceEntry 12 }
--
-- tnRmdSystemIdlAccSrcInterface OBJECT-TYPE
--     SYNTAX      InterfaceIndex
--     MAX-ACCESS  read-create
--     STATUS      current
--     DESCRIPTION
--         "The number of the interface on the RMD via which the source
--          can be reached."
--     ::= { tnRmdSystemIdlAcceptableSourceEntry 13 }
--
-- tnRmdSystemIdlAccSrcDesignatedMaster OBJECT-TYPE
--     SYNTAX      TruthValue
--     MAX-ACCESS  read-create
--     STATUS      current
--     DESCRIPTION
--         "Indicates whether the source has the IBC Master role."
--     ::= { tnRmdSystemIdlAcceptableSourceEntry 14 }
--
-- tnRmdSystemIdlAccSrcDiscoveryMode OBJECT-TYPE
--     SYNTAX      TnRmdDiscoveryMode
--     MAX-ACCESS  read-create
--     STATUS      current
--     DESCRIPTION
--         "Determines how the RMD replies to discovery requests.
--           pollAll   : the device replies to both 'all' and 'group'
--                       types of requests
--           pollGroup : the device replies only to 'group' type requests"
--     ::= { tnRmdSystemIdlAcceptableSourceEntry 15 }
--
-- tnRmdSystemIdlAccSrcRowStatus OBJECT-TYPE
--     SYNTAX      RowStatus
--     MAX-ACCESS  read-create
--     STATUS      current
--     DESCRIPTION
--         "Used to create, delete or activate an entry in this table."
--     ::= { tnRmdSystemIdlAcceptableSourceEntry 16 }

-- =============================================================
-- tnRmdSystemRmdAccessIfTable
-- =============================================================
tnRmdSystemRmdAccessIfTable OBJECT-TYPE
    SYNTAX      SEQUENCE OF TnRmdSystemRmdAccessIfEntry
    MAX-ACCESS  not-accessible
    STATUS      current
    DESCRIPTION
        "A table containing the parameters of all the RMD access interfaces of
         RMDs.  An RmdAccessIf is a logical interface where remote managed
         devices are accessed."
    ::= { tnRmdSystemObjects 12 }

tnRmdSystemRmdAccessIfEntry OBJECT-TYPE
    SYNTAX      TnRmdSystemRmdAccessIfEntry
    MAX-ACCESS  not-accessible
    STATUS      current
    DESCRIPTION
        "The tnRmdSystemRmdAccessIfEntry contains the parameters of an access
         interface to RMDs.

         Rows in this table are created and destroyed using the
         tnRmdSystemRmdAccessIfRowStatus object."
    INDEX  { tnSysSwitchId,
             tnRmdSystemRmdAccessIfIndex }
    ::= { tnRmdSystemRmdAccessIfTable 1 }

TnRmdSystemRmdAccessIfEntry ::=
    SEQUENCE {
        tnRmdSystemRmdAccessIfIndex          TnRmdAccessIfIndex,
        tnRmdSystemRmdAccessIfRowStatus      RowStatus,
        tnRmdSystemRmdAccessIfType           TnRmdSystemRmdAccessIfType,
        tnRmdSystemRmdAccessIfPortId         TmnxPortID,
        tnRmdSystemRmdAccessIfEncapVal       TmnxEncapVal,
        tnRmdSystemRmdAccessIfPortIdExt      TmnxPortID,
        tnRmdSystemRmdAccessIfEncapValExt    TmnxEncapVal
    }

tnRmdSystemRmdAccessIfIndex OBJECT-TYPE
    SYNTAX      TnRmdAccessIfIndex
    MAX-ACCESS  not-accessible
    STATUS      current
    DESCRIPTION
        "Unique value identifying the access interface to the RMD."
    ::= { tnRmdSystemRmdAccessIfEntry 1 }

tnRmdSystemRmdAccessIfRowStatus OBJECT-TYPE
    SYNTAX      RowStatus
    MAX-ACCESS  read-create
    STATUS      current
    DESCRIPTION
        "The row status controls the creation and deletion of row entries
         in the table."
    ::= { tnRmdSystemRmdAccessIfEntry 2 }

tnRmdSystemRmdAccessIfType OBJECT-TYPE
    SYNTAX      TnRmdSystemRmdAccessIfType
    MAX-ACCESS  read-create
    STATUS      current
    DESCRIPTION
        "Indicates the type of the access interface."
    ::= { tnRmdSystemRmdAccessIfEntry 3 }

tnRmdSystemRmdAccessIfPortId OBJECT-TYPE
    SYNTAX      TmnxPortID
    MAX-ACCESS  read-create
    STATUS      current
    DESCRIPTION
        "The port ID of the access interface."
    ::= { tnRmdSystemRmdAccessIfEntry 4 }

tnRmdSystemRmdAccessIfEncapVal OBJECT-TYPE
    SYNTAX      TmnxEncapVal
    MAX-ACCESS  read-create
    STATUS      current
    DESCRIPTION
        "Indicates the label used to identify the SAP on the port specified by
         tnRmdSystemRmdAccessIfPortId.

         This object is only applicable when tnRmdSystemRmdAccessIfType is set
         to sap."
    ::= { tnRmdSystemRmdAccessIfEntry 5 }

tnRmdSystemRmdAccessIfPortIdExt OBJECT-TYPE
    SYNTAX      TmnxPortID
    MAX-ACCESS  read-create
    STATUS      current
    DESCRIPTION
        "An additional port ID for the access interface.

         This object is optional, and only applicable when
         tnRmdSystemRmdAccessIfType is set to sap."
    ::= { tnRmdSystemRmdAccessIfEntry 6 }

tnRmdSystemRmdAccessIfEncapValExt OBJECT-TYPE
    SYNTAX      TmnxEncapVal
    MAX-ACCESS  read-create
    STATUS      current
    DESCRIPTION
        "Indicates the label used to identify a second SAP on the port
         specified by tnRmdSystemRmdAccessIfPortIdExt.

         This object is only applicable when tnRmdSystemRmdAccessIfType is set
         to sap."
    ::= { tnRmdSystemRmdAccessIfEntry 7 }

END -- DEFINITION OF TN-RMD-SYSTEM-MIB
