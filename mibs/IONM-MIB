--
-- IONM-MIB.mib
-- MIB generated by MG-SOFT Visual MIB Builder Version 3.0 Build 253
-- Monday, June 16, 2014 at 10:32:21
--

	IONM-MIB DEFINITIONS ::= BEGIN
 
		IMPORTS
			OBJECT-GROUP			
				FROM SNMPv2-CONF			
			Integer32, OBJECT-TYPE, MODULE-IDENTITY, OBJECT-IDENTITY			
				FROM SNMPv2-SMI			
			TruthValue			
				FROM SNMPv2-TC			
			ionM, CTA, PositiveIntegerButNotZero			
				FROM WIRELESS-INNOVATIONS-PRODUCTS-MIB;
	
	
		ionmConfiguration MODULE-IDENTITY 
			LAST-UPDATED "201406111645Z"		-- June 11, 2014 at 16:45 GMT
			ORGANIZATION 
				"Wireless Innovations"
			CONTACT-INFO 
				"Industriering 10
				86675 Buchdorf
				Germany"
			DESCRIPTION 
				"MIB for ION-M device configuration."
			REVISION "201406111645Z"		-- June 11, 2014 at 16:45 GMT
			DESCRIPTION
				"1.0.0.0
				Created."
			::= { ionM 1 }
		
	
	
--
-- Node definitions
--
	
		-- 1.3.6.1.4.1.331.1.2.1.6.1.1.1
		ionmCommon OBJECT-IDENTITY
			STATUS current
			DESCRIPTION 
				"Description."
			::= { ionmConfiguration 1 }
		
		-- 1.3.6.1.4.1.331.1.2.1.6.1.1.2
		ionmLocal OBJECT-IDENTITY
			STATUS current
			DESCRIPTION 
				"Description."
			::= { ionmConfiguration 2 }
		
		-- 1.3.6.1.4.1.331.1.2.1.6.1.1.2.1
		muOtrxTable OBJECT-TYPE
			SYNTAX SEQUENCE OF MuOtrxEntry
			MAX-ACCESS not-accessible
			STATUS current
			DESCRIPTION
				"Description."
			::= { ionmLocal 1 }
		
		-- 1.3.6.1.4.1.331.1.2.1.6.1.1.2.1.1
		muOtrxEntry OBJECT-TYPE
			SYNTAX MuOtrxEntry
			MAX-ACCESS not-accessible
			STATUS current
			DESCRIPTION
				"Description."
			INDEX { muOtrxCTA }
			::= { muOtrxTable 1 }
		
		MuOtrxEntry ::=
			SEQUENCE { 
				muOtrxCTA
					CTA,
				muOtrxReboot
					TruthValue,
				muOtrxTempOptic
					OCTET STRING
			 }

		-- 1.3.6.1.4.1.331.1.2.1.6.1.1.2.1.1.1
		muOtrxCTA OBJECT-TYPE
			SYNTAX CTA
			MAX-ACCESS read-only
			STATUS current
			DESCRIPTION
				"Description."
			::= { muOtrxEntry 1 }
		
		-- 1.3.6.1.4.1.331.1.2.1.6.1.1.2.1.1.2
		muOtrxReboot OBJECT-TYPE
			SYNTAX TruthValue
			MAX-ACCESS read-write
			STATUS current
			DESCRIPTION
				"Description."
			::= { muOtrxEntry 2 }
		
		-- 1.3.6.1.4.1.331.1.2.1.6.1.1.2.1.1.3
		muOtrxTempOptic OBJECT-TYPE
			SYNTAX OCTET STRING
			MAX-ACCESS read-only
			STATUS current
			DESCRIPTION
				"String representation of float value."
			::= { muOtrxEntry 3 }
		
		-- 1.3.6.1.4.1.331.1.2.1.6.1.1.3
		ionmRemote OBJECT-IDENTITY
			STATUS current
			DESCRIPTION 
				"Description."
			::= { ionmConfiguration 3 }
		
		-- 1.3.6.1.4.1.331.1.2.1.6.1.1.3.1
		ruTable OBJECT-TYPE
			SYNTAX SEQUENCE OF RuEntry
			MAX-ACCESS not-accessible
			STATUS current
			DESCRIPTION
				"Description."
			::= { ionmRemote 1 }
		
		-- 1.3.6.1.4.1.331.1.2.1.6.1.1.3.1.1
		ruEntry OBJECT-TYPE
			SYNTAX RuEntry
			MAX-ACCESS not-accessible
			STATUS current
			DESCRIPTION
				"Description."
			INDEX { ruCTA }
			::= { ruTable 1 }
		
		RuEntry ::=
			SEQUENCE { 
				ruCTA
					CTA,
				ruReboot
					TruthValue,
				ruPsuPowerCycle
					TruthValue,
				ruAutoLevellingOpticalLossUL
					OCTET STRING,
				ruAutoLevellingOpticalLossDL
					OCTET STRING,
				ruTempOperating
					Integer32,
				ruTempOptic
					OCTET STRING,
				ruTempPSU1
					OCTET STRING,
				ruTempPSU2
					OCTET STRING,
				ruGainReductionMonitoringActive
					TruthValue,
				ruGainReductionMonitoringInterval
					Integer32,
				ruPsuWatchdogActive
					TruthValue,
				ruPsuWatchdogInterval
					Integer32
			 }

		-- 1.3.6.1.4.1.331.1.2.1.6.1.1.3.1.1.1
		ruCTA OBJECT-TYPE
			SYNTAX CTA
			MAX-ACCESS read-only
			STATUS current
			DESCRIPTION
				"Description."
			::= { ruEntry 1 }
		
		-- 1.3.6.1.4.1.331.1.2.1.6.1.1.3.1.1.2
		ruReboot OBJECT-TYPE
			SYNTAX TruthValue
			MAX-ACCESS read-write
			STATUS current
			DESCRIPTION
				"Description."
			::= { ruEntry 2 }
		
		-- 1.3.6.1.4.1.331.1.2.1.6.1.1.3.1.1.3
		ruPsuPowerCycle OBJECT-TYPE
			SYNTAX TruthValue
			MAX-ACCESS read-write
			STATUS current
			DESCRIPTION
				"Description."
			::= { ruEntry 3 }
		
		-- 1.3.6.1.4.1.331.1.2.1.6.1.1.3.1.1.4
		ruAutoLevellingOpticalLossUL OBJECT-TYPE
			SYNTAX OCTET STRING
			MAX-ACCESS read-only
			STATUS current
			DESCRIPTION
				"String representation of float value."
			::= { ruEntry 4 }
		
		-- 1.3.6.1.4.1.331.1.2.1.6.1.1.3.1.1.5
		ruAutoLevellingOpticalLossDL OBJECT-TYPE
			SYNTAX OCTET STRING
			MAX-ACCESS read-only
			STATUS current
			DESCRIPTION
				"String representation of float value."
			::= { ruEntry 5 }
		
		-- 1.3.6.1.4.1.331.1.2.1.6.1.1.3.1.1.6
		ruTempOperating OBJECT-TYPE
			SYNTAX Integer32
			MAX-ACCESS read-write
			STATUS current
			DESCRIPTION
				"Description."
			::= { ruEntry 6 }
		
		-- 1.3.6.1.4.1.331.1.2.1.6.1.1.3.1.1.7
		ruTempOptic OBJECT-TYPE
			SYNTAX OCTET STRING
			MAX-ACCESS read-only
			STATUS current
			DESCRIPTION
				"String representation of float value."
			::= { ruEntry 7 }
		
		-- 1.3.6.1.4.1.331.1.2.1.6.1.1.3.1.1.8
		ruTempPSU1 OBJECT-TYPE
			SYNTAX OCTET STRING
			MAX-ACCESS read-only
			STATUS current
			DESCRIPTION
				"String representation of float value."
			::= { ruEntry 8 }
		
		-- 1.3.6.1.4.1.331.1.2.1.6.1.1.3.1.1.9
		ruTempPSU2 OBJECT-TYPE
			SYNTAX OCTET STRING
			MAX-ACCESS read-only
			STATUS current
			DESCRIPTION
				"String representation of float value."
			::= { ruEntry 9 }
		
		-- 1.3.6.1.4.1.331.1.2.1.6.1.1.3.1.1.10
		ruGainReductionMonitoringActive OBJECT-TYPE
			SYNTAX TruthValue
			MAX-ACCESS read-write
			STATUS current
			DESCRIPTION
				"Description."
			::= { ruEntry 10 }
		
		-- 1.3.6.1.4.1.331.1.2.1.6.1.1.3.1.1.11
		ruGainReductionMonitoringInterval OBJECT-TYPE
			SYNTAX Integer32
			MAX-ACCESS read-write
			STATUS current
			DESCRIPTION
				"Description."
			::= { ruEntry 11 }
		
		-- 1.3.6.1.4.1.331.1.2.1.6.1.1.3.1.1.12
		ruPsuWatchdogActive OBJECT-TYPE
			SYNTAX TruthValue
			MAX-ACCESS read-write
			STATUS current
			DESCRIPTION
				"Description."
			::= { ruEntry 12 }
		
		-- 1.3.6.1.4.1.331.1.2.1.6.1.1.3.1.1.13
		ruPsuWatchdogInterval OBJECT-TYPE
			SYNTAX Integer32
			MAX-ACCESS read-write
			STATUS current
			DESCRIPTION
				"Description."
			::= { ruEntry 13 }
		
		-- 1.3.6.1.4.1.331.1.2.1.6.1.1.3.2
		euTable OBJECT-TYPE
			SYNTAX SEQUENCE OF EuEntry
			MAX-ACCESS not-accessible
			STATUS current
			DESCRIPTION
				"Description."
			::= { ionmRemote 2 }
		
		-- 1.3.6.1.4.1.331.1.2.1.6.1.1.3.2.1
		euEntry OBJECT-TYPE
			SYNTAX EuEntry
			MAX-ACCESS not-accessible
			STATUS current
			DESCRIPTION
				"Description."
			INDEX { euCTA }
			::= { euTable 1 }
		
		EuEntry ::=
			SEQUENCE { 
				euCTA
					CTA,
				euReboot
					TruthValue,
				euPsuPowerCycle
					TruthValue,
				euTempOperating
					Integer32,
				euTempPSU1
					OCTET STRING,
				euTempPSU2
					OCTET STRING,
				euPsuWatchdogActive
					TruthValue,
				euPsuWatchdogInterval
					Integer32
			 }

		-- 1.3.6.1.4.1.331.1.2.1.6.1.1.3.2.1.1
		euCTA OBJECT-TYPE
			SYNTAX CTA
			MAX-ACCESS read-only
			STATUS current
			DESCRIPTION
				"Description."
			::= { euEntry 1 }
		
		-- 1.3.6.1.4.1.331.1.2.1.6.1.1.3.2.1.2
		euReboot OBJECT-TYPE
			SYNTAX TruthValue
			MAX-ACCESS read-write
			STATUS current
			DESCRIPTION
				"Description."
			::= { euEntry 2 }
		
		-- 1.3.6.1.4.1.331.1.2.1.6.1.1.3.2.1.3
		euPsuPowerCycle OBJECT-TYPE
			SYNTAX TruthValue
			MAX-ACCESS read-write
			STATUS current
			DESCRIPTION
				"Description."
			::= { euEntry 3 }
		
		-- 1.3.6.1.4.1.331.1.2.1.6.1.1.3.2.1.4
		euTempOperating OBJECT-TYPE
			SYNTAX Integer32
			MAX-ACCESS read-write
			STATUS current
			DESCRIPTION
				"Description."
			::= { euEntry 4 }
		
		-- 1.3.6.1.4.1.331.1.2.1.6.1.1.3.2.1.5
		euTempPSU1 OBJECT-TYPE
			SYNTAX OCTET STRING
			MAX-ACCESS read-only
			STATUS current
			DESCRIPTION
				"String representation of float value."
			::= { euEntry 5 }
		
		-- 1.3.6.1.4.1.331.1.2.1.6.1.1.3.2.1.6
		euTempPSU2 OBJECT-TYPE
			SYNTAX OCTET STRING
			MAX-ACCESS read-only
			STATUS current
			DESCRIPTION
				"String representation of float value."
			::= { euEntry 6 }
		
		-- 1.3.6.1.4.1.331.1.2.1.6.1.1.3.2.1.7
		euPsuWatchdogActive OBJECT-TYPE
			SYNTAX TruthValue
			MAX-ACCESS read-write
			STATUS current
			DESCRIPTION
				"Description."
			::= { euEntry 7 }
		
		-- 1.3.6.1.4.1.331.1.2.1.6.1.1.3.2.1.8
		euPsuWatchdogInterval OBJECT-TYPE
			SYNTAX Integer32
			MAX-ACCESS read-write
			STATUS current
			DESCRIPTION
				"Description."
			::= { euEntry 8 }
		
		-- 1.3.6.1.4.1.331.1.2.1.6.1.1.3.3
		dlpaTable OBJECT-TYPE
			SYNTAX SEQUENCE OF DlpaEntry
			MAX-ACCESS not-accessible
			STATUS current
			DESCRIPTION
				"Description."
			::= { ionmRemote 3 }
		
		-- 1.3.6.1.4.1.331.1.2.1.6.1.1.3.3.1
		dlpaEntry OBJECT-TYPE
			SYNTAX DlpaEntry
			MAX-ACCESS not-accessible
			STATUS current
			DESCRIPTION
				"Description."
			INDEX { dlpaContainingUnitCTA, dlpaNo }
			::= { dlpaTable 1 }
		
		DlpaEntry ::=
			SEQUENCE { 
				dlpaContainingUnitCTA
					CTA,
				dlpaNo
					PositiveIntegerButNotZero,
				dlpaReset
					TruthValue,
				dlpaActive
					TruthValue,
				dlpaFrequency
					OCTET STRING,
				dlpaOutputPower
					OCTET STRING,
				dlpaTemp
					OCTET STRING,
				dlpaLowRmsEnabled
					TruthValue,
				dlpaLowRmsThreshold
					OCTET STRING,
				dlpaLowRmsHysteresis
					OCTET STRING
			 }

		-- 1.3.6.1.4.1.331.1.2.1.6.1.1.3.3.1.1
		dlpaContainingUnitCTA OBJECT-TYPE
			SYNTAX CTA
			MAX-ACCESS read-only
			STATUS current
			DESCRIPTION
				"Description."
			::= { dlpaEntry 1 }
		
		-- 1.3.6.1.4.1.331.1.2.1.6.1.1.3.3.1.2
		dlpaNo OBJECT-TYPE
			SYNTAX PositiveIntegerButNotZero
			MAX-ACCESS read-only
			STATUS current
			DESCRIPTION
				"Description."
			::= { dlpaEntry 2 }
		
		-- 1.3.6.1.4.1.331.1.2.1.6.1.1.3.3.1.3
		dlpaReset OBJECT-TYPE
			SYNTAX TruthValue
			MAX-ACCESS read-write
			STATUS current
			DESCRIPTION
				"Description."
			::= { dlpaEntry 3 }
		
		-- 1.3.6.1.4.1.331.1.2.1.6.1.1.3.3.1.4
		dlpaActive OBJECT-TYPE
			SYNTAX TruthValue
			MAX-ACCESS read-write
			STATUS current
			DESCRIPTION
				"Description."
			::= { dlpaEntry 4 }
		
		-- 1.3.6.1.4.1.331.1.2.1.6.1.1.3.3.1.5
		dlpaFrequency OBJECT-TYPE
			SYNTAX OCTET STRING
			MAX-ACCESS read-only
			STATUS current
			DESCRIPTION
				"Description."
			::= { dlpaEntry 5 }
		
		-- 1.3.6.1.4.1.331.1.2.1.6.1.1.3.3.1.6
		dlpaOutputPower OBJECT-TYPE
			SYNTAX OCTET STRING
			MAX-ACCESS read-only
			STATUS current
			DESCRIPTION
				"String representation of float value."
			::= { dlpaEntry 6 }
		
		-- 1.3.6.1.4.1.331.1.2.1.6.1.1.3.3.1.7
		dlpaTemp OBJECT-TYPE
			SYNTAX OCTET STRING
			MAX-ACCESS read-only
			STATUS current
			DESCRIPTION
				"String representation of float value."
			::= { dlpaEntry 7 }
		
		-- 1.3.6.1.4.1.331.1.2.1.6.1.1.3.3.1.8
		dlpaLowRmsEnabled OBJECT-TYPE
			SYNTAX TruthValue
			MAX-ACCESS read-write
			STATUS current
			DESCRIPTION
				"Description."
			::= { dlpaEntry 8 }
		
		-- 1.3.6.1.4.1.331.1.2.1.6.1.1.3.3.1.9
		dlpaLowRmsThreshold OBJECT-TYPE
			SYNTAX OCTET STRING
			MAX-ACCESS read-write
			STATUS current
			DESCRIPTION
				"String representation of float value."
			::= { dlpaEntry 9 }
		
		-- 1.3.6.1.4.1.331.1.2.1.6.1.1.3.3.1.10
		dlpaLowRmsHysteresis OBJECT-TYPE
			SYNTAX OCTET STRING
			MAX-ACCESS read-write
			STATUS current
			DESCRIPTION
				"String representation of float value."
			::= { dlpaEntry 10 }
		
		-- 1.3.6.1.4.1.331.1.2.1.6.1.1.4
		ionmConformance OBJECT-IDENTITY
			STATUS current
			DESCRIPTION 
				"Description."
			::= { ionmConfiguration 4 }
		
		-- 1.3.6.1.4.1.331.1.2.1.6.1.1.4.1
		ionmConfigurationGroup OBJECT-GROUP
			OBJECTS { muOtrxCTA, muOtrxReboot, muOtrxTempOptic, ruCTA, ruReboot, 
				ruPsuPowerCycle, ruAutoLevellingOpticalLossUL, ruAutoLevellingOpticalLossDL, ruTempOperating, ruTempOptic, 
				ruTempPSU1, ruTempPSU2, ruGainReductionMonitoringActive, ruGainReductionMonitoringInterval, ruPsuWatchdogActive, 
				ruPsuWatchdogInterval, euCTA, euReboot, euPsuPowerCycle, euTempOperating, 
				euTempPSU1, euTempPSU2, euPsuWatchdogActive, euPsuWatchdogInterval, dlpaContainingUnitCTA, 
				dlpaNo, dlpaReset, dlpaActive, dlpaFrequency, dlpaOutputPower, 
				dlpaTemp, dlpaLowRmsEnabled, dlpaLowRmsThreshold, dlpaLowRmsHysteresis }
			STATUS current
			DESCRIPTION 
				"Description."
			::= { ionmConformance 1 }
		
	
	END

--
-- IONM-MIB.mib
--
