-- file automatically created


TELDAT-TRAP-NSM-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


nsmTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NSM event subsystem."
    REVISION "201401200930Z"
    DESCRIPTION "Initial implementation"
        ::= { telEventTraps 170 }


nsmEventsGroup	OBJECT IDENTIFIER	::= { nsmTrapsMIB 1 }

nsmNotifications	OBJECT IDENTIFIER	::= { nsmTrapsMIB 2 }
nsmNotificationsPrefix	OBJECT IDENTIFIER	::= { nsmNotifications 0 }

nsmEventObjects1 OBJECT-IDENTITY
    STATUS current
    DESCRIPTION
        "Event NSM.1
        Generic event to display any information."
    ::= { nsmEventsGroup 1 }

nsm1_generic_info OBJECT-TYPE
    SYNTAX DisplayString
    MAX-ACCESS accessible-for-notify
    STATUS current
    DESCRIPTION
        "Parameter 'generic_info' in event NSM.1"
    ::= { nsmEventObjects1 1 }

nsmEventObjects2 OBJECT-IDENTITY
    STATUS current
    DESCRIPTION
        "Event NSM.2
        Inserts operation whose identifier is indicated in the active or pending
        execution operations list."
    ::= { nsmEventsGroup 2 }

nsm2_operation OBJECT-TYPE
    SYNTAX Integer32
    MAX-ACCESS accessible-for-notify
    STATUS current
    DESCRIPTION
        "Parameter 'operation' in event NSM.2"
    ::= { nsmEventObjects2 1 }

nsmEventObjects3 OBJECT-IDENTITY
    STATUS current
    DESCRIPTION
        "Event NSM.3
        Indicates scheduled start up or instance for an operation."
    ::= { nsmEventsGroup 3 }

nsm3_operation OBJECT-TYPE
    SYNTAX Integer32
    MAX-ACCESS accessible-for-notify
    STATUS current
    DESCRIPTION
        "Parameter 'operation' in event NSM.3"
    ::= { nsmEventObjects3 1 }

nsmEventObjects4 OBJECT-IDENTITY
    STATUS current
    DESCRIPTION
        "Event NSM.4
        Indicates the end of an instance execution for a specific operation and
        the procedure to process the result and update related statistics and
        other related information."
    ::= { nsmEventsGroup 4 }

nsm4_operation OBJECT-TYPE
    SYNTAX Integer32
    MAX-ACCESS accessible-for-notify
    STATUS current
    DESCRIPTION
        "Parameter 'operation' in event NSM.4"
    ::= { nsmEventObjects4 1 }

nsmEventObjects5 OBJECT-IDENTITY
    STATUS current
    DESCRIPTION
        "Event NSM.5
        Timer controlling the indicated operation life has timed out: this is
        the time an entry can be in an 'active' or 'pending' state. Once this
        time has timed out, the entry passes to 'inactive'."
    ::= { nsmEventsGroup 5 }

nsm5_operation OBJECT-TYPE
    SYNTAX Integer32
    MAX-ACCESS accessible-for-notify
    STATUS current
    DESCRIPTION
        "Parameter 'operation' in event NSM.5"
    ::= { nsmEventObjects5 1 }

nsmEventObjects6 OBJECT-IDENTITY
    STATUS current
    DESCRIPTION
        "Event NSM.6
        Timer controlling the indicated operation ageout has timed out: this is
        the time than an entry can be in a state distinct to 'active'. Once this
        time has timed out the entry is deleted from the list of active
        operations."
    ::= { nsmEventsGroup 6 }

nsm6_operation OBJECT-TYPE
    SYNTAX Integer32
    MAX-ACCESS accessible-for-notify
    STATUS current
    DESCRIPTION
        "Parameter 'operation' in event NSM.6"
    ::= { nsmEventObjects6 1 }

nsmEventObjects7 OBJECT-IDENTITY
    STATUS current
    DESCRIPTION
        "Event NSM.7
        Operation with indicated identifier has been destroyed: it has been
        deleted from the list of active operations and also memory assigned to
        it released, which corresponds to the memory block beginning with the
        displayed address."
    ::= { nsmEventsGroup 7 }

nsm7_operation OBJECT-TYPE
    SYNTAX Integer32
    MAX-ACCESS accessible-for-notify
    STATUS current
    DESCRIPTION
        "Parameter 'operation' in event NSM.7"
    ::= { nsmEventObjects7 1 }

nsm7_op_memory_addr OBJECT-TYPE
    SYNTAX Integer32
    MAX-ACCESS accessible-for-notify
    STATUS current
    DESCRIPTION
        "Parameter 'op_memory_addr' in event NSM.7"
    ::= { nsmEventObjects7 2 }

nsmEventObjects8 OBJECT-IDENTITY
    STATUS current
    DESCRIPTION
        "Event NSM.8
        Operation with indicated identifier has been deleted: the assigned
        memory has been released, which corresponds to the memory block
        beginning with the displayed address. Before deleting (releasing memory)
        it may be necessary to remove the entry from the active operations list
        (e.g. perhaps due to the fact an error was produced before this was
        introduced in the list and it is necessary to release the memory
        assigned to it)."
    ::= { nsmEventsGroup 8 }

nsm8_operation OBJECT-TYPE
    SYNTAX Integer32
    MAX-ACCESS accessible-for-notify
    STATUS current
    DESCRIPTION
        "Parameter 'operation' in event NSM.8"
    ::= { nsmEventObjects8 1 }

nsm8_op_memory_addr OBJECT-TYPE
    SYNTAX Integer32
    MAX-ACCESS accessible-for-notify
    STATUS current
    DESCRIPTION
        "Parameter 'op_memory_addr' in event NSM.8"
    ::= { nsmEventObjects8 2 }

nsmEventObjects9 OBJECT-IDENTITY
    STATUS current
    DESCRIPTION
        "Event NSM.9
        Indicates the end of the operation with the indicated identifier."
    ::= { nsmEventsGroup 9 }

nsm9_operation OBJECT-TYPE
    SYNTAX Integer32
    MAX-ACCESS accessible-for-notify
    STATUS current
    DESCRIPTION
        "Parameter 'operation' in event NSM.9"
    ::= { nsmEventObjects9 1 }

nsm9_op_memory_addr OBJECT-TYPE
    SYNTAX Integer32
    MAX-ACCESS accessible-for-notify
    STATUS current
    DESCRIPTION
        "Parameter 'op_memory_addr' in event NSM.9"
    ::= { nsmEventObjects9 2 }

nsmEventObjects10 OBJECT-IDENTITY
    STATUS current
    DESCRIPTION
        "Event NSM.10
        Timer for an operation execution or instance has timed out."
    ::= { nsmEventsGroup 10 }

nsm10_operation OBJECT-TYPE
    SYNTAX Integer32
    MAX-ACCESS accessible-for-notify
    STATUS current
    DESCRIPTION
        "Parameter 'operation' in event NSM.10"
    ::= { nsmEventObjects10 1 }

nsmEventObjects12 OBJECT-IDENTITY
    STATUS current
    DESCRIPTION
        "Event NSM.12
        Info about an operation client"
    ::= { nsmEventsGroup 12 }

nsm12_operation OBJECT-TYPE
    SYNTAX Integer32
    MAX-ACCESS accessible-for-notify
    STATUS current
    DESCRIPTION
        "Parameter 'operation' in event NSM.12"
    ::= { nsmEventObjects12 1 }

nsm12_detail OBJECT-TYPE
    SYNTAX DisplayString
    MAX-ACCESS accessible-for-notify
    STATUS current
    DESCRIPTION
        "Parameter 'detail' in event NSM.12"
    ::= { nsmEventObjects12 2 }

nsmEventObjects21 OBJECT-IDENTITY
    STATUS current
    DESCRIPTION
        "Event NSM.21
        Indicates start of executing an instance for a determined echo
        operation."
    ::= { nsmEventsGroup 21 }

nsm21_operation OBJECT-TYPE
    SYNTAX Integer32
    MAX-ACCESS accessible-for-notify
    STATUS current
    DESCRIPTION
        "Parameter 'operation' in event NSM.21"
    ::= { nsmEventObjects21 1 }

nsmEventObjects22 OBJECT-IDENTITY
    STATUS current
    DESCRIPTION
        "Event NSM.22
        After executing ECHO operation, the obtained Round Trip Time is
        indicated."
    ::= { nsmEventsGroup 22 }

nsm22_operation OBJECT-TYPE
    SYNTAX Integer32
    MAX-ACCESS accessible-for-notify
    STATUS current
    DESCRIPTION
        "Parameter 'operation' in event NSM.22"
    ::= { nsmEventObjects22 1 }

nsm22_rtt OBJECT-TYPE
    SYNTAX Integer32
    MAX-ACCESS accessible-for-notify
    STATUS current
    DESCRIPTION
        "Parameter 'rtt' in event NSM.22"
    ::= { nsmEventObjects22 2 }

nsmEventObjects23 OBJECT-IDENTITY
    STATUS current
    DESCRIPTION
        "Event NSM.23
        Indicates start of executing an instance for a determined BFD
        operation."
    ::= { nsmEventsGroup 23 }

nsm23_operation OBJECT-TYPE
    SYNTAX Integer32
    MAX-ACCESS accessible-for-notify
    STATUS current
    DESCRIPTION
        "Parameter 'operation' in event NSM.23"
    ::= { nsmEventObjects23 1 }

nsmEventObjects31 OBJECT-IDENTITY
    STATUS current
    DESCRIPTION
        "Event NSM.31
        Indicates execution start for a determined DNS operation instance."
    ::= { nsmEventsGroup 31 }

nsm31_operation OBJECT-TYPE
    SYNTAX Integer32
    MAX-ACCESS accessible-for-notify
    STATUS current
    DESCRIPTION
        "Parameter 'operation' in event NSM.31"
    ::= { nsmEventObjects31 1 }

nsmEventObjects32 OBJECT-IDENTITY
    STATUS current
    DESCRIPTION
        "Event NSM.32
        A DNS operation is being executed to resolve the indicated name."
    ::= { nsmEventsGroup 32 }

nsm32_operation OBJECT-TYPE
    SYNTAX Integer32
    MAX-ACCESS accessible-for-notify
    STATUS current
    DESCRIPTION
        "Parameter 'operation' in event NSM.32"
    ::= { nsmEventObjects32 1 }

nsm32_url OBJECT-TYPE
    SYNTAX DisplayString
    MAX-ACCESS accessible-for-notify
    STATUS current
    DESCRIPTION
        "Parameter 'url' in event NSM.32"
    ::= { nsmEventObjects32 2 }

nsmEventObjects33 OBJECT-IDENTITY
    STATUS current
    DESCRIPTION
        "Event NSM.33
        A DNS operation is being executed with the indicated server."
    ::= { nsmEventsGroup 33 }

nsm33_operation OBJECT-TYPE
    SYNTAX Integer32
    MAX-ACCESS accessible-for-notify
    STATUS current
    DESCRIPTION
        "Parameter 'operation' in event NSM.33"
    ::= { nsmEventObjects33 1 }

nsm33_server_ip_address OBJECT-TYPE
    SYNTAX IpAddress
    MAX-ACCESS accessible-for-notify
    STATUS current
    DESCRIPTION
        "Parameter 'server_ip_address' in event NSM.33"
    ::= { nsmEventObjects33 2 }

nsmEventObjects34 OBJECT-IDENTITY
    STATUS current
    DESCRIPTION
        "Event NSM.34
        A DNS operation has terminated with the result shown in the string
        (describes the return code). Possible return codes:
        0. DNS OK
        1. Name: Empty Label
        2. Name: Label too long
        3. Name: Bad escape
        4. Name: Bad bitstring
        5. Name: Bit string too long
        6. Name: Bad dotted quad
        7. Name: No space to store name
        8. Name: Unexpected end
        9. No iorb to send query
        10. No memory
        11. DNS not initialized
        12. Query of an IP address
        13. Query needed (internal)
        14. Maximum number of retries reached
        15. Received format error
        16. Received name error
        17. Unexpected end of query (internal)
        18. Query killed
        19. DNS Generic Error"
    ::= { nsmEventsGroup 34 }

nsm34_operation OBJECT-TYPE
    SYNTAX Integer32
    MAX-ACCESS accessible-for-notify
    STATUS current
    DESCRIPTION
        "Parameter 'operation' in event NSM.34"
    ::= { nsmEventObjects34 1 }

nsm34_dns_result OBJECT-TYPE
    SYNTAX DisplayString
    MAX-ACCESS accessible-for-notify
    STATUS current
    DESCRIPTION
        "Parameter 'dns_result' in event NSM.34"
    ::= { nsmEventObjects34 2 }

nsmEventObjects35 OBJECT-IDENTITY
    STATUS current
    DESCRIPTION
        "Event NSM.35
        After executing the DNS operation, the IP address corresponding to
        requested name is indicated."
    ::= { nsmEventsGroup 35 }

nsm35_operation OBJECT-TYPE
    SYNTAX Integer32
    MAX-ACCESS accessible-for-notify
    STATUS current
    DESCRIPTION
        "Parameter 'operation' in event NSM.35"
    ::= { nsmEventObjects35 1 }

nsm35_ip_address OBJECT-TYPE
    SYNTAX IpAddress
    MAX-ACCESS accessible-for-notify
    STATUS current
    DESCRIPTION
        "Parameter 'ip_address' in event NSM.35"
    ::= { nsmEventObjects35 2 }

nsmEventObjects36 OBJECT-IDENTITY
    STATUS current
    DESCRIPTION
        "Event NSM.36
        After executing DNS operation, the obtained Round Trip Time is
        indicated."
    ::= { nsmEventsGroup 36 }

nsm36_operation OBJECT-TYPE
    SYNTAX Integer32
    MAX-ACCESS accessible-for-notify
    STATUS current
    DESCRIPTION
        "Parameter 'operation' in event NSM.36"
    ::= { nsmEventObjects36 1 }

nsm36_rtt OBJECT-TYPE
    SYNTAX Integer32
    MAX-ACCESS accessible-for-notify
    STATUS current
    DESCRIPTION
        "Parameter 'rtt' in event NSM.36"
    ::= { nsmEventObjects36 2 }

nsmEventObjects37 OBJECT-IDENTITY
    STATUS current
    DESCRIPTION
        "Event NSM.37
        DNS resolve is not required as an IP address has been directly
        indicated."
    ::= { nsmEventsGroup 37 }

nsm37_operation OBJECT-TYPE
    SYNTAX Integer32
    MAX-ACCESS accessible-for-notify
    STATUS current
    DESCRIPTION
        "Parameter 'operation' in event NSM.37"
    ::= { nsmEventObjects37 1 }

nsm37_ip_address OBJECT-TYPE
    SYNTAX IpAddress
    MAX-ACCESS accessible-for-notify
    STATUS current
    DESCRIPTION
        "Parameter 'ip_address' in event NSM.37"
    ::= { nsmEventObjects37 2 }

nsmEventObjects41 OBJECT-IDENTITY
    STATUS current
    DESCRIPTION
        "Event NSM.41
        Indicates the execution startup for a determined HTTP operation
        instance."
    ::= { nsmEventsGroup 41 }

nsm41_operation OBJECT-TYPE
    SYNTAX Integer32
    MAX-ACCESS accessible-for-notify
    STATUS current
    DESCRIPTION
        "Parameter 'operation' in event NSM.41"
    ::= { nsmEventObjects41 1 }

nsmEventObjects42 OBJECT-IDENTITY
    STATUS current
    DESCRIPTION
        "Event NSM.42
        An HTTP operation is being executed: the number of sent bytes from a
        total is displayed together with the total."
    ::= { nsmEventsGroup 42 }

nsm42_operation OBJECT-TYPE
    SYNTAX Integer32
    MAX-ACCESS accessible-for-notify
    STATUS current
    DESCRIPTION
        "Parameter 'operation' in event NSM.42"
    ::= { nsmEventObjects42 1 }

nsm42_sent_bytes OBJECT-TYPE
    SYNTAX Integer32
    MAX-ACCESS accessible-for-notify
    STATUS current
    DESCRIPTION
        "Parameter 'sent_bytes' in event NSM.42"
    ::= { nsmEventObjects42 2 }

nsm42_total_bytes OBJECT-TYPE
    SYNTAX Integer32
    MAX-ACCESS accessible-for-notify
    STATUS current
    DESCRIPTION
        "Parameter 'total_bytes' in event NSM.42"
    ::= { nsmEventObjects42 3 }

nsmEventObjects43 OBJECT-IDENTITY
    STATUS current
    DESCRIPTION
        "Event NSM.43
        An HTTP operation is being executed: specifically, the process is at the
        point where it's waiting to connect, the connection attempt result is
        indicated.
        Possible results are:
        1. connected.
        2. error."
    ::= { nsmEventsGroup 43 }

nsm43_operation OBJECT-TYPE
    SYNTAX Integer32
    MAX-ACCESS accessible-for-notify
    STATUS current
    DESCRIPTION
        "Parameter 'operation' in event NSM.43"
    ::= { nsmEventObjects43 1 }

nsm43_connection_result OBJECT-TYPE
    SYNTAX DisplayString
    MAX-ACCESS accessible-for-notify
    STATUS current
    DESCRIPTION
        "Parameter 'connection_result' in event NSM.43"
    ::= { nsmEventObjects43 2 }

nsmEventObjects44 OBJECT-IDENTITY
    STATUS current
    DESCRIPTION
        "Event NSM.44
        After executing HTTP operation, the obtained Round Trip Time is
        indicated."
    ::= { nsmEventsGroup 44 }

nsm44_operation OBJECT-TYPE
    SYNTAX Integer32
    MAX-ACCESS accessible-for-notify
    STATUS current
    DESCRIPTION
        "Parameter 'operation' in event NSM.44"
    ::= { nsmEventObjects44 1 }

nsm44_rtt OBJECT-TYPE
    SYNTAX Integer32
    MAX-ACCESS accessible-for-notify
    STATUS current
    DESCRIPTION
        "Parameter 'rtt' in event NSM.44"
    ::= { nsmEventObjects44 2 }

nsmEventObjects45 OBJECT-IDENTITY
    STATUS current
    DESCRIPTION
        "Event NSM.45
        An unexpected error has occurred (lack of memory, insufficient space in
        buffer, etc.), during an HTTP operation execution."
    ::= { nsmEventsGroup 45 }

nsm45_operation OBJECT-TYPE
    SYNTAX Integer32
    MAX-ACCESS accessible-for-notify
    STATUS current
    DESCRIPTION
        "Parameter 'operation' in event NSM.45"
    ::= { nsmEventObjects45 1 }

nsm45_error_message OBJECT-TYPE
    SYNTAX DisplayString
    MAX-ACCESS accessible-for-notify
    STATUS current
    DESCRIPTION
        "Parameter 'error_message' in event NSM.45"
    ::= { nsmEventObjects45 2 }

nsmEventObjects51 OBJECT-IDENTITY
    STATUS current
    DESCRIPTION
        "Event NSM.51
        Startup of exchange of control messages corresponding to the ARR
        protocol from the device whose IP address and port are those indicated
        and that are transmitted to the destination IP address and port also
        included in the event."
    ::= { nsmEventsGroup 51 }

nsm51_operation OBJECT-TYPE
    SYNTAX Integer32
    MAX-ACCESS accessible-for-notify
    STATUS current
    DESCRIPTION
        "Parameter 'operation' in event NSM.51"
    ::= { nsmEventObjects51 1 }

nsm51_source_ip_address OBJECT-TYPE
    SYNTAX IpAddress
    MAX-ACCESS accessible-for-notify
    STATUS current
    DESCRIPTION
        "Parameter 'source_ip_address' in event NSM.51"
    ::= { nsmEventObjects51 2 }

nsm51_source_port OBJECT-TYPE
    SYNTAX Integer32
    MAX-ACCESS accessible-for-notify
    STATUS current
    DESCRIPTION
        "Parameter 'source_port' in event NSM.51"
    ::= { nsmEventObjects51 3 }

nsm51_destination_ip_address OBJECT-TYPE
    SYNTAX IpAddress
    MAX-ACCESS accessible-for-notify
    STATUS current
    DESCRIPTION
        "Parameter 'destination_ip_address' in event NSM.51"
    ::= { nsmEventObjects51 4 }

nsm51_destination_port OBJECT-TYPE
    SYNTAX Integer32
    MAX-ACCESS accessible-for-notify
    STATUS current
    DESCRIPTION
        "Parameter 'destination_port' in event NSM.51"
    ::= { nsmEventObjects51 5 }

nsmEventObjects52 OBJECT-IDENTITY
    STATUS current
    DESCRIPTION
        "Event NSM.52
        End of exchange of control messages corresponding to the ARR protocol
        from the device whose IP address and port are those indicated and with
        destination IP address and port also displayed. The open port is closed
        to carry out this communication, which appears as a second parameter."
    ::= { nsmEventsGroup 52 }

nsm52_operation OBJECT-TYPE
    SYNTAX Integer32
    MAX-ACCESS accessible-for-notify
    STATUS current
    DESCRIPTION
        "Parameter 'operation' in event NSM.52"
    ::= { nsmEventObjects52 1 }

nsm52_source_ip_address OBJECT-TYPE
    SYNTAX IpAddress
    MAX-ACCESS accessible-for-notify
    STATUS current
    DESCRIPTION
        "Parameter 'source_ip_address' in event NSM.52"
    ::= { nsmEventObjects52 2 }

nsm52_source_port OBJECT-TYPE
    SYNTAX Integer32
    MAX-ACCESS accessible-for-notify
    STATUS current
    DESCRIPTION
        "Parameter 'source_port' in event NSM.52"
    ::= { nsmEventObjects52 3 }

nsm52_destination_ip_address OBJECT-TYPE
    SYNTAX IpAddress
    MAX-ACCESS accessible-for-notify
    STATUS current
    DESCRIPTION
        "Parameter 'destination_ip_address' in event NSM.52"
    ::= { nsmEventObjects52 4 }

nsm52_destination_port OBJECT-TYPE
    SYNTAX Integer32
    MAX-ACCESS accessible-for-notify
    STATUS current
    DESCRIPTION
        "Parameter 'destination_port' in event NSM.52"
    ::= { nsmEventObjects52 5 }

nsmEventObjects53 OBJECT-IDENTITY
    STATUS current
    DESCRIPTION
        "Event NSM.53
        Sending an ARR protocol control message to the indicated IP address and
        port. This is significant to operations supporting this protocol e.g.
        Jitter."
    ::= { nsmEventsGroup 53 }

nsm53_operation OBJECT-TYPE
    SYNTAX Integer32
    MAX-ACCESS accessible-for-notify
    STATUS current
    DESCRIPTION
        "Parameter 'operation' in event NSM.53"
    ::= { nsmEventObjects53 1 }

nsm53_version OBJECT-TYPE
    SYNTAX Integer32
    MAX-ACCESS accessible-for-notify
    STATUS current
    DESCRIPTION
        "Parameter 'version' in event NSM.53"
    ::= { nsmEventObjects53 2 }

nsm53_identifier OBJECT-TYPE
    SYNTAX Integer32
    MAX-ACCESS accessible-for-notify
    STATUS current
    DESCRIPTION
        "Parameter 'identifier' in event NSM.53"
    ::= { nsmEventObjects53 3 }

nsm53_length OBJECT-TYPE
    SYNTAX Integer32
    MAX-ACCESS accessible-for-notify
    STATUS current
    DESCRIPTION
        "Parameter 'length' in event NSM.53"
    ::= { nsmEventObjects53 4 }

nsm53_command OBJECT-TYPE
    SYNTAX Integer32
    MAX-ACCESS accessible-for-notify
    STATUS current
    DESCRIPTION
        "Parameter 'command' in event NSM.53"
    ::= { nsmEventObjects53 5 }

nsm53_destination_ip_address OBJECT-TYPE
    SYNTAX IpAddress
    MAX-ACCESS accessible-for-notify
    STATUS current
    DESCRIPTION
        "Parameter 'destination_ip_address' in event NSM.53"
    ::= { nsmEventObjects53 6 }

nsm53_destination_data_port OBJECT-TYPE
    SYNTAX Integer32
    MAX-ACCESS accessible-for-notify
    STATUS current
    DESCRIPTION
        "Parameter 'destination_data_port' in event NSM.53"
    ::= { nsmEventObjects53 7 }

nsm53_duration OBJECT-TYPE
    SYNTAX Integer32
    MAX-ACCESS accessible-for-notify
    STATUS current
    DESCRIPTION
        "Parameter 'duration' in event NSM.53"
    ::= { nsmEventObjects53 8 }

nsmEventObjects54 OBJECT-IDENTITY
    STATUS current
    DESCRIPTION
        "Event NSM.54
        Control message response wait timer has timed out."
    ::= { nsmEventsGroup 54 }

nsm54_operation OBJECT-TYPE
    SYNTAX Integer32
    MAX-ACCESS accessible-for-notify
    STATUS current
    DESCRIPTION
        "Parameter 'operation' in event NSM.54"
    ::= { nsmEventObjects54 1 }

nsmEventObjects55 OBJECT-IDENTITY
    STATUS current
    DESCRIPTION
        "Event NSM.55
        A response to a previously sent control message has been received, the
        result is indicated."
    ::= { nsmEventsGroup 55 }

nsm55_operation OBJECT-TYPE
    SYNTAX Integer32
    MAX-ACCESS accessible-for-notify
    STATUS current
    DESCRIPTION
        "Parameter 'operation' in event NSM.55"
    ::= { nsmEventObjects55 1 }

nsm55_receive_status OBJECT-TYPE
    SYNTAX Integer32
    MAX-ACCESS accessible-for-notify
    STATUS current
    DESCRIPTION
        "Parameter 'receive_status' in event NSM.55"
    ::= { nsmEventObjects55 2 }

nsmEventObjects61 OBJECT-IDENTITY
    STATUS current
    DESCRIPTION
        "Event NSM.61
        A Jitter operation is started using VRF."
    ::= { nsmEventsGroup 61 }

nsm61_operation OBJECT-TYPE
    SYNTAX Integer32
    MAX-ACCESS accessible-for-notify
    STATUS current
    DESCRIPTION
        "Parameter 'operation' in event NSM.61"
    ::= { nsmEventObjects61 1 }

nsm61_vrf OBJECT-TYPE
    SYNTAX Integer32
    MAX-ACCESS accessible-for-notify
    STATUS current
    DESCRIPTION
        "Parameter 'vrf' in event NSM.61"
    ::= { nsmEventObjects61 2 }

nsm61_lookup_table_id OBJECT-TYPE
    SYNTAX Integer32
    MAX-ACCESS accessible-for-notify
    STATUS current
    DESCRIPTION
        "Parameter 'lookup_table_id' in event NSM.61"
    ::= { nsmEventObjects61 3 }

nsmEventObjects62 OBJECT-IDENTITY
    STATUS current
    DESCRIPTION
        "Event NSM.62
        Jitter operation starting."
    ::= { nsmEventsGroup 62 }

nsm62_operation OBJECT-TYPE
    SYNTAX Integer32
    MAX-ACCESS accessible-for-notify
    STATUS current
    DESCRIPTION
        "Parameter 'operation' in event NSM.62"
    ::= { nsmEventObjects62 1 }

nsmEventObjects63 OBJECT-IDENTITY
    STATUS current
    DESCRIPTION
        "Event NSM.63
        A Jitter operation is being executed: the operation identifier is
        displayed together with the sequence number and the obtained RTT."
    ::= { nsmEventsGroup 63 }

nsm63_operation OBJECT-TYPE
    SYNTAX Integer32
    MAX-ACCESS accessible-for-notify
    STATUS current
    DESCRIPTION
        "Parameter 'operation' in event NSM.63"
    ::= { nsmEventObjects63 1 }

nsm63_sequence_number OBJECT-TYPE
    SYNTAX Integer32
    MAX-ACCESS accessible-for-notify
    STATUS current
    DESCRIPTION
        "Parameter 'sequence_number' in event NSM.63"
    ::= { nsmEventObjects63 2 }

nsm63_rtt OBJECT-TYPE
    SYNTAX Integer32
    MAX-ACCESS accessible-for-notify
    STATUS current
    DESCRIPTION
        "Parameter 'rtt' in event NSM.63"
    ::= { nsmEventObjects63 3 }

nsmEventObjects64 OBJECT-IDENTITY
    STATUS current
    DESCRIPTION
        "Event NSM.64
        A Jitter operation is being executed: the operation identifier is
        displayed together with the sequence number and the jitterOut (jitterSD)
        and jitterIn (jitterDS) values."
    ::= { nsmEventsGroup 64 }

nsm64_operation OBJECT-TYPE
    SYNTAX Integer32
    MAX-ACCESS accessible-for-notify
    STATUS current
    DESCRIPTION
        "Parameter 'operation' in event NSM.64"
    ::= { nsmEventObjects64 1 }

nsm64_sequence_number OBJECT-TYPE
    SYNTAX Integer32
    MAX-ACCESS accessible-for-notify
    STATUS current
    DESCRIPTION
        "Parameter 'sequence_number' in event NSM.64"
    ::= { nsmEventObjects64 2 }

nsm64_jitterOut OBJECT-TYPE
    SYNTAX Integer32
    MAX-ACCESS accessible-for-notify
    STATUS current
    DESCRIPTION
        "Parameter 'jitterOut' in event NSM.64"
    ::= { nsmEventObjects64 3 }

nsm64_jitterIn OBJECT-TYPE
    SYNTAX Integer32
    MAX-ACCESS accessible-for-notify
    STATUS current
    DESCRIPTION
        "Parameter 'jitterIn' in event NSM.64"
    ::= { nsmEventObjects64 4 }

nsmEventObjects65 OBJECT-IDENTITY
    STATUS current
    DESCRIPTION
        "Event NSM.65
        An out of sequence packet has been received."
    ::= { nsmEventsGroup 65 }

nsm65_operation OBJECT-TYPE
    SYNTAX Integer32
    MAX-ACCESS accessible-for-notify
    STATUS current
    DESCRIPTION
        "Parameter 'operation' in event NSM.65"
    ::= { nsmEventObjects65 1 }

nsm65_sequence_number OBJECT-TYPE
    SYNTAX Integer32
    MAX-ACCESS accessible-for-notify
    STATUS current
    DESCRIPTION
        "Parameter 'sequence_number' in event NSM.65"
    ::= { nsmEventObjects65 2 }

nsmEventObjects66 OBJECT-IDENTITY
    STATUS current
    DESCRIPTION
        "Event NSM.66
        Packets to carry out calculations in source-destination direction have
        been lost."
    ::= { nsmEventsGroup 66 }

nsm66_operation OBJECT-TYPE
    SYNTAX Integer32
    MAX-ACCESS accessible-for-notify
    STATUS current
    DESCRIPTION
        "Parameter 'operation' in event NSM.66"
    ::= { nsmEventObjects66 1 }

nsm66_counter OBJECT-TYPE
    SYNTAX Integer32
    MAX-ACCESS accessible-for-notify
    STATUS current
    DESCRIPTION
        "Parameter 'counter' in event NSM.66"
    ::= { nsmEventObjects66 2 }

nsmEventObjects67 OBJECT-IDENTITY
    STATUS current
    DESCRIPTION
        "Event NSM.67
        Packets to carry out calculations in destination-source direction have
        been lost."
    ::= { nsmEventsGroup 67 }

nsm67_operation OBJECT-TYPE
    SYNTAX Integer32
    MAX-ACCESS accessible-for-notify
    STATUS current
    DESCRIPTION
        "Parameter 'operation' in event NSM.67"
    ::= { nsmEventObjects67 1 }

nsm67_counter OBJECT-TYPE
    SYNTAX Integer32
    MAX-ACCESS accessible-for-notify
    STATUS current
    DESCRIPTION
        "Parameter 'counter' in event NSM.67"
    ::= { nsmEventObjects67 2 }

nsmEventObjects68 OBJECT-IDENTITY
    STATUS current
    DESCRIPTION
        "Event NSM.68
        A packet has been received outside the reception window."
    ::= { nsmEventsGroup 68 }

nsm68_operation OBJECT-TYPE
    SYNTAX Integer32
    MAX-ACCESS accessible-for-notify
    STATUS current
    DESCRIPTION
        "Parameter 'operation' in event NSM.68"
    ::= { nsmEventObjects68 1 }

nsm68_counter OBJECT-TYPE
    SYNTAX Integer32
    MAX-ACCESS accessible-for-notify
    STATUS current
    DESCRIPTION
        "Parameter 'counter' in event NSM.68"
    ::= { nsmEventObjects68 2 }

nsmEventObjects69 OBJECT-IDENTITY
    STATUS current
    DESCRIPTION
        "Event NSM.69
        Packets to carry out calculations in unknown direction have been lost."
    ::= { nsmEventsGroup 69 }

nsm69_operation OBJECT-TYPE
    SYNTAX Integer32
    MAX-ACCESS accessible-for-notify
    STATUS current
    DESCRIPTION
        "Parameter 'operation' in event NSM.69"
    ::= { nsmEventObjects69 1 }

nsm69_counter OBJECT-TYPE
    SYNTAX Integer32
    MAX-ACCESS accessible-for-notify
    STATUS current
    DESCRIPTION
        "Parameter 'counter' in event NSM.69"
    ::= { nsmEventObjects69 2 }

nsmEventObjects71 OBJECT-IDENTITY
    STATUS current
    DESCRIPTION
        "Event NSM.71
        Responder receives a control message from indicated IP address and port."
    ::= { nsmEventsGroup 71 }

nsm71_source_ip_address OBJECT-TYPE
    SYNTAX IpAddress
    MAX-ACCESS accessible-for-notify
    STATUS current
    DESCRIPTION
        "Parameter 'source_ip_address' in event NSM.71"
    ::= { nsmEventObjects71 1 }

nsm71_source_port OBJECT-TYPE
    SYNTAX Integer32
    MAX-ACCESS accessible-for-notify
    STATUS current
    DESCRIPTION
        "Parameter 'source_port' in event NSM.71"
    ::= { nsmEventObjects71 2 }

nsmEventObjects72 OBJECT-IDENTITY
    STATUS current
    DESCRIPTION
        "Event NSM.72
        Starting control messages exchange corresponding to the ARR protocol
        from the device whose IP address is indicated and which listens on this
        port to receive response messages from the local device. This latter
        acts as responder and its IP address and port are also displayed."
    ::= { nsmEventsGroup 72 }

nsm72_source_ip_address OBJECT-TYPE
    SYNTAX IpAddress
    MAX-ACCESS accessible-for-notify
    STATUS current
    DESCRIPTION
        "Parameter 'source_ip_address' in event NSM.72"
    ::= { nsmEventObjects72 1 }

nsm72_source_port OBJECT-TYPE
    SYNTAX Integer32
    MAX-ACCESS accessible-for-notify
    STATUS current
    DESCRIPTION
        "Parameter 'source_port' in event NSM.72"
    ::= { nsmEventObjects72 2 }

nsm72_destination_ip_address OBJECT-TYPE
    SYNTAX IpAddress
    MAX-ACCESS accessible-for-notify
    STATUS current
    DESCRIPTION
        "Parameter 'destination_ip_address' in event NSM.72"
    ::= { nsmEventObjects72 3 }

nsm72_destination_port OBJECT-TYPE
    SYNTAX Integer32
    MAX-ACCESS accessible-for-notify
    STATUS current
    DESCRIPTION
        "Parameter 'destination_port' in event NSM.72"
    ::= { nsmEventObjects72 4 }

nsmEventObjects73 OBJECT-IDENTITY
    STATUS current
    DESCRIPTION
        "Event NSM.73
        Responder has received a control message (starting ARR protocol)
        containing indicated data (version, identifier, data length, command
        type, destination IP address, destination port, total duration of
        operation)."
    ::= { nsmEventsGroup 73 }

nsm73_version OBJECT-TYPE
    SYNTAX Integer32
    MAX-ACCESS accessible-for-notify
    STATUS current
    DESCRIPTION
        "Parameter 'version' in event NSM.73"
    ::= { nsmEventObjects73 1 }

nsm73_identifier OBJECT-TYPE
    SYNTAX Integer32
    MAX-ACCESS accessible-for-notify
    STATUS current
    DESCRIPTION
        "Parameter 'identifier' in event NSM.73"
    ::= { nsmEventObjects73 2 }

nsm73_length OBJECT-TYPE
    SYNTAX Integer32
    MAX-ACCESS accessible-for-notify
    STATUS current
    DESCRIPTION
        "Parameter 'length' in event NSM.73"
    ::= { nsmEventObjects73 3 }

nsm73_command OBJECT-TYPE
    SYNTAX Integer32
    MAX-ACCESS accessible-for-notify
    STATUS current
    DESCRIPTION
        "Parameter 'command' in event NSM.73"
    ::= { nsmEventObjects73 4 }

nsm73_destination_ip_address OBJECT-TYPE
    SYNTAX IpAddress
    MAX-ACCESS accessible-for-notify
    STATUS current
    DESCRIPTION
        "Parameter 'destination_ip_address' in event NSM.73"
    ::= { nsmEventObjects73 5 }

nsm73_destination_port OBJECT-TYPE
    SYNTAX Integer32
    MAX-ACCESS accessible-for-notify
    STATUS current
    DESCRIPTION
        "Parameter 'destination_port' in event NSM.73"
    ::= { nsmEventObjects73 6 }

nsm73_duration OBJECT-TYPE
    SYNTAX Integer32
    MAX-ACCESS accessible-for-notify
    STATUS current
    DESCRIPTION
        "Parameter 'duration' in event NSM.73"
    ::= { nsmEventObjects73 7 }

nsmEventObjects74 OBJECT-IDENTITY
    STATUS current
    DESCRIPTION
        "Event NSM.74
        Responder sends a response to the previously received control packet
        (ARR protocol), indicating destination IP address and port."
    ::= { nsmEventsGroup 74 }

nsm74_client_ip_address OBJECT-TYPE
    SYNTAX IpAddress
    MAX-ACCESS accessible-for-notify
    STATUS current
    DESCRIPTION
        "Parameter 'client_ip_address' in event NSM.74"
    ::= { nsmEventObjects74 1 }

nsm74_client_port OBJECT-TYPE
    SYNTAX Integer32
    MAX-ACCESS accessible-for-notify
    STATUS current
    DESCRIPTION
        "Parameter 'client_port' in event NSM.74"
    ::= { nsmEventObjects74 2 }

nsmEventObjects75 OBJECT-IDENTITY
    STATUS current
    DESCRIPTION
        "Event NSM.75
        End of control message exchange corresponding to ARR protocol between
        the devices whose IP addresses and ports are indicated."
    ::= { nsmEventsGroup 75 }

nsm75_source_ip_address OBJECT-TYPE
    SYNTAX IpAddress
    MAX-ACCESS accessible-for-notify
    STATUS current
    DESCRIPTION
        "Parameter 'source_ip_address' in event NSM.75"
    ::= { nsmEventObjects75 1 }

nsm75_source_port OBJECT-TYPE
    SYNTAX Integer32
    MAX-ACCESS accessible-for-notify
    STATUS current
    DESCRIPTION
        "Parameter 'source_port' in event NSM.75"
    ::= { nsmEventObjects75 2 }

nsm75_destination_ip_address OBJECT-TYPE
    SYNTAX IpAddress
    MAX-ACCESS accessible-for-notify
    STATUS current
    DESCRIPTION
        "Parameter 'destination_ip_address' in event NSM.75"
    ::= { nsmEventObjects75 3 }

nsm75_destination_port OBJECT-TYPE
    SYNTAX Integer32
    MAX-ACCESS accessible-for-notify
    STATUS current
    DESCRIPTION
        "Parameter 'destination_port' in event NSM.75"
    ::= { nsmEventObjects75 4 }

nsmEventObjects76 OBJECT-IDENTITY
    STATUS current
    DESCRIPTION
        "Event NSM.76
        Responder receives a TEST message with indicated data."
    ::= { nsmEventsGroup 76 }

nsm76_source_ip_address OBJECT-TYPE
    SYNTAX IpAddress
    MAX-ACCESS accessible-for-notify
    STATUS current
    DESCRIPTION
        "Parameter 'source_ip_address' in event NSM.76"
    ::= { nsmEventObjects76 1 }

nsm76_source_port OBJECT-TYPE
    SYNTAX Integer32
    MAX-ACCESS accessible-for-notify
    STATUS current
    DESCRIPTION
        "Parameter 'source_port' in event NSM.76"
    ::= { nsmEventObjects76 2 }

nsm76_destination_ip_address OBJECT-TYPE
    SYNTAX IpAddress
    MAX-ACCESS accessible-for-notify
    STATUS current
    DESCRIPTION
        "Parameter 'destination_ip_address' in event NSM.76"
    ::= { nsmEventObjects76 3 }

nsm76_destination_port OBJECT-TYPE
    SYNTAX Integer32
    MAX-ACCESS accessible-for-notify
    STATUS current
    DESCRIPTION
        "Parameter 'destination_port' in event NSM.76"
    ::= { nsmEventObjects76 4 }

nsm76_client_sequence_number OBJECT-TYPE
    SYNTAX Integer32
    MAX-ACCESS accessible-for-notify
    STATUS current
    DESCRIPTION
        "Parameter 'client_sequence_number' in event NSM.76"
    ::= { nsmEventObjects76 5 }

nsmEventObjects77 OBJECT-IDENTITY
    STATUS current
    DESCRIPTION
        "Event NSM.77
        Responder sends a response to the previously received control packet
        (ARR protocol), indicating destination IP address and port."
    ::= { nsmEventsGroup 77 }

nsm77_client_ip_address OBJECT-TYPE
    SYNTAX IpAddress
    MAX-ACCESS accessible-for-notify
    STATUS current
    DESCRIPTION
        "Parameter 'client_ip_address' in event NSM.77"
    ::= { nsmEventObjects77 1 }

nsm77_client_port OBJECT-TYPE
    SYNTAX Integer32
    MAX-ACCESS accessible-for-notify
    STATUS current
    DESCRIPTION
        "Parameter 'client_port' in event NSM.77"
    ::= { nsmEventObjects77 2 }

nsmEventObjects79 OBJECT-IDENTITY
    STATUS current
    DESCRIPTION
        "Event NSM.79
        Once the TEST packet exchange has finalized or the wait timed out, the
        listening port for a given client is released."
    ::= { nsmEventsGroup 79 }

nsm79_client_port OBJECT-TYPE
    SYNTAX Integer32
    MAX-ACCESS accessible-for-notify
    STATUS current
    DESCRIPTION
        "Parameter 'client_port' in event NSM.79"
    ::= { nsmEventObjects79 1 }

nsmEventObjects81 OBJECT-IDENTITY
    STATUS current
    DESCRIPTION
        "Event NSM.81
        The UDP port, through which TEST messages are received for a Jitter
        operation, cannot be opened."
    ::= { nsmEventsGroup 81 }

nsm81_port OBJECT-TYPE
    SYNTAX Integer32
    MAX-ACCESS accessible-for-notify
    STATUS current
    DESCRIPTION
        "Parameter 'port' in event NSM.81"
    ::= { nsmEventObjects81 1 }

nsmEventObjects82 OBJECT-IDENTITY
    STATUS current
    DESCRIPTION
        "Event NSM.82
        Indicates that the specified port cannot be found on the list of used
        ports."
    ::= { nsmEventsGroup 82 }

nsm82_port OBJECT-TYPE
    SYNTAX Integer32
    MAX-ACCESS accessible-for-notify
    STATUS current
    DESCRIPTION
        "Parameter 'port' in event NSM.82"
    ::= { nsmEventObjects82 1 }

nsmEventObjects83 OBJECT-IDENTITY
    STATUS current
    DESCRIPTION
        "Event NSM.83
        The specified session could not be created."
    ::= { nsmEventsGroup 83 }

nsm83_source_ip_address OBJECT-TYPE
    SYNTAX IpAddress
    MAX-ACCESS accessible-for-notify
    STATUS current
    DESCRIPTION
        "Parameter 'source_ip_address' in event NSM.83"
    ::= { nsmEventObjects83 1 }

nsm83_source_port OBJECT-TYPE
    SYNTAX Integer32
    MAX-ACCESS accessible-for-notify
    STATUS current
    DESCRIPTION
        "Parameter 'source_port' in event NSM.83"
    ::= { nsmEventObjects83 2 }

nsm83_destination_ip_address OBJECT-TYPE
    SYNTAX IpAddress
    MAX-ACCESS accessible-for-notify
    STATUS current
    DESCRIPTION
        "Parameter 'destination_ip_address' in event NSM.83"
    ::= { nsmEventObjects83 3 }

nsm83_destination_port OBJECT-TYPE
    SYNTAX Integer32
    MAX-ACCESS accessible-for-notify
    STATUS current
    DESCRIPTION
        "Parameter 'destination_port' in event NSM.83"
    ::= { nsmEventObjects83 4 }


nsmNotification1 NOTIFICATION-TYPE
    OBJECTS { 
              nsm1_generic_info 
            }
    STATUS current
    DESCRIPTION
        "Notification of Event NSM.1

        Message: '$1'

        Parameters list:
              $1: nsm1_generic_info

        Generic event to display any information."
    ::= { nsmNotificationsPrefix 1 }

nsmNotification2 NOTIFICATION-TYPE
    OBJECTS { 
              nsm2_operation 
            }
    STATUS current
    DESCRIPTION
        "Notification of Event NSM.2

        Message: 'Operation($1): Inserting operation in memory list'

        Parameters list:
              $1: nsm2_operation

        Inserts operation whose identifier is indicated in the active or pending
        execution operations list."
    ::= { nsmNotificationsPrefix 2 }

nsmNotification3 NOTIFICATION-TYPE
    OBJECTS { 
              nsm3_operation 
            }
    STATUS current
    DESCRIPTION
        "Notification of Event NSM.3

        Message: 'Operation($1) Scheduler: Starting an operation'

        Parameters list:
              $1: nsm3_operation

        Indicates scheduled start up or instance for an operation."
    ::= { nsmNotificationsPrefix 3 }

nsmNotification4 NOTIFICATION-TYPE
    OBJECTS { 
              nsm4_operation 
            }
    STATUS current
    DESCRIPTION
        "Notification of Event NSM.4

        Message: 'Operation($1) Scheduler: Updating result'

        Parameters list:
              $1: nsm4_operation

        Indicates the end of an instance execution for a specific operation and
        the procedure to process the result and update related statistics and
        other related information."
    ::= { nsmNotificationsPrefix 4 }

nsmNotification5 NOTIFICATION-TYPE
    OBJECTS { 
              nsm5_operation 
            }
    STATUS current
    DESCRIPTION
        "Notification of Event NSM.5

        Message: 'Operation($1) Scheduler: Life complete'

        Parameters list:
              $1: nsm5_operation

        Timer controlling the indicated operation life has timed out: this is
        the time an entry can be in an 'active' or 'pending' state. Once this
        time has timed out, the entry passes to 'inactive'."
    ::= { nsmNotificationsPrefix 5 }

nsmNotification6 NOTIFICATION-TYPE
    OBJECTS { 
              nsm6_operation 
            }
    STATUS current
    DESCRIPTION
        "Notification of Event NSM.6

        Message: 'Operation($1) Scheduler: Ageout'

        Parameters list:
              $1: nsm6_operation

        Timer controlling the indicated operation ageout has timed out: this is
        the time than an entry can be in a state distinct to 'active'. Once this
        time has timed out the entry is deleted from the list of active
        operations."
    ::= { nsmNotificationsPrefix 6 }

nsmNotification7 NOTIFICATION-TYPE
    OBJECTS { 
              nsm7_operation, 
              nsm7_op_memory_addr 
            }
    STATUS current
    DESCRIPTION
        "Notification of Event NSM.7

        Message: 'Operation($1) Destroy: Operation 0x$2 destroyed'

        Parameters list:
              $1: nsm7_operation
              $2: nsm7_op_memory_addr

        Operation with indicated identifier has been destroyed: it has been
        deleted from the list of active operations and also memory assigned to
        it released, which corresponds to the memory block beginning with the
        displayed address."
    ::= { nsmNotificationsPrefix 7 }

nsmNotification8 NOTIFICATION-TYPE
    OBJECTS { 
              nsm8_operation, 
              nsm8_op_memory_addr 
            }
    STATUS current
    DESCRIPTION
        "Notification of Event NSM.8

        Message: 'Operation($1) Delete: Operation 0x$2 deleted'

        Parameters list:
              $1: nsm8_operation
              $2: nsm8_op_memory_addr

        Operation with indicated identifier has been deleted: the assigned
        memory has been released, which corresponds to the memory block
        beginning with the displayed address. Before deleting (releasing memory)
        it may be necessary to remove the entry from the active operations list
        (e.g. perhaps due to the fact an error was produced before this was
        introduced in the list and it is necessary to release the memory
        assigned to it)."
    ::= { nsmNotificationsPrefix 8 }

nsmNotification9 NOTIFICATION-TYPE
    OBJECTS { 
              nsm9_operation, 
              nsm9_op_memory_addr 
            }
    STATUS current
    DESCRIPTION
        "Notification of Event NSM.9

        Message: 'Operation($1) Finish: Operation 0x$2 finished'

        Parameters list:
              $1: nsm9_operation
              $2: nsm9_op_memory_addr

        Indicates the end of the operation with the indicated identifier."
    ::= { nsmNotificationsPrefix 9 }

nsmNotification10 NOTIFICATION-TYPE
    OBJECTS { 
              nsm10_operation 
            }
    STATUS current
    DESCRIPTION
        "Notification of Event NSM.10

        Message: 'Operation($1) Scheduler: Operation timeout'

        Parameters list:
              $1: nsm10_operation

        Timer for an operation execution or instance has timed out."
    ::= { nsmNotificationsPrefix 10 }

nsmNotification11 NOTIFICATION-TYPE
    STATUS current
    DESCRIPTION
        "Notification of Event NSM.11

        Message: 'No internal timestamp found'

        A packet without internal timestamp (in iorb) has been received.
        Internal timestamp is necessary in certain NSM operations."
    ::= { nsmNotificationsPrefix 11 }

nsmNotification12 NOTIFICATION-TYPE
    OBJECTS { 
              nsm12_operation, 
              nsm12_detail 
            }
    STATUS current
    DESCRIPTION
        "Notification of Event NSM.12

        Message: 'Operation($1) Client: $2'

        Parameters list:
              $1: nsm12_operation
              $2: nsm12_detail

        Info about an operation client"
    ::= { nsmNotificationsPrefix 12 }

nsmNotification13 NOTIFICATION-TYPE
    STATUS current
    DESCRIPTION
        "Notification of Event NSM.13

        Message: '---'

        Reserved for possible future use."
    ::= { nsmNotificationsPrefix 13 }

nsmNotification14 NOTIFICATION-TYPE
    STATUS current
    DESCRIPTION
        "Notification of Event NSM.14

        Message: '---'

        Reserved for possible future use."
    ::= { nsmNotificationsPrefix 14 }

nsmNotification15 NOTIFICATION-TYPE
    STATUS current
    DESCRIPTION
        "Notification of Event NSM.15

        Message: '---'

        Reserved for possible future use."
    ::= { nsmNotificationsPrefix 15 }

nsmNotification16 NOTIFICATION-TYPE
    STATUS current
    DESCRIPTION
        "Notification of Event NSM.16

        Message: '---'

        Reserved for possible future use."
    ::= { nsmNotificationsPrefix 16 }

nsmNotification17 NOTIFICATION-TYPE
    STATUS current
    DESCRIPTION
        "Notification of Event NSM.17

        Message: '---'

        Reserved for possible future use."
    ::= { nsmNotificationsPrefix 17 }

nsmNotification18 NOTIFICATION-TYPE
    STATUS current
    DESCRIPTION
        "Notification of Event NSM.18

        Message: '---'

        Reserved for possible future use."
    ::= { nsmNotificationsPrefix 18 }

nsmNotification19 NOTIFICATION-TYPE
    STATUS current
    DESCRIPTION
        "Notification of Event NSM.19

        Message: '---'

        Reserved for possible future use."
    ::= { nsmNotificationsPrefix 19 }

nsmNotification20 NOTIFICATION-TYPE
    STATUS current
    DESCRIPTION
        "Notification of Event NSM.20

        Message: '---'

        Reserved for possible future use."
    ::= { nsmNotificationsPrefix 20 }

nsmNotification21 NOTIFICATION-TYPE
    OBJECTS { 
              nsm21_operation 
            }
    STATUS current
    DESCRIPTION
        "Notification of Event NSM.21

        Message: 'Operation($1) ECHO operation: Sending an echo operation'

        Parameters list:
              $1: nsm21_operation

        Indicates start of executing an instance for a determined echo
        operation."
    ::= { nsmNotificationsPrefix 21 }

nsmNotification22 NOTIFICATION-TYPE
    OBJECTS { 
              nsm22_operation, 
              nsm22_rtt 
            }
    STATUS current
    DESCRIPTION
        "Notification of Event NSM.22

        Message: 'Operation($1) ECHO operation: RTT = $2'

        Parameters list:
              $1: nsm22_operation
              $2: nsm22_rtt

        After executing ECHO operation, the obtained Round Trip Time is
        indicated."
    ::= { nsmNotificationsPrefix 22 }

nsmNotification23 NOTIFICATION-TYPE
    OBJECTS { 
              nsm23_operation 
            }
    STATUS current
    DESCRIPTION
        "Notification of Event NSM.23

        Message: 'Operation($1) BFD operation: Starting a BFD polling sequence'

        Parameters list:
              $1: nsm23_operation

        Indicates start of executing an instance for a determined BFD
        operation."
    ::= { nsmNotificationsPrefix 23 }

nsmNotification24 NOTIFICATION-TYPE
    STATUS current
    DESCRIPTION
        "Notification of Event NSM.24

        Message: '---'

        Reserved for possible future use."
    ::= { nsmNotificationsPrefix 24 }

nsmNotification25 NOTIFICATION-TYPE
    STATUS current
    DESCRIPTION
        "Notification of Event NSM.25

        Message: '---'

        Reserved for possible future use."
    ::= { nsmNotificationsPrefix 25 }

nsmNotification26 NOTIFICATION-TYPE
    STATUS current
    DESCRIPTION
        "Notification of Event NSM.26

        Message: '---'

        Reserved for possible future use."
    ::= { nsmNotificationsPrefix 26 }

nsmNotification27 NOTIFICATION-TYPE
    STATUS current
    DESCRIPTION
        "Notification of Event NSM.27

        Message: '---'

        Reserved for possible future use."
    ::= { nsmNotificationsPrefix 27 }

nsmNotification28 NOTIFICATION-TYPE
    STATUS current
    DESCRIPTION
        "Notification of Event NSM.28

        Message: '---'

        Reserved for possible future use."
    ::= { nsmNotificationsPrefix 28 }

nsmNotification29 NOTIFICATION-TYPE
    STATUS current
    DESCRIPTION
        "Notification of Event NSM.29

        Message: '---'

        Reserved for possible future use."
    ::= { nsmNotificationsPrefix 29 }

nsmNotification30 NOTIFICATION-TYPE
    STATUS current
    DESCRIPTION
        "Notification of Event NSM.30

        Message: '---'

        Reserved for possible future use."
    ::= { nsmNotificationsPrefix 30 }

nsmNotification31 NOTIFICATION-TYPE
    OBJECTS { 
              nsm31_operation 
            }
    STATUS current
    DESCRIPTION
        "Notification of Event NSM.31

        Message: 'Operation($1) DNS operation: Starting dns operation'

        Parameters list:
              $1: nsm31_operation

        Indicates execution start for a determined DNS operation instance."
    ::= { nsmNotificationsPrefix 31 }

nsmNotification32 NOTIFICATION-TYPE
    OBJECTS { 
              nsm32_operation, 
              nsm32_url 
            }
    STATUS current
    DESCRIPTION
        "Notification of Event NSM.32

        Message: 'Operation($1) DNS operation: Query name - $2'

        Parameters list:
              $1: nsm32_operation
              $2: nsm32_url

        A DNS operation is being executed to resolve the indicated name."
    ::= { nsmNotificationsPrefix 32 }

nsmNotification33 NOTIFICATION-TYPE
    OBJECTS { 
              nsm33_operation, 
              nsm33_server_ip_address 
            }
    STATUS current
    DESCRIPTION
        "Notification of Event NSM.33

        Message: 'Operation($1) DNS operation: Query name server - $2'

        Parameters list:
              $1: nsm33_operation
              $2: nsm33_server_ip_address

        A DNS operation is being executed with the indicated server."
    ::= { nsmNotificationsPrefix 33 }

nsmNotification34 NOTIFICATION-TYPE
    OBJECTS { 
              nsm34_operation, 
              nsm34_dns_result 
            }
    STATUS current
    DESCRIPTION
        "Notification of Event NSM.34

        Message: 'Operation($1) DNS operation: Query return code - $2'

        Parameters list:
              $1: nsm34_operation
              $2: nsm34_dns_result

        A DNS operation has terminated with the result shown in the string
        (describes the return code). Possible return codes:
        0. DNS OK
        1. Name: Empty Label
        2. Name: Label too long
        3. Name: Bad escape
        4. Name: Bad bitstring
        5. Name: Bit string too long
        6. Name: Bad dotted quad
        7. Name: No space to store name
        8. Name: Unexpected end
        9. No iorb to send query
        10. No memory
        11. DNS not initialized
        12. Query of an IP address
        13. Query needed (internal)
        14. Maximum number of retries reached
        15. Received format error
        16. Received name error
        17. Unexpected end of query (internal)
        18. Query killed
        19. DNS Generic Error"
    ::= { nsmNotificationsPrefix 34 }

nsmNotification35 NOTIFICATION-TYPE
    OBJECTS { 
              nsm35_operation, 
              nsm35_ip_address 
            }
    STATUS current
    DESCRIPTION
        "Notification of Event NSM.35

        Message: 'Operation($1) DNS operation: received IP address $2'

        Parameters list:
              $1: nsm35_operation
              $2: nsm35_ip_address

        After executing the DNS operation, the IP address corresponding to
        requested name is indicated."
    ::= { nsmNotificationsPrefix 35 }

nsmNotification36 NOTIFICATION-TYPE
    OBJECTS { 
              nsm36_operation, 
              nsm36_rtt 
            }
    STATUS current
    DESCRIPTION
        "Notification of Event NSM.36

        Message: 'Operation($1) DNS operation: RTT = $2'

        Parameters list:
              $1: nsm36_operation
              $2: nsm36_rtt

        After executing DNS operation, the obtained Round Trip Time is
        indicated."
    ::= { nsmNotificationsPrefix 36 }

nsmNotification37 NOTIFICATION-TYPE
    OBJECTS { 
              nsm37_operation, 
              nsm37_ip_address 
            }
    STATUS current
    DESCRIPTION
        "Notification of Event NSM.37

        Message: 'Operation($1) DNS operation NOT needed: $2'

        Parameters list:
              $1: nsm37_operation
              $2: nsm37_ip_address

        DNS resolve is not required as an IP address has been directly
        indicated."
    ::= { nsmNotificationsPrefix 37 }

nsmNotification38 NOTIFICATION-TYPE
    STATUS current
    DESCRIPTION
        "Notification of Event NSM.38

        Message: '---'

        Reserved for possible future use."
    ::= { nsmNotificationsPrefix 38 }

nsmNotification39 NOTIFICATION-TYPE
    STATUS current
    DESCRIPTION
        "Notification of Event NSM.39

        Message: '---'

        Reserved for possible future use."
    ::= { nsmNotificationsPrefix 39 }

nsmNotification40 NOTIFICATION-TYPE
    STATUS current
    DESCRIPTION
        "Notification of Event NSM.40

        Message: '---'

        Reserved for possible future use."
    ::= { nsmNotificationsPrefix 40 }

nsmNotification41 NOTIFICATION-TYPE
    OBJECTS { 
              nsm41_operation 
            }
    STATUS current
    DESCRIPTION
        "Notification of Event NSM.41

        Message: 'Operation($1) HTTP operation: Starting http operation'

        Parameters list:
              $1: nsm41_operation

        Indicates the execution startup for a determined HTTP operation
        instance."
    ::= { nsmNotificationsPrefix 41 }

nsmNotification42 NOTIFICATION-TYPE
    OBJECTS { 
              nsm42_operation, 
              nsm42_sent_bytes,
              nsm42_total_bytes 
            }
    STATUS current
    DESCRIPTION
        "Notification of Event NSM.42

        Message: 'Operation($1) HTTP operation: Sent $2 of $3 bytes'

        Parameters list:
              $1: nsm42_operation
              $2: nsm42_sent_bytes
              $3: nsm42_total_bytes

        An HTTP operation is being executed: the number of sent bytes from a
        total is displayed together with the total."
    ::= { nsmNotificationsPrefix 42 }

nsmNotification43 NOTIFICATION-TYPE
    OBJECTS { 
              nsm43_operation, 
              nsm43_connection_result 
            }
    STATUS current
    DESCRIPTION
        "Notification of Event NSM.43

        Message: 'Operation($1) HTTP operation: Connection - $2'

        Parameters list:
              $1: nsm43_operation
              $2: nsm43_connection_result

        An HTTP operation is being executed: specifically, the process is at the
        point where it's waiting to connect, the connection attempt result is
        indicated.
        Possible results are:
        1. connected.
        2. error."
    ::= { nsmNotificationsPrefix 43 }

nsmNotification44 NOTIFICATION-TYPE
    OBJECTS { 
              nsm44_operation, 
              nsm44_rtt 
            }
    STATUS current
    DESCRIPTION
        "Notification of Event NSM.44

        Message: 'Operation($1) HTTP operation: RTT = $2'

        Parameters list:
              $1: nsm44_operation
              $2: nsm44_rtt

        After executing HTTP operation, the obtained Round Trip Time is
        indicated."
    ::= { nsmNotificationsPrefix 44 }

nsmNotification45 NOTIFICATION-TYPE
    OBJECTS { 
              nsm45_operation, 
              nsm45_error_message 
            }
    STATUS current
    DESCRIPTION
        "Notification of Event NSM.45

        Message: 'Operation($1) HTTP operation ERROR: $2'

        Parameters list:
              $1: nsm45_operation
              $2: nsm45_error_message

        An unexpected error has occurred (lack of memory, insufficient space in
        buffer, etc.), during an HTTP operation execution."
    ::= { nsmNotificationsPrefix 45 }

nsmNotification46 NOTIFICATION-TYPE
    STATUS current
    DESCRIPTION
        "Notification of Event NSM.46

        Message: '---'

        Reserved for possible future use."
    ::= { nsmNotificationsPrefix 46 }

nsmNotification47 NOTIFICATION-TYPE
    STATUS current
    DESCRIPTION
        "Notification of Event NSM.47

        Message: '---'

        Reserved for possible future use."
    ::= { nsmNotificationsPrefix 47 }

nsmNotification48 NOTIFICATION-TYPE
    STATUS current
    DESCRIPTION
        "Notification of Event NSM.48

        Message: '---'

        Reserved for possible future use."
    ::= { nsmNotificationsPrefix 48 }

nsmNotification49 NOTIFICATION-TYPE
    STATUS current
    DESCRIPTION
        "Notification of Event NSM.49

        Message: '---'

        Reserved for possible future use."
    ::= { nsmNotificationsPrefix 49 }

nsmNotification50 NOTIFICATION-TYPE
    STATUS current
    DESCRIPTION
        "Notification of Event NSM.50

        Message: '---'

        Reserved for possible future use."
    ::= { nsmNotificationsPrefix 50 }

nsmNotification51 NOTIFICATION-TYPE
    OBJECTS { 
              nsm51_operation, 
              nsm51_source_ip_address,
              nsm51_source_port,
              nsm51_destination_ip_address,
              nsm51_destination_port 
            }
    STATUS current
    DESCRIPTION
        "Notification of Event NSM.51

        Message: 'Operation($1) ARR protocol: Starting (src IP addr = $2, src port = $3) <-> (dest IP addr = $4, dest port = $5)'

        Parameters list:
              $1: nsm51_operation
              $2: nsm51_source_ip_address
              $3: nsm51_source_port
              $4: nsm51_destination_ip_address
              $5: nsm51_destination_port

        Startup of exchange of control messages corresponding to the ARR
        protocol from the device whose IP address and port are those indicated
        and that are transmitted to the destination IP address and port also
        included in the event."
    ::= { nsmNotificationsPrefix 51 }

nsmNotification52 NOTIFICATION-TYPE
    OBJECTS { 
              nsm52_operation, 
              nsm52_source_ip_address,
              nsm52_source_port,
              nsm52_destination_ip_address,
              nsm52_destination_port 
            }
    STATUS current
    DESCRIPTION
        "Notification of Event NSM.52

        Message: 'Operation($1) ARR protocol: Control packets interchange finished (src IP addr = $2, src port = $3) <-> (dest IP addr = $4, dest port = $5)'

        Parameters list:
              $1: nsm52_operation
              $2: nsm52_source_ip_address
              $3: nsm52_source_port
              $4: nsm52_destination_ip_address
              $5: nsm52_destination_port

        End of exchange of control messages corresponding to the ARR protocol
        from the device whose IP address and port are those indicated and with
        destination IP address and port also displayed. The open port is closed
        to carry out this communication, which appears as a second parameter."
    ::= { nsmNotificationsPrefix 52 }

nsmNotification53 NOTIFICATION-TYPE
    OBJECTS { 
              nsm53_operation, 
              nsm53_version,
              nsm53_identifier,
              nsm53_length,
              nsm53_command,
              nsm53_destination_ip_address,
              nsm53_destination_data_port,
              nsm53_duration 
            }
    STATUS current
    DESCRIPTION
        "Notification of Event NSM.53

        Message: 'Operation($1) Control Message: Sending message, version=$2, identifier=$3, length=$4, command=$5, destination IP address=$6, port=$7, duration=$8ms'

        Parameters list:
              $1: nsm53_operation
              $2: nsm53_version
              $3: nsm53_identifier
              $4: nsm53_length
              $5: nsm53_command
              $6: nsm53_destination_ip_address
              $7: nsm53_destination_data_port
              $8: nsm53_duration

        Sending an ARR protocol control message to the indicated IP address and
        port. This is significant to operations supporting this protocol e.g.
        Jitter."
    ::= { nsmNotificationsPrefix 53 }

nsmNotification54 NOTIFICATION-TYPE
    OBJECTS { 
              nsm54_operation 
            }
    STATUS current
    DESCRIPTION
        "Notification of Event NSM.54

        Message: 'Operation($1) Control Message: Timeout'

        Parameters list:
              $1: nsm54_operation

        Control message response wait timer has timed out."
    ::= { nsmNotificationsPrefix 54 }

nsmNotification55 NOTIFICATION-TYPE
    OBJECTS { 
              nsm55_operation, 
              nsm55_receive_status 
            }
    STATUS current
    DESCRIPTION
        "Notification of Event NSM.55

        Message: 'Operation($1) Control Message: Receive status = $2'

        Parameters list:
              $1: nsm55_operation
              $2: nsm55_receive_status

        A response to a previously sent control message has been received, the
        result is indicated."
    ::= { nsmNotificationsPrefix 55 }

nsmNotification56 NOTIFICATION-TYPE
    STATUS current
    DESCRIPTION
        "Notification of Event NSM.56

        Message: '---'

        Reserved for possible future use."
    ::= { nsmNotificationsPrefix 56 }

nsmNotification57 NOTIFICATION-TYPE
    STATUS current
    DESCRIPTION
        "Notification of Event NSM.57

        Message: '---'

        Reserved for possible future use."
    ::= { nsmNotificationsPrefix 57 }

nsmNotification58 NOTIFICATION-TYPE
    STATUS current
    DESCRIPTION
        "Notification of Event NSM.58

        Message: '---'

        Reserved for possible future use."
    ::= { nsmNotificationsPrefix 58 }

nsmNotification59 NOTIFICATION-TYPE
    STATUS current
    DESCRIPTION
        "Notification of Event NSM.59

        Message: '---'

        Reserved for possible future use."
    ::= { nsmNotificationsPrefix 59 }

nsmNotification60 NOTIFICATION-TYPE
    STATUS current
    DESCRIPTION
        "Notification of Event NSM.60

        Message: '---'

        Reserved for possible future use."
    ::= { nsmNotificationsPrefix 60 }

nsmNotification61 NOTIFICATION-TYPE
    OBJECTS { 
              nsm61_operation, 
              nsm61_vrf,
              nsm61_lookup_table_id 
            }
    STATUS current
    DESCRIPTION
        "Notification of Event NSM.61

        Message: 'Operation($1) Jitter operation: VRF: $2 lookup table id: $3'

        Parameters list:
              $1: nsm61_operation
              $2: nsm61_vrf
              $3: nsm61_lookup_table_id

        A Jitter operation is started using VRF."
    ::= { nsmNotificationsPrefix 61 }

nsmNotification62 NOTIFICATION-TYPE
    OBJECTS { 
              nsm62_operation 
            }
    STATUS current
    DESCRIPTION
        "Notification of Event NSM.62

        Message: 'Operation($1) Jitter operation: Starting jitter operation'

        Parameters list:
              $1: nsm62_operation

        Jitter operation starting."
    ::= { nsmNotificationsPrefix 62 }

nsmNotification63 NOTIFICATION-TYPE
    OBJECTS { 
              nsm63_operation, 
              nsm63_sequence_number,
              nsm63_rtt 
            }
    STATUS current
    DESCRIPTION
        "Notification of Event NSM.63

        Message: 'Operation($1) Jitter operation: seq=$2, rtt=$3'

        Parameters list:
              $1: nsm63_operation
              $2: nsm63_sequence_number
              $3: nsm63_rtt

        A Jitter operation is being executed: the operation identifier is
        displayed together with the sequence number and the obtained RTT."
    ::= { nsmNotificationsPrefix 63 }

nsmNotification64 NOTIFICATION-TYPE
    OBJECTS { 
              nsm64_operation, 
              nsm64_sequence_number,
              nsm64_jitterOut,
              nsm64_jitterIn 
            }
    STATUS current
    DESCRIPTION
        "Notification of Event NSM.64

        Message: 'Operation($1) Jitter operation: seq=$2, jitterOut=$3, jitterIn=$4'

        Parameters list:
              $1: nsm64_operation
              $2: nsm64_sequence_number
              $3: nsm64_jitterOut
              $4: nsm64_jitterIn

        A Jitter operation is being executed: the operation identifier is
        displayed together with the sequence number and the jitterOut (jitterSD)
        and jitterIn (jitterDS) values."
    ::= { nsmNotificationsPrefix 64 }

nsmNotification65 NOTIFICATION-TYPE
    OBJECTS { 
              nsm65_operation, 
              nsm65_sequence_number 
            }
    STATUS current
    DESCRIPTION
        "Notification of Event NSM.65

        Message: 'Operation($1) Jitter operation: Packet out of sequence ($2)'

        Parameters list:
              $1: nsm65_operation
              $2: nsm65_sequence_number

        An out of sequence packet has been received."
    ::= { nsmNotificationsPrefix 65 }

nsmNotification66 NOTIFICATION-TYPE
    OBJECTS { 
              nsm66_operation, 
              nsm66_counter 
            }
    STATUS current
    DESCRIPTION
        "Notification of Event NSM.66

        Message: 'Operation($1) Jitter operation: Packets SD lost ($2)'

        Parameters list:
              $1: nsm66_operation
              $2: nsm66_counter

        Packets to carry out calculations in source-destination direction have
        been lost."
    ::= { nsmNotificationsPrefix 66 }

nsmNotification67 NOTIFICATION-TYPE
    OBJECTS { 
              nsm67_operation, 
              nsm67_counter 
            }
    STATUS current
    DESCRIPTION
        "Notification of Event NSM.67

        Message: 'Operation($1) Jitter operation: Packets DS lost ($2)'

        Parameters list:
              $1: nsm67_operation
              $2: nsm67_counter

        Packets to carry out calculations in destination-source direction have
        been lost."
    ::= { nsmNotificationsPrefix 67 }

nsmNotification68 NOTIFICATION-TYPE
    OBJECTS { 
              nsm68_operation, 
              nsm68_counter 
            }
    STATUS current
    DESCRIPTION
        "Notification of Event NSM.68

        Message: 'Operation($1) Jitter operation: Packet late arrival ($2)'

        Parameters list:
              $1: nsm68_operation
              $2: nsm68_counter

        A packet has been received outside the reception window."
    ::= { nsmNotificationsPrefix 68 }

nsmNotification69 NOTIFICATION-TYPE
    OBJECTS { 
              nsm69_operation, 
              nsm69_counter 
            }
    STATUS current
    DESCRIPTION
        "Notification of Event NSM.69

        Message: 'Operation($1) Jitter operation: Packets MIA lost ($2)'

        Parameters list:
              $1: nsm69_operation
              $2: nsm69_counter

        Packets to carry out calculations in unknown direction have been lost."
    ::= { nsmNotificationsPrefix 69 }

nsmNotification70 NOTIFICATION-TYPE
    STATUS current
    DESCRIPTION
        "Notification of Event NSM.70

        Message: '---'

        Reserved for possible future use."
    ::= { nsmNotificationsPrefix 70 }

nsmNotification71 NOTIFICATION-TYPE
    OBJECTS { 
              nsm71_source_ip_address, 
              nsm71_source_port 
            }
    STATUS current
    DESCRIPTION
        "Notification of Event NSM.71

        Message: 'Responder: Received request from IP address $1, source port $2'

        Parameters list:
              $1: nsm71_source_ip_address
              $2: nsm71_source_port

        Responder receives a control message from indicated IP address and port."
    ::= { nsmNotificationsPrefix 71 }

nsmNotification72 NOTIFICATION-TYPE
    OBJECTS { 
              nsm72_source_ip_address, 
              nsm72_source_port,
              nsm72_destination_ip_address,
              nsm72_destination_port 
            }
    STATUS current
    DESCRIPTION
        "Notification of Event NSM.72

        Message: 'Responder: Starting ARR protocol (src IP addr = $1, src port = $2) <-> (dest IP addr = $3, dest port = $4)'

        Parameters list:
              $1: nsm72_source_ip_address
              $2: nsm72_source_port
              $3: nsm72_destination_ip_address
              $4: nsm72_destination_port

        Starting control messages exchange corresponding to the ARR protocol
        from the device whose IP address is indicated and which listens on this
        port to receive response messages from the local device. This latter
        acts as responder and its IP address and port are also displayed."
    ::= { nsmNotificationsPrefix 72 }

nsmNotification73 NOTIFICATION-TYPE
    OBJECTS { 
              nsm73_version, 
              nsm73_identifier,
              nsm73_length,
              nsm73_command,
              nsm73_destination_ip_address,
              nsm73_destination_port,
              nsm73_duration 
            }
    STATUS current
    DESCRIPTION
        "Notification of Event NSM.73

        Message: 'Responder: Received control message, version=$1, identifier=$2, length=$3, command=$4, destination IP address=$5, port=$6, duration=$7ms'

        Parameters list:
              $1: nsm73_version
              $2: nsm73_identifier
              $3: nsm73_length
              $4: nsm73_command
              $5: nsm73_destination_ip_address
              $6: nsm73_destination_port
              $7: nsm73_duration

        Responder has received a control message (starting ARR protocol)
        containing indicated data (version, identifier, data length, command
        type, destination IP address, destination port, total duration of
        operation)."
    ::= { nsmNotificationsPrefix 73 }

nsmNotification74 NOTIFICATION-TYPE
    OBJECTS { 
              nsm74_client_ip_address, 
              nsm74_client_port 
            }
    STATUS current
    DESCRIPTION
        "Notification of Event NSM.74

        Message: 'Responder: Sending control response to IP address $1, destination port $2'

        Parameters list:
              $1: nsm74_client_ip_address
              $2: nsm74_client_port

        Responder sends a response to the previously received control packet
        (ARR protocol), indicating destination IP address and port."
    ::= { nsmNotificationsPrefix 74 }

nsmNotification75 NOTIFICATION-TYPE
    OBJECTS { 
              nsm75_source_ip_address, 
              nsm75_source_port,
              nsm75_destination_ip_address,
              nsm75_destination_port 
            }
    STATUS current
    DESCRIPTION
        "Notification of Event NSM.75

        Message: 'Responder: ARR protocol - Control interchange finished (src IP addr = $1, src port = $2) <-> (dest IP addr = $3, dest port = $4)'

        Parameters list:
              $1: nsm75_source_ip_address
              $2: nsm75_source_port
              $3: nsm75_destination_ip_address
              $4: nsm75_destination_port

        End of control message exchange corresponding to ARR protocol between
        the devices whose IP addresses and ports are indicated."
    ::= { nsmNotificationsPrefix 75 }

nsmNotification76 NOTIFICATION-TYPE
    OBJECTS { 
              nsm76_source_ip_address, 
              nsm76_source_port,
              nsm76_destination_ip_address,
              nsm76_destination_port,
              nsm76_client_sequence_number 
            }
    STATUS current
    DESCRIPTION
        "Notification of Event NSM.76

        Message: 'Responder: Received TEST message (src IP addr = $1, src port = $2) -> (dest IP addr = $3, dest port = $4) sequence=$5'

        Parameters list:
              $1: nsm76_source_ip_address
              $2: nsm76_source_port
              $3: nsm76_destination_ip_address
              $4: nsm76_destination_port
              $5: nsm76_client_sequence_number

        Responder receives a TEST message with indicated data."
    ::= { nsmNotificationsPrefix 76 }

nsmNotification77 NOTIFICATION-TYPE
    OBJECTS { 
              nsm77_client_ip_address, 
              nsm77_client_port 
            }
    STATUS current
    DESCRIPTION
        "Notification of Event NSM.77

        Message: 'Responder: Sending TEST response to IP address $1, destination port $2'

        Parameters list:
              $1: nsm77_client_ip_address
              $2: nsm77_client_port

        Responder sends a response to the previously received control packet
        (ARR protocol), indicating destination IP address and port."
    ::= { nsmNotificationsPrefix 77 }

nsmNotification78 NOTIFICATION-TYPE
    STATUS current
    DESCRIPTION
        "Notification of Event NSM.78

        Message: 'Responder: expTimer expired'

        Timer to control the exchange of TEST packets between the responder and
        the client has timed out: the client has not sent test packets to the
        port indicated in the control packets during a determined time and the
        responder will proceed to end the communication."
    ::= { nsmNotificationsPrefix 78 }

nsmNotification79 NOTIFICATION-TYPE
    OBJECTS { 
              nsm79_client_port 
            }
    STATUS current
    DESCRIPTION
        "Notification of Event NSM.79

        Message: 'Responder: cleaning up port ($1)'

        Parameters list:
              $1: nsm79_client_port

        Once the TEST packet exchange has finalized or the wait timed out, the
        listening port for a given client is released."
    ::= { nsmNotificationsPrefix 79 }

nsmNotification80 NOTIFICATION-TYPE
    STATUS current
    DESCRIPTION
        "Notification of Event NSM.80

        Message: 'Responder: No memory available'

        No memory available to insert a new element in the list of ports being
        used."
    ::= { nsmNotificationsPrefix 80 }

nsmNotification81 NOTIFICATION-TYPE
    OBJECTS { 
              nsm81_port 
            }
    STATUS current
    DESCRIPTION
        "Notification of Event NSM.81

        Message: 'Responder: Error opening UDP port ($1)'

        Parameters list:
              $1: nsm81_port

        The UDP port, through which TEST messages are received for a Jitter
        operation, cannot be opened."
    ::= { nsmNotificationsPrefix 81 }

nsmNotification82 NOTIFICATION-TYPE
    OBJECTS { 
              nsm82_port 
            }
    STATUS current
    DESCRIPTION
        "Notification of Event NSM.82

        Message: 'Responder: Port not found ($1)'

        Parameters list:
              $1: nsm82_port

        Indicates that the specified port cannot be found on the list of used
        ports."
    ::= { nsmNotificationsPrefix 82 }

nsmNotification83 NOTIFICATION-TYPE
    OBJECTS { 
              nsm83_source_ip_address, 
              nsm83_source_port,
              nsm83_destination_ip_address,
              nsm83_destination_port 
            }
    STATUS current
    DESCRIPTION
        "Notification of Event NSM.83

        Message: 'Responder: Session ($1, $2) -> ($3, $4) could not be created'

        Parameters list:
              $1: nsm83_source_ip_address
              $2: nsm83_source_port
              $3: nsm83_destination_ip_address
              $4: nsm83_destination_port

        The specified session could not be created."
    ::= { nsmNotificationsPrefix 83 }


END
