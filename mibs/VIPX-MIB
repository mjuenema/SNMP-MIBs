--  Title:    vipx_snmp.mib
--  Version:  02500415
--  Date:     Thu Jan 17 14:33:32 2013 
--
--  Copyright @ 2010 VCS BOSCH GROUP
--
--  Auto-generated file parsed from source code
--  This MIB defines objects for an SNMP agent and provides the 
--  functionality to configure VCS devices 
--
--
-- 
-- List of traps:
--    relay_output_state
--    input_pin_state
--    video_alarm_state
--    motion_alarm_state
--    connect_to
--    disconnect_primitive
--    viproc_alarm
--    hd_recording_active
--    hd_mgr_start
--    storage_report
--    span_use_status
--    power_supply
--    vca_task_running_state
-- 
-- 
-- All commands:
-- 1.3.6.1.4.1.3967.1.1            sys
-- 1.3.6.1.4.1.3967.1.1.1             identification
-- 1.3.6.1.4.1.3967.1.1.1.1              unit_name
-- 1.3.6.1.4.1.3967.1.1.1.2              unit_id
-- 1.3.6.1.4.1.3967.1.1.1.3              camnameTable
-- 1.3.6.1.4.1.3967.1.1.1.3.1               camnameEntry
-- 1.3.6.1.4.1.3967.1.1.1.3.1.1                camname
-- 1.3.6.1.4.1.3967.1.1.1.4              hardware_version
-- 1.3.6.1.4.1.3967.1.1.1.5              software_version
-- 1.3.6.1.4.1.3967.1.1.2             time
-- 1.3.6.1.4.1.3967.1.1.2.1              timezone
-- 1.3.6.1.4.1.3967.1.1.2.2              ntp_server_ip_str
-- 1.3.6.1.4.1.3967.1.1.3             connection
-- 1.3.6.1.4.1.3967.1.1.3.1              connect_to
-- 1.3.6.1.4.1.3967.1.1.3.2              disconnect_primitive
-- 1.3.6.1.4.1.3967.1.1.4             viproc
-- 1.3.6.1.4.1.3967.1.1.4.1              viproc_id
-- 1.3.6.1.4.1.3967.1.1.4.2              viproc_onoff
-- 1.3.6.1.4.1.3967.1.1.5             aux
-- 1.3.6.1.4.1.3967.1.1.5.1              oem_device_name
-- 1.3.6.1.4.1.3967.1.1.5.2              oem_ext_id
-- 1.3.6.1.4.1.3967.1.1.5.3              defaults
-- 1.3.6.1.4.1.3967.1.1.5.4              factory_defaults
-- 1.3.6.1.4.1.3967.1.1.5.5              board_reset
-- 1.3.6.1.4.1.3967.1.1.5.6              boot_default_app
-- 1.3.6.1.4.1.3967.1.1.5.7              led_blinking
-- 1.3.6.1.4.1.3967.1.1.5.8              sanity_check
-- 1.3.6.1.4.1.3967.1.1.5.9              bsp_dev_errorTable
-- 1.3.6.1.4.1.3967.1.1.5.9.1               bsp_dev_errorEntry
-- 1.3.6.1.4.1.3967.1.1.5.9.1.1                bsp_dev_error
-- 1.3.6.1.4.1.3967.1.1.5.10             livetime_max_temp
-- 1.3.6.1.4.1.3967.1.1.5.11             livetime_min_temp
-- 1.3.6.1.4.1.3967.1.1.5.12             livetime_op_minutes
-- 1.3.6.1.4.1.3967.1.1.6             power_supply
-- 1.3.6.1.4.1.3967.1.1.7             temperatureTable
-- 1.3.6.1.4.1.3967.1.1.7.1              temperatureEntry
-- 1.3.6.1.4.1.3967.1.1.7.1.1               temp_sens
-- 1.3.6.1.4.1.3967.1.1.8             fan_speedTable
-- 1.3.6.1.4.1.3967.1.1.8.1              fan_speedEntry
-- 1.3.6.1.4.1.3967.1.1.8.1.1               fan_speed
-- 1.3.6.1.4.1.3967.1.1.9             cpu_loadTable
-- 1.3.6.1.4.1.3967.1.1.9.1              cpu_loadEntry
-- 1.3.6.1.4.1.3967.1.1.9.1.1               cpu_load_idle
-- 1.3.6.1.4.1.3967.1.1.9.1.2               cpu_load_coder
-- 1.3.6.1.4.1.3967.1.1.9.1.3               cpu_load_vca
-- 1.3.6.1.4.1.3967.1.1.9.1.4               cpu_load
-- 1.3.6.1.4.1.3967.1.2            video
-- 1.3.6.1.4.1.3967.1.2.1             inputTable
-- 1.3.6.1.4.1.3967.1.2.1.1              inputEntry
-- 1.3.6.1.4.1.3967.1.2.1.1.1               input_source_val
-- 1.3.6.1.4.1.3967.1.2.2             encoderTable
-- 1.3.6.1.4.1.3967.1.2.2.1              encoderEntry
-- 1.3.6.1.4.1.3967.1.2.2.1.1               video_encoder_status
-- 1.3.6.1.4.1.3967.1.3            alarm
-- 1.3.6.1.4.1.3967.1.3.1             video_alarmTable
-- 1.3.6.1.4.1.3967.1.3.1.1              video_alarmEntry
-- 1.3.6.1.4.1.3967.1.3.1.1.1               video_alarm_state
-- 1.3.6.1.4.1.3967.1.3.2             motion_detectorTable
-- 1.3.6.1.4.1.3967.1.3.2.1              motion_detectorEntry
-- 1.3.6.1.4.1.3967.1.3.2.1.1               motion_alarm_state
-- 1.3.6.1.4.1.3967.1.3.3             viproc_alarmTable
-- 1.3.6.1.4.1.3967.1.3.3.1              viproc_alarmEntry
-- 1.3.6.1.4.1.3967.1.3.3.1.1               viproc_alarm
-- 1.3.6.1.4.1.3967.1.3.3.1.2               vca_task_running_state
-- 1.3.6.1.4.1.3967.1.4            digital_io
-- 1.3.6.1.4.1.3967.1.4.1             out
-- 1.3.6.1.4.1.3967.1.4.1.1              relaisTable
-- 1.3.6.1.4.1.3967.1.4.1.1.1               relaisEntry
-- 1.3.6.1.4.1.3967.1.4.1.1.1.1                relay_output_state
-- 1.3.6.1.4.1.3967.1.4.2             in
-- 1.3.6.1.4.1.3967.1.4.2.1              input_pin_stateTable
-- 1.3.6.1.4.1.3967.1.4.2.1.1               input_pin_stateEntry
-- 1.3.6.1.4.1.3967.1.4.2.1.1.1                input_pin_state
-- 1.3.6.1.4.1.3967.1.5            network
-- 1.3.6.1.4.1.3967.1.5.1             interface
-- 1.3.6.1.4.1.3967.1.5.1.1              mac_address
-- 1.3.6.1.4.1.3967.1.5.1.2              ip_str
-- 1.3.6.1.4.1.3967.1.5.1.3              subnet_str
-- 1.3.6.1.4.1.3967.1.5.1.4              gateway_ip_str
-- 1.3.6.1.4.1.3967.1.5.1.5              dhcp_val
-- 1.3.6.1.4.1.3967.1.5.1.6              eth_link
-- 1.3.6.1.4.1.3967.1.5.1.7              enable_traffic_led
-- 1.3.6.1.4.1.3967.1.5.2             snmp_Table
-- 1.3.6.1.4.1.3967.1.5.2.1              snmp_Entry
-- 1.3.6.1.4.1.3967.1.5.2.1.1               snmp_traps_host_str
-- 1.3.6.1.4.1.3967.1.6            storage
-- 1.3.6.1.4.1.3967.1.6.1             recording
-- 1.3.6.1.4.1.3967.1.6.1.1              hd_size_mb
-- 1.3.6.1.4.1.3967.1.6.1.2              hd_recording_active
-- 1.3.6.1.4.1.3967.1.6.1.3              partTable
-- 1.3.6.1.4.1.3967.1.6.1.3.1               partEntry
-- 1.3.6.1.4.1.3967.1.6.1.3.1.1                hd_partition_recording
-- 1.3.6.1.4.1.3967.1.6.1.3.1.2                hd_mgr_start
-- 1.3.6.1.4.1.3967.1.6.2             replay
-- 1.3.6.1.4.1.3967.1.6.2.1              hd_replay_seek_time
-- 1.3.6.1.4.1.3967.1.6.3             span
-- 1.3.6.1.4.1.3967.1.6.3.1              record_mode_spans
-- 1.3.6.1.4.1.3967.1.6.3.2              span_use_status
-- 1.3.6.1.4.1.3967.1.6.4             storage_report
-- 

VCS_RCP-MIB DEFINITIONS ::= BEGIN

IMPORTS
   enterprises, Counter, TimeTicks, Gauge   FROM RFC1155-SMI
   sysUpTime, DisplayString                 FROM RFC1213-MIB
   OBJECT-TYPE                              FROM RFC-1212
   TRAP-TYPE                                FROM RFC-1215;

vcs_ag OBJECT IDENTIFIER ::= { enterprises 3967 }

--
-- Divisions of VCS
--

rcp OBJECT IDENTIFIER ::= { vcs_ag 1 }



sys OBJECT IDENTIFIER ::= { rcp 1 }



identification OBJECT IDENTIFIER ::= { sys 1 }

unit_name OBJECT-TYPE
SYNTAX DisplayString
ACCESS read-write
STATUS optional
DESCRIPTION 
"WRITE: set unit name
 READ: read the unit name
 "
::= {identification 1}

unit_id OBJECT-TYPE
SYNTAX DisplayString
ACCESS read-write
STATUS optional
DESCRIPTION 
"WRITE: set unit ID
 READ: read the unit ID
 "
::= {identification 2}


camnameTable OBJECT-TYPE
SYNTAX  SEQUENCE OF CamnameEntry
ACCESS  not-accessible
STATUS  mandatory
DESCRIPTION ""
::= { identification 3 }

camnameEntry OBJECT-TYPE
SYNTAX  CamnameEntry
ACCESS  not-accessible
STATUS  mandatory
DESCRIPTION ""
INDEX   { camname }
::= { camnameTable 1 }

camname OBJECT-TYPE
SYNTAX DisplayString
ACCESS read-write
STATUS optional
DESCRIPTION 
"WRITE: set the camera name
 READ: read the camera name
 "
::= {camnameEntry 1}

CamnameEntry ::= SEQUENCE {
camname DisplayString
}

hardware_version OBJECT-TYPE
SYNTAX DisplayString
ACCESS read-only
STATUS optional
DESCRIPTION 
"READ: read the hardware version
 "
::= {identification 4}

software_version OBJECT-TYPE
SYNTAX DisplayString
ACCESS read-only
STATUS optional
DESCRIPTION 
"READ: read the software version
 "
::= {identification 5}



time OBJECT IDENTIFIER ::= { sys 2 }

timezone OBJECT-TYPE
SYNTAX INTEGER
ACCESS read-write
STATUS optional
DESCRIPTION 
"READ: the timezone in which the unit has to operate (GMT +- nbr of seconds +- nbr of seconds DLS), read only version 2.50
 "
::= {time 1}

ntp_server_ip_str OBJECT-TYPE
SYNTAX DisplayString
ACCESS read-write
STATUS optional
DESCRIPTION 
"WRITE: sets the server ip in xxx.xxx.xxx.xxx to sync time from, not supported while recording is running
 READ: reads the time servers ip address in xxx.xxx.xxx.xxx used to sync time from
 "
::= {time 2}



connection OBJECT IDENTIFIER ::= { sys 3 }

connect_to OBJECT-TYPE
SYNTAX OCTET STRING
ACCESS read-only
STATUS optional
DESCRIPTION 
"%"
::= {connection 1}

disconnect_primitive OBJECT-TYPE
SYNTAX OCTET STRING
ACCESS read-only
STATUS optional
DESCRIPTION 
"%"
::= {connection 2}



viproc OBJECT IDENTIFIER ::= { sys 4 }

viproc_id OBJECT-TYPE
SYNTAX INTEGER
ACCESS read-write
STATUS optional
DESCRIPTION 
"WRITE: not supported
 READ: get the viproc interface id (0:= no viproc)
 "
::= {viproc 1}

viproc_onoff OBJECT-TYPE
SYNTAX INTEGER
ACCESS read-write
STATUS optional
DESCRIPTION 
"WRITE: switches on/off the video content analysis (VCA). command is obsolete with firmware 4.0 and replaced by VIPROC_MODE.
 READ: reads the VCA status 0=off, 1=on. command is obsolete with firmware 4.0 and replaced by VIPROC_MODE.
 "
::= {viproc 2}



aux OBJECT IDENTIFIER ::= { sys 5 }

oem_device_name OBJECT-TYPE
SYNTAX DisplayString
ACCESS read-only
STATUS optional
DESCRIPTION 
"WRITE: not supported
 READ: get the oem device name
 "
::= {aux 1}

oem_ext_id OBJECT-TYPE
SYNTAX INTEGER
ACCESS read-only
STATUS optional
DESCRIPTION 
"WRITE: not supported
 READ: get the oem extension id
 "
::= {aux 2}

defaults OBJECT-TYPE
SYNTAX INTEGER
ACCESS write-only
STATUS optional
DESCRIPTION 
"WRITE: sets config to default values exept IP,mcIP,subnet and gateway, reset is necessary to apply all default settings
 READ: not supported
 "
::= {aux 3}

factory_defaults OBJECT-TYPE
SYNTAX INTEGER
ACCESS write-only
STATUS optional
DESCRIPTION 
"WRITE: set the configuration to factory defaults and reset the board
 READ: not supported
 "
::= {aux 4}

board_reset OBJECT-TYPE
SYNTAX INTEGER
ACCESS write-only
STATUS optional
DESCRIPTION 
"WRITE: reset the board
 READ: not supported
 "
::= {aux 5}

boot_default_app OBJECT-TYPE
SYNTAX INTEGER
ACCESS write-only
STATUS optional
DESCRIPTION 
"WRITE: boot the default application
 READ: not supported
 "
::= {aux 6}

led_blinking OBJECT-TYPE
SYNTAX INTEGER
ACCESS read-write
STATUS optional
DESCRIPTION 
"WRITE: 1=power LED will flash for 7 sec
 READ: always 1
 "
::= {aux 7}

sanity_check OBJECT-TYPE
SYNTAX OCTET STRING
ACCESS read-write
STATUS optional
DESCRIPTION 
"WRITE: set the array of sanity bits (bit0:hdd)
 READ: read the array of sanity bits (bit0: hdd, bit1: device error host, bit2: device error coproc)
 "
::= {aux 8}


bsp_dev_errorTable OBJECT-TYPE
SYNTAX  SEQUENCE OF Bsp_dev_errorEntry
ACCESS  not-accessible
STATUS  mandatory
DESCRIPTION ""
::= { aux 9 }

bsp_dev_errorEntry OBJECT-TYPE
SYNTAX  Bsp_dev_errorEntry
ACCESS  not-accessible
STATUS  mandatory
DESCRIPTION ""
INDEX   { bsp_dev_error }
::= { bsp_dev_errorTable 1 }

bsp_dev_error OBJECT-TYPE
SYNTAX INTEGER
ACCESS read-only
STATUS optional
DESCRIPTION 
"WRITE: number of bsp devices that encountered an error
 READ: number of bsp devices that encountered an error
 "
::= {bsp_dev_errorEntry 1}

Bsp_dev_errorEntry ::= SEQUENCE {
bsp_dev_error INTEGER
}

livetime_max_temp OBJECT-TYPE
SYNTAX INTEGER
ACCESS read-write
STATUS optional
DESCRIPTION 
"WRITE: write the highest temerature during device livetime device internal only
 READ: read the highest temerature during device livetime
 "
::= {aux 10}

livetime_min_temp OBJECT-TYPE
SYNTAX INTEGER
ACCESS read-write
STATUS optional
DESCRIPTION 
"WRITE: write the lowest temerature during device livetime device internal only
 READ: read the lowest temerature during device livetime
 "
::= {aux 11}

livetime_op_minutes OBJECT-TYPE
SYNTAX INTEGER
ACCESS read-write
STATUS optional
DESCRIPTION 
"WRITE: write the operation hours counter (total device livetime) device internal only
 READ: read the operation hours counter (total device livetime)
 "
::= {aux 12}

power_supply OBJECT-TYPE
SYNTAX INTEGER
ACCESS read-only
STATUS optional
DESCRIPTION 
"WRITE: bit field of power supplies (supply n: supplybits = 1<<(n-1))
 READ: bit field of power supplies (supply n: supplybits = 1<<(n-1))
 "
::= {sys 6}


temperatureTable OBJECT-TYPE
SYNTAX  SEQUENCE OF TemperatureEntry
ACCESS  not-accessible
STATUS  mandatory
DESCRIPTION ""
::= { sys 7 }

temperatureEntry OBJECT-TYPE
SYNTAX  TemperatureEntry
ACCESS  not-accessible
STATUS  mandatory
DESCRIPTION ""
INDEX   { temp_sens }
::= { temperatureTable 1 }

temp_sens OBJECT-TYPE
SYNTAX INTEGER
ACCESS read-only
STATUS optional
DESCRIPTION 
"WRITE: not supported
 READ: value of the temperature sensor specified by numdes
 "
::= {temperatureEntry 1}

TemperatureEntry ::= SEQUENCE {
temp_sens INTEGER
}


fan_speedTable OBJECT-TYPE
SYNTAX  SEQUENCE OF Fan_speedEntry
ACCESS  not-accessible
STATUS  mandatory
DESCRIPTION ""
::= { sys 8 }

fan_speedEntry OBJECT-TYPE
SYNTAX  Fan_speedEntry
ACCESS  not-accessible
STATUS  mandatory
DESCRIPTION ""
INDEX   { fan_speed }
::= { fan_speedTable 1 }

fan_speed OBJECT-TYPE
SYNTAX INTEGER
ACCESS read-only
STATUS optional
DESCRIPTION 
"WRITE: not supported
 READ: fan speed in RPM
 "
::= {fan_speedEntry 1}

Fan_speedEntry ::= SEQUENCE {
fan_speed INTEGER
}


cpu_loadTable OBJECT-TYPE
SYNTAX  SEQUENCE OF Cpu_loadEntry
ACCESS  not-accessible
STATUS  mandatory
DESCRIPTION ""
::= { sys 9 }

cpu_loadEntry OBJECT-TYPE
SYNTAX  Cpu_loadEntry
ACCESS  not-accessible
STATUS  mandatory
DESCRIPTION ""
INDEX   { cpu_load_idle }
::= { cpu_loadTable 1 }

cpu_load_idle OBJECT-TYPE
SYNTAX INTEGER
ACCESS read-only
STATUS optional
DESCRIPTION 
"WRITE: not supported
 READ: cpu load idle in percent
 "
::= {cpu_loadEntry 1}

cpu_load_coder OBJECT-TYPE
SYNTAX INTEGER
ACCESS read-only
STATUS optional
DESCRIPTION 
"WRITE: not supported
 READ: cpu load coder in percent
 "
::= {cpu_loadEntry 2}

cpu_load_vca OBJECT-TYPE
SYNTAX INTEGER
ACCESS read-only
STATUS optional
DESCRIPTION 
"WRITE: not supported
 READ: cpu load vca in percent
 "
::= {cpu_loadEntry 3}

cpu_load OBJECT-TYPE
SYNTAX OCTET STRING
ACCESS read-only
STATUS optional
DESCRIPTION 
"WRITE: not supported
 READ: cpu load vca in percent (byte 0=idle, byte 1 = coder, byte 2=vca)
 "
::= {cpu_loadEntry 4}

Cpu_loadEntry ::= SEQUENCE {
cpu_load_idle INTEGER,
cpu_load_coder INTEGER,
cpu_load_vca INTEGER,
cpu_load OCTET STRING
}



video OBJECT IDENTIFIER ::= { rcp 2 }


inputTable OBJECT-TYPE
SYNTAX  SEQUENCE OF InputEntry
ACCESS  not-accessible
STATUS  mandatory
DESCRIPTION ""
::= { video 1 }

inputEntry OBJECT-TYPE
SYNTAX  InputEntry
ACCESS  not-accessible
STATUS  mandatory
DESCRIPTION ""
INDEX   { input_source_val }
::= { inputTable 1 }

input_source_val OBJECT-TYPE
SYNTAX INTEGER
ACCESS read-write
STATUS optional
DESCRIPTION 
"WRITE: =1: camera; =2: vcr; =3: color_plane
 READ: =1: camera; =2: vcr
 "
::= {inputEntry 1}

InputEntry ::= SEQUENCE {
input_source_val INTEGER
}


encoderTable OBJECT-TYPE
SYNTAX  SEQUENCE OF EncoderEntry
ACCESS  not-accessible
STATUS  mandatory
DESCRIPTION ""
::= { video 2 }

encoderEntry OBJECT-TYPE
SYNTAX  EncoderEntry
ACCESS  not-accessible
STATUS  mandatory
DESCRIPTION ""
INDEX   { video_encoder_status }
::= { encoderTable 1 }

video_encoder_status OBJECT-TYPE
SYNTAX OCTET STRING
ACCESS read-only
STATUS optional
DESCRIPTION 
"WRITE: not supported
 READ: get encoder status (8bytes) 4 (high order) bytes 10*frames per sec, 4 (low order) bytes KBPS
 "
::= {encoderEntry 1}

EncoderEntry ::= SEQUENCE {
video_encoder_status OCTET STRING
}



alarm OBJECT IDENTIFIER ::= { rcp 3 }


video_alarmTable OBJECT-TYPE
SYNTAX  SEQUENCE OF Video_alarmEntry
ACCESS  not-accessible
STATUS  mandatory
DESCRIPTION ""
::= { alarm 1 }

video_alarmEntry OBJECT-TYPE
SYNTAX  Video_alarmEntry
ACCESS  not-accessible
STATUS  mandatory
DESCRIPTION ""
INDEX   { video_alarm_state }
::= { video_alarmTable 1 }

video_alarm_state OBJECT-TYPE
SYNTAX INTEGER
ACCESS read-only
STATUS optional
DESCRIPTION 
"READ: 0=video alarm is off; 1=video alarm is on
 "
::= {video_alarmEntry 1}

Video_alarmEntry ::= SEQUENCE {
video_alarm_state INTEGER
}


motion_detectorTable OBJECT-TYPE
SYNTAX  SEQUENCE OF Motion_detectorEntry
ACCESS  not-accessible
STATUS  mandatory
DESCRIPTION ""
::= { alarm 2 }

motion_detectorEntry OBJECT-TYPE
SYNTAX  Motion_detectorEntry
ACCESS  not-accessible
STATUS  mandatory
DESCRIPTION ""
INDEX   { motion_alarm_state }
::= { motion_detectorTable 1 }

motion_alarm_state OBJECT-TYPE
SYNTAX INTEGER
ACCESS read-only
STATUS optional
DESCRIPTION 
"READ: 0=motion alarm off; 1=motion alarm on (at elast one of the CONF_VIPROC_ALARM alarmbit (except the video loss alarm) is set
 "
::= {motion_detectorEntry 1}

Motion_detectorEntry ::= SEQUENCE {
motion_alarm_state INTEGER
}


viproc_alarmTable OBJECT-TYPE
SYNTAX  SEQUENCE OF Viproc_alarmEntry
ACCESS  not-accessible
STATUS  mandatory
DESCRIPTION ""
::= { alarm 3 }

viproc_alarmEntry OBJECT-TYPE
SYNTAX  Viproc_alarmEntry
ACCESS  not-accessible
STATUS  mandatory
DESCRIPTION ""
INDEX   { viproc_alarm }
::= { viproc_alarmTable 1 }

viproc_alarm OBJECT-TYPE
SYNTAX OCTET STRING
ACCESS read-only
STATUS optional
DESCRIPTION 
"WRITE: message only
 READ: see detailed description 
 "
::= {viproc_alarmEntry 1}

vca_task_running_state OBJECT-TYPE
SYNTAX INTEGER
ACCESS read-only
STATUS optional
DESCRIPTION 
"READ: returs the current processing state of the VCA engine; TRUE when vca engine is running with no problems; FALSE if vca engine lack cpu performance
 "
::= {viproc_alarmEntry 2}

Viproc_alarmEntry ::= SEQUENCE {
viproc_alarm OCTET STRING,
vca_task_running_state INTEGER
}



digital_io OBJECT IDENTIFIER ::= { rcp 4 }



out OBJECT IDENTIFIER ::= { digital_io 1 }


relaisTable OBJECT-TYPE
SYNTAX  SEQUENCE OF RelaisEntry
ACCESS  not-accessible
STATUS  mandatory
DESCRIPTION ""
::= { out 1 }

relaisEntry OBJECT-TYPE
SYNTAX  RelaisEntry
ACCESS  not-accessible
STATUS  mandatory
DESCRIPTION ""
INDEX   { relay_output_state }
::= { relaisTable 1 }

relay_output_state OBJECT-TYPE
SYNTAX INTEGER
ACCESS read-write
STATUS optional
DESCRIPTION 
"WRITE: set the logical level of an relay output
 READ: returns the current logical level of an relay output
 "
::= {relaisEntry 1}

RelaisEntry ::= SEQUENCE {
relay_output_state INTEGER
}



in OBJECT IDENTIFIER ::= { digital_io 2 }


input_pin_stateTable OBJECT-TYPE
SYNTAX  SEQUENCE OF Input_pin_stateEntry
ACCESS  not-accessible
STATUS  mandatory
DESCRIPTION ""
::= { in 1 }

input_pin_stateEntry OBJECT-TYPE
SYNTAX  Input_pin_stateEntry
ACCESS  not-accessible
STATUS  mandatory
DESCRIPTION ""
INDEX   { input_pin_state }
::= { input_pin_stateTable 1 }

input_pin_state OBJECT-TYPE
SYNTAX INTEGER
ACCESS read-only
STATUS optional
DESCRIPTION 
"READ: 0=alarm input off; 1= alarm input on
 "
::= {input_pin_stateEntry 1}

Input_pin_stateEntry ::= SEQUENCE {
input_pin_state INTEGER
}



network OBJECT IDENTIFIER ::= { rcp 5 }



interface OBJECT IDENTIFIER ::= { network 1 }

mac_address OBJECT-TYPE
SYNTAX OCTET STRING
ACCESS read-only
STATUS optional
DESCRIPTION 
"READ: read out the systems MAC address
 "
::= {interface 1}

ip_str OBJECT-TYPE
SYNTAX DisplayString
ACCESS read-write
STATUS optional
DESCRIPTION 
"WRITE: set unit's IP address using string notation (xxx.xxx.xxx.xxx)
 READ: read the unit's IP address using string notation (xxx.xxx.xxx.xxx)
 "
::= {interface 2}

subnet_str OBJECT-TYPE
SYNTAX DisplayString
ACCESS read-write
STATUS optional
DESCRIPTION 
"WRITE: set subnet mask using string notation (xxx.xxx.xxx.xxx)
 READ: read the subnet mask using string notation (xxx.xxx.xxx.xxx)
 "
::= {interface 3}

gateway_ip_str OBJECT-TYPE
SYNTAX DisplayString
ACCESS read-write
STATUS optional
DESCRIPTION 
"WRITE: set gateway IP using string notation (xxx.xxx.xxx.xxx)
 READ: read the gateway IP using string notation (xxx.xxx.xxx.xxx)
 "
::= {interface 4}

dhcp_val OBJECT-TYPE
SYNTAX INTEGER
ACCESS read-write
STATUS optional
DESCRIPTION 
"WRITE: set DHCP ip configuration value (0=OFF, 1=ON, 2=ON, but do not kick mechanism now)
 READ: read the DHCP state (0=OFF, 1=ON);
 "
::= {interface 5}

eth_link OBJECT-TYPE
SYNTAX INTEGER
ACCESS read-write
STATUS optional
DESCRIPTION 
"WRITE: (half duplex=HD, full duplex =FD) 0=auto, 1=10MbitHD, 2=10MbitFD, 3=100MbitHD, 4=100MbitFD, 5=1000FD
 READ: (half duplex=HD, full duplex =FD) 0=auto, 1=10MbitHD, 2=10MbitFD, 3=100MbitHD, 4=100MbitFD
 "
::= {interface 6}

enable_traffic_led OBJECT-TYPE
SYNTAX INTEGER
ACCESS read-write
STATUS optional
DESCRIPTION 
"WRITE: Enables or disables the network activity LED (Dinion, NBC-255 camera)
 READ: network activity LED (Dinion, NBC-255 camera): 0=off, 1=on
 "
::= {interface 7}


snmp_Table OBJECT-TYPE
SYNTAX  SEQUENCE OF Snmp_Entry
ACCESS  not-accessible
STATUS  mandatory
DESCRIPTION ""
::= { network 2 }

snmp_Entry OBJECT-TYPE
SYNTAX  Snmp_Entry
ACCESS  not-accessible
STATUS  mandatory
DESCRIPTION ""
INDEX   { snmp_traps_host_str }
::= { snmp_Table 1 }

snmp_traps_host_str OBJECT-TYPE
SYNTAX DisplayString
ACCESS read-write
STATUS optional
DESCRIPTION 
"WRITE: not documented
 READ: not documented
 "
::= {snmp_Entry 1}

Snmp_Entry ::= SEQUENCE {
snmp_traps_host_str DisplayString
}



storage OBJECT IDENTIFIER ::= { rcp 6 }



recording OBJECT IDENTIFIER ::= { storage 1 }

hd_size_mb OBJECT-TYPE
SYNTAX INTEGER
ACCESS read-only
STATUS optional
DESCRIPTION 
"WRITE: not writable
 READ: read the total size of a local storage in megabytes
 "
::= {recording 1}

hd_recording_active OBJECT-TYPE
SYNTAX INTEGER
ACCESS read-write
STATUS optional
DESCRIPTION 
"WRITE: not supported
 READ: 1: yes  0: no (message only, a request on this command always returns zero)
 "
::= {recording 2}


partTable OBJECT-TYPE
SYNTAX  SEQUENCE OF PartEntry
ACCESS  not-accessible
STATUS  mandatory
DESCRIPTION ""
::= { recording 3 }

partEntry OBJECT-TYPE
SYNTAX  PartEntry
ACCESS  not-accessible
STATUS  mandatory
DESCRIPTION ""
INDEX   { hd_partition_recording }
::= { partTable 1 }

hd_partition_recording OBJECT-TYPE
SYNTAX INTEGER
ACCESS read-write
STATUS optional
DESCRIPTION 
"WRITE: not supported
 READ: recording status of partition or cam if span recording for primary recording (1 = running, 0 = not running)
 "
::= {partEntry 1}

hd_mgr_start OBJECT-TYPE
SYNTAX INTEGER
ACCESS read-write
STATUS optional
DESCRIPTION 
"WRITE: start the recording manager. Can cause recording if time/alarm recording selected. If in span recording mode the set span recording to on.
 READ: return TRUE when manager is on or when primary span recording is on and device is in span recording mode
 "
::= {partEntry 2}

PartEntry ::= SEQUENCE {
hd_partition_recording INTEGER,
hd_mgr_start INTEGER
}



replay OBJECT IDENTIFIER ::= { storage 2 }

hd_replay_seek_time OBJECT-TYPE
SYNTAX OCTET STRING
ACCESS read-write
STATUS optional
DESCRIPTION 
"WRITE: see detailed description 
 READ: see detailed description
 "
::= {replay 1}



span OBJECT IDENTIFIER ::= { storage 3 }

record_mode_spans OBJECT-TYPE
SYNTAX INTEGER
ACCESS read-write
STATUS optional
DESCRIPTION 
"WRITE: Set span recording mode to on 0x01 or off 0x00 (obsolete, device is always in mode on)
 READ: returns 0x00 if span recording is off, 0x01 if on
 "
::= {span 1}

span_use_status OBJECT-TYPE
SYNTAX INTEGER
ACCESS read-only
STATUS optional
DESCRIPTION 
"WRITE: not supported
 READ: usage status of a span, see detailed description 
 "
::= {span 2}

storage_report OBJECT-TYPE
SYNTAX OCTET STRING
ACCESS read-write
STATUS optional
DESCRIPTION 
"READ: get information about the storage device 
 "
::= {storage 4}



END
