-- file automatically created


TELDAT-TRAP-EOAM-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


eoamTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the EOAM event subsystem."
    REVISION "201401200930Z"
    DESCRIPTION "Initial implementation"
        ::= { telEventTraps 214 }


eoamEventsGroup	OBJECT IDENTIFIER	::= { eoamTrapsMIB 1 }

eoamNotifications	OBJECT IDENTIFIER	::= { eoamTrapsMIB 2 }
eoamNotificationsPrefix	OBJECT IDENTIFIER	::= { eoamNotifications 0 }

eoamEventObjects1 OBJECT-IDENTITY
    STATUS current
    DESCRIPTION
        "Event EOAM.1
        FSM event"
    ::= { eoamEventsGroup 1 }

eoam1_interface OBJECT-TYPE
    SYNTAX DisplayString
    MAX-ACCESS accessible-for-notify
    STATUS current
    DESCRIPTION
        "Parameter 'interface' in event EOAM.1"
    ::= { eoamEventObjects1 1 }

eoam1_fsm OBJECT-TYPE
    SYNTAX DisplayString
    MAX-ACCESS accessible-for-notify
    STATUS current
    DESCRIPTION
        "Parameter 'fsm' in event EOAM.1"
    ::= { eoamEventObjects1 2 }

eoam1_event OBJECT-TYPE
    SYNTAX DisplayString
    MAX-ACCESS accessible-for-notify
    STATUS current
    DESCRIPTION
        "Parameter 'event' in event EOAM.1"
    ::= { eoamEventObjects1 3 }

eoamEventObjects2 OBJECT-IDENTITY
    STATUS current
    DESCRIPTION
        "Event EOAM.2
        Next FSM state"
    ::= { eoamEventsGroup 2 }

eoam2_interface OBJECT-TYPE
    SYNTAX DisplayString
    MAX-ACCESS accessible-for-notify
    STATUS current
    DESCRIPTION
        "Parameter 'interface' in event EOAM.2"
    ::= { eoamEventObjects2 1 }

eoam2_fsm OBJECT-TYPE
    SYNTAX DisplayString
    MAX-ACCESS accessible-for-notify
    STATUS current
    DESCRIPTION
        "Parameter 'fsm' in event EOAM.2"
    ::= { eoamEventObjects2 2 }

eoam2_state OBJECT-TYPE
    SYNTAX DisplayString
    MAX-ACCESS accessible-for-notify
    STATUS current
    DESCRIPTION
        "Parameter 'state' in event EOAM.2"
    ::= { eoamEventObjects2 3 }

eoamEventObjects3 OBJECT-IDENTITY
    STATUS current
    DESCRIPTION
        "Event EOAM.3
        FSM incongruous event"
    ::= { eoamEventsGroup 3 }

eoam3_interface OBJECT-TYPE
    SYNTAX DisplayString
    MAX-ACCESS accessible-for-notify
    STATUS current
    DESCRIPTION
        "Parameter 'interface' in event EOAM.3"
    ::= { eoamEventObjects3 1 }

eoam3_fsm OBJECT-TYPE
    SYNTAX DisplayString
    MAX-ACCESS accessible-for-notify
    STATUS current
    DESCRIPTION
        "Parameter 'fsm' in event EOAM.3"
    ::= { eoamEventObjects3 2 }

eoam3_event OBJECT-TYPE
    SYNTAX DisplayString
    MAX-ACCESS accessible-for-notify
    STATUS current
    DESCRIPTION
        "Parameter 'event' in event EOAM.3"
    ::= { eoamEventObjects3 3 }

eoamEventObjects4 OBJECT-IDENTITY
    STATUS current
    DESCRIPTION
        "Event EOAM.4
        Wrong FSM event"
    ::= { eoamEventsGroup 4 }

eoam4_interface OBJECT-TYPE
    SYNTAX DisplayString
    MAX-ACCESS accessible-for-notify
    STATUS current
    DESCRIPTION
        "Parameter 'interface' in event EOAM.4"
    ::= { eoamEventObjects4 1 }

eoam4_fsm OBJECT-TYPE
    SYNTAX DisplayString
    MAX-ACCESS accessible-for-notify
    STATUS current
    DESCRIPTION
        "Parameter 'fsm' in event EOAM.4"
    ::= { eoamEventObjects4 2 }

eoamEventObjects5 OBJECT-IDENTITY
    STATUS current
    DESCRIPTION
        "Event EOAM.5
        Wrong FSM state"
    ::= { eoamEventsGroup 5 }

eoam5_interface OBJECT-TYPE
    SYNTAX DisplayString
    MAX-ACCESS accessible-for-notify
    STATUS current
    DESCRIPTION
        "Parameter 'interface' in event EOAM.5"
    ::= { eoamEventObjects5 1 }

eoam5_fsm OBJECT-TYPE
    SYNTAX DisplayString
    MAX-ACCESS accessible-for-notify
    STATUS current
    DESCRIPTION
        "Parameter 'fsm' in event EOAM.5"
    ::= { eoamEventObjects5 2 }

eoamEventObjects6 OBJECT-IDENTITY
    STATUS current
    DESCRIPTION
        "Event EOAM.6
        Discarding packet from FSM"
    ::= { eoamEventsGroup 6 }

eoam6_interface OBJECT-TYPE
    SYNTAX DisplayString
    MAX-ACCESS accessible-for-notify
    STATUS current
    DESCRIPTION
        "Parameter 'interface' in event EOAM.6"
    ::= { eoamEventObjects6 1 }

eoam6_FSM OBJECT-TYPE
    SYNTAX DisplayString
    MAX-ACCESS accessible-for-notify
    STATUS current
    DESCRIPTION
        "Parameter 'FSM' in event EOAM.6"
    ::= { eoamEventObjects6 2 }

eoamEventObjects7 OBJECT-IDENTITY
    STATUS current
    DESCRIPTION
        "Event EOAM.7
        General Ethernet OAM information event"
    ::= { eoamEventsGroup 7 }

eoam7_interface OBJECT-TYPE
    SYNTAX DisplayString
    MAX-ACCESS accessible-for-notify
    STATUS current
    DESCRIPTION
        "Parameter 'interface' in event EOAM.7"
    ::= { eoamEventObjects7 1 }

eoam7_message OBJECT-TYPE
    SYNTAX DisplayString
    MAX-ACCESS accessible-for-notify
    STATUS current
    DESCRIPTION
        "Parameter 'message' in event EOAM.7"
    ::= { eoamEventObjects7 2 }

eoamEventObjects8 OBJECT-IDENTITY
    STATUS current
    DESCRIPTION
        "Event EOAM.8
        General Ethernet OAM internal error event"
    ::= { eoamEventsGroup 8 }

eoam8_interface OBJECT-TYPE
    SYNTAX DisplayString
    MAX-ACCESS accessible-for-notify
    STATUS current
    DESCRIPTION
        "Parameter 'interface' in event EOAM.8"
    ::= { eoamEventObjects8 1 }

eoam8_message OBJECT-TYPE
    SYNTAX DisplayString
    MAX-ACCESS accessible-for-notify
    STATUS current
    DESCRIPTION
        "Parameter 'message' in event EOAM.8"
    ::= { eoamEventObjects8 2 }

eoamEventObjects9 OBJECT-IDENTITY
    STATUS current
    DESCRIPTION
        "Event EOAM.9
        General Ethernet OAM external error event"
    ::= { eoamEventsGroup 9 }

eoam9_interface OBJECT-TYPE
    SYNTAX DisplayString
    MAX-ACCESS accessible-for-notify
    STATUS current
    DESCRIPTION
        "Parameter 'interface' in event EOAM.9"
    ::= { eoamEventObjects9 1 }

eoam9_message OBJECT-TYPE
    SYNTAX DisplayString
    MAX-ACCESS accessible-for-notify
    STATUS current
    DESCRIPTION
        "Parameter 'message' in event EOAM.9"
    ::= { eoamEventObjects9 2 }

eoamEventObjects10 OBJECT-IDENTITY
    STATUS current
    DESCRIPTION
        "Event EOAM.10
        OAMPDU received"
    ::= { eoamEventsGroup 10 }

eoam10_interface OBJECT-TYPE
    SYNTAX DisplayString
    MAX-ACCESS accessible-for-notify
    STATUS current
    DESCRIPTION
        "Parameter 'interface' in event EOAM.10"
    ::= { eoamEventObjects10 1 }

eoam10_message OBJECT-TYPE
    SYNTAX DisplayString
    MAX-ACCESS accessible-for-notify
    STATUS current
    DESCRIPTION
        "Parameter 'message' in event EOAM.10"
    ::= { eoamEventObjects10 2 }

eoamEventObjects11 OBJECT-IDENTITY
    STATUS current
    DESCRIPTION
        "Event EOAM.11
        General Ethernet OAM information event"
    ::= { eoamEventsGroup 11 }

eoam11_interface OBJECT-TYPE
    SYNTAX DisplayString
    MAX-ACCESS accessible-for-notify
    STATUS current
    DESCRIPTION
        "Parameter 'interface' in event EOAM.11"
    ::= { eoamEventObjects11 1 }

eoam11_message OBJECT-TYPE
    SYNTAX DisplayString
    MAX-ACCESS accessible-for-notify
    STATUS current
    DESCRIPTION
        "Parameter 'message' in event EOAM.11"
    ::= { eoamEventObjects11 2 }

eoamEventObjects12 OBJECT-IDENTITY
    STATUS current
    DESCRIPTION
        "Event EOAM.12
        An Ethernet OAM timer has expired"
    ::= { eoamEventsGroup 12 }

eoam12_interface OBJECT-TYPE
    SYNTAX DisplayString
    MAX-ACCESS accessible-for-notify
    STATUS current
    DESCRIPTION
        "Parameter 'interface' in event EOAM.12"
    ::= { eoamEventObjects12 1 }

eoam12_timer OBJECT-TYPE
    SYNTAX DisplayString
    MAX-ACCESS accessible-for-notify
    STATUS current
    DESCRIPTION
        "Parameter 'timer' in event EOAM.12"
    ::= { eoamEventObjects12 2 }

eoamEventObjects13 OBJECT-IDENTITY
    STATUS current
    DESCRIPTION
        "Event EOAM.13
        Transmitting OAMPDU"
    ::= { eoamEventsGroup 13 }

eoam13_interface OBJECT-TYPE
    SYNTAX DisplayString
    MAX-ACCESS accessible-for-notify
    STATUS current
    DESCRIPTION
        "Parameter 'interface' in event EOAM.13"
    ::= { eoamEventObjects13 1 }

eoam13_message OBJECT-TYPE
    SYNTAX DisplayString
    MAX-ACCESS accessible-for-notify
    STATUS current
    DESCRIPTION
        "Parameter 'message' in event EOAM.13"
    ::= { eoamEventObjects13 2 }


eoamNotification1 NOTIFICATION-TYPE
    OBJECTS { 
              eoam1_interface, 
              eoam1_fsm,
              eoam1_event 
            }
    STATUS current
    DESCRIPTION
        "Notification of Event EOAM.1

        Message: '$1 FSM $2 event $3'

        Parameters list:
              $1: eoam1_interface
              $2: eoam1_fsm
              $3: eoam1_event

        FSM event"
    ::= { eoamNotificationsPrefix 1 }

eoamNotification2 NOTIFICATION-TYPE
    OBJECTS { 
              eoam2_interface, 
              eoam2_fsm,
              eoam2_state 
            }
    STATUS current
    DESCRIPTION
        "Notification of Event EOAM.2

        Message: '$1 Next $2 state is $3'

        Parameters list:
              $1: eoam2_interface
              $2: eoam2_fsm
              $3: eoam2_state

        Next FSM state"
    ::= { eoamNotificationsPrefix 2 }

eoamNotification3 NOTIFICATION-TYPE
    OBJECTS { 
              eoam3_interface, 
              eoam3_fsm,
              eoam3_event 
            }
    STATUS current
    DESCRIPTION
        "Notification of Event EOAM.3

        Message: '$1 FSM $2 incongruous event $3'

        Parameters list:
              $1: eoam3_interface
              $2: eoam3_fsm
              $3: eoam3_event

        FSM incongruous event"
    ::= { eoamNotificationsPrefix 3 }

eoamNotification4 NOTIFICATION-TYPE
    OBJECTS { 
              eoam4_interface, 
              eoam4_fsm 
            }
    STATUS current
    DESCRIPTION
        "Notification of Event EOAM.4

        Message: '$1 Wrong FSM $2 event'

        Parameters list:
              $1: eoam4_interface
              $2: eoam4_fsm

        Wrong FSM event"
    ::= { eoamNotificationsPrefix 4 }

eoamNotification5 NOTIFICATION-TYPE
    OBJECTS { 
              eoam5_interface, 
              eoam5_fsm 
            }
    STATUS current
    DESCRIPTION
        "Notification of Event EOAM.5

        Message: '$1 Wrong FSM $2 state'

        Parameters list:
              $1: eoam5_interface
              $2: eoam5_fsm

        Wrong FSM state"
    ::= { eoamNotificationsPrefix 5 }

eoamNotification6 NOTIFICATION-TYPE
    OBJECTS { 
              eoam6_interface, 
              eoam6_FSM 
            }
    STATUS current
    DESCRIPTION
        "Notification of Event EOAM.6

        Message: '$1 Discarding packet from $2'

        Parameters list:
              $1: eoam6_interface
              $2: eoam6_FSM

        Discarding packet from FSM"
    ::= { eoamNotificationsPrefix 6 }

eoamNotification7 NOTIFICATION-TYPE
    OBJECTS { 
              eoam7_interface, 
              eoam7_message 
            }
    STATUS current
    DESCRIPTION
        "Notification of Event EOAM.7

        Message: '$1 $2'

        Parameters list:
              $1: eoam7_interface
              $2: eoam7_message

        General Ethernet OAM information event"
    ::= { eoamNotificationsPrefix 7 }

eoamNotification8 NOTIFICATION-TYPE
    OBJECTS { 
              eoam8_interface, 
              eoam8_message 
            }
    STATUS current
    DESCRIPTION
        "Notification of Event EOAM.8

        Message: '$1 $2'

        Parameters list:
              $1: eoam8_interface
              $2: eoam8_message

        General Ethernet OAM internal error event"
    ::= { eoamNotificationsPrefix 8 }

eoamNotification9 NOTIFICATION-TYPE
    OBJECTS { 
              eoam9_interface, 
              eoam9_message 
            }
    STATUS current
    DESCRIPTION
        "Notification of Event EOAM.9

        Message: '$1 $2'

        Parameters list:
              $1: eoam9_interface
              $2: eoam9_message

        General Ethernet OAM external error event"
    ::= { eoamNotificationsPrefix 9 }

eoamNotification10 NOTIFICATION-TYPE
    OBJECTS { 
              eoam10_interface, 
              eoam10_message 
            }
    STATUS current
    DESCRIPTION
        "Notification of Event EOAM.10

        Message: '$1 $2 OAMPDU received'

        Parameters list:
              $1: eoam10_interface
              $2: eoam10_message

        OAMPDU received"
    ::= { eoamNotificationsPrefix 10 }

eoamNotification11 NOTIFICATION-TYPE
    OBJECTS { 
              eoam11_interface, 
              eoam11_message 
            }
    STATUS current
    DESCRIPTION
        "Notification of Event EOAM.11

        Message: '$1 $2'

        Parameters list:
              $1: eoam11_interface
              $2: eoam11_message

        General Ethernet OAM information event"
    ::= { eoamNotificationsPrefix 11 }

eoamNotification12 NOTIFICATION-TYPE
    OBJECTS { 
              eoam12_interface, 
              eoam12_timer 
            }
    STATUS current
    DESCRIPTION
        "Notification of Event EOAM.12

        Message: '$1 Timer $2 expired'

        Parameters list:
              $1: eoam12_interface
              $2: eoam12_timer

        An Ethernet OAM timer has expired"
    ::= { eoamNotificationsPrefix 12 }

eoamNotification13 NOTIFICATION-TYPE
    OBJECTS { 
              eoam13_interface, 
              eoam13_message 
            }
    STATUS current
    DESCRIPTION
        "Notification of Event EOAM.13

        Message: '$1 Transmitting $2 OAMPDU'

        Parameters list:
              $1: eoam13_interface
              $2: eoam13_message

        Transmitting OAMPDU"
    ::= { eoamNotificationsPrefix 13 }


END
