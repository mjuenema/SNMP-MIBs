-- file automatically created


TELDAT-TRAP-EAP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


eapTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the EAP event subsystem."
    REVISION "201401200930Z"
    DESCRIPTION "Initial implementation"
        ::= { telEventTraps 191 }


eapEventsGroup	OBJECT IDENTIFIER	::= { eapTrapsMIB 1 }

eapNotifications	OBJECT IDENTIFIER	::= { eapTrapsMIB 2 }
eapNotificationsPrefix	OBJECT IDENTIFIER	::= { eapNotifications 0 }

eapEventObjects1 OBJECT-IDENTITY
    STATUS current
    DESCRIPTION
        "Event EAP.1
        An EAP packet of the type indicated has just arrived for processing."
    ::= { eapEventsGroup 1 }

eap1_code_string OBJECT-TYPE
    SYNTAX DisplayString
    MAX-ACCESS accessible-for-notify
    STATUS current
    DESCRIPTION
        "Parameter 'code_string' in event EAP.1"
    ::= { eapEventObjects1 1 }

eap1_type_string OBJECT-TYPE
    SYNTAX DisplayString
    MAX-ACCESS accessible-for-notify
    STATUS current
    DESCRIPTION
        "Parameter 'type_string' in event EAP.1"
    ::= { eapEventObjects1 2 }

eap1_identificer OBJECT-TYPE
    SYNTAX Integer32
    MAX-ACCESS accessible-for-notify
    STATUS current
    DESCRIPTION
        "Parameter 'identificer' in event EAP.1"
    ::= { eapEventObjects1 3 }

eap1_length OBJECT-TYPE
    SYNTAX Integer32
    MAX-ACCESS accessible-for-notify
    STATUS current
    DESCRIPTION
        "Parameter 'length' in event EAP.1"
    ::= { eapEventObjects1 4 }

eap1_eap_ctrl OBJECT-TYPE
    SYNTAX Integer32
    MAX-ACCESS accessible-for-notify
    STATUS current
    DESCRIPTION
        "Parameter 'eap_ctrl' in event EAP.1"
    ::= { eapEventObjects1 5 }

eapEventObjects2 OBJECT-IDENTITY
    STATUS current
    DESCRIPTION
        "Event EAP.2
        An EAP packet of the type indicated has been transmitted."
    ::= { eapEventsGroup 2 }

eap2_code_string OBJECT-TYPE
    SYNTAX DisplayString
    MAX-ACCESS accessible-for-notify
    STATUS current
    DESCRIPTION
        "Parameter 'code_string' in event EAP.2"
    ::= { eapEventObjects2 1 }

eap2_type_string OBJECT-TYPE
    SYNTAX DisplayString
    MAX-ACCESS accessible-for-notify
    STATUS current
    DESCRIPTION
        "Parameter 'type_string' in event EAP.2"
    ::= { eapEventObjects2 2 }

eap2_identificer OBJECT-TYPE
    SYNTAX Integer32
    MAX-ACCESS accessible-for-notify
    STATUS current
    DESCRIPTION
        "Parameter 'identificer' in event EAP.2"
    ::= { eapEventObjects2 3 }

eap2_length OBJECT-TYPE
    SYNTAX Integer32
    MAX-ACCESS accessible-for-notify
    STATUS current
    DESCRIPTION
        "Parameter 'length' in event EAP.2"
    ::= { eapEventObjects2 4 }

eap2_eap_ctrl OBJECT-TYPE
    SYNTAX Integer32
    MAX-ACCESS accessible-for-notify
    STATUS current
    DESCRIPTION
        "Parameter 'eap_ctrl' in event EAP.2"
    ::= { eapEventObjects2 5 }

eapEventObjects3 OBJECT-IDENTITY
    STATUS current
    DESCRIPTION
        "Event EAP.3
        An EAP request was sent and no response was received. The packet is
        retransmitted."
    ::= { eapEventsGroup 3 }

eap3_retry_count OBJECT-TYPE
    SYNTAX Integer32
    MAX-ACCESS accessible-for-notify
    STATUS current
    DESCRIPTION
        "Parameter 'retry_count' in event EAP.3"
    ::= { eapEventObjects3 1 }

eap3_eap_ctrl OBJECT-TYPE
    SYNTAX Integer32
    MAX-ACCESS accessible-for-notify
    STATUS current
    DESCRIPTION
        "Parameter 'eap_ctrl' in event EAP.3"
    ::= { eapEventObjects3 2 }

eapEventObjects4 OBJECT-IDENTITY
    STATUS current
    DESCRIPTION
        "Event EAP.4
        An EAP request has been sent with no response for the maximum configured
        retries. The EAP session is closed."
    ::= { eapEventsGroup 4 }

eap4_eap_ctrl OBJECT-TYPE
    SYNTAX Integer32
    MAX-ACCESS accessible-for-notify
    STATUS current
    DESCRIPTION
        "Parameter 'eap_ctrl' in event EAP.4"
    ::= { eapEventObjects4 1 }

eapEventObjects5 OBJECT-IDENTITY
    STATUS current
    DESCRIPTION
        "Event EAP.5
        The received EAP identity can not be processed because it is longer
        than the available buffer."
    ::= { eapEventsGroup 5 }

eap5_Identity_len OBJECT-TYPE
    SYNTAX Integer32
    MAX-ACCESS accessible-for-notify
    STATUS current
    DESCRIPTION
        "Parameter 'Identity_len' in event EAP.5"
    ::= { eapEventObjects5 1 }

eap5_Available_len OBJECT-TYPE
    SYNTAX Integer32
    MAX-ACCESS accessible-for-notify
    STATUS current
    DESCRIPTION
        "Parameter 'Available_len' in event EAP.5"
    ::= { eapEventObjects5 2 }

eap5_eap_ctrl OBJECT-TYPE
    SYNTAX Integer32
    MAX-ACCESS accessible-for-notify
    STATUS current
    DESCRIPTION
        "Parameter 'eap_ctrl' in event EAP.5"
    ::= { eapEventObjects5 3 }

eapEventObjects6 OBJECT-IDENTITY
    STATUS current
    DESCRIPTION
        "Event EAP.6
        EAP control block created."
    ::= { eapEventsGroup 6 }

eap6_eap_ctrl OBJECT-TYPE
    SYNTAX Integer32
    MAX-ACCESS accessible-for-notify
    STATUS current
    DESCRIPTION
        "Parameter 'eap_ctrl' in event EAP.6"
    ::= { eapEventObjects6 1 }

eapEventObjects7 OBJECT-IDENTITY
    STATUS current
    DESCRIPTION
        "Event EAP.7
        EAP control block destroyed."
    ::= { eapEventsGroup 7 }

eap7_eap_ctrl OBJECT-TYPE
    SYNTAX Integer32
    MAX-ACCESS accessible-for-notify
    STATUS current
    DESCRIPTION
        "Parameter 'eap_ctrl' in event EAP.7"
    ::= { eapEventObjects7 1 }

eapEventObjects8 OBJECT-IDENTITY
    STATUS current
    DESCRIPTION
        "Event EAP.8
        The received EAP packet was discarded because an error ocurred while
        processing it."
    ::= { eapEventsGroup 8 }

eap8_error_string OBJECT-TYPE
    SYNTAX DisplayString
    MAX-ACCESS accessible-for-notify
    STATUS current
    DESCRIPTION
        "Parameter 'error_string' in event EAP.8"
    ::= { eapEventObjects8 1 }

eap8_eap_ctrl OBJECT-TYPE
    SYNTAX Integer32
    MAX-ACCESS accessible-for-notify
    STATUS current
    DESCRIPTION
        "Parameter 'eap_ctrl' in event EAP.8"
    ::= { eapEventObjects8 2 }


eapNotification1 NOTIFICATION-TYPE
    OBJECTS { 
              eap1_code_string, 
              eap1_type_string,
              eap1_identificer,
              eap1_length,
              eap1_eap_ctrl 
            }
    STATUS current
    DESCRIPTION
        "Notification of Event EAP.1

        Message: 'Received EAP $1/$2 Packet, identifier $3, length $4, eap_ctrl 0x$5'

        Parameters list:
              $1: eap1_code_string
              $2: eap1_type_string
              $3: eap1_identificer
              $4: eap1_length
              $5: eap1_eap_ctrl

        An EAP packet of the type indicated has just arrived for processing."
    ::= { eapNotificationsPrefix 1 }

eapNotification2 NOTIFICATION-TYPE
    OBJECTS { 
              eap2_code_string, 
              eap2_type_string,
              eap2_identificer,
              eap2_length,
              eap2_eap_ctrl 
            }
    STATUS current
    DESCRIPTION
        "Notification of Event EAP.2

        Message: 'Transmitted EAP $1/$2 Packet, identifier $3, length $4, eap_ctrl 0x$5'

        Parameters list:
              $1: eap2_code_string
              $2: eap2_type_string
              $3: eap2_identificer
              $4: eap2_length
              $5: eap2_eap_ctrl

        An EAP packet of the type indicated has been transmitted."
    ::= { eapNotificationsPrefix 2 }

eapNotification3 NOTIFICATION-TYPE
    OBJECTS { 
              eap3_retry_count, 
              eap3_eap_ctrl 
            }
    STATUS current
    DESCRIPTION
        "Notification of Event EAP.3

        Message: 'EAP Timeout retry $1, eap_ctrl 0x$2'

        Parameters list:
              $1: eap3_retry_count
              $2: eap3_eap_ctrl

        An EAP request was sent and no response was received. The packet is
        retransmitted."
    ::= { eapNotificationsPrefix 3 }

eapNotification4 NOTIFICATION-TYPE
    OBJECTS { 
              eap4_eap_ctrl 
            }
    STATUS current
    DESCRIPTION
        "Notification of Event EAP.4

        Message: 'EAP Timeout max retries reached, eap_ctrl 0x$1'

        Parameters list:
              $1: eap4_eap_ctrl

        An EAP request has been sent with no response for the maximum configured
        retries. The EAP session is closed."
    ::= { eapNotificationsPrefix 4 }

eapNotification5 NOTIFICATION-TYPE
    OBJECTS { 
              eap5_Identity_len, 
              eap5_Available_len,
              eap5_eap_ctrl 
            }
    STATUS current
    DESCRIPTION
        "Notification of Event EAP.5

        Message: 'Not enough space to store Identity len $1, available $2, eap_ctrl 0x$3'

        Parameters list:
              $1: eap5_Identity_len
              $2: eap5_Available_len
              $3: eap5_eap_ctrl

        The received EAP identity can not be processed because it is longer
        than the available buffer."
    ::= { eapNotificationsPrefix 5 }

eapNotification6 NOTIFICATION-TYPE
    OBJECTS { 
              eap6_eap_ctrl 
            }
    STATUS current
    DESCRIPTION
        "Notification of Event EAP.6

        Message: 'Created EAP ctrl 0x$1'

        Parameters list:
              $1: eap6_eap_ctrl

        EAP control block created."
    ::= { eapNotificationsPrefix 6 }

eapNotification7 NOTIFICATION-TYPE
    OBJECTS { 
              eap7_eap_ctrl 
            }
    STATUS current
    DESCRIPTION
        "Notification of Event EAP.7

        Message: 'Destroyed EAP ctrl 0x$1'

        Parameters list:
              $1: eap7_eap_ctrl

        EAP control block destroyed."
    ::= { eapNotificationsPrefix 7 }

eapNotification8 NOTIFICATION-TYPE
    OBJECTS { 
              eap8_error_string, 
              eap8_eap_ctrl 
            }
    STATUS current
    DESCRIPTION
        "Notification of Event EAP.8

        Message: 'Received EAP packet discarded ($1), eap_ctrl 0x$2'

        Parameters list:
              $1: eap8_error_string
              $2: eap8_eap_ctrl

        The received EAP packet was discarded because an error ocurred while
        processing it."
    ::= { eapNotificationsPrefix 8 }


END
