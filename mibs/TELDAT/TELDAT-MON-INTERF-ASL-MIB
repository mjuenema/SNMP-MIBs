-- Teldat, S.A.

                -- Parque Tecnolgico de Madrid

                -- 28760, Tres Cantos (Madrid)

                -- Tlf: +34 918076565

                -- Fax: +34 918076521

                -- e-mail: id@teldat.es


            -- MIB privada de Teldat


            -- Interfaces de l�nea serie as�ncronos



    -- Historial:
    --      07/02/14    M.A. Pastor     XH 3523. Errors with HP Openview 9.20
    -- 1.1  02/02/06    M.A. Pastor     Variables que indican si se ha activado
    --                                  el modo loopback o el modo echo, si se
    --                                  ha establecido ignorar la se±al CD o la
    --                                  se±al DSR, o si se ha desconectado la
    --                                  se±al CD del hardware interno
    -- 1.0  01/07/04    J. Molina       Archivo procedente de ASL.MIB




    -- Historial de ASL.MIB:
    -- 1.0  15-06-01    J. L. Fuentes   MIB extra�da de la PPP.MIB debido a la
    --                                  separacin de los interfaces PPP y
    --                                  l�nea serie as�ncrono
    --------------------------------------------------------------------------

TELDAT-MON-INTERF-ASL-MIB DEFINITIONS ::= BEGIN

    IMPORTS
            Counter
        FROM RFC1155-SMI
            OBJECT-TYPE
        FROM RFC-1212
            DisplayString
        FROM RFC1213-MIB
            telProdNpMonInterfRouter
        FROM TELDAT-SW-STRUCTURE-MIB;


-- telProdNpMonInterfASL group

    telProdNpMonInterfASL   OBJECT IDENTIFIER ::= { telProdNpMonInterfRouter 16 }


-- Incluye los parßmetros referentes a la monitorizacin de los interfaces de
-- l�nea serie as�ncronos.

    -- Tabla de datos generales de los interfaces de l�nea serie as�ncrona.
    -- Habrß una entrada en la tabla por cada interfaz, y en cada entrada se
    -- muestran los datos que dan informacin sobre el tipo de interfaz o driver
    -- f�sico (DCE o DTE), la velocidad de l�nea, el throughput en bits por
    -- segundo, el ”ltimo throughput, el n”mero de bits por carßcter, el n”mero
    -- de bits de parada, la paridad seleccionada (si la hay), el n”mero de
    -- errores de paridad, errores de datos, errores debidos a overrun, el
    -- tiempo transcurrido desde el ”ltimo reset del puerto, si la SCC se
    -- encuentra en modo Loopback o en modo Echo, si se ha establecido ignorar
    -- la se±al CD o la se±al DSR, o si se ha desconectado la se±al CD del
    -- hardware interno.

    telProdNpMonIfcASLGlobalTable OBJECT-TYPE
        SYNTAX SEQUENCE OF TelProdNpMonIfcASLGlobalEntry
        ACCESS not-accessible
        STATUS mandatory
        DESCRIPTION
        "This table contains general information about asynchronous serial line
        interfaces. There will be one entry per each interface of this kind."
        ::= { telProdNpMonInterfASL 1 }

    telProdNpMonIfcASLGlobalEntry OBJECT-TYPE
        SYNTAX TelProdNpMonIfcASLGlobalEntry
        ACCESS not-accessible
        STATUS mandatory
        DESCRIPTION
        "Each entry contains the interface number that will be the table index
        used to go over the table, the line speed, the throughput in bits per
        second, the last throughput, the number of bits per character, the
        number of stop bits, the parity chosen (if it exists), the number of
        parity errors, data errors, overrun errors, the amount of time passed
        since the last port reset and variables to indicate if the SCC loopback
        mode or echo mode are active, if CD or DSR signal states are ignored and
        if CD signal is disconnected from internal hardware."
        INDEX { telProdNpMonIfcASLGloIndex }
        ::= { telProdNpMonIfcASLGlobalTable 1 }

    TelProdNpMonIfcASLGlobalEntry ::=
        SEQUENCE{
            telProdNpMonIfcASLGloIndex
                INTEGER,
            telProdNpMonIfcASLGloDriverType
                DisplayString,
            telProdNpMonIfcASLGloSpeed
                INTEGER,
            telProdNpMonIfcASLGloThrou
                INTEGER,
            telProdNpMonIfcASLGloLastThrou
                INTEGER,
            telProdNpMonIfcASLGloBitsChar
                INTEGER,
            telProdNpMonIfcASLGloStopBits
                INTEGER,
            telProdNpMonIfcASLGloParitySel
                INTEGER,
            telProdNpMonIfcASLGloLastResetWeek
                INTEGER,
            telProdNpMonIfcASLGloLastResetDay
                INTEGER,
            telProdNpMonIfcASLGloLastResetHour
                INTEGER,
            telProdNpMonIfcASLGloLastResetMin
                INTEGER,
            telProdNpMonIfcASLGloLastResetSec
                INTEGER,
            telProdNpMonIfcASLGloLoopback
                INTEGER,
            telProdNpMonIfcASLGloEcho
                INTEGER,
            telProdNpMonIfcASLGloIgnoreCD
                INTEGER,
            telProdNpMonIfcASLGloDisconnectCD
                INTEGER,
            telProdNpMonIfcASLGloIgnoreDSR
                INTEGER
            }

    telProdNpMonIfcASLGloIndex OBJECT-TYPE
        SYNTAX INTEGER
        ACCESS read-only
        STATUS mandatory
        DESCRIPTION
        "Interface number. The interface must be asynchronous serial line.
        It is the table index."
        ::= { telProdNpMonIfcASLGlobalEntry 1 }

    telProdNpMonIfcASLGloDriverType OBJECT-TYPE
        SYNTAX DisplayString
        ACCESS read-only
        STATUS mandatory
        DESCRIPTION
        "Type of physical driverP: (1) DCE, (2) DTE. The variable is a string."
        ::= { telProdNpMonIfcASLGlobalEntry 2 }

    telProdNpMonIfcASLGloSpeed OBJECT-TYPE
        SYNTAX INTEGER
        ACCESS read-only
        STATUS mandatory
        DESCRIPTION
        "Speed of the asynchronous serial line. (Clock speed, in bps)."
        ::= { telProdNpMonIfcASLGlobalEntry 3 }

    telProdNpMonIfcASLGloThrou OBJECT-TYPE
        SYNTAX INTEGER
        ACCESS read-only
        STATUS mandatory
        DESCRIPTION
        "Throughput in bits per second. It is the mean effective speed."
        ::= { telProdNpMonIfcASLGlobalEntry 4 }

    telProdNpMonIfcASLGloLastThrou OBJECT-TYPE
        SYNTAX INTEGER
        ACCESS read-only
        STATUS mandatory
        DESCRIPTION
        "Last throughput, in bits per second. It is the mean instantaneous
        speed."
        ::= { telProdNpMonIfcASLGlobalEntry 5 }

    telProdNpMonIfcASLGloBitsChar OBJECT-TYPE
        SYNTAX INTEGER
        ACCESS read-only
        STATUS mandatory
        DESCRIPTION
        "Number of bits per character."
        ::= { telProdNpMonIfcASLGlobalEntry 6 }

    telProdNpMonIfcASLGloStopBits OBJECT-TYPE
        SYNTAX INTEGER
        ACCESS read-only
        STATUS mandatory
        DESCRIPTION
        "Number of stop bits."
        ::= { telProdNpMonIfcASLGlobalEntry 7 }

    telProdNpMonIfcASLGloParitySel OBJECT-TYPE
        SYNTAX INTEGER{
            none(0),
            odd(1),
            space(2),
            even(3),
            mark(4)
            }
        ACCESS read-only
        STATUS mandatory
        DESCRIPTION
        "Parity chosen (if parity has been chosen). The possible values are:
        (0) if no parity has been selected, (1) odd, (2) space, (3) even,
        (4) mark."
        ::= { telProdNpMonIfcASLGlobalEntry 8 }

    telProdNpMonIfcASLGloLastResetWeek OBJECT-TYPE
        SYNTAX INTEGER
        ACCESS read-only
        STATUS mandatory
        DESCRIPTION
        "Weeks passed since the last port reset."
        ::= { telProdNpMonIfcASLGlobalEntry 9 }

    telProdNpMonIfcASLGloLastResetDay OBJECT-TYPE
        SYNTAX INTEGER
        ACCESS read-only
        STATUS mandatory
        DESCRIPTION
        "Days passed since the last port reset: the remaining days that we get
        after counting the number of weeks that are not enough to form a week,
        this implies that the value of the variable must be under 7."
        ::= { telProdNpMonIfcASLGlobalEntry 10 }

    telProdNpMonIfcASLGloLastResetHour OBJECT-TYPE
        SYNTAX INTEGER
        ACCESS read-only
        STATUS mandatory
        DESCRIPTION
        "Hours passed since the last reset of the port. If it has passed more
        than a week, this variable indicates the number of hours to be added
        to the number of weeks and days, and its value should be under 24 so
        as not form a complete day."
        ::= { telProdNpMonIfcASLGlobalEntry 11 }

    telProdNpMonIfcASLGloLastResetMin OBJECT-TYPE
        SYNTAX INTEGER
        ACCESS read-only
        STATUS mandatory
        DESCRIPTION
        "Minutes passed since the last reset of the port. This variable
        indicates the number of minutes since the last hour was added to the
        hour counter."
        ::= { telProdNpMonIfcASLGlobalEntry 12 }

    telProdNpMonIfcASLGloLastResetSec OBJECT-TYPE
        SYNTAX INTEGER
        ACCESS read-only
        STATUS mandatory
        DESCRIPTION
        "Seconds passed since the last reset of the port. The total time passed
        will be calculated by adding weeks, days, hours, minutes and seconds
        since the last reset."
        ::= { telProdNpMonIfcASLGlobalEntry 13 }

    telProdNpMonIfcASLGloLoopback OBJECT-TYPE
        SYNTAX INTEGER{
                active(1),
                inactive(2)
            }
        ACCESS read-only
        STATUS mandatory
        DESCRIPTION
        "This variable indicates if SCC loopback mode is active: transmitter is
        connected internally to the receiver."
        ::= { telProdNpMonIfcASLGlobalEntry 14 }

    telProdNpMonIfcASLGloEcho OBJECT-TYPE
        SYNTAX INTEGER{
                active(1),
                inactive(2)
            }
        ACCESS read-only
        STATUS mandatory
        DESCRIPTION
        "This variable indicates if SCC echo mode is active: transmitter
        resends received data."
        ::= { telProdNpMonIfcASLGlobalEntry 15 }

    telProdNpMonIfcASLGloIgnoreCD OBJECT-TYPE
        SYNTAX INTEGER{
                yes(1),
                no(2)
            }
        ACCESS read-only
        STATUS mandatory
        DESCRIPTION
        "This variable indicates if CD signal state is ignored."
        ::= { telProdNpMonIfcASLGlobalEntry 16 }

    telProdNpMonIfcASLGloDisconnectCD OBJECT-TYPE
        SYNTAX INTEGER{
                yes(1),
                no(2)
            }
        ACCESS read-only
        STATUS mandatory
        DESCRIPTION
        "This variable indicates if CD signal is disconnected from internal
        hardware."
        ::= { telProdNpMonIfcASLGlobalEntry 17 }

    telProdNpMonIfcASLGloIgnoreDSR OBJECT-TYPE
        SYNTAX INTEGER{
                yes(1),
                no(2)
            }
        ACCESS read-only
        STATUS mandatory
        DESCRIPTION
        "This variable indicates if DSR signal state is ignored."
        ::= { telProdNpMonIfcASLGlobalEntry 18 }

    -- Tabla de los circuitos RS232. Esta tabla da informacin acerca de si las
    -- se±ales RTS, CTS, DSR, DTR, DCD, RI y LL estßn activas o no.
    -- Habrß una entrada por cada interfaz l�nea serie as�ncrono, siendo el
    -- n”mero de interfaz el �ndice con que se recorre la tabla y con que se
    -- accede a la entrada correspondiente, y en cada una se proporciona el
    -- n”mero de orden del circuito RS232 (segundo �ndice de la tabla), el
    -- n”mero de circuito, su nombre y si estß o no activo.

    telProdNpMonIfcASLRS232Table OBJECT-TYPE
        SYNTAX SEQUENCE OF TelProdNpMonIfcASLRS232Entry
        ACCESS not-accessible
        STATUS mandatory
        DESCRIPTION
        "This table contains the signals or circuits RS232. It shows wether the
        signals are active or not. The entry number is determined by the
        interface number considered."
        ::= { telProdNpMonInterfASL 2 }

    telProdNpMonIfcASLRS232Entry OBJECT-TYPE
        SYNTAX TelProdNpMonIfcASLRS232Entry
        ACCESS not-accessible
        STATUS mandatory
        DESCRIPTION
        "Each entry contains the interface number of the node considered, which
        will be the first index used to go over the table, the order number of
        the circuit inside that interface (second index), which must be between
        1 and a maximum value that depends on the conector type (the highest
        value will be 7), the circuit number (105, 106, 107, 108, 109, 125,
        141), its name (RTS, CTS, DSR, DTR, DCD, RI, LL) and wether it is
        active or not."
        INDEX { telProdNpMonIfcASLRS232IfcIndex, telProdNpMonIfcASLRS232CircIndex }
        ::= { telProdNpMonIfcASLRS232Table 1 }

    TelProdNpMonIfcASLRS232Entry ::=
        SEQUENCE{
            telProdNpMonIfcASLRS232IfcIndex
                INTEGER,
            telProdNpMonIfcASLRS232CircIndex
                INTEGER,
            telProdNpMonIfcASLRS232Circuit
                INTEGER,
            telProdNpMonIfcASLRS232Nickname
                DisplayString,
            telProdNpMonIfcASLRS232State
                DisplayString
            }

    telProdNpMonIfcASLRS232IfcIndex OBJECT-TYPE
        SYNTAX INTEGER
        ACCESS read-only
        STATUS mandatory
        DESCRIPTION
        "Interface number, which must be synchronous serial line. It is the
        first table index."
        ::= { telProdNpMonIfcASLRS232Entry 1 }

    telProdNpMonIfcASLRS232CircIndex OBJECT-TYPE
        SYNTAX INTEGER(1..7)
        ACCESS read-only
        STATUS mandatory
        DESCRIPTION
        "Second table index. This value goes between 1 to the number of this
        type of circuits, that varies depending on the conector type."
        ::= { telProdNpMonIfcASLRS232Entry 2 }

    telProdNpMonIfcASLRS232Circuit OBJECT-TYPE
        SYNTAX INTEGER(105..141)
        ACCESS read-only
        STATUS mandatory
        DESCRIPTION
        "RS232 circuit number. The possible values are 105, 106, 107, 108,
        109, 125 y 141."
        ::= { telProdNpMonIfcASLRS232Entry 3 }

    telProdNpMonIfcASLRS232Nickname OBJECT-TYPE
        SYNTAX DisplayString
            ACCESS read-only
        STATUS mandatory
        DESCRIPTION
        "Circuit name."
        ::= { telProdNpMonIfcASLRS232Entry 4 }

    telProdNpMonIfcASLRS232State OBJECT-TYPE
        SYNTAX DisplayString
        ACCESS read-only
        STATUS mandatory
        DESCRIPTION
        "Signal state (circuit signals): on, off or unknown."
        ::= { telProdNpMonIfcASLRS232Entry 5 }

    -- Tabla donde se recogen los estad�sticos propios de los interfaces de tipo
    -- l�nea serie as�ncrono.
    -- Habrß una entrada en la tabla por cada interfaz, y en cada entrada se
    -- muestran los datos que dan informacin sobre los errores en la paridad,
    -- errores de datos y errores debidos a overrun, ademßs del n”mero de
    -- interfaz de l�nea serie as�ncrono que act”a como �ndice y de una variable
    -- que en lectura indica el resultado en el ”ltimo intento de borrado de la
    -- tabla y en escritura inicia el borrado de la misma.

    telProdNpMonIfcASLStatsTable OBJECT-TYPE
        SYNTAX SEQUENCE OF TelProdNpMonIfcASLStatsEntry
        ACCESS not-accessible
        STATUS mandatory
        DESCRIPTION
        "This table contains statistics of asynchronous serial line interfaces."
        ::= { telProdNpMonInterfASL 3 }

    telProdNpMonIfcASLStatsEntry OBJECT-TYPE
        SYNTAX TelProdNpMonIfcASLStatsEntry
        ACCESS not-accessible
        STATUS mandatory
        DESCRIPTION
        "Each entry contains the interface number that is the table index, the
        variable that shows the output from the last table deletion operation
        (in get operations) or begins the deletion (in set operations), the
        number of parity errors, the number of data errors and the number of
        overrun errors."
        INDEX { telProdNpMonIfcASLStatsIndex }
        ::= { telProdNpMonIfcASLStatsTable 1 }

    TelProdNpMonIfcASLStatsEntry ::=
        SEQUENCE{
            telProdNpMonIfcASLStatsIndex
                INTEGER,
            telProdNpMonIfcASLStatsClear
                INTEGER,
            telProdNpMonIfcASLStatsParityErr
                Counter,
            telProdNpMonIfcASLStatsDataErr
                Counter,
            telProdNpMonIfcASLStatsOverrun
                Counter
            }

    telProdNpMonIfcASLStatsIndex OBJECT-TYPE
        SYNTAX INTEGER
        ACCESS read-only
        STATUS mandatory
        DESCRIPTION
        "Interface number. The interface must be asynchronous serial line to
        appear in the table. It is the table index."
        ::= { telProdNpMonIfcASLStatsEntry 1 }

    telProdNpMonIfcASLStatsClear OBJECT-TYPE
        SYNTAX INTEGER{
            delete(1),
            ok(2),
            error(3),
            undefined(4)
            }
        ACCESS read-write
        STATUS mandatory
        DESCRIPTION
        "This variable when is read shows the output from the last table delete
        attempt: the value is 2 if the deletion was performed succesfully, 3 if
        an error ocurred and 4 for an undefined result, that means that nobody
        has tried to delete the table yet. In set operations, the value 1 (it is
        the only value that can be assigned by a writing operation) causes a
        table deletion: frame counters are set to 0."
        ::= { telProdNpMonIfcASLStatsEntry 2 }

    telProdNpMonIfcASLStatsParityErr OBJECT-TYPE
        SYNTAX Counter
        ACCESS read-only
        STATUS mandatory
        DESCRIPTION
        "Number of parity errors."
        ::= { telProdNpMonIfcASLStatsEntry 3 }

    telProdNpMonIfcASLStatsDataErr OBJECT-TYPE
        SYNTAX Counter
        ACCESS read-only
        STATUS mandatory
        DESCRIPTION
        "Number of data errors."
        ::= { telProdNpMonIfcASLStatsEntry 4 }

    telProdNpMonIfcASLStatsOverrun OBJECT-TYPE
        SYNTAX Counter
        ACCESS read-only
        STATUS mandatory
        DESCRIPTION
        "Number of overrun errors."
        ::= { telProdNpMonIfcASLStatsEntry 5 }

END
