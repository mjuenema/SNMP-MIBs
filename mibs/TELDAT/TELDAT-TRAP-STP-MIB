-- file automatically created


TELDAT-TRAP-STP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


stpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the STP event subsystem."
    REVISION "201401200930Z"
    DESCRIPTION "Initial implementation"
        ::= { telEventTraps 73 }


stpEventsGroup	OBJECT IDENTIFIER	::= { stpTrapsMIB 1 }

stpNotifications	OBJECT IDENTIFIER	::= { stpTrapsMIB 2 }
stpNotificationsPrefix	OBJECT IDENTIFIER	::= { stpNotifications 0 }

stpEventObjects1 OBJECT-IDENTITY
    STATUS current
    DESCRIPTION
        "Event STP.1
        A configuration BPDU has been received from the specified MAC address."
    ::= { stpEventsGroup 1 }

stp1_source_address OBJECT-TYPE
    SYNTAX DisplayString
    MAX-ACCESS accessible-for-notify
    STATUS current
    DESCRIPTION
        "Parameter 'source_address' in event STP.1"
    ::= { stpEventObjects1 1 }

stp1_bridge_type OBJECT-TYPE
    SYNTAX DisplayString
    MAX-ACCESS accessible-for-notify
    STATUS current
    DESCRIPTION
        "Parameter 'bridge_type' in event STP.1"
    ::= { stpEventObjects1 2 }

stp1_bridge_instance OBJECT-TYPE
    SYNTAX Integer32
    MAX-ACCESS accessible-for-notify
    STATUS current
    DESCRIPTION
        "Parameter 'bridge_instance' in event STP.1"
    ::= { stpEventObjects1 3 }

stp1_bridge_port OBJECT-TYPE
    SYNTAX Integer32
    MAX-ACCESS accessible-for-notify
    STATUS current
    DESCRIPTION
        "Parameter 'bridge_port' in event STP.1"
    ::= { stpEventObjects1 4 }

stp1_interface OBJECT-TYPE
    SYNTAX DisplayString
    MAX-ACCESS accessible-for-notify
    STATUS current
    DESCRIPTION
        "Parameter 'interface' in event STP.1"
    ::= { stpEventObjects1 5 }

stp1_circuit_name OBJECT-TYPE
    SYNTAX DisplayString
    MAX-ACCESS accessible-for-notify
    STATUS current
    DESCRIPTION
        "Parameter 'circuit_name' in event STP.1"
    ::= { stpEventObjects1 6 }

stpEventObjects2 OBJECT-IDENTITY
    STATUS current
    DESCRIPTION
        "Event STP.2
        A topology change notification BPDU has been received from
        the specified MAC address."
    ::= { stpEventsGroup 2 }

stp2_source_address OBJECT-TYPE
    SYNTAX DisplayString
    MAX-ACCESS accessible-for-notify
    STATUS current
    DESCRIPTION
        "Parameter 'source_address' in event STP.2"
    ::= { stpEventObjects2 1 }

stp2_bridge_type OBJECT-TYPE
    SYNTAX DisplayString
    MAX-ACCESS accessible-for-notify
    STATUS current
    DESCRIPTION
        "Parameter 'bridge_type' in event STP.2"
    ::= { stpEventObjects2 2 }

stp2_bridge_instance OBJECT-TYPE
    SYNTAX Integer32
    MAX-ACCESS accessible-for-notify
    STATUS current
    DESCRIPTION
        "Parameter 'bridge_instance' in event STP.2"
    ::= { stpEventObjects2 3 }

stp2_bridge_port OBJECT-TYPE
    SYNTAX Integer32
    MAX-ACCESS accessible-for-notify
    STATUS current
    DESCRIPTION
        "Parameter 'bridge_port' in event STP.2"
    ::= { stpEventObjects2 4 }

stp2_interface OBJECT-TYPE
    SYNTAX DisplayString
    MAX-ACCESS accessible-for-notify
    STATUS current
    DESCRIPTION
        "Parameter 'interface' in event STP.2"
    ::= { stpEventObjects2 5 }

stp2_circuit_name OBJECT-TYPE
    SYNTAX DisplayString
    MAX-ACCESS accessible-for-notify
    STATUS current
    DESCRIPTION
        "Parameter 'circuit_name' in event STP.2"
    ::= { stpEventObjects2 6 }

stpEventObjects3 OBJECT-IDENTITY
    STATUS current
    DESCRIPTION
        "Event STP.3
        A BPDU with an undefined value in the BPDU Type field was received
        from the specified host. It will be ignored."
    ::= { stpEventsGroup 3 }

stp3_BDPU_type OBJECT-TYPE
    SYNTAX Integer32
    MAX-ACCESS accessible-for-notify
    STATUS current
    DESCRIPTION
        "Parameter 'BDPU_type' in event STP.3"
    ::= { stpEventObjects3 1 }

stp3_source_address OBJECT-TYPE
    SYNTAX DisplayString
    MAX-ACCESS accessible-for-notify
    STATUS current
    DESCRIPTION
        "Parameter 'source_address' in event STP.3"
    ::= { stpEventObjects3 2 }

stp3_bridge_type OBJECT-TYPE
    SYNTAX DisplayString
    MAX-ACCESS accessible-for-notify
    STATUS current
    DESCRIPTION
        "Parameter 'bridge_type' in event STP.3"
    ::= { stpEventObjects3 3 }

stp3_bridge_instance OBJECT-TYPE
    SYNTAX Integer32
    MAX-ACCESS accessible-for-notify
    STATUS current
    DESCRIPTION
        "Parameter 'bridge_instance' in event STP.3"
    ::= { stpEventObjects3 4 }

stp3_bridge_port OBJECT-TYPE
    SYNTAX Integer32
    MAX-ACCESS accessible-for-notify
    STATUS current
    DESCRIPTION
        "Parameter 'bridge_port' in event STP.3"
    ::= { stpEventObjects3 5 }

stp3_interface OBJECT-TYPE
    SYNTAX DisplayString
    MAX-ACCESS accessible-for-notify
    STATUS current
    DESCRIPTION
        "Parameter 'interface' in event STP.3"
    ::= { stpEventObjects3 6 }

stp3_circuit_name OBJECT-TYPE
    SYNTAX DisplayString
    MAX-ACCESS accessible-for-notify
    STATUS current
    DESCRIPTION
        "Parameter 'circuit_name' in event STP.3"
    ::= { stpEventObjects3 7 }

stpEventObjects4 OBJECT-IDENTITY
    STATUS current
    DESCRIPTION
        "Event STP.4
        A configuration BPDU has been received with a Protocol Identifier
        that is not 0000. It will be ignored."
    ::= { stpEventsGroup 4 }

stp4_Protocol_Identifier OBJECT-TYPE
    SYNTAX Integer32
    MAX-ACCESS accessible-for-notify
    STATUS current
    DESCRIPTION
        "Parameter 'Protocol_Identifier' in event STP.4"
    ::= { stpEventObjects4 1 }

stp4_source_address OBJECT-TYPE
    SYNTAX DisplayString
    MAX-ACCESS accessible-for-notify
    STATUS current
    DESCRIPTION
        "Parameter 'source_address' in event STP.4"
    ::= { stpEventObjects4 2 }

stp4_bridge_type OBJECT-TYPE
    SYNTAX DisplayString
    MAX-ACCESS accessible-for-notify
    STATUS current
    DESCRIPTION
        "Parameter 'bridge_type' in event STP.4"
    ::= { stpEventObjects4 3 }

stp4_bridge_instance OBJECT-TYPE
    SYNTAX Integer32
    MAX-ACCESS accessible-for-notify
    STATUS current
    DESCRIPTION
        "Parameter 'bridge_instance' in event STP.4"
    ::= { stpEventObjects4 4 }

stp4_bridge_port OBJECT-TYPE
    SYNTAX Integer32
    MAX-ACCESS accessible-for-notify
    STATUS current
    DESCRIPTION
        "Parameter 'bridge_port' in event STP.4"
    ::= { stpEventObjects4 5 }

stp4_interface OBJECT-TYPE
    SYNTAX DisplayString
    MAX-ACCESS accessible-for-notify
    STATUS current
    DESCRIPTION
        "Parameter 'interface' in event STP.4"
    ::= { stpEventObjects4 6 }

stp4_circuit_name OBJECT-TYPE
    SYNTAX DisplayString
    MAX-ACCESS accessible-for-notify
    STATUS current
    DESCRIPTION
        "Parameter 'circuit_name' in event STP.4"
    ::= { stpEventObjects4 7 }

stpEventObjects5 OBJECT-IDENTITY
    STATUS current
    DESCRIPTION
        "Event STP.5
        A configuration BPDU has been received with a Protocol Version
        Identifier that is not 00. It will be ignored."
    ::= { stpEventsGroup 5 }

stp5_Protocol_Version_Identifier OBJECT-TYPE
    SYNTAX Integer32
    MAX-ACCESS accessible-for-notify
    STATUS current
    DESCRIPTION
        "Parameter 'Protocol_Version_Identifier' in event STP.5"
    ::= { stpEventObjects5 1 }

stp5_source_address OBJECT-TYPE
    SYNTAX DisplayString
    MAX-ACCESS accessible-for-notify
    STATUS current
    DESCRIPTION
        "Parameter 'source_address' in event STP.5"
    ::= { stpEventObjects5 2 }

stp5_bridge_type OBJECT-TYPE
    SYNTAX DisplayString
    MAX-ACCESS accessible-for-notify
    STATUS current
    DESCRIPTION
        "Parameter 'bridge_type' in event STP.5"
    ::= { stpEventObjects5 3 }

stp5_bridge_instance OBJECT-TYPE
    SYNTAX Integer32
    MAX-ACCESS accessible-for-notify
    STATUS current
    DESCRIPTION
        "Parameter 'bridge_instance' in event STP.5"
    ::= { stpEventObjects5 4 }

stp5_bridge_port OBJECT-TYPE
    SYNTAX Integer32
    MAX-ACCESS accessible-for-notify
    STATUS current
    DESCRIPTION
        "Parameter 'bridge_port' in event STP.5"
    ::= { stpEventObjects5 5 }

stp5_interface OBJECT-TYPE
    SYNTAX DisplayString
    MAX-ACCESS accessible-for-notify
    STATUS current
    DESCRIPTION
        "Parameter 'interface' in event STP.5"
    ::= { stpEventObjects5 6 }

stp5_circuit_name OBJECT-TYPE
    SYNTAX DisplayString
    MAX-ACCESS accessible-for-notify
    STATUS current
    DESCRIPTION
        "Parameter 'circuit_name' in event STP.5"
    ::= { stpEventObjects5 7 }

stpEventObjects6 OBJECT-IDENTITY
    STATUS current
    DESCRIPTION
        "Event STP.6
        A configuration BPDU has been received which is less than 35 bytes
        in length. It will be ignored."
    ::= { stpEventsGroup 6 }

stp6_length OBJECT-TYPE
    SYNTAX Integer32
    MAX-ACCESS accessible-for-notify
    STATUS current
    DESCRIPTION
        "Parameter 'length' in event STP.6"
    ::= { stpEventObjects6 1 }

stp6_source_address OBJECT-TYPE
    SYNTAX DisplayString
    MAX-ACCESS accessible-for-notify
    STATUS current
    DESCRIPTION
        "Parameter 'source_address' in event STP.6"
    ::= { stpEventObjects6 2 }

stp6_bridge_type OBJECT-TYPE
    SYNTAX DisplayString
    MAX-ACCESS accessible-for-notify
    STATUS current
    DESCRIPTION
        "Parameter 'bridge_type' in event STP.6"
    ::= { stpEventObjects6 3 }

stp6_bridge_instance OBJECT-TYPE
    SYNTAX Integer32
    MAX-ACCESS accessible-for-notify
    STATUS current
    DESCRIPTION
        "Parameter 'bridge_instance' in event STP.6"
    ::= { stpEventObjects6 4 }

stp6_bridge_port OBJECT-TYPE
    SYNTAX Integer32
    MAX-ACCESS accessible-for-notify
    STATUS current
    DESCRIPTION
        "Parameter 'bridge_port' in event STP.6"
    ::= { stpEventObjects6 5 }

stp6_interface OBJECT-TYPE
    SYNTAX DisplayString
    MAX-ACCESS accessible-for-notify
    STATUS current
    DESCRIPTION
        "Parameter 'interface' in event STP.6"
    ::= { stpEventObjects6 6 }

stp6_circuit_name OBJECT-TYPE
    SYNTAX DisplayString
    MAX-ACCESS accessible-for-notify
    STATUS current
    DESCRIPTION
        "Parameter 'circuit_name' in event STP.6"
    ::= { stpEventObjects6 7 }

stpEventObjects7 OBJECT-IDENTITY
    STATUS current
    DESCRIPTION
        "Event STP.7
        A configuration BPDU has been received which has undefined bits set
        in the flags field. It will be ignored."
    ::= { stpEventsGroup 7 }

stp7_flags OBJECT-TYPE
    SYNTAX Integer32
    MAX-ACCESS accessible-for-notify
    STATUS current
    DESCRIPTION
        "Parameter 'flags' in event STP.7"
    ::= { stpEventObjects7 1 }

stp7_source_address OBJECT-TYPE
    SYNTAX DisplayString
    MAX-ACCESS accessible-for-notify
    STATUS current
    DESCRIPTION
        "Parameter 'source_address' in event STP.7"
    ::= { stpEventObjects7 2 }

stp7_bridge_type OBJECT-TYPE
    SYNTAX DisplayString
    MAX-ACCESS accessible-for-notify
    STATUS current
    DESCRIPTION
        "Parameter 'bridge_type' in event STP.7"
    ::= { stpEventObjects7 3 }

stp7_bridge_instance OBJECT-TYPE
    SYNTAX Integer32
    MAX-ACCESS accessible-for-notify
    STATUS current
    DESCRIPTION
        "Parameter 'bridge_instance' in event STP.7"
    ::= { stpEventObjects7 4 }

stp7_bridge_port OBJECT-TYPE
    SYNTAX Integer32
    MAX-ACCESS accessible-for-notify
    STATUS current
    DESCRIPTION
        "Parameter 'bridge_port' in event STP.7"
    ::= { stpEventObjects7 5 }

stp7_interface OBJECT-TYPE
    SYNTAX DisplayString
    MAX-ACCESS accessible-for-notify
    STATUS current
    DESCRIPTION
        "Parameter 'interface' in event STP.7"
    ::= { stpEventObjects7 6 }

stp7_circuit_name OBJECT-TYPE
    SYNTAX DisplayString
    MAX-ACCESS accessible-for-notify
    STATUS current
    DESCRIPTION
        "Parameter 'circuit_name' in event STP.7"
    ::= { stpEventObjects7 7 }

stpEventObjects8 OBJECT-IDENTITY
    STATUS current
    DESCRIPTION
        "Event STP.8
        A topology change notificaton BPDU has been received that is less than
        4 bytes in length. It will be ignored."
    ::= { stpEventsGroup 8 }

stp8_length OBJECT-TYPE
    SYNTAX Integer32
    MAX-ACCESS accessible-for-notify
    STATUS current
    DESCRIPTION
        "Parameter 'length' in event STP.8"
    ::= { stpEventObjects8 1 }

stp8_source_address OBJECT-TYPE
    SYNTAX DisplayString
    MAX-ACCESS accessible-for-notify
    STATUS current
    DESCRIPTION
        "Parameter 'source_address' in event STP.8"
    ::= { stpEventObjects8 2 }

stp8_bridge_type OBJECT-TYPE
    SYNTAX DisplayString
    MAX-ACCESS accessible-for-notify
    STATUS current
    DESCRIPTION
        "Parameter 'bridge_type' in event STP.8"
    ::= { stpEventObjects8 3 }

stp8_bridge_instance OBJECT-TYPE
    SYNTAX Integer32
    MAX-ACCESS accessible-for-notify
    STATUS current
    DESCRIPTION
        "Parameter 'bridge_instance' in event STP.8"
    ::= { stpEventObjects8 4 }

stp8_bridge_port OBJECT-TYPE
    SYNTAX Integer32
    MAX-ACCESS accessible-for-notify
    STATUS current
    DESCRIPTION
        "Parameter 'bridge_port' in event STP.8"
    ::= { stpEventObjects8 5 }

stp8_interface OBJECT-TYPE
    SYNTAX DisplayString
    MAX-ACCESS accessible-for-notify
    STATUS current
    DESCRIPTION
        "Parameter 'interface' in event STP.8"
    ::= { stpEventObjects8 6 }

stp8_circuit_name OBJECT-TYPE
    SYNTAX DisplayString
    MAX-ACCESS accessible-for-notify
    STATUS current
    DESCRIPTION
        "Parameter 'circuit_name' in event STP.8"
    ::= { stpEventObjects8 7 }

stpEventObjects9 OBJECT-IDENTITY
    STATUS current
    DESCRIPTION
        "Event STP.9
        No packet buffer was available to construct and send a BDPU on the
        specified port."
    ::= { stpEventsGroup 9 }

stp9_bridge_type OBJECT-TYPE
    SYNTAX DisplayString
    MAX-ACCESS accessible-for-notify
    STATUS current
    DESCRIPTION
        "Parameter 'bridge_type' in event STP.9"
    ::= { stpEventObjects9 1 }

stp9_bridge_instance OBJECT-TYPE
    SYNTAX Integer32
    MAX-ACCESS accessible-for-notify
    STATUS current
    DESCRIPTION
        "Parameter 'bridge_instance' in event STP.9"
    ::= { stpEventObjects9 2 }

stp9_bridge_port OBJECT-TYPE
    SYNTAX Integer32
    MAX-ACCESS accessible-for-notify
    STATUS current
    DESCRIPTION
        "Parameter 'bridge_port' in event STP.9"
    ::= { stpEventObjects9 3 }

stp9_interface OBJECT-TYPE
    SYNTAX DisplayString
    MAX-ACCESS accessible-for-notify
    STATUS current
    DESCRIPTION
        "Parameter 'interface' in event STP.9"
    ::= { stpEventObjects9 4 }

stp9_circuit_name OBJECT-TYPE
    SYNTAX DisplayString
    MAX-ACCESS accessible-for-notify
    STATUS current
    DESCRIPTION
        "Parameter 'circuit_name' in event STP.9"
    ::= { stpEventObjects9 5 }

stpEventObjects10 OBJECT-IDENTITY
    STATUS current
    DESCRIPTION
        "Event STP.10
        A Configuration BPDU will be sent on the specified port.
        This is done normally on a periodic basis as part of the
        Spanning Tree Protocol.
        The flags field in this BPDU is zero, e.g., neither the Topology Change
        or the Topology Change Acknowledgement bits are set."
    ::= { stpEventsGroup 10 }

stp10_bridge_type OBJECT-TYPE
    SYNTAX DisplayString
    MAX-ACCESS accessible-for-notify
    STATUS current
    DESCRIPTION
        "Parameter 'bridge_type' in event STP.10"
    ::= { stpEventObjects10 1 }

stp10_bridge_instance OBJECT-TYPE
    SYNTAX Integer32
    MAX-ACCESS accessible-for-notify
    STATUS current
    DESCRIPTION
        "Parameter 'bridge_instance' in event STP.10"
    ::= { stpEventObjects10 2 }

stp10_bridge_port OBJECT-TYPE
    SYNTAX Integer32
    MAX-ACCESS accessible-for-notify
    STATUS current
    DESCRIPTION
        "Parameter 'bridge_port' in event STP.10"
    ::= { stpEventObjects10 3 }

stp10_interface OBJECT-TYPE
    SYNTAX DisplayString
    MAX-ACCESS accessible-for-notify
    STATUS current
    DESCRIPTION
        "Parameter 'interface' in event STP.10"
    ::= { stpEventObjects10 4 }

stp10_circuit_name OBJECT-TYPE
    SYNTAX DisplayString
    MAX-ACCESS accessible-for-notify
    STATUS current
    DESCRIPTION
        "Parameter 'circuit_name' in event STP.10"
    ::= { stpEventObjects10 5 }

stpEventObjects11 OBJECT-IDENTITY
    STATUS current
    DESCRIPTION
        "Event STP.11
        A Configuration BPDU will be sent on the specified port.
        This is done normally on a periodic basis as part of the
        Spanning Tree Protocol. TC will be displayed if the Topology Change bit
        is set in the Flags byte of the BPDU, TCA will be displayed if
        the Topology Change Acknowledge bit is set in the Flags byte."
    ::= { stpEventsGroup 11 }

stp11_TC OBJECT-TYPE
    SYNTAX DisplayString
    MAX-ACCESS accessible-for-notify
    STATUS current
    DESCRIPTION
        "Parameter 'TC' in event STP.11"
    ::= { stpEventObjects11 1 }

stp11_TCA OBJECT-TYPE
    SYNTAX DisplayString
    MAX-ACCESS accessible-for-notify
    STATUS current
    DESCRIPTION
        "Parameter 'TCA' in event STP.11"
    ::= { stpEventObjects11 2 }

stp11_bridge_type OBJECT-TYPE
    SYNTAX DisplayString
    MAX-ACCESS accessible-for-notify
    STATUS current
    DESCRIPTION
        "Parameter 'bridge_type' in event STP.11"
    ::= { stpEventObjects11 3 }

stp11_bridge_instance OBJECT-TYPE
    SYNTAX Integer32
    MAX-ACCESS accessible-for-notify
    STATUS current
    DESCRIPTION
        "Parameter 'bridge_instance' in event STP.11"
    ::= { stpEventObjects11 4 }

stp11_bridge_port OBJECT-TYPE
    SYNTAX Integer32
    MAX-ACCESS accessible-for-notify
    STATUS current
    DESCRIPTION
        "Parameter 'bridge_port' in event STP.11"
    ::= { stpEventObjects11 5 }

stp11_interface OBJECT-TYPE
    SYNTAX DisplayString
    MAX-ACCESS accessible-for-notify
    STATUS current
    DESCRIPTION
        "Parameter 'interface' in event STP.11"
    ::= { stpEventObjects11 6 }

stp11_circuit_name OBJECT-TYPE
    SYNTAX DisplayString
    MAX-ACCESS accessible-for-notify
    STATUS current
    DESCRIPTION
        "Parameter 'circuit_name' in event STP.11"
    ::= { stpEventObjects11 7 }

stpEventObjects12 OBJECT-IDENTITY
    STATUS current
    DESCRIPTION
        "Event STP.12
        A Topology Change Notification BPDU will be sent on the specified port.
        These are sent on the root port of non-root ports when they detect
        a topology change in the spanning tree."
    ::= { stpEventsGroup 12 }

stp12_bridge_type OBJECT-TYPE
    SYNTAX DisplayString
    MAX-ACCESS accessible-for-notify
    STATUS current
    DESCRIPTION
        "Parameter 'bridge_type' in event STP.12"
    ::= { stpEventObjects12 1 }

stp12_bridge_instance OBJECT-TYPE
    SYNTAX Integer32
    MAX-ACCESS accessible-for-notify
    STATUS current
    DESCRIPTION
        "Parameter 'bridge_instance' in event STP.12"
    ::= { stpEventObjects12 2 }

stp12_bridge_port OBJECT-TYPE
    SYNTAX Integer32
    MAX-ACCESS accessible-for-notify
    STATUS current
    DESCRIPTION
        "Parameter 'bridge_port' in event STP.12"
    ::= { stpEventObjects12 3 }

stp12_interface OBJECT-TYPE
    SYNTAX DisplayString
    MAX-ACCESS accessible-for-notify
    STATUS current
    DESCRIPTION
        "Parameter 'interface' in event STP.12"
    ::= { stpEventObjects12 4 }

stp12_circuit_name OBJECT-TYPE
    SYNTAX DisplayString
    MAX-ACCESS accessible-for-notify
    STATUS current
    DESCRIPTION
        "Parameter 'circuit_name' in event STP.12"
    ::= { stpEventObjects12 5 }

stpEventObjects13 OBJECT-IDENTITY
    STATUS current
    DESCRIPTION
        "Event STP.13
        The attempt to queue a BPDU for transmission on the specified port
        failed."
    ::= { stpEventsGroup 13 }

stp13_reason_code OBJECT-TYPE
    SYNTAX Integer32
    MAX-ACCESS accessible-for-notify
    STATUS current
    DESCRIPTION
        "Parameter 'reason_code' in event STP.13"
    ::= { stpEventObjects13 1 }

stp13_bridge_type OBJECT-TYPE
    SYNTAX DisplayString
    MAX-ACCESS accessible-for-notify
    STATUS current
    DESCRIPTION
        "Parameter 'bridge_type' in event STP.13"
    ::= { stpEventObjects13 2 }

stp13_bridge_instance OBJECT-TYPE
    SYNTAX Integer32
    MAX-ACCESS accessible-for-notify
    STATUS current
    DESCRIPTION
        "Parameter 'bridge_instance' in event STP.13"
    ::= { stpEventObjects13 3 }

stp13_bridge_port OBJECT-TYPE
    SYNTAX Integer32
    MAX-ACCESS accessible-for-notify
    STATUS current
    DESCRIPTION
        "Parameter 'bridge_port' in event STP.13"
    ::= { stpEventObjects13 4 }

stp13_interface OBJECT-TYPE
    SYNTAX DisplayString
    MAX-ACCESS accessible-for-notify
    STATUS current
    DESCRIPTION
        "Parameter 'interface' in event STP.13"
    ::= { stpEventObjects13 5 }

stp13_circuit_name OBJECT-TYPE
    SYNTAX DisplayString
    MAX-ACCESS accessible-for-notify
    STATUS current
    DESCRIPTION
        "Parameter 'circuit_name' in event STP.13"
    ::= { stpEventObjects13 6 }

stpEventObjects14 OBJECT-IDENTITY
    STATUS current
    DESCRIPTION
        "Event STP.14
        This port has just been placed in Blocking state. This is a change in
        the topology, so this bridge detects a topology change.
        This will in turn cause topology change notifications to be sent."
    ::= { stpEventsGroup 14 }

stp14_bridge_type OBJECT-TYPE
    SYNTAX DisplayString
    MAX-ACCESS accessible-for-notify
    STATUS current
    DESCRIPTION
        "Parameter 'bridge_type' in event STP.14"
    ::= { stpEventObjects14 1 }

stp14_bridge_instance OBJECT-TYPE
    SYNTAX Integer32
    MAX-ACCESS accessible-for-notify
    STATUS current
    DESCRIPTION
        "Parameter 'bridge_instance' in event STP.14"
    ::= { stpEventObjects14 2 }

stp14_bridge_port OBJECT-TYPE
    SYNTAX Integer32
    MAX-ACCESS accessible-for-notify
    STATUS current
    DESCRIPTION
        "Parameter 'bridge_port' in event STP.14"
    ::= { stpEventObjects14 3 }

stp14_interface OBJECT-TYPE
    SYNTAX DisplayString
    MAX-ACCESS accessible-for-notify
    STATUS current
    DESCRIPTION
        "Parameter 'interface' in event STP.14"
    ::= { stpEventObjects14 4 }

stp14_circuit_name OBJECT-TYPE
    SYNTAX DisplayString
    MAX-ACCESS accessible-for-notify
    STATUS current
    DESCRIPTION
        "Parameter 'circuit_name' in event STP.14"
    ::= { stpEventObjects14 5 }

stpEventObjects15 OBJECT-IDENTITY
    STATUS current
    DESCRIPTION
        "Event STP.15
        A topology change notification has been received on this port, and
        this port is the designated port on its LAN. This causes the protocol
        to enter topology change notification state.
        The topology change will be acknowledged towards the sender, and
        propogated towards the root."
    ::= { stpEventsGroup 15 }

stp15_bridge_type OBJECT-TYPE
    SYNTAX DisplayString
    MAX-ACCESS accessible-for-notify
    STATUS current
    DESCRIPTION
        "Parameter 'bridge_type' in event STP.15"
    ::= { stpEventObjects15 1 }

stp15_bridge_instance OBJECT-TYPE
    SYNTAX Integer32
    MAX-ACCESS accessible-for-notify
    STATUS current
    DESCRIPTION
        "Parameter 'bridge_instance' in event STP.15"
    ::= { stpEventObjects15 2 }

stp15_bridge_port OBJECT-TYPE
    SYNTAX Integer32
    MAX-ACCESS accessible-for-notify
    STATUS current
    DESCRIPTION
        "Parameter 'bridge_port' in event STP.15"
    ::= { stpEventObjects15 3 }

stp15_interface OBJECT-TYPE
    SYNTAX DisplayString
    MAX-ACCESS accessible-for-notify
    STATUS current
    DESCRIPTION
        "Parameter 'interface' in event STP.15"
    ::= { stpEventObjects15 4 }

stp15_circuit_name OBJECT-TYPE
    SYNTAX DisplayString
    MAX-ACCESS accessible-for-notify
    STATUS current
    DESCRIPTION
        "Parameter 'circuit_name' in event STP.15"
    ::= { stpEventObjects15 5 }

stpEventObjects16 OBJECT-IDENTITY
    STATUS current
    DESCRIPTION
        "Event STP.16
        This bridge has just selected itself as the root of the spanning tree
        when it previously had not been. This causes the bridge to enter
        topology change notification state."
    ::= { stpEventsGroup 16 }

stp16_bridge_type OBJECT-TYPE
    SYNTAX DisplayString
    MAX-ACCESS accessible-for-notify
    STATUS current
    DESCRIPTION
        "Parameter 'bridge_type' in event STP.16"
    ::= { stpEventObjects16 1 }

stp16_bridge_instance OBJECT-TYPE
    SYNTAX Integer32
    MAX-ACCESS accessible-for-notify
    STATUS current
    DESCRIPTION
        "Parameter 'bridge_instance' in event STP.16"
    ::= { stpEventObjects16 2 }

stpEventObjects17 OBJECT-IDENTITY
    STATUS current
    DESCRIPTION
        "Event STP.17
        A topology change acknowledgement has been detected on the specified
        port. This port is the root port of the bridge."
    ::= { stpEventsGroup 17 }

stp17_bridge_type OBJECT-TYPE
    SYNTAX DisplayString
    MAX-ACCESS accessible-for-notify
    STATUS current
    DESCRIPTION
        "Parameter 'bridge_type' in event STP.17"
    ::= { stpEventObjects17 1 }

stp17_bridge_instance OBJECT-TYPE
    SYNTAX Integer32
    MAX-ACCESS accessible-for-notify
    STATUS current
    DESCRIPTION
        "Parameter 'bridge_instance' in event STP.17"
    ::= { stpEventObjects17 2 }

stp17_bridge_port OBJECT-TYPE
    SYNTAX Integer32
    MAX-ACCESS accessible-for-notify
    STATUS current
    DESCRIPTION
        "Parameter 'bridge_port' in event STP.17"
    ::= { stpEventObjects17 3 }

stp17_interface OBJECT-TYPE
    SYNTAX DisplayString
    MAX-ACCESS accessible-for-notify
    STATUS current
    DESCRIPTION
        "Parameter 'interface' in event STP.17"
    ::= { stpEventObjects17 4 }

stp17_circuit_name OBJECT-TYPE
    SYNTAX DisplayString
    MAX-ACCESS accessible-for-notify
    STATUS current
    DESCRIPTION
        "Parameter 'circuit_name' in event STP.17"
    ::= { stpEventObjects17 5 }

stpEventObjects18 OBJECT-IDENTITY
    STATUS current
    DESCRIPTION
        "Event STP.18
        A topology change notification is being acknowledged on the
        specified port. This is done when a topology change notification
        is received on a port that is the designated port for that LAN."
    ::= { stpEventsGroup 18 }

stp18_bridge_type OBJECT-TYPE
    SYNTAX DisplayString
    MAX-ACCESS accessible-for-notify
    STATUS current
    DESCRIPTION
        "Parameter 'bridge_type' in event STP.18"
    ::= { stpEventObjects18 1 }

stp18_bridge_instance OBJECT-TYPE
    SYNTAX Integer32
    MAX-ACCESS accessible-for-notify
    STATUS current
    DESCRIPTION
        "Parameter 'bridge_instance' in event STP.18"
    ::= { stpEventObjects18 2 }

stp18_bridge_port OBJECT-TYPE
    SYNTAX Integer32
    MAX-ACCESS accessible-for-notify
    STATUS current
    DESCRIPTION
        "Parameter 'bridge_port' in event STP.18"
    ::= { stpEventObjects18 3 }

stp18_interface OBJECT-TYPE
    SYNTAX DisplayString
    MAX-ACCESS accessible-for-notify
    STATUS current
    DESCRIPTION
        "Parameter 'interface' in event STP.18"
    ::= { stpEventObjects18 4 }

stp18_circuit_name OBJECT-TYPE
    SYNTAX DisplayString
    MAX-ACCESS accessible-for-notify
    STATUS current
    DESCRIPTION
        "Parameter 'circuit_name' in event STP.18"
    ::= { stpEventObjects18 5 }

stpEventObjects19 OBJECT-IDENTITY
    STATUS current
    DESCRIPTION
        "Event STP.19
        The Topology Change timer expired. This bridge will cease sending
        topology change notification BPDU's on its root port."
    ::= { stpEventsGroup 19 }

stp19_bridge_type OBJECT-TYPE
    SYNTAX DisplayString
    MAX-ACCESS accessible-for-notify
    STATUS current
    DESCRIPTION
        "Parameter 'bridge_type' in event STP.19"
    ::= { stpEventObjects19 1 }

stp19_bridge_instance OBJECT-TYPE
    SYNTAX Integer32
    MAX-ACCESS accessible-for-notify
    STATUS current
    DESCRIPTION
        "Parameter 'bridge_instance' in event STP.19"
    ::= { stpEventObjects19 2 }

stpEventObjects20 OBJECT-IDENTITY
    STATUS current
    DESCRIPTION
        "Event STP.20
        The Topology Change timer expired. This bridge, which is the root,
        will cease sending the Topology Change in its Configuration BPDUs."
    ::= { stpEventsGroup 20 }

stp20_bridge_type OBJECT-TYPE
    SYNTAX DisplayString
    MAX-ACCESS accessible-for-notify
    STATUS current
    DESCRIPTION
        "Parameter 'bridge_type' in event STP.20"
    ::= { stpEventObjects20 1 }

stp20_bridge_instance OBJECT-TYPE
    SYNTAX Integer32
    MAX-ACCESS accessible-for-notify
    STATUS current
    DESCRIPTION
        "Parameter 'bridge_instance' in event STP.20"
    ::= { stpEventObjects20 2 }

stpEventObjects21 OBJECT-IDENTITY
    STATUS current
    DESCRIPTION
        "Event STP.21
        The message age timer has expired on this port. The bridge will attempt
        to become the root. It will become the designated port on that LAN."
    ::= { stpEventsGroup 21 }

stp21_bridge_type OBJECT-TYPE
    SYNTAX DisplayString
    MAX-ACCESS accessible-for-notify
    STATUS current
    DESCRIPTION
        "Parameter 'bridge_type' in event STP.21"
    ::= { stpEventObjects21 1 }

stp21_bridge_instance OBJECT-TYPE
    SYNTAX Integer32
    MAX-ACCESS accessible-for-notify
    STATUS current
    DESCRIPTION
        "Parameter 'bridge_instance' in event STP.21"
    ::= { stpEventObjects21 2 }

stp21_bridge_port OBJECT-TYPE
    SYNTAX Integer32
    MAX-ACCESS accessible-for-notify
    STATUS current
    DESCRIPTION
        "Parameter 'bridge_port' in event STP.21"
    ::= { stpEventObjects21 3 }

stp21_interface OBJECT-TYPE
    SYNTAX DisplayString
    MAX-ACCESS accessible-for-notify
    STATUS current
    DESCRIPTION
        "Parameter 'interface' in event STP.21"
    ::= { stpEventObjects21 4 }

stp21_circuit_name OBJECT-TYPE
    SYNTAX DisplayString
    MAX-ACCESS accessible-for-notify
    STATUS current
    DESCRIPTION
        "Parameter 'circuit_name' in event STP.21"
    ::= { stpEventObjects21 5 }

stpEventObjects22 OBJECT-IDENTITY
    STATUS current
    DESCRIPTION
        "Event STP.22
        The hello timer has expired on this port. Configuration BPDUs will be
        sent on all ports."
    ::= { stpEventsGroup 22 }

stp22_bridge_type OBJECT-TYPE
    SYNTAX DisplayString
    MAX-ACCESS accessible-for-notify
    STATUS current
    DESCRIPTION
        "Parameter 'bridge_type' in event STP.22"
    ::= { stpEventObjects22 1 }

stp22_bridge_instance OBJECT-TYPE
    SYNTAX Integer32
    MAX-ACCESS accessible-for-notify
    STATUS current
    DESCRIPTION
        "Parameter 'bridge_instance' in event STP.22"
    ::= { stpEventObjects22 2 }

stpEventObjects23 OBJECT-IDENTITY
    STATUS current
    DESCRIPTION
        "Event STP.23
        Stopping the message age timer on this port because it is
        the designated port on its LAN."
    ::= { stpEventsGroup 23 }

stp23_bridge_type OBJECT-TYPE
    SYNTAX DisplayString
    MAX-ACCESS accessible-for-notify
    STATUS current
    DESCRIPTION
        "Parameter 'bridge_type' in event STP.23"
    ::= { stpEventObjects23 1 }

stp23_bridge_instance OBJECT-TYPE
    SYNTAX Integer32
    MAX-ACCESS accessible-for-notify
    STATUS current
    DESCRIPTION
        "Parameter 'bridge_instance' in event STP.23"
    ::= { stpEventObjects23 2 }

stp23_bridge_port OBJECT-TYPE
    SYNTAX Integer32
    MAX-ACCESS accessible-for-notify
    STATUS current
    DESCRIPTION
        "Parameter 'bridge_port' in event STP.23"
    ::= { stpEventObjects23 3 }

stp23_interface OBJECT-TYPE
    SYNTAX DisplayString
    MAX-ACCESS accessible-for-notify
    STATUS current
    DESCRIPTION
        "Parameter 'interface' in event STP.23"
    ::= { stpEventObjects23 4 }

stp23_circuit_name OBJECT-TYPE
    SYNTAX DisplayString
    MAX-ACCESS accessible-for-notify
    STATUS current
    DESCRIPTION
        "Parameter 'circuit_name' in event STP.23"
    ::= { stpEventObjects23 5 }

stpEventObjects24 OBJECT-IDENTITY
    STATUS current
    DESCRIPTION
        "Event STP.24
        This bridge has just decided that it is no longer the root bridge of
        the spanning tree. The hello timer will also be cancelled."
    ::= { stpEventsGroup 24 }

stp24_bridge_type OBJECT-TYPE
    SYNTAX DisplayString
    MAX-ACCESS accessible-for-notify
    STATUS current
    DESCRIPTION
        "Parameter 'bridge_type' in event STP.24"
    ::= { stpEventObjects24 1 }

stp24_bridge_instance OBJECT-TYPE
    SYNTAX Integer32
    MAX-ACCESS accessible-for-notify
    STATUS current
    DESCRIPTION
        "Parameter 'bridge_instance' in event STP.24"
    ::= { stpEventObjects24 2 }

stpEventObjects25 OBJECT-IDENTITY
    STATUS current
    DESCRIPTION
        "Event STP.25
        Stopping the topology change timer because this bridge is no longer
        the root."
    ::= { stpEventsGroup 25 }

stp25_bridge_type OBJECT-TYPE
    SYNTAX DisplayString
    MAX-ACCESS accessible-for-notify
    STATUS current
    DESCRIPTION
        "Parameter 'bridge_type' in event STP.25"
    ::= { stpEventObjects25 1 }

stp25_bridge_instance OBJECT-TYPE
    SYNTAX Integer32
    MAX-ACCESS accessible-for-notify
    STATUS current
    DESCRIPTION
        "Parameter 'bridge_instance' in event STP.25"
    ::= { stpEventObjects25 2 }

stpEventObjects26 OBJECT-IDENTITY
    STATUS current
    DESCRIPTION
        "Event STP.26
        This bridge has just decided that it is the root bridge of
        the spanning tree. The hello timer will be started."
    ::= { stpEventsGroup 26 }

stp26_bridge_type OBJECT-TYPE
    SYNTAX DisplayString
    MAX-ACCESS accessible-for-notify
    STATUS current
    DESCRIPTION
        "Parameter 'bridge_type' in event STP.26"
    ::= { stpEventObjects26 1 }

stp26_bridge_instance OBJECT-TYPE
    SYNTAX Integer32
    MAX-ACCESS accessible-for-notify
    STATUS current
    DESCRIPTION
        "Parameter 'bridge_instance' in event STP.26"
    ::= { stpEventObjects26 2 }

stpEventObjects27 OBJECT-IDENTITY
    STATUS current
    DESCRIPTION
        "Event STP.27
        Starting the message age timer on this port."
    ::= { stpEventsGroup 27 }

stp27_bridge_type OBJECT-TYPE
    SYNTAX DisplayString
    MAX-ACCESS accessible-for-notify
    STATUS current
    DESCRIPTION
        "Parameter 'bridge_type' in event STP.27"
    ::= { stpEventObjects27 1 }

stp27_bridge_instance OBJECT-TYPE
    SYNTAX Integer32
    MAX-ACCESS accessible-for-notify
    STATUS current
    DESCRIPTION
        "Parameter 'bridge_instance' in event STP.27"
    ::= { stpEventObjects27 2 }

stp27_bridge_port OBJECT-TYPE
    SYNTAX Integer32
    MAX-ACCESS accessible-for-notify
    STATUS current
    DESCRIPTION
        "Parameter 'bridge_port' in event STP.27"
    ::= { stpEventObjects27 3 }

stp27_interface OBJECT-TYPE
    SYNTAX DisplayString
    MAX-ACCESS accessible-for-notify
    STATUS current
    DESCRIPTION
        "Parameter 'interface' in event STP.27"
    ::= { stpEventObjects27 4 }

stp27_circuit_name OBJECT-TYPE
    SYNTAX DisplayString
    MAX-ACCESS accessible-for-notify
    STATUS current
    DESCRIPTION
        "Parameter 'circuit_name' in event STP.27"
    ::= { stpEventObjects27 5 }

stpEventObjects28 OBJECT-IDENTITY
    STATUS current
    DESCRIPTION
        "Event STP.28
        This bridge is attempting to become the root bridge of
        the spanning tree. The hello timer will be started."
    ::= { stpEventsGroup 28 }

stp28_bridge_type OBJECT-TYPE
    SYNTAX DisplayString
    MAX-ACCESS accessible-for-notify
    STATUS current
    DESCRIPTION
        "Parameter 'bridge_type' in event STP.28"
    ::= { stpEventObjects28 1 }

stp28_bridge_instance OBJECT-TYPE
    SYNTAX Integer32
    MAX-ACCESS accessible-for-notify
    STATUS current
    DESCRIPTION
        "Parameter 'bridge_instance' in event STP.28"
    ::= { stpEventObjects28 2 }

stpEventObjects29 OBJECT-IDENTITY
    STATUS current
    DESCRIPTION
        "Event STP.29
        A configuration BPDU has been received from the specified MAC address,
        but the port is not participating in the Spanning Tree Protocol."
    ::= { stpEventsGroup 29 }

stp29_source_address OBJECT-TYPE
    SYNTAX DisplayString
    MAX-ACCESS accessible-for-notify
    STATUS current
    DESCRIPTION
        "Parameter 'source_address' in event STP.29"
    ::= { stpEventObjects29 1 }

stp29_bridge_type OBJECT-TYPE
    SYNTAX DisplayString
    MAX-ACCESS accessible-for-notify
    STATUS current
    DESCRIPTION
        "Parameter 'bridge_type' in event STP.29"
    ::= { stpEventObjects29 2 }

stp29_bridge_instance OBJECT-TYPE
    SYNTAX Integer32
    MAX-ACCESS accessible-for-notify
    STATUS current
    DESCRIPTION
        "Parameter 'bridge_instance' in event STP.29"
    ::= { stpEventObjects29 3 }

stp29_bridge_port OBJECT-TYPE
    SYNTAX Integer32
    MAX-ACCESS accessible-for-notify
    STATUS current
    DESCRIPTION
        "Parameter 'bridge_port' in event STP.29"
    ::= { stpEventObjects29 4 }

stp29_interface OBJECT-TYPE
    SYNTAX DisplayString
    MAX-ACCESS accessible-for-notify
    STATUS current
    DESCRIPTION
        "Parameter 'interface' in event STP.29"
    ::= { stpEventObjects29 5 }

stp29_circuit_name OBJECT-TYPE
    SYNTAX DisplayString
    MAX-ACCESS accessible-for-notify
    STATUS current
    DESCRIPTION
        "Parameter 'circuit_name' in event STP.29"
    ::= { stpEventObjects29 6 }

stpEventObjects30 OBJECT-IDENTITY
    STATUS current
    DESCRIPTION
        "Event STP.30
        A topology change notification BPDU has been received from
        the specified MAC address, but the port is not participating in
        the Spanning Tree Protocol."
    ::= { stpEventsGroup 30 }

stp30_source_address OBJECT-TYPE
    SYNTAX DisplayString
    MAX-ACCESS accessible-for-notify
    STATUS current
    DESCRIPTION
        "Parameter 'source_address' in event STP.30"
    ::= { stpEventObjects30 1 }

stp30_bridge_type OBJECT-TYPE
    SYNTAX DisplayString
    MAX-ACCESS accessible-for-notify
    STATUS current
    DESCRIPTION
        "Parameter 'bridge_type' in event STP.30"
    ::= { stpEventObjects30 2 }

stp30_bridge_instance OBJECT-TYPE
    SYNTAX Integer32
    MAX-ACCESS accessible-for-notify
    STATUS current
    DESCRIPTION
        "Parameter 'bridge_instance' in event STP.30"
    ::= { stpEventObjects30 3 }

stp30_bridge_port OBJECT-TYPE
    SYNTAX Integer32
    MAX-ACCESS accessible-for-notify
    STATUS current
    DESCRIPTION
        "Parameter 'bridge_port' in event STP.30"
    ::= { stpEventObjects30 4 }

stp30_interface OBJECT-TYPE
    SYNTAX DisplayString
    MAX-ACCESS accessible-for-notify
    STATUS current
    DESCRIPTION
        "Parameter 'interface' in event STP.30"
    ::= { stpEventObjects30 5 }

stp30_circuit_name OBJECT-TYPE
    SYNTAX DisplayString
    MAX-ACCESS accessible-for-notify
    STATUS current
    DESCRIPTION
        "Parameter 'circuit_name' in event STP.30"
    ::= { stpEventObjects30 6 }

stpEventObjects31 OBJECT-IDENTITY
    STATUS current
    DESCRIPTION
        "Event STP.31
        This bridge is declaring itself the designated port on the LAN connected
        to this port."
    ::= { stpEventsGroup 31 }

stp31_bridge_type OBJECT-TYPE
    SYNTAX DisplayString
    MAX-ACCESS accessible-for-notify
    STATUS current
    DESCRIPTION
        "Parameter 'bridge_type' in event STP.31"
    ::= { stpEventObjects31 1 }

stp31_bridge_instance OBJECT-TYPE
    SYNTAX Integer32
    MAX-ACCESS accessible-for-notify
    STATUS current
    DESCRIPTION
        "Parameter 'bridge_instance' in event STP.31"
    ::= { stpEventObjects31 2 }

stp31_bridge_port OBJECT-TYPE
    SYNTAX Integer32
    MAX-ACCESS accessible-for-notify
    STATUS current
    DESCRIPTION
        "Parameter 'bridge_port' in event STP.31"
    ::= { stpEventObjects31 3 }

stp31_interface OBJECT-TYPE
    SYNTAX DisplayString
    MAX-ACCESS accessible-for-notify
    STATUS current
    DESCRIPTION
        "Parameter 'interface' in event STP.31"
    ::= { stpEventObjects31 4 }

stp31_circuit_name OBJECT-TYPE
    SYNTAX DisplayString
    MAX-ACCESS accessible-for-notify
    STATUS current
    DESCRIPTION
        "Parameter 'circuit_name' in event STP.31"
    ::= { stpEventObjects31 5 }

stpEventObjects32 OBJECT-IDENTITY
    STATUS current
    DESCRIPTION
        "Event STP.32
        A Source Route Bridge BPDU or IEEE802.1D BPDU has been received,
        but the port is not participating in the SRB or IEEE802.1D Spanning
        Tree Protocol."
    ::= { stpEventsGroup 32 }

stp32_bpdu_type OBJECT-TYPE
    SYNTAX DisplayString
    MAX-ACCESS accessible-for-notify
    STATUS current
    DESCRIPTION
        "Parameter 'bpdu_type' in event STP.32"
    ::= { stpEventObjects32 1 }

stp32_bridge_port OBJECT-TYPE
    SYNTAX Integer32
    MAX-ACCESS accessible-for-notify
    STATUS current
    DESCRIPTION
        "Parameter 'bridge_port' in event STP.32"
    ::= { stpEventObjects32 2 }

stp32_interface OBJECT-TYPE
    SYNTAX DisplayString
    MAX-ACCESS accessible-for-notify
    STATUS current
    DESCRIPTION
        "Parameter 'interface' in event STP.32"
    ::= { stpEventObjects32 3 }

stp32_circuit_name OBJECT-TYPE
    SYNTAX DisplayString
    MAX-ACCESS accessible-for-notify
    STATUS current
    DESCRIPTION
        "Parameter 'circuit_name' in event STP.32"
    ::= { stpEventObjects32 4 }

stpEventObjects33 OBJECT-IDENTITY
    STATUS current
    DESCRIPTION
        "Event STP.33
        A BPDU has been received which is less than the minimum size needed
        in length. It will be ignored."
    ::= { stpEventsGroup 33 }

stp33_bpdu_type OBJECT-TYPE
    SYNTAX DisplayString
    MAX-ACCESS accessible-for-notify
    STATUS current
    DESCRIPTION
        "Parameter 'bpdu_type' in event STP.33"
    ::= { stpEventObjects33 1 }

stp33_length OBJECT-TYPE
    SYNTAX Integer32
    MAX-ACCESS accessible-for-notify
    STATUS current
    DESCRIPTION
        "Parameter 'length' in event STP.33"
    ::= { stpEventObjects33 2 }

stp33_source_address OBJECT-TYPE
    SYNTAX DisplayString
    MAX-ACCESS accessible-for-notify
    STATUS current
    DESCRIPTION
        "Parameter 'source_address' in event STP.33"
    ::= { stpEventObjects33 3 }

stp33_bridge_type OBJECT-TYPE
    SYNTAX DisplayString
    MAX-ACCESS accessible-for-notify
    STATUS current
    DESCRIPTION
        "Parameter 'bridge_type' in event STP.33"
    ::= { stpEventObjects33 4 }

stp33_bridge_instance OBJECT-TYPE
    SYNTAX Integer32
    MAX-ACCESS accessible-for-notify
    STATUS current
    DESCRIPTION
        "Parameter 'bridge_instance' in event STP.33"
    ::= { stpEventObjects33 5 }

stp33_bridge_port OBJECT-TYPE
    SYNTAX Integer32
    MAX-ACCESS accessible-for-notify
    STATUS current
    DESCRIPTION
        "Parameter 'bridge_port' in event STP.33"
    ::= { stpEventObjects33 6 }

stp33_interface OBJECT-TYPE
    SYNTAX DisplayString
    MAX-ACCESS accessible-for-notify
    STATUS current
    DESCRIPTION
        "Parameter 'interface' in event STP.33"
    ::= { stpEventObjects33 7 }

stp33_circuit_name OBJECT-TYPE
    SYNTAX DisplayString
    MAX-ACCESS accessible-for-notify
    STATUS current
    DESCRIPTION
        "Parameter 'circuit_name' in event STP.33"
    ::= { stpEventObjects33 8 }

stpEventObjects34 OBJECT-IDENTITY
    STATUS current
    DESCRIPTION
        "Event STP.34
        A BPDU has been received which is less than 4 bytes in length.
        It will be ignored."
    ::= { stpEventsGroup 34 }

stp34_length OBJECT-TYPE
    SYNTAX Integer32
    MAX-ACCESS accessible-for-notify
    STATUS current
    DESCRIPTION
        "Parameter 'length' in event STP.34"
    ::= { stpEventObjects34 1 }

stp34_source_address OBJECT-TYPE
    SYNTAX DisplayString
    MAX-ACCESS accessible-for-notify
    STATUS current
    DESCRIPTION
        "Parameter 'source_address' in event STP.34"
    ::= { stpEventObjects34 2 }

stp34_bridge_type OBJECT-TYPE
    SYNTAX DisplayString
    MAX-ACCESS accessible-for-notify
    STATUS current
    DESCRIPTION
        "Parameter 'bridge_type' in event STP.34"
    ::= { stpEventObjects34 3 }

stp34_bridge_instance OBJECT-TYPE
    SYNTAX Integer32
    MAX-ACCESS accessible-for-notify
    STATUS current
    DESCRIPTION
        "Parameter 'bridge_instance' in event STP.34"
    ::= { stpEventObjects34 4 }

stp34_bridge_port OBJECT-TYPE
    SYNTAX Integer32
    MAX-ACCESS accessible-for-notify
    STATUS current
    DESCRIPTION
        "Parameter 'bridge_port' in event STP.34"
    ::= { stpEventObjects34 5 }

stp34_interface OBJECT-TYPE
    SYNTAX DisplayString
    MAX-ACCESS accessible-for-notify
    STATUS current
    DESCRIPTION
        "Parameter 'interface' in event STP.34"
    ::= { stpEventObjects34 6 }

stp34_circuit_name OBJECT-TYPE
    SYNTAX DisplayString
    MAX-ACCESS accessible-for-notify
    STATUS current
    DESCRIPTION
        "Parameter 'circuit_name' in event STP.34"
    ::= { stpEventObjects34 7 }

stpEventObjects35 OBJECT-IDENTITY
    STATUS current
    DESCRIPTION
        "Event STP.35
        A BPDU has been received with a message age that is not less than its
        max age parameter. It will be ignored."
    ::= { stpEventsGroup 35 }

stp35_bpdu_type OBJECT-TYPE
    SYNTAX DisplayString
    MAX-ACCESS accessible-for-notify
    STATUS current
    DESCRIPTION
        "Parameter 'bpdu_type' in event STP.35"
    ::= { stpEventObjects35 1 }

stp35_msg_age_sc OBJECT-TYPE
    SYNTAX Integer32
    MAX-ACCESS accessible-for-notify
    STATUS current
    DESCRIPTION
        "Parameter 'msg_age_sc' in event STP.35"
    ::= { stpEventObjects35 2 }

stp35_msg_age_fr OBJECT-TYPE
    SYNTAX Integer32
    MAX-ACCESS accessible-for-notify
    STATUS current
    DESCRIPTION
        "Parameter 'msg_age_fr' in event STP.35"
    ::= { stpEventObjects35 3 }

stp35_max_age_sc OBJECT-TYPE
    SYNTAX Integer32
    MAX-ACCESS accessible-for-notify
    STATUS current
    DESCRIPTION
        "Parameter 'max_age_sc' in event STP.35"
    ::= { stpEventObjects35 4 }

stp35_max_age_fr OBJECT-TYPE
    SYNTAX Integer32
    MAX-ACCESS accessible-for-notify
    STATUS current
    DESCRIPTION
        "Parameter 'max_age_fr' in event STP.35"
    ::= { stpEventObjects35 5 }

stp35_source_address OBJECT-TYPE
    SYNTAX DisplayString
    MAX-ACCESS accessible-for-notify
    STATUS current
    DESCRIPTION
        "Parameter 'source_address' in event STP.35"
    ::= { stpEventObjects35 6 }

stp35_bridge_type OBJECT-TYPE
    SYNTAX DisplayString
    MAX-ACCESS accessible-for-notify
    STATUS current
    DESCRIPTION
        "Parameter 'bridge_type' in event STP.35"
    ::= { stpEventObjects35 7 }

stp35_bridge_instance OBJECT-TYPE
    SYNTAX Integer32
    MAX-ACCESS accessible-for-notify
    STATUS current
    DESCRIPTION
        "Parameter 'bridge_instance' in event STP.35"
    ::= { stpEventObjects35 8 }

stp35_bridge_port OBJECT-TYPE
    SYNTAX Integer32
    MAX-ACCESS accessible-for-notify
    STATUS current
    DESCRIPTION
        "Parameter 'bridge_port' in event STP.35"
    ::= { stpEventObjects35 9 }

stp35_interface OBJECT-TYPE
    SYNTAX DisplayString
    MAX-ACCESS accessible-for-notify
    STATUS current
    DESCRIPTION
        "Parameter 'interface' in event STP.35"
    ::= { stpEventObjects35 10 }

stp35_circuit_name OBJECT-TYPE
    SYNTAX DisplayString
    MAX-ACCESS accessible-for-notify
    STATUS current
    DESCRIPTION
        "Parameter 'circuit_name' in event STP.35"
    ::= { stpEventObjects35 11 }

stpEventObjects36 OBJECT-IDENTITY
    STATUS current
    DESCRIPTION
        "Event STP.36
        A BPDU has been received with a Bridge Identifier and Port Identifier
        that match the values that would be transmitted in a BPDU from the
        port. It will be ignored."
    ::= { stpEventsGroup 36 }

stp36_bpdu_type OBJECT-TYPE
    SYNTAX DisplayString
    MAX-ACCESS accessible-for-notify
    STATUS current
    DESCRIPTION
        "Parameter 'bpdu_type' in event STP.36"
    ::= { stpEventObjects36 1 }

stp36_source_address OBJECT-TYPE
    SYNTAX DisplayString
    MAX-ACCESS accessible-for-notify
    STATUS current
    DESCRIPTION
        "Parameter 'source_address' in event STP.36"
    ::= { stpEventObjects36 2 }

stp36_bridge_type OBJECT-TYPE
    SYNTAX DisplayString
    MAX-ACCESS accessible-for-notify
    STATUS current
    DESCRIPTION
        "Parameter 'bridge_type' in event STP.36"
    ::= { stpEventObjects36 3 }

stp36_bridge_instance OBJECT-TYPE
    SYNTAX Integer32
    MAX-ACCESS accessible-for-notify
    STATUS current
    DESCRIPTION
        "Parameter 'bridge_instance' in event STP.36"
    ::= { stpEventObjects36 4 }

stp36_bridge_port OBJECT-TYPE
    SYNTAX Integer32
    MAX-ACCESS accessible-for-notify
    STATUS current
    DESCRIPTION
        "Parameter 'bridge_port' in event STP.36"
    ::= { stpEventObjects36 5 }

stp36_interface OBJECT-TYPE
    SYNTAX DisplayString
    MAX-ACCESS accessible-for-notify
    STATUS current
    DESCRIPTION
        "Parameter 'interface' in event STP.36"
    ::= { stpEventObjects36 6 }

stp36_circuit_name OBJECT-TYPE
    SYNTAX DisplayString
    MAX-ACCESS accessible-for-notify
    STATUS current
    DESCRIPTION
        "Parameter 'circuit_name' in event STP.36"
    ::= { stpEventObjects36 7 }

stpEventObjects37 OBJECT-IDENTITY
    STATUS current
    DESCRIPTION
        "Event STP.37
        A BPDU has been received from the specified MAC address."
    ::= { stpEventsGroup 37 }

stp37_bpdu_type OBJECT-TYPE
    SYNTAX DisplayString
    MAX-ACCESS accessible-for-notify
    STATUS current
    DESCRIPTION
        "Parameter 'bpdu_type' in event STP.37"
    ::= { stpEventObjects37 1 }

stp37_version OBJECT-TYPE
    SYNTAX Integer32
    MAX-ACCESS accessible-for-notify
    STATUS current
    DESCRIPTION
        "Parameter 'version' in event STP.37"
    ::= { stpEventObjects37 2 }

stp37_flags OBJECT-TYPE
    SYNTAX Integer32
    MAX-ACCESS accessible-for-notify
    STATUS current
    DESCRIPTION
        "Parameter 'flags' in event STP.37"
    ::= { stpEventObjects37 3 }

stp37_flags_str OBJECT-TYPE
    SYNTAX DisplayString
    MAX-ACCESS accessible-for-notify
    STATUS current
    DESCRIPTION
        "Parameter 'flags_str' in event STP.37"
    ::= { stpEventObjects37 4 }

stp37_source_address OBJECT-TYPE
    SYNTAX DisplayString
    MAX-ACCESS accessible-for-notify
    STATUS current
    DESCRIPTION
        "Parameter 'source_address' in event STP.37"
    ::= { stpEventObjects37 5 }

stp37_bridge_type OBJECT-TYPE
    SYNTAX DisplayString
    MAX-ACCESS accessible-for-notify
    STATUS current
    DESCRIPTION
        "Parameter 'bridge_type' in event STP.37"
    ::= { stpEventObjects37 6 }

stp37_bridge_instance OBJECT-TYPE
    SYNTAX Integer32
    MAX-ACCESS accessible-for-notify
    STATUS current
    DESCRIPTION
        "Parameter 'bridge_instance' in event STP.37"
    ::= { stpEventObjects37 7 }

stp37_bridge_port OBJECT-TYPE
    SYNTAX Integer32
    MAX-ACCESS accessible-for-notify
    STATUS current
    DESCRIPTION
        "Parameter 'bridge_port' in event STP.37"
    ::= { stpEventObjects37 8 }

stp37_interface OBJECT-TYPE
    SYNTAX DisplayString
    MAX-ACCESS accessible-for-notify
    STATUS current
    DESCRIPTION
        "Parameter 'interface' in event STP.37"
    ::= { stpEventObjects37 9 }

stp37_circuit_name OBJECT-TYPE
    SYNTAX DisplayString
    MAX-ACCESS accessible-for-notify
    STATUS current
    DESCRIPTION
        "Parameter 'circuit_name' in event STP.37"
    ::= { stpEventObjects37 10 }

stpEventObjects38 OBJECT-IDENTITY
    STATUS current
    DESCRIPTION
        "Event STP.38
        A Rapid Spanning Tree BPDU will be sent on the specified port. This is
        done normally on a periodic basis as part of the Spanning Tree Protocol."
    ::= { stpEventsGroup 38 }

stp38_flags OBJECT-TYPE
    SYNTAX Integer32
    MAX-ACCESS accessible-for-notify
    STATUS current
    DESCRIPTION
        "Parameter 'flags' in event STP.38"
    ::= { stpEventObjects38 1 }

stp38_flags_str OBJECT-TYPE
    SYNTAX DisplayString
    MAX-ACCESS accessible-for-notify
    STATUS current
    DESCRIPTION
        "Parameter 'flags_str' in event STP.38"
    ::= { stpEventObjects38 2 }

stp38_bridge_type OBJECT-TYPE
    SYNTAX DisplayString
    MAX-ACCESS accessible-for-notify
    STATUS current
    DESCRIPTION
        "Parameter 'bridge_type' in event STP.38"
    ::= { stpEventObjects38 3 }

stp38_bridge_instance OBJECT-TYPE
    SYNTAX Integer32
    MAX-ACCESS accessible-for-notify
    STATUS current
    DESCRIPTION
        "Parameter 'bridge_instance' in event STP.38"
    ::= { stpEventObjects38 4 }

stp38_bridge_port OBJECT-TYPE
    SYNTAX Integer32
    MAX-ACCESS accessible-for-notify
    STATUS current
    DESCRIPTION
        "Parameter 'bridge_port' in event STP.38"
    ::= { stpEventObjects38 5 }

stp38_interface OBJECT-TYPE
    SYNTAX DisplayString
    MAX-ACCESS accessible-for-notify
    STATUS current
    DESCRIPTION
        "Parameter 'interface' in event STP.38"
    ::= { stpEventObjects38 6 }

stp38_circuit_name OBJECT-TYPE
    SYNTAX DisplayString
    MAX-ACCESS accessible-for-notify
    STATUS current
    DESCRIPTION
        "Parameter 'circuit_name' in event STP.38"
    ::= { stpEventObjects38 7 }

stpEventObjects39 OBJECT-IDENTITY
    STATUS current
    DESCRIPTION
        "Event STP.39
        State change on a port."
    ::= { stpEventsGroup 39 }

stp39_state OBJECT-TYPE
    SYNTAX DisplayString
    MAX-ACCESS accessible-for-notify
    STATUS current
    DESCRIPTION
        "Parameter 'state' in event STP.39"
    ::= { stpEventObjects39 1 }

stp39_bridge_type OBJECT-TYPE
    SYNTAX DisplayString
    MAX-ACCESS accessible-for-notify
    STATUS current
    DESCRIPTION
        "Parameter 'bridge_type' in event STP.39"
    ::= { stpEventObjects39 2 }

stp39_bridge_instance OBJECT-TYPE
    SYNTAX Integer32
    MAX-ACCESS accessible-for-notify
    STATUS current
    DESCRIPTION
        "Parameter 'bridge_instance' in event STP.39"
    ::= { stpEventObjects39 3 }

stp39_bridge_port OBJECT-TYPE
    SYNTAX Integer32
    MAX-ACCESS accessible-for-notify
    STATUS current
    DESCRIPTION
        "Parameter 'bridge_port' in event STP.39"
    ::= { stpEventObjects39 4 }

stp39_interface OBJECT-TYPE
    SYNTAX DisplayString
    MAX-ACCESS accessible-for-notify
    STATUS current
    DESCRIPTION
        "Parameter 'interface' in event STP.39"
    ::= { stpEventObjects39 5 }

stp39_circuit_name OBJECT-TYPE
    SYNTAX DisplayString
    MAX-ACCESS accessible-for-notify
    STATUS current
    DESCRIPTION
        "Parameter 'circuit_name' in event STP.39"
    ::= { stpEventObjects39 6 }

stpEventObjects40 OBJECT-IDENTITY
    STATUS current
    DESCRIPTION
        "Event STP.40
        Role change on a port."
    ::= { stpEventsGroup 40 }

stp40_role OBJECT-TYPE
    SYNTAX DisplayString
    MAX-ACCESS accessible-for-notify
    STATUS current
    DESCRIPTION
        "Parameter 'role' in event STP.40"
    ::= { stpEventObjects40 1 }

stp40_bridge_type OBJECT-TYPE
    SYNTAX DisplayString
    MAX-ACCESS accessible-for-notify
    STATUS current
    DESCRIPTION
        "Parameter 'bridge_type' in event STP.40"
    ::= { stpEventObjects40 2 }

stp40_bridge_instance OBJECT-TYPE
    SYNTAX Integer32
    MAX-ACCESS accessible-for-notify
    STATUS current
    DESCRIPTION
        "Parameter 'bridge_instance' in event STP.40"
    ::= { stpEventObjects40 3 }

stp40_bridge_port OBJECT-TYPE
    SYNTAX Integer32
    MAX-ACCESS accessible-for-notify
    STATUS current
    DESCRIPTION
        "Parameter 'bridge_port' in event STP.40"
    ::= { stpEventObjects40 4 }

stp40_interface OBJECT-TYPE
    SYNTAX DisplayString
    MAX-ACCESS accessible-for-notify
    STATUS current
    DESCRIPTION
        "Parameter 'interface' in event STP.40"
    ::= { stpEventObjects40 5 }

stp40_circuit_name OBJECT-TYPE
    SYNTAX DisplayString
    MAX-ACCESS accessible-for-notify
    STATUS current
    DESCRIPTION
        "Parameter 'circuit_name' in event STP.40"
    ::= { stpEventObjects40 6 }

stpEventObjects41 OBJECT-IDENTITY
    STATUS current
    DESCRIPTION
        "Event STP.41
        Role change on a port."
    ::= { stpEventsGroup 41 }

stp41_root_vector OBJECT-TYPE
    SYNTAX DisplayString
    MAX-ACCESS accessible-for-notify
    STATUS current
    DESCRIPTION
        "Parameter 'root_vector' in event STP.41"
    ::= { stpEventObjects41 1 }

stp41_bridge_type OBJECT-TYPE
    SYNTAX DisplayString
    MAX-ACCESS accessible-for-notify
    STATUS current
    DESCRIPTION
        "Parameter 'bridge_type' in event STP.41"
    ::= { stpEventObjects41 2 }

stp41_bridge_instance OBJECT-TYPE
    SYNTAX Integer32
    MAX-ACCESS accessible-for-notify
    STATUS current
    DESCRIPTION
        "Parameter 'bridge_instance' in event STP.41"
    ::= { stpEventObjects41 3 }

stp41_bridge_port OBJECT-TYPE
    SYNTAX Integer32
    MAX-ACCESS accessible-for-notify
    STATUS current
    DESCRIPTION
        "Parameter 'bridge_port' in event STP.41"
    ::= { stpEventObjects41 4 }

stp41_interface OBJECT-TYPE
    SYNTAX DisplayString
    MAX-ACCESS accessible-for-notify
    STATUS current
    DESCRIPTION
        "Parameter 'interface' in event STP.41"
    ::= { stpEventObjects41 5 }

stp41_circuit_name OBJECT-TYPE
    SYNTAX DisplayString
    MAX-ACCESS accessible-for-notify
    STATUS current
    DESCRIPTION
        "Parameter 'circuit_name' in event STP.41"
    ::= { stpEventObjects41 6 }

stpEventObjects42 OBJECT-IDENTITY
    STATUS current
    DESCRIPTION
        "Event STP.42
        Role change on a port."
    ::= { stpEventsGroup 42 }

stp42_root_vector OBJECT-TYPE
    SYNTAX DisplayString
    MAX-ACCESS accessible-for-notify
    STATUS current
    DESCRIPTION
        "Parameter 'root_vector' in event STP.42"
    ::= { stpEventObjects42 1 }

stp42_bridge_type OBJECT-TYPE
    SYNTAX DisplayString
    MAX-ACCESS accessible-for-notify
    STATUS current
    DESCRIPTION
        "Parameter 'bridge_type' in event STP.42"
    ::= { stpEventObjects42 2 }

stp42_bridge_instance OBJECT-TYPE
    SYNTAX Integer32
    MAX-ACCESS accessible-for-notify
    STATUS current
    DESCRIPTION
        "Parameter 'bridge_instance' in event STP.42"
    ::= { stpEventObjects42 3 }

stp42_bridge_port OBJECT-TYPE
    SYNTAX Integer32
    MAX-ACCESS accessible-for-notify
    STATUS current
    DESCRIPTION
        "Parameter 'bridge_port' in event STP.42"
    ::= { stpEventObjects42 4 }

stp42_interface OBJECT-TYPE
    SYNTAX DisplayString
    MAX-ACCESS accessible-for-notify
    STATUS current
    DESCRIPTION
        "Parameter 'interface' in event STP.42"
    ::= { stpEventObjects42 5 }

stp42_circuit_name OBJECT-TYPE
    SYNTAX DisplayString
    MAX-ACCESS accessible-for-notify
    STATUS current
    DESCRIPTION
        "Parameter 'circuit_name' in event STP.42"
    ::= { stpEventObjects42 6 }

stpEventObjects43 OBJECT-IDENTITY
    STATUS current
    DESCRIPTION
        "Event STP.43
        Received BPDU discarded because BPDU filtering is enabled on a port."
    ::= { stpEventsGroup 43 }

stp43_bridge_id OBJECT-TYPE
    SYNTAX Integer32
    MAX-ACCESS accessible-for-notify
    STATUS current
    DESCRIPTION
        "Parameter 'bridge_id' in event STP.43"
    ::= { stpEventObjects43 1 }

stp43_bridge_port OBJECT-TYPE
    SYNTAX Integer32
    MAX-ACCESS accessible-for-notify
    STATUS current
    DESCRIPTION
        "Parameter 'bridge_port' in event STP.43"
    ::= { stpEventObjects43 2 }

stp43_interface OBJECT-TYPE
    SYNTAX DisplayString
    MAX-ACCESS accessible-for-notify
    STATUS current
    DESCRIPTION
        "Parameter 'interface' in event STP.43"
    ::= { stpEventObjects43 3 }

stp43_circuit_name OBJECT-TYPE
    SYNTAX DisplayString
    MAX-ACCESS accessible-for-notify
    STATUS current
    DESCRIPTION
        "Parameter 'circuit_name' in event STP.43"
    ::= { stpEventObjects43 4 }

stpEventObjects44 OBJECT-IDENTITY
    STATUS current
    DESCRIPTION
        "Event STP.44
        Transmitted BPDU discarded because BPDU filtering is enabled on a port.
        The BPDU is not sent."
    ::= { stpEventsGroup 44 }

stp44_bridge_id OBJECT-TYPE
    SYNTAX Integer32
    MAX-ACCESS accessible-for-notify
    STATUS current
    DESCRIPTION
        "Parameter 'bridge_id' in event STP.44"
    ::= { stpEventObjects44 1 }

stp44_bridge_port OBJECT-TYPE
    SYNTAX Integer32
    MAX-ACCESS accessible-for-notify
    STATUS current
    DESCRIPTION
        "Parameter 'bridge_port' in event STP.44"
    ::= { stpEventObjects44 2 }

stp44_interface OBJECT-TYPE
    SYNTAX DisplayString
    MAX-ACCESS accessible-for-notify
    STATUS current
    DESCRIPTION
        "Parameter 'interface' in event STP.44"
    ::= { stpEventObjects44 3 }

stp44_circuit_name OBJECT-TYPE
    SYNTAX DisplayString
    MAX-ACCESS accessible-for-notify
    STATUS current
    DESCRIPTION
        "Parameter 'circuit_name' in event STP.44"
    ::= { stpEventObjects44 4 }

stpEventObjects45 OBJECT-IDENTITY
    STATUS current
    DESCRIPTION
        "Event STP.45
        Received BPDU on port with BPDU Guard enabled. The port is disabled"
    ::= { stpEventsGroup 45 }

stp45_bridge_id OBJECT-TYPE
    SYNTAX Integer32
    MAX-ACCESS accessible-for-notify
    STATUS current
    DESCRIPTION
        "Parameter 'bridge_id' in event STP.45"
    ::= { stpEventObjects45 1 }

stp45_bridge_port OBJECT-TYPE
    SYNTAX Integer32
    MAX-ACCESS accessible-for-notify
    STATUS current
    DESCRIPTION
        "Parameter 'bridge_port' in event STP.45"
    ::= { stpEventObjects45 2 }

stp45_interface OBJECT-TYPE
    SYNTAX DisplayString
    MAX-ACCESS accessible-for-notify
    STATUS current
    DESCRIPTION
        "Parameter 'interface' in event STP.45"
    ::= { stpEventObjects45 3 }

stp45_circuit_name OBJECT-TYPE
    SYNTAX DisplayString
    MAX-ACCESS accessible-for-notify
    STATUS current
    DESCRIPTION
        "Parameter 'circuit_name' in event STP.45"
    ::= { stpEventObjects45 4 }

stpEventObjects46 OBJECT-IDENTITY
    STATUS current
    DESCRIPTION
        "Event STP.46
        Received PVST+ BPDU with inconsistent VID. The VID conveyed in the
        BPDU does not match the VID assigned to the frame"
    ::= { stpEventsGroup 46 }

stp46_VID OBJECT-TYPE
    SYNTAX Integer32
    MAX-ACCESS accessible-for-notify
    STATUS current
    DESCRIPTION
        "Parameter 'VID' in event STP.46"
    ::= { stpEventObjects46 1 }

stp46_VID2 OBJECT-TYPE
    SYNTAX Integer32
    MAX-ACCESS accessible-for-notify
    STATUS current
    DESCRIPTION
        "Parameter 'VID2' in event STP.46"
    ::= { stpEventObjects46 2 }

stp46_source_address OBJECT-TYPE
    SYNTAX DisplayString
    MAX-ACCESS accessible-for-notify
    STATUS current
    DESCRIPTION
        "Parameter 'source_address' in event STP.46"
    ::= { stpEventObjects46 3 }

stp46_bridge_id OBJECT-TYPE
    SYNTAX Integer32
    MAX-ACCESS accessible-for-notify
    STATUS current
    DESCRIPTION
        "Parameter 'bridge_id' in event STP.46"
    ::= { stpEventObjects46 4 }

stp46_bridge_port OBJECT-TYPE
    SYNTAX Integer32
    MAX-ACCESS accessible-for-notify
    STATUS current
    DESCRIPTION
        "Parameter 'bridge_port' in event STP.46"
    ::= { stpEventObjects46 5 }

stp46_interface OBJECT-TYPE
    SYNTAX DisplayString
    MAX-ACCESS accessible-for-notify
    STATUS current
    DESCRIPTION
        "Parameter 'interface' in event STP.46"
    ::= { stpEventObjects46 6 }

stp46_circuit_name OBJECT-TYPE
    SYNTAX DisplayString
    MAX-ACCESS accessible-for-notify
    STATUS current
    DESCRIPTION
        "Parameter 'circuit_name' in event STP.46"
    ::= { stpEventObjects46 7 }

stpEventObjects47 OBJECT-IDENTITY
    STATUS current
    DESCRIPTION
        "Event STP.47
        Received malformed PVST+ BPDU"
    ::= { stpEventsGroup 47 }

stp47_VID OBJECT-TYPE
    SYNTAX Integer32
    MAX-ACCESS accessible-for-notify
    STATUS current
    DESCRIPTION
        "Parameter 'VID' in event STP.47"
    ::= { stpEventObjects47 1 }

stp47_source_address OBJECT-TYPE
    SYNTAX DisplayString
    MAX-ACCESS accessible-for-notify
    STATUS current
    DESCRIPTION
        "Parameter 'source_address' in event STP.47"
    ::= { stpEventObjects47 2 }

stp47_bridge_id OBJECT-TYPE
    SYNTAX Integer32
    MAX-ACCESS accessible-for-notify
    STATUS current
    DESCRIPTION
        "Parameter 'bridge_id' in event STP.47"
    ::= { stpEventObjects47 3 }

stp47_bridge_port OBJECT-TYPE
    SYNTAX Integer32
    MAX-ACCESS accessible-for-notify
    STATUS current
    DESCRIPTION
        "Parameter 'bridge_port' in event STP.47"
    ::= { stpEventObjects47 4 }

stp47_interface OBJECT-TYPE
    SYNTAX DisplayString
    MAX-ACCESS accessible-for-notify
    STATUS current
    DESCRIPTION
        "Parameter 'interface' in event STP.47"
    ::= { stpEventObjects47 5 }

stp47_circuit_name OBJECT-TYPE
    SYNTAX DisplayString
    MAX-ACCESS accessible-for-notify
    STATUS current
    DESCRIPTION
        "Parameter 'circuit_name' in event STP.47"
    ::= { stpEventObjects47 6 }

stpEventObjects48 OBJECT-IDENTITY
    STATUS current
    DESCRIPTION
        "Event STP.48
        PVST+ BPDU conveying VLAN 1 received. Silently discarded, since
        the common BPDU is used instead"
    ::= { stpEventsGroup 48 }

stp48_bpdu_type OBJECT-TYPE
    SYNTAX DisplayString
    MAX-ACCESS accessible-for-notify
    STATUS current
    DESCRIPTION
        "Parameter 'bpdu_type' in event STP.48"
    ::= { stpEventObjects48 1 }

stp48_source_address OBJECT-TYPE
    SYNTAX DisplayString
    MAX-ACCESS accessible-for-notify
    STATUS current
    DESCRIPTION
        "Parameter 'source_address' in event STP.48"
    ::= { stpEventObjects48 2 }

stp48_bridge_id OBJECT-TYPE
    SYNTAX Integer32
    MAX-ACCESS accessible-for-notify
    STATUS current
    DESCRIPTION
        "Parameter 'bridge_id' in event STP.48"
    ::= { stpEventObjects48 3 }

stp48_bridge_port OBJECT-TYPE
    SYNTAX Integer32
    MAX-ACCESS accessible-for-notify
    STATUS current
    DESCRIPTION
        "Parameter 'bridge_port' in event STP.48"
    ::= { stpEventObjects48 4 }

stp48_interface OBJECT-TYPE
    SYNTAX DisplayString
    MAX-ACCESS accessible-for-notify
    STATUS current
    DESCRIPTION
        "Parameter 'interface' in event STP.48"
    ::= { stpEventObjects48 5 }

stp48_circuit_name OBJECT-TYPE
    SYNTAX DisplayString
    MAX-ACCESS accessible-for-notify
    STATUS current
    DESCRIPTION
        "Parameter 'circuit_name' in event STP.48"
    ::= { stpEventObjects48 6 }


stpNotification1 NOTIFICATION-TYPE
    OBJECTS { 
              stp1_source_address, 
              stp1_bridge_type,
              stp1_bridge_instance,
              stp1_bridge_port,
              stp1_interface,
              stp1_circuit_name 
            }
    STATUS current
    DESCRIPTION
        "Notification of Event STP.1

        Message: 'Configuration BPDU received frm $1 on $2-$3 port $4, interface $5$6'

        Parameters list:
              $1: stp1_source_address
              $2: stp1_bridge_type
              $3: stp1_bridge_instance
              $4: stp1_bridge_port
              $5: stp1_interface
              $6: stp1_circuit_name

        A configuration BPDU has been received from the specified MAC address."
    ::= { stpNotificationsPrefix 1 }

stpNotification2 NOTIFICATION-TYPE
    OBJECTS { 
              stp2_source_address, 
              stp2_bridge_type,
              stp2_bridge_instance,
              stp2_bridge_port,
              stp2_interface,
              stp2_circuit_name 
            }
    STATUS current
    DESCRIPTION
        "Notification of Event STP.2

        Message: 'Topology change notification BPDU received frm $1 on $2-$3 port $4, interface $5$6'

        Parameters list:
              $1: stp2_source_address
              $2: stp2_bridge_type
              $3: stp2_bridge_instance
              $4: stp2_bridge_port
              $5: stp2_interface
              $6: stp2_circuit_name

        A topology change notification BPDU has been received from
        the specified MAC address."
    ::= { stpNotificationsPrefix 2 }

stpNotification3 NOTIFICATION-TYPE
    OBJECTS { 
              stp3_BDPU_type, 
              stp3_source_address,
              stp3_bridge_type,
              stp3_bridge_instance,
              stp3_bridge_port,
              stp3_interface,
              stp3_circuit_name 
            }
    STATUS current
    DESCRIPTION
        "Notification of Event STP.3

        Message: 'Unkown BPDU type $1 received frm $2 on $3-$4 port $5, interface $6$7'

        Parameters list:
              $1: stp3_BDPU_type
              $2: stp3_source_address
              $3: stp3_bridge_type
              $4: stp3_bridge_instance
              $5: stp3_bridge_port
              $6: stp3_interface
              $7: stp3_circuit_name

        A BPDU with an undefined value in the BPDU Type field was received
        from the specified host. It will be ignored."
    ::= { stpNotificationsPrefix 3 }

stpNotification4 NOTIFICATION-TYPE
    OBJECTS { 
              stp4_Protocol_Identifier, 
              stp4_source_address,
              stp4_bridge_type,
              stp4_bridge_instance,
              stp4_bridge_port,
              stp4_interface,
              stp4_circuit_name 
            }
    STATUS current
    DESCRIPTION
        "Notification of Event STP.4

        Message: 'BPDU bad protocol identifier $1 frm $2 on $3-$4 port $5, interface $6$7'

        Parameters list:
              $1: stp4_Protocol_Identifier
              $2: stp4_source_address
              $3: stp4_bridge_type
              $4: stp4_bridge_instance
              $5: stp4_bridge_port
              $6: stp4_interface
              $7: stp4_circuit_name

        A configuration BPDU has been received with a Protocol Identifier
        that is not 0000. It will be ignored."
    ::= { stpNotificationsPrefix 4 }

stpNotification5 NOTIFICATION-TYPE
    OBJECTS { 
              stp5_Protocol_Version_Identifier, 
              stp5_source_address,
              stp5_bridge_type,
              stp5_bridge_instance,
              stp5_bridge_port,
              stp5_interface,
              stp5_circuit_name 
            }
    STATUS current
    DESCRIPTION
        "Notification of Event STP.5

        Message: 'BPDU bad Version $1 frm $2 on $3-$4 port $5, interface $6$7'

        Parameters list:
              $1: stp5_Protocol_Version_Identifier
              $2: stp5_source_address
              $3: stp5_bridge_type
              $4: stp5_bridge_instance
              $5: stp5_bridge_port
              $6: stp5_interface
              $7: stp5_circuit_name

        A configuration BPDU has been received with a Protocol Version
        Identifier that is not 00. It will be ignored."
    ::= { stpNotificationsPrefix 5 }

stpNotification6 NOTIFICATION-TYPE
    OBJECTS { 
              stp6_length, 
              stp6_source_address,
              stp6_bridge_type,
              stp6_bridge_instance,
              stp6_bridge_port,
              stp6_interface,
              stp6_circuit_name 
            }
    STATUS current
    DESCRIPTION
        "Notification of Event STP.6

        Message: 'Configuration BPDU truncated ($1 bytes) frm $2 on $3-$4 port $5, interface $6$7'

        Parameters list:
              $1: stp6_length
              $2: stp6_source_address
              $3: stp6_bridge_type
              $4: stp6_bridge_instance
              $5: stp6_bridge_port
              $6: stp6_interface
              $7: stp6_circuit_name

        A configuration BPDU has been received which is less than 35 bytes
        in length. It will be ignored."
    ::= { stpNotificationsPrefix 6 }

stpNotification7 NOTIFICATION-TYPE
    OBJECTS { 
              stp7_flags, 
              stp7_source_address,
              stp7_bridge_type,
              stp7_bridge_instance,
              stp7_bridge_port,
              stp7_interface,
              stp7_circuit_name 
            }
    STATUS current
    DESCRIPTION
        "Notification of Event STP.7

        Message: 'Configuration BPDU unknown flags $1 frm $2 on $3-$4 port $5, interface $6$7'

        Parameters list:
              $1: stp7_flags
              $2: stp7_source_address
              $3: stp7_bridge_type
              $4: stp7_bridge_instance
              $5: stp7_bridge_port
              $6: stp7_interface
              $7: stp7_circuit_name

        A configuration BPDU has been received which has undefined bits set
        in the flags field. It will be ignored."
    ::= { stpNotificationsPrefix 7 }

stpNotification8 NOTIFICATION-TYPE
    OBJECTS { 
              stp8_length, 
              stp8_source_address,
              stp8_bridge_type,
              stp8_bridge_instance,
              stp8_bridge_port,
              stp8_interface,
              stp8_circuit_name 
            }
    STATUS current
    DESCRIPTION
        "Notification of Event STP.8

        Message: 'Toplogy change notification BPDU tuncated ($1 bytes) frm $2 on $3-$4 port $5, interface $6$7'

        Parameters list:
              $1: stp8_length
              $2: stp8_source_address
              $3: stp8_bridge_type
              $4: stp8_bridge_instance
              $5: stp8_bridge_port
              $6: stp8_interface
              $7: stp8_circuit_name

        A topology change notificaton BPDU has been received that is less than
        4 bytes in length. It will be ignored."
    ::= { stpNotificationsPrefix 8 }

stpNotification9 NOTIFICATION-TYPE
    OBJECTS { 
              stp9_bridge_type, 
              stp9_bridge_instance,
              stp9_bridge_port,
              stp9_interface,
              stp9_circuit_name 
            }
    STATUS current
    DESCRIPTION
        "Notification of Event STP.9

        Message: 'No buffer to send BDPU on $1-$2 port $3, interface $4$5'

        Parameters list:
              $1: stp9_bridge_type
              $2: stp9_bridge_instance
              $3: stp9_bridge_port
              $4: stp9_interface
              $5: stp9_circuit_name

        No packet buffer was available to construct and send a BDPU on the
        specified port."
    ::= { stpNotificationsPrefix 9 }

stpNotification10 NOTIFICATION-TYPE
    OBJECTS { 
              stp10_bridge_type, 
              stp10_bridge_instance,
              stp10_bridge_port,
              stp10_interface,
              stp10_circuit_name 
            }
    STATUS current
    DESCRIPTION
        "Notification of Event STP.10

        Message: 'Sending Configuration BPDU on $1-$2 port $3, interface $4$5'

        Parameters list:
              $1: stp10_bridge_type
              $2: stp10_bridge_instance
              $3: stp10_bridge_port
              $4: stp10_interface
              $5: stp10_circuit_name

        A Configuration BPDU will be sent on the specified port.
        This is done normally on a periodic basis as part of the
        Spanning Tree Protocol.
        The flags field in this BPDU is zero, e.g., neither the Topology Change
        or the Topology Change Acknowledgement bits are set."
    ::= { stpNotificationsPrefix 10 }

stpNotification11 NOTIFICATION-TYPE
    OBJECTS { 
              stp11_TC, 
              stp11_TCA,
              stp11_bridge_type,
              stp11_bridge_instance,
              stp11_bridge_port,
              stp11_interface,
              stp11_circuit_name 
            }
    STATUS current
    DESCRIPTION
        "Notification of Event STP.11

        Message: 'Sending Configuration BPDU with flags $1 $2 on $3-$4 port $5, interface $6$7'

        Parameters list:
              $1: stp11_TC
              $2: stp11_TCA
              $3: stp11_bridge_type
              $4: stp11_bridge_instance
              $5: stp11_bridge_port
              $6: stp11_interface
              $7: stp11_circuit_name

        A Configuration BPDU will be sent on the specified port.
        This is done normally on a periodic basis as part of the
        Spanning Tree Protocol. TC will be displayed if the Topology Change bit
        is set in the Flags byte of the BPDU, TCA will be displayed if
        the Topology Change Acknowledge bit is set in the Flags byte."
    ::= { stpNotificationsPrefix 11 }

stpNotification12 NOTIFICATION-TYPE
    OBJECTS { 
              stp12_bridge_type, 
              stp12_bridge_instance,
              stp12_bridge_port,
              stp12_interface,
              stp12_circuit_name 
            }
    STATUS current
    DESCRIPTION
        "Notification of Event STP.12

        Message: 'Sending Topology Change Notification BPDU on $1-$2 port $3, interface $4$5'

        Parameters list:
              $1: stp12_bridge_type
              $2: stp12_bridge_instance
              $3: stp12_bridge_port
              $4: stp12_interface
              $5: stp12_circuit_name

        A Topology Change Notification BPDU will be sent on the specified port.
        These are sent on the root port of non-root ports when they detect
        a topology change in the spanning tree."
    ::= { stpNotificationsPrefix 12 }

stpNotification13 NOTIFICATION-TYPE
    OBJECTS { 
              stp13_reason_code, 
              stp13_bridge_type,
              stp13_bridge_instance,
              stp13_bridge_port,
              stp13_interface,
              stp13_circuit_name 
            }
    STATUS current
    DESCRIPTION
        "Notification of Event STP.13

        Message: 'BPDU send failed for reason code $1 on $2-$3 port $4, interface $5$6'

        Parameters list:
              $1: stp13_reason_code
              $2: stp13_bridge_type
              $3: stp13_bridge_instance
              $4: stp13_bridge_port
              $5: stp13_interface
              $6: stp13_circuit_name

        The attempt to queue a BPDU for transmission on the specified port
        failed."
    ::= { stpNotificationsPrefix 13 }

stpNotification14 NOTIFICATION-TYPE
    OBJECTS { 
              stp14_bridge_type, 
              stp14_bridge_instance,
              stp14_bridge_port,
              stp14_interface,
              stp14_circuit_name 
            }
    STATUS current
    DESCRIPTION
        "Notification of Event STP.14

        Message: 'Blocking $1-$2 port $3, interface $4$5, detecting topology change'

        Parameters list:
              $1: stp14_bridge_type
              $2: stp14_bridge_instance
              $3: stp14_bridge_port
              $4: stp14_interface
              $5: stp14_circuit_name

        This port has just been placed in Blocking state. This is a change in
        the topology, so this bridge detects a topology change.
        This will in turn cause topology change notifications to be sent."
    ::= { stpNotificationsPrefix 14 }

stpNotification15 NOTIFICATION-TYPE
    OBJECTS { 
              stp15_bridge_type, 
              stp15_bridge_instance,
              stp15_bridge_port,
              stp15_interface,
              stp15_circuit_name 
            }
    STATUS current
    DESCRIPTION
        "Notification of Event STP.15

        Message: 'Topology change detected on $1-$2 port $3, interface $4$5'

        Parameters list:
              $1: stp15_bridge_type
              $2: stp15_bridge_instance
              $3: stp15_bridge_port
              $4: stp15_interface
              $5: stp15_circuit_name

        A topology change notification has been received on this port, and
        this port is the designated port on its LAN. This causes the protocol
        to enter topology change notification state.
        The topology change will be acknowledged towards the sender, and
        propogated towards the root."
    ::= { stpNotificationsPrefix 15 }

stpNotification16 NOTIFICATION-TYPE
    OBJECTS { 
              stp16_bridge_type, 
              stp16_bridge_instance 
            }
    STATUS current
    DESCRIPTION
        "Notification of Event STP.16

        Message: 'Selected as root on $1-$2, detecting topology change'

        Parameters list:
              $1: stp16_bridge_type
              $2: stp16_bridge_instance

        This bridge has just selected itself as the root of the spanning tree
        when it previously had not been. This causes the bridge to enter
        topology change notification state."
    ::= { stpNotificationsPrefix 16 }

stpNotification17 NOTIFICATION-TYPE
    OBJECTS { 
              stp17_bridge_type, 
              stp17_bridge_instance,
              stp17_bridge_port,
              stp17_interface,
              stp17_circuit_name 
            }
    STATUS current
    DESCRIPTION
        "Notification of Event STP.17

        Message: 'Topology change acknowledged on $1-$2 port $3, interface $4$5'

        Parameters list:
              $1: stp17_bridge_type
              $2: stp17_bridge_instance
              $3: stp17_bridge_port
              $4: stp17_interface
              $5: stp17_circuit_name

        A topology change acknowledgement has been detected on the specified
        port. This port is the root port of the bridge."
    ::= { stpNotificationsPrefix 17 }

stpNotification18 NOTIFICATION-TYPE
    OBJECTS { 
              stp18_bridge_type, 
              stp18_bridge_instance,
              stp18_bridge_port,
              stp18_interface,
              stp18_circuit_name 
            }
    STATUS current
    DESCRIPTION
        "Notification of Event STP.18

        Message: 'Acknowledging topology change on $1-$2 port $3, interface $4$5'

        Parameters list:
              $1: stp18_bridge_type
              $2: stp18_bridge_instance
              $3: stp18_bridge_port
              $4: stp18_interface
              $5: stp18_circuit_name

        A topology change notification is being acknowledged on the
        specified port. This is done when a topology change notification
        is received on a port that is the designated port for that LAN."
    ::= { stpNotificationsPrefix 18 }

stpNotification19 NOTIFICATION-TYPE
    OBJECTS { 
              stp19_bridge_type, 
              stp19_bridge_instance 
            }
    STATUS current
    DESCRIPTION
        "Notification of Event STP.19

        Message: 'Topology Change Notification timer expired on $1-$2'

        Parameters list:
              $1: stp19_bridge_type
              $2: stp19_bridge_instance

        The Topology Change timer expired. This bridge will cease sending
        topology change notification BPDU's on its root port."
    ::= { stpNotificationsPrefix 19 }

stpNotification20 NOTIFICATION-TYPE
    OBJECTS { 
              stp20_bridge_type, 
              stp20_bridge_instance 
            }
    STATUS current
    DESCRIPTION
        "Notification of Event STP.20

        Message: 'Topology Change timer expired on $1-$2'

        Parameters list:
              $1: stp20_bridge_type
              $2: stp20_bridge_instance

        The Topology Change timer expired. This bridge, which is the root,
        will cease sending the Topology Change in its Configuration BPDUs."
    ::= { stpNotificationsPrefix 20 }

stpNotification21 NOTIFICATION-TYPE
    OBJECTS { 
              stp21_bridge_type, 
              stp21_bridge_instance,
              stp21_bridge_port,
              stp21_interface,
              stp21_circuit_name 
            }
    STATUS current
    DESCRIPTION
        "Notification of Event STP.21

        Message: 'Message age timer expired on $1-$2 port $3, interface $4$5, will try and become root'

        Parameters list:
              $1: stp21_bridge_type
              $2: stp21_bridge_instance
              $3: stp21_bridge_port
              $4: stp21_interface
              $5: stp21_circuit_name

        The message age timer has expired on this port. The bridge will attempt
        to become the root. It will become the designated port on that LAN."
    ::= { stpNotificationsPrefix 21 }

stpNotification22 NOTIFICATION-TYPE
    OBJECTS { 
              stp22_bridge_type, 
              stp22_bridge_instance 
            }
    STATUS current
    DESCRIPTION
        "Notification of Event STP.22

        Message: 'Hello timer expired on $1-$2'

        Parameters list:
              $1: stp22_bridge_type
              $2: stp22_bridge_instance

        The hello timer has expired on this port. Configuration BPDUs will be
        sent on all ports."
    ::= { stpNotificationsPrefix 22 }

stpNotification23 NOTIFICATION-TYPE
    OBJECTS { 
              stp23_bridge_type, 
              stp23_bridge_instance,
              stp23_bridge_port,
              stp23_interface,
              stp23_circuit_name 
            }
    STATUS current
    DESCRIPTION
        "Notification of Event STP.23

        Message: 'Stopping message age timer for $1-$2 port $3, interface $4$5'

        Parameters list:
              $1: stp23_bridge_type
              $2: stp23_bridge_instance
              $3: stp23_bridge_port
              $4: stp23_interface
              $5: stp23_circuit_name

        Stopping the message age timer on this port because it is
        the designated port on its LAN."
    ::= { stpNotificationsPrefix 23 }

stpNotification24 NOTIFICATION-TYPE
    OBJECTS { 
              stp24_bridge_type, 
              stp24_bridge_instance 
            }
    STATUS current
    DESCRIPTION
        "Notification of Event STP.24

        Message: 'Not root anymore on $1-$2, stopping hello timer'

        Parameters list:
              $1: stp24_bridge_type
              $2: stp24_bridge_instance

        This bridge has just decided that it is no longer the root bridge of
        the spanning tree. The hello timer will also be cancelled."
    ::= { stpNotificationsPrefix 24 }

stpNotification25 NOTIFICATION-TYPE
    OBJECTS { 
              stp25_bridge_type, 
              stp25_bridge_instance 
            }
    STATUS current
    DESCRIPTION
        "Notification of Event STP.25

        Message: 'Stopping topology change timer for $1-$2'

        Parameters list:
              $1: stp25_bridge_type
              $2: stp25_bridge_instance

        Stopping the topology change timer because this bridge is no longer
        the root."
    ::= { stpNotificationsPrefix 25 }

stpNotification26 NOTIFICATION-TYPE
    OBJECTS { 
              stp26_bridge_type, 
              stp26_bridge_instance 
            }
    STATUS current
    DESCRIPTION
        "Notification of Event STP.26

        Message: 'Selected as root on $1-$2, starting hello timer'

        Parameters list:
              $1: stp26_bridge_type
              $2: stp26_bridge_instance

        This bridge has just decided that it is the root bridge of
        the spanning tree. The hello timer will be started."
    ::= { stpNotificationsPrefix 26 }

stpNotification27 NOTIFICATION-TYPE
    OBJECTS { 
              stp27_bridge_type, 
              stp27_bridge_instance,
              stp27_bridge_port,
              stp27_interface,
              stp27_circuit_name 
            }
    STATUS current
    DESCRIPTION
        "Notification of Event STP.27

        Message: 'Starting message age timer for $1-$2 port $3, interface $4$5'

        Parameters list:
              $1: stp27_bridge_type
              $2: stp27_bridge_instance
              $3: stp27_bridge_port
              $4: stp27_interface
              $5: stp27_circuit_name

        Starting the message age timer on this port."
    ::= { stpNotificationsPrefix 27 }

stpNotification28 NOTIFICATION-TYPE
    OBJECTS { 
              stp28_bridge_type, 
              stp28_bridge_instance 
            }
    STATUS current
    DESCRIPTION
        "Notification of Event STP.28

        Message: 'Attempting to become root on $1-$2, starting hello timer'

        Parameters list:
              $1: stp28_bridge_type
              $2: stp28_bridge_instance

        This bridge is attempting to become the root bridge of
        the spanning tree. The hello timer will be started."
    ::= { stpNotificationsPrefix 28 }

stpNotification29 NOTIFICATION-TYPE
    OBJECTS { 
              stp29_source_address, 
              stp29_bridge_type,
              stp29_bridge_instance,
              stp29_bridge_port,
              stp29_interface,
              stp29_circuit_name 
            }
    STATUS current
    DESCRIPTION
        "Notification of Event STP.29

        Message: 'Configuration BPDU from $1 on $2-$3 ignored, inactive port $4, interface $5$6'

        Parameters list:
              $1: stp29_source_address
              $2: stp29_bridge_type
              $3: stp29_bridge_instance
              $4: stp29_bridge_port
              $5: stp29_interface
              $6: stp29_circuit_name

        A configuration BPDU has been received from the specified MAC address,
        but the port is not participating in the Spanning Tree Protocol."
    ::= { stpNotificationsPrefix 29 }

stpNotification30 NOTIFICATION-TYPE
    OBJECTS { 
              stp30_source_address, 
              stp30_bridge_type,
              stp30_bridge_instance,
              stp30_bridge_port,
              stp30_interface,
              stp30_circuit_name 
            }
    STATUS current
    DESCRIPTION
        "Notification of Event STP.30

        Message: 'Topology change notification BPDU from $1 on $2-$3 ignored, inactive port $4, interface $5$6'

        Parameters list:
              $1: stp30_source_address
              $2: stp30_bridge_type
              $3: stp30_bridge_instance
              $4: stp30_bridge_port
              $5: stp30_interface
              $6: stp30_circuit_name

        A topology change notification BPDU has been received from
        the specified MAC address, but the port is not participating in
        the Spanning Tree Protocol."
    ::= { stpNotificationsPrefix 30 }

stpNotification31 NOTIFICATION-TYPE
    OBJECTS { 
              stp31_bridge_type, 
              stp31_bridge_instance,
              stp31_bridge_port,
              stp31_interface,
              stp31_circuit_name 
            }
    STATUS current
    DESCRIPTION
        "Notification of Event STP.31

        Message: '$1-$2 becoming designated port $3, interface $4$5'

        Parameters list:
              $1: stp31_bridge_type
              $2: stp31_bridge_instance
              $3: stp31_bridge_port
              $4: stp31_interface
              $5: stp31_circuit_name

        This bridge is declaring itself the designated port on the LAN connected
        to this port."
    ::= { stpNotificationsPrefix 31 }

stpNotification32 NOTIFICATION-TYPE
    OBJECTS { 
              stp32_bpdu_type, 
              stp32_bridge_port,
              stp32_interface,
              stp32_circuit_name 
            }
    STATUS current
    DESCRIPTION
        "Notification of Event STP.32

        Message: 'DROP: $1 BPDU frame received on non-participating port $2, interface $3$4'

        Parameters list:
              $1: stp32_bpdu_type
              $2: stp32_bridge_port
              $3: stp32_interface
              $4: stp32_circuit_name

        A Source Route Bridge BPDU or IEEE802.1D BPDU has been received,
        but the port is not participating in the SRB or IEEE802.1D Spanning
        Tree Protocol."
    ::= { stpNotificationsPrefix 32 }

stpNotification33 NOTIFICATION-TYPE
    OBJECTS { 
              stp33_bpdu_type, 
              stp33_length,
              stp33_source_address,
              stp33_bridge_type,
              stp33_bridge_instance,
              stp33_bridge_port,
              stp33_interface,
              stp33_circuit_name 
            }
    STATUS current
    DESCRIPTION
        "Notification of Event STP.33

        Message: '$1 BPDU truncated ($2 bytes) frm $3 on $4-$5 port $6, interface $7$8'

        Parameters list:
              $1: stp33_bpdu_type
              $2: stp33_length
              $3: stp33_source_address
              $4: stp33_bridge_type
              $5: stp33_bridge_instance
              $6: stp33_bridge_port
              $7: stp33_interface
              $8: stp33_circuit_name

        A BPDU has been received which is less than the minimum size needed
        in length. It will be ignored."
    ::= { stpNotificationsPrefix 33 }

stpNotification34 NOTIFICATION-TYPE
    OBJECTS { 
              stp34_length, 
              stp34_source_address,
              stp34_bridge_type,
              stp34_bridge_instance,
              stp34_bridge_port,
              stp34_interface,
              stp34_circuit_name 
            }
    STATUS current
    DESCRIPTION
        "Notification of Event STP.34

        Message: 'BPDU truncated ($1 bytes) frm $2 on $3-$4 port $5, interface $6$7'

        Parameters list:
              $1: stp34_length
              $2: stp34_source_address
              $3: stp34_bridge_type
              $4: stp34_bridge_instance
              $5: stp34_bridge_port
              $6: stp34_interface
              $7: stp34_circuit_name

        A BPDU has been received which is less than 4 bytes in length.
        It will be ignored."
    ::= { stpNotificationsPrefix 34 }

stpNotification35 NOTIFICATION-TYPE
    OBJECTS { 
              stp35_bpdu_type, 
              stp35_msg_age_sc,
              stp35_msg_age_fr,
              stp35_max_age_sc,
              stp35_max_age_fr,
              stp35_source_address,
              stp35_bridge_type,
              stp35_bridge_instance,
              stp35_bridge_port,
              stp35_interface,
              stp35_circuit_name 
            }
    STATUS current
    DESCRIPTION
        "Notification of Event STP.35

        Message: '$1 BPDU discarded Message Age $2.$3 not less than Max Age $4.$5 frm $6 on $7-$8 port $9, interface $10$11'

        Parameters list:
              $1: stp35_bpdu_type
              $2: stp35_msg_age_sc
              $3: stp35_msg_age_fr
              $4: stp35_max_age_sc
              $5: stp35_max_age_fr
              $6: stp35_source_address
              $7: stp35_bridge_type
              $8: stp35_bridge_instance
              $9: stp35_bridge_port
              $10: stp35_interface
              $11: stp35_circuit_name

        A BPDU has been received with a message age that is not less than its
        max age parameter. It will be ignored."
    ::= { stpNotificationsPrefix 35 }

stpNotification36 NOTIFICATION-TYPE
    OBJECTS { 
              stp36_bpdu_type, 
              stp36_source_address,
              stp36_bridge_type,
              stp36_bridge_instance,
              stp36_bridge_port,
              stp36_interface,
              stp36_circuit_name 
            }
    STATUS current
    DESCRIPTION
        "Notification of Event STP.36

        Message: '$1 BPDU discarded parameters match transmitted frm $2 on $3-$4 port $5, interface $6$7'

        Parameters list:
              $1: stp36_bpdu_type
              $2: stp36_source_address
              $3: stp36_bridge_type
              $4: stp36_bridge_instance
              $5: stp36_bridge_port
              $6: stp36_interface
              $7: stp36_circuit_name

        A BPDU has been received with a Bridge Identifier and Port Identifier
        that match the values that would be transmitted in a BPDU from the
        port. It will be ignored."
    ::= { stpNotificationsPrefix 36 }

stpNotification37 NOTIFICATION-TYPE
    OBJECTS { 
              stp37_bpdu_type, 
              stp37_version,
              stp37_flags,
              stp37_flags_str,
              stp37_source_address,
              stp37_bridge_type,
              stp37_bridge_instance,
              stp37_bridge_port,
              stp37_interface,
              stp37_circuit_name 
            }
    STATUS current
    DESCRIPTION
        "Notification of Event STP.37

        Message: '$1 BPDU received version $2 flags 0x$3 ($4) frm $5 on $6-$7 port $8, interface $9$10'

        Parameters list:
              $1: stp37_bpdu_type
              $2: stp37_version
              $3: stp37_flags
              $4: stp37_flags_str
              $5: stp37_source_address
              $6: stp37_bridge_type
              $7: stp37_bridge_instance
              $8: stp37_bridge_port
              $9: stp37_interface
              $10: stp37_circuit_name

        A BPDU has been received from the specified MAC address."
    ::= { stpNotificationsPrefix 37 }

stpNotification38 NOTIFICATION-TYPE
    OBJECTS { 
              stp38_flags, 
              stp38_flags_str,
              stp38_bridge_type,
              stp38_bridge_instance,
              stp38_bridge_port,
              stp38_interface,
              stp38_circuit_name 
            }
    STATUS current
    DESCRIPTION
        "Notification of Event STP.38

        Message: 'Sending Rapid Spanning Tree BPDU with flags 0x$1 ($2) on $3-$4 port $5, interface $6$7'

        Parameters list:
              $1: stp38_flags
              $2: stp38_flags_str
              $3: stp38_bridge_type
              $4: stp38_bridge_instance
              $5: stp38_bridge_port
              $6: stp38_interface
              $7: stp38_circuit_name

        A Rapid Spanning Tree BPDU will be sent on the specified port. This is
        done normally on a periodic basis as part of the Spanning Tree Protocol."
    ::= { stpNotificationsPrefix 38 }

stpNotification39 NOTIFICATION-TYPE
    OBJECTS { 
              stp39_state, 
              stp39_bridge_type,
              stp39_bridge_instance,
              stp39_bridge_port,
              stp39_interface,
              stp39_circuit_name 
            }
    STATUS current
    DESCRIPTION
        "Notification of Event STP.39

        Message: 'state $1 $2-$3 port $4, interface $5$6'

        Parameters list:
              $1: stp39_state
              $2: stp39_bridge_type
              $3: stp39_bridge_instance
              $4: stp39_bridge_port
              $5: stp39_interface
              $6: stp39_circuit_name

        State change on a port."
    ::= { stpNotificationsPrefix 39 }

stpNotification40 NOTIFICATION-TYPE
    OBJECTS { 
              stp40_role, 
              stp40_bridge_type,
              stp40_bridge_instance,
              stp40_bridge_port,
              stp40_interface,
              stp40_circuit_name 
            }
    STATUS current
    DESCRIPTION
        "Notification of Event STP.40

        Message: 'role $1 $2-$3 port $4, interface $5$6'

        Parameters list:
              $1: stp40_role
              $2: stp40_bridge_type
              $3: stp40_bridge_instance
              $4: stp40_bridge_port
              $5: stp40_interface
              $6: stp40_circuit_name

        Role change on a port."
    ::= { stpNotificationsPrefix 40 }

stpNotification41 NOTIFICATION-TYPE
    OBJECTS { 
              stp41_root_vector, 
              stp41_bridge_type,
              stp41_bridge_instance,
              stp41_bridge_port,
              stp41_interface,
              stp41_circuit_name 
            }
    STATUS current
    DESCRIPTION
        "Notification of Event STP.41

        Message: 'rcvd root $1 $2-$3 port $4, interface $5$6'

        Parameters list:
              $1: stp41_root_vector
              $2: stp41_bridge_type
              $3: stp41_bridge_instance
              $4: stp41_bridge_port
              $5: stp41_interface
              $6: stp41_circuit_name

        Role change on a port."
    ::= { stpNotificationsPrefix 41 }

stpNotification42 NOTIFICATION-TYPE
    OBJECTS { 
              stp42_root_vector, 
              stp42_bridge_type,
              stp42_bridge_instance,
              stp42_bridge_port,
              stp42_interface,
              stp42_circuit_name 
            }
    STATUS current
    DESCRIPTION
        "Notification of Event STP.42

        Message: 'rcvd better root $1 $2-$3 port $4, interface $5$6'

        Parameters list:
              $1: stp42_root_vector
              $2: stp42_bridge_type
              $3: stp42_bridge_instance
              $4: stp42_bridge_port
              $5: stp42_interface
              $6: stp42_circuit_name

        Role change on a port."
    ::= { stpNotificationsPrefix 42 }

stpNotification43 NOTIFICATION-TYPE
    OBJECTS { 
              stp43_bridge_id, 
              stp43_bridge_port,
              stp43_interface,
              stp43_circuit_name 
            }
    STATUS current
    DESCRIPTION
        "Notification of Event STP.43

        Message: 'BPDU received filtered on bridge $1 port $2, interface $3$4'

        Parameters list:
              $1: stp43_bridge_id
              $2: stp43_bridge_port
              $3: stp43_interface
              $4: stp43_circuit_name

        Received BPDU discarded because BPDU filtering is enabled on a port."
    ::= { stpNotificationsPrefix 43 }

stpNotification44 NOTIFICATION-TYPE
    OBJECTS { 
              stp44_bridge_id, 
              stp44_bridge_port,
              stp44_interface,
              stp44_circuit_name 
            }
    STATUS current
    DESCRIPTION
        "Notification of Event STP.44

        Message: 'Transmitted BPDU filtered on bridge $1 port $2, interface $3$4'

        Parameters list:
              $1: stp44_bridge_id
              $2: stp44_bridge_port
              $3: stp44_interface
              $4: stp44_circuit_name

        Transmitted BPDU discarded because BPDU filtering is enabled on a port.
        The BPDU is not sent."
    ::= { stpNotificationsPrefix 44 }

stpNotification45 NOTIFICATION-TYPE
    OBJECTS { 
              stp45_bridge_id, 
              stp45_bridge_port,
              stp45_interface,
              stp45_circuit_name 
            }
    STATUS current
    DESCRIPTION
        "Notification of Event STP.45

        Message: 'BPDU Guard, port disabled, on bridge $1 port $2, interface $3$4'

        Parameters list:
              $1: stp45_bridge_id
              $2: stp45_bridge_port
              $3: stp45_interface
              $4: stp45_circuit_name

        Received BPDU on port with BPDU Guard enabled. The port is disabled"
    ::= { stpNotificationsPrefix 45 }

stpNotification46 NOTIFICATION-TYPE
    OBJECTS { 
              stp46_VID, 
              stp46_VID2,
              stp46_source_address,
              stp46_bridge_id,
              stp46_bridge_port,
              stp46_interface,
              stp46_circuit_name 
            }
    STATUS current
    DESCRIPTION
        "Notification of Event STP.46

        Message: 'PVST+ inconsistency detected on VLAN $1, conveyed VLAN $2 from $3 bridge $4 port $5, interface $6$7'

        Parameters list:
              $1: stp46_VID
              $2: stp46_VID2
              $3: stp46_source_address
              $4: stp46_bridge_id
              $5: stp46_bridge_port
              $6: stp46_interface
              $7: stp46_circuit_name

        Received PVST+ BPDU with inconsistent VID. The VID conveyed in the
        BPDU does not match the VID assigned to the frame"
    ::= { stpNotificationsPrefix 46 }

stpNotification47 NOTIFICATION-TYPE
    OBJECTS { 
              stp47_VID, 
              stp47_source_address,
              stp47_bridge_id,
              stp47_bridge_port,
              stp47_interface,
              stp47_circuit_name 
            }
    STATUS current
    DESCRIPTION
        "Notification of Event STP.47

        Message: 'Malformed PVST+ BPDU on VLAN $1 from $2 bridge $3 port $4, interface $5$6'

        Parameters list:
              $1: stp47_VID
              $2: stp47_source_address
              $3: stp47_bridge_id
              $4: stp47_bridge_port
              $5: stp47_interface
              $6: stp47_circuit_name

        Received malformed PVST+ BPDU"
    ::= { stpNotificationsPrefix 47 }

stpNotification48 NOTIFICATION-TYPE
    OBJECTS { 
              stp48_bpdu_type, 
              stp48_source_address,
              stp48_bridge_id,
              stp48_bridge_port,
              stp48_interface,
              stp48_circuit_name 
            }
    STATUS current
    DESCRIPTION
        "Notification of Event STP.48

        Message: '$1 BPDU discarded (VLAN 1) from $2 bridge $3 port $4, interface $5$6'

        Parameters list:
              $1: stp48_bpdu_type
              $2: stp48_source_address
              $3: stp48_bridge_id
              $4: stp48_bridge_port
              $5: stp48_interface
              $6: stp48_circuit_name

        PVST+ BPDU conveying VLAN 1 received. Silently discarded, since
        the common BPDU is used instead"
    ::= { stpNotificationsPrefix 48 }


END
