-- file automatically created


TELDAT-TRAP-ISDN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


isdnTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ISDN event subsystem."
    REVISION "201401200930Z"
    DESCRIPTION "Initial implementation"
        ::= { telEventTraps 99 }


isdnEventsGroup	OBJECT IDENTIFIER	::= { isdnTrapsMIB 1 }

isdnNotifications	OBJECT IDENTIFIER	::= { isdnTrapsMIB 2 }
isdnNotificationsPrefix	OBJECT IDENTIFIER	::= { isdnNotifications 0 }

isdnEventObjects1 OBJECT-IDENTITY
    STATUS current
    DESCRIPTION
        "Event ISDN.1
        ALERTING message received for the mentioned Q931 conversation."
    ::= { isdnEventsGroup 1 }

isdn1_call_ref OBJECT-TYPE
    SYNTAX Integer32
    MAX-ACCESS accessible-for-notify
    STATUS current
    DESCRIPTION
        "Parameter 'call_ref' in event ISDN.1"
    ::= { isdnEventObjects1 1 }

isdn1_interface OBJECT-TYPE
    SYNTAX DisplayString
    MAX-ACCESS accessible-for-notify
    STATUS current
    DESCRIPTION
        "Parameter 'interface' in event ISDN.1"
    ::= { isdnEventObjects1 2 }

isdnEventObjects2 OBJECT-IDENTITY
    STATUS current
    DESCRIPTION
        "Event ISDN.2
        CONN ACK message received for the mentioned Q931 conversation."
    ::= { isdnEventsGroup 2 }

isdn2_call_ref OBJECT-TYPE
    SYNTAX Integer32
    MAX-ACCESS accessible-for-notify
    STATUS current
    DESCRIPTION
        "Parameter 'call_ref' in event ISDN.2"
    ::= { isdnEventObjects2 1 }

isdn2_interface OBJECT-TYPE
    SYNTAX DisplayString
    MAX-ACCESS accessible-for-notify
    STATUS current
    DESCRIPTION
        "Parameter 'interface' in event ISDN.2"
    ::= { isdnEventObjects2 2 }

isdnEventObjects3 OBJECT-IDENTITY
    STATUS current
    DESCRIPTION
        "Event ISDN.3
        CONN message received for the mentioned Q931 conversation."
    ::= { isdnEventsGroup 3 }

isdn3_call_ref OBJECT-TYPE
    SYNTAX Integer32
    MAX-ACCESS accessible-for-notify
    STATUS current
    DESCRIPTION
        "Parameter 'call_ref' in event ISDN.3"
    ::= { isdnEventObjects3 1 }

isdn3_interface OBJECT-TYPE
    SYNTAX DisplayString
    MAX-ACCESS accessible-for-notify
    STATUS current
    DESCRIPTION
        "Parameter 'interface' in event ISDN.3"
    ::= { isdnEventObjects3 2 }

isdnEventObjects4 OBJECT-IDENTITY
    STATUS current
    DESCRIPTION
        "Event ISDN.4
        CALL PROC message received for the mentioned Q931 conversation."
    ::= { isdnEventsGroup 4 }

isdn4_call_ref OBJECT-TYPE
    SYNTAX Integer32
    MAX-ACCESS accessible-for-notify
    STATUS current
    DESCRIPTION
        "Parameter 'call_ref' in event ISDN.4"
    ::= { isdnEventObjects4 1 }

isdn4_chan OBJECT-TYPE
    SYNTAX DisplayString
    MAX-ACCESS accessible-for-notify
    STATUS current
    DESCRIPTION
        "Parameter 'chan' in event ISDN.4"
    ::= { isdnEventObjects4 2 }

isdn4_interface OBJECT-TYPE
    SYNTAX DisplayString
    MAX-ACCESS accessible-for-notify
    STATUS current
    DESCRIPTION
        "Parameter 'interface' in event ISDN.4"
    ::= { isdnEventObjects4 3 }

isdnEventObjects5 OBJECT-IDENTITY
    STATUS current
    DESCRIPTION
        "Event ISDN.5
        DISC message received for the mentioned Q931 conversation."
    ::= { isdnEventsGroup 5 }

isdn5_call_ref OBJECT-TYPE
    SYNTAX Integer32
    MAX-ACCESS accessible-for-notify
    STATUS current
    DESCRIPTION
        "Parameter 'call_ref' in event ISDN.5"
    ::= { isdnEventObjects5 1 }

isdn5_cause OBJECT-TYPE
    SYNTAX Integer32
    MAX-ACCESS accessible-for-notify
    STATUS current
    DESCRIPTION
        "Parameter 'cause' in event ISDN.5"
    ::= { isdnEventObjects5 2 }

isdn5_cost OBJECT-TYPE
    SYNTAX Integer32
    MAX-ACCESS accessible-for-notify
    STATUS current
    DESCRIPTION
        "Parameter 'cost' in event ISDN.5"
    ::= { isdnEventObjects5 3 }

isdn5_interface OBJECT-TYPE
    SYNTAX DisplayString
    MAX-ACCESS accessible-for-notify
    STATUS current
    DESCRIPTION
        "Parameter 'interface' in event ISDN.5"
    ::= { isdnEventObjects5 4 }

isdnEventObjects6 OBJECT-IDENTITY
    STATUS current
    DESCRIPTION
        "Event ISDN.6
        INFO message received for the mentioned Q931 conversation."
    ::= { isdnEventsGroup 6 }

isdn6_call_ref OBJECT-TYPE
    SYNTAX Integer32
    MAX-ACCESS accessible-for-notify
    STATUS current
    DESCRIPTION
        "Parameter 'call_ref' in event ISDN.6"
    ::= { isdnEventObjects6 1 }

isdn6_interface OBJECT-TYPE
    SYNTAX DisplayString
    MAX-ACCESS accessible-for-notify
    STATUS current
    DESCRIPTION
        "Parameter 'interface' in event ISDN.6"
    ::= { isdnEventObjects6 2 }

isdnEventObjects7 OBJECT-IDENTITY
    STATUS current
    DESCRIPTION
        "Event ISDN.7
        PROGR message received for the mentioned Q931 conversation."
    ::= { isdnEventsGroup 7 }

isdn7_call_ref OBJECT-TYPE
    SYNTAX Integer32
    MAX-ACCESS accessible-for-notify
    STATUS current
    DESCRIPTION
        "Parameter 'call_ref' in event ISDN.7"
    ::= { isdnEventObjects7 1 }

isdn7_interface OBJECT-TYPE
    SYNTAX DisplayString
    MAX-ACCESS accessible-for-notify
    STATUS current
    DESCRIPTION
        "Parameter 'interface' in event ISDN.7"
    ::= { isdnEventObjects7 2 }

isdnEventObjects8 OBJECT-IDENTITY
    STATUS current
    DESCRIPTION
        "Event ISDN.8
        RELEASE message received for the mentioned Q931 conversation."
    ::= { isdnEventsGroup 8 }

isdn8_call_ref OBJECT-TYPE
    SYNTAX Integer32
    MAX-ACCESS accessible-for-notify
    STATUS current
    DESCRIPTION
        "Parameter 'call_ref' in event ISDN.8"
    ::= { isdnEventObjects8 1 }

isdn8_cause OBJECT-TYPE
    SYNTAX Integer32
    MAX-ACCESS accessible-for-notify
    STATUS current
    DESCRIPTION
        "Parameter 'cause' in event ISDN.8"
    ::= { isdnEventObjects8 2 }

isdn8_cost OBJECT-TYPE
    SYNTAX Integer32
    MAX-ACCESS accessible-for-notify
    STATUS current
    DESCRIPTION
        "Parameter 'cost' in event ISDN.8"
    ::= { isdnEventObjects8 3 }

isdn8_interface OBJECT-TYPE
    SYNTAX DisplayString
    MAX-ACCESS accessible-for-notify
    STATUS current
    DESCRIPTION
        "Parameter 'interface' in event ISDN.8"
    ::= { isdnEventObjects8 4 }

isdnEventObjects9 OBJECT-IDENTITY
    STATUS current
    DESCRIPTION
        "Event ISDN.9
        REL COMPLETE message received for the mentioned Q931 conversation."
    ::= { isdnEventsGroup 9 }

isdn9_call_ref OBJECT-TYPE
    SYNTAX Integer32
    MAX-ACCESS accessible-for-notify
    STATUS current
    DESCRIPTION
        "Parameter 'call_ref' in event ISDN.9"
    ::= { isdnEventObjects9 1 }

isdn9_cause OBJECT-TYPE
    SYNTAX Integer32
    MAX-ACCESS accessible-for-notify
    STATUS current
    DESCRIPTION
        "Parameter 'cause' in event ISDN.9"
    ::= { isdnEventObjects9 2 }

isdn9_cost OBJECT-TYPE
    SYNTAX Integer32
    MAX-ACCESS accessible-for-notify
    STATUS current
    DESCRIPTION
        "Parameter 'cost' in event ISDN.9"
    ::= { isdnEventObjects9 3 }

isdn9_interface OBJECT-TYPE
    SYNTAX DisplayString
    MAX-ACCESS accessible-for-notify
    STATUS current
    DESCRIPTION
        "Parameter 'interface' in event ISDN.9"
    ::= { isdnEventObjects9 4 }

isdnEventObjects10 OBJECT-IDENTITY
    STATUS current
    DESCRIPTION
        "Event ISDN.10
        STATUS message received for the mentioned Q931 conversation."
    ::= { isdnEventsGroup 10 }

isdn10_call_ref OBJECT-TYPE
    SYNTAX Integer32
    MAX-ACCESS accessible-for-notify
    STATUS current
    DESCRIPTION
        "Parameter 'call_ref' in event ISDN.10"
    ::= { isdnEventObjects10 1 }

isdn10_interface OBJECT-TYPE
    SYNTAX DisplayString
    MAX-ACCESS accessible-for-notify
    STATUS current
    DESCRIPTION
        "Parameter 'interface' in event ISDN.10"
    ::= { isdnEventObjects10 2 }

isdnEventObjects11 OBJECT-IDENTITY
    STATUS current
    DESCRIPTION
        "Event ISDN.11
        SETUP message received for the mentioned Q931 conversation."
    ::= { isdnEventsGroup 11 }

isdn11_call_ref OBJECT-TYPE
    SYNTAX Integer32
    MAX-ACCESS accessible-for-notify
    STATUS current
    DESCRIPTION
        "Parameter 'call_ref' in event ISDN.11"
    ::= { isdnEventObjects11 1 }

isdn11_chan OBJECT-TYPE
    SYNTAX Integer32
    MAX-ACCESS accessible-for-notify
    STATUS current
    DESCRIPTION
        "Parameter 'chan' in event ISDN.11"
    ::= { isdnEventObjects11 2 }

isdn11_caller_num OBJECT-TYPE
    SYNTAX DisplayString
    MAX-ACCESS accessible-for-notify
    STATUS current
    DESCRIPTION
        "Parameter 'caller_num' in event ISDN.11"
    ::= { isdnEventObjects11 3 }

isdn11_interface OBJECT-TYPE
    SYNTAX DisplayString
    MAX-ACCESS accessible-for-notify
    STATUS current
    DESCRIPTION
        "Parameter 'interface' in event ISDN.11"
    ::= { isdnEventObjects11 4 }

isdnEventObjects12 OBJECT-IDENTITY
    STATUS current
    DESCRIPTION
        "Event ISDN.12
        An incoming call has been established."
    ::= { isdnEventsGroup 12 }

isdn12_called OBJECT-TYPE
    SYNTAX DisplayString
    MAX-ACCESS accessible-for-notify
    STATUS current
    DESCRIPTION
        "Parameter 'called' in event ISDN.12"
    ::= { isdnEventObjects12 1 }

isdn12_caller OBJECT-TYPE
    SYNTAX DisplayString
    MAX-ACCESS accessible-for-notify
    STATUS current
    DESCRIPTION
        "Parameter 'caller' in event ISDN.12"
    ::= { isdnEventObjects12 2 }

isdn12_interface OBJECT-TYPE
    SYNTAX DisplayString
    MAX-ACCESS accessible-for-notify
    STATUS current
    DESCRIPTION
        "Parameter 'interface' in event ISDN.12"
    ::= { isdnEventObjects12 3 }

isdnEventObjects13 OBJECT-IDENTITY
    STATUS current
    DESCRIPTION
        "Event ISDN.13
        An outgoing call has been established."
    ::= { isdnEventsGroup 13 }

isdn13_called OBJECT-TYPE
    SYNTAX DisplayString
    MAX-ACCESS accessible-for-notify
    STATUS current
    DESCRIPTION
        "Parameter 'called' in event ISDN.13"
    ::= { isdnEventObjects13 1 }

isdn13_caller OBJECT-TYPE
    SYNTAX DisplayString
    MAX-ACCESS accessible-for-notify
    STATUS current
    DESCRIPTION
        "Parameter 'caller' in event ISDN.13"
    ::= { isdnEventObjects13 2 }

isdn13_interface OBJECT-TYPE
    SYNTAX DisplayString
    MAX-ACCESS accessible-for-notify
    STATUS current
    DESCRIPTION
        "Parameter 'interface' in event ISDN.13"
    ::= { isdnEventObjects13 3 }

isdnEventObjects14 OBJECT-IDENTITY
    STATUS current
    DESCRIPTION
        "Event ISDN.14
        An incoming call has been released."
    ::= { isdnEventsGroup 14 }

isdn14_called OBJECT-TYPE
    SYNTAX DisplayString
    MAX-ACCESS accessible-for-notify
    STATUS current
    DESCRIPTION
        "Parameter 'called' in event ISDN.14"
    ::= { isdnEventObjects14 1 }

isdn14_caller OBJECT-TYPE
    SYNTAX DisplayString
    MAX-ACCESS accessible-for-notify
    STATUS current
    DESCRIPTION
        "Parameter 'caller' in event ISDN.14"
    ::= { isdnEventObjects14 2 }

isdn14_interface OBJECT-TYPE
    SYNTAX DisplayString
    MAX-ACCESS accessible-for-notify
    STATUS current
    DESCRIPTION
        "Parameter 'interface' in event ISDN.14"
    ::= { isdnEventObjects14 3 }

isdnEventObjects15 OBJECT-IDENTITY
    STATUS current
    DESCRIPTION
        "Event ISDN.15
        An outgoing call has been released."
    ::= { isdnEventsGroup 15 }

isdn15_called OBJECT-TYPE
    SYNTAX DisplayString
    MAX-ACCESS accessible-for-notify
    STATUS current
    DESCRIPTION
        "Parameter 'called' in event ISDN.15"
    ::= { isdnEventObjects15 1 }

isdn15_caller OBJECT-TYPE
    SYNTAX DisplayString
    MAX-ACCESS accessible-for-notify
    STATUS current
    DESCRIPTION
        "Parameter 'caller' in event ISDN.15"
    ::= { isdnEventObjects15 2 }

isdn15_interface OBJECT-TYPE
    SYNTAX DisplayString
    MAX-ACCESS accessible-for-notify
    STATUS current
    DESCRIPTION
        "Parameter 'interface' in event ISDN.15"
    ::= { isdnEventObjects15 3 }

isdnEventObjects16 OBJECT-IDENTITY
    STATUS current
    DESCRIPTION
        "Event ISDN.16
        CONN message transmitted for the mentioned Q931 conversation."
    ::= { isdnEventsGroup 16 }

isdn16_call_ref OBJECT-TYPE
    SYNTAX Integer32
    MAX-ACCESS accessible-for-notify
    STATUS current
    DESCRIPTION
        "Parameter 'call_ref' in event ISDN.16"
    ::= { isdnEventObjects16 1 }

isdn16_chan OBJECT-TYPE
    SYNTAX Integer32
    MAX-ACCESS accessible-for-notify
    STATUS current
    DESCRIPTION
        "Parameter 'chan' in event ISDN.16"
    ::= { isdnEventObjects16 2 }

isdn16_interface OBJECT-TYPE
    SYNTAX DisplayString
    MAX-ACCESS accessible-for-notify
    STATUS current
    DESCRIPTION
        "Parameter 'interface' in event ISDN.16"
    ::= { isdnEventObjects16 3 }

isdnEventObjects17 OBJECT-IDENTITY
    STATUS current
    DESCRIPTION
        "Event ISDN.17
        CONN ACK message transmitted for the mentioned Q931 conversation."
    ::= { isdnEventsGroup 17 }

isdn17_call_ref OBJECT-TYPE
    SYNTAX Integer32
    MAX-ACCESS accessible-for-notify
    STATUS current
    DESCRIPTION
        "Parameter 'call_ref' in event ISDN.17"
    ::= { isdnEventObjects17 1 }

isdn17_interface OBJECT-TYPE
    SYNTAX DisplayString
    MAX-ACCESS accessible-for-notify
    STATUS current
    DESCRIPTION
        "Parameter 'interface' in event ISDN.17"
    ::= { isdnEventObjects17 2 }

isdnEventObjects18 OBJECT-IDENTITY
    STATUS current
    DESCRIPTION
        "Event ISDN.18
        DISC message transmitted for the mentioned Q931 conversation."
    ::= { isdnEventsGroup 18 }

isdn18_call_ref OBJECT-TYPE
    SYNTAX Integer32
    MAX-ACCESS accessible-for-notify
    STATUS current
    DESCRIPTION
        "Parameter 'call_ref' in event ISDN.18"
    ::= { isdnEventObjects18 1 }

isdn18_cause OBJECT-TYPE
    SYNTAX Integer32
    MAX-ACCESS accessible-for-notify
    STATUS current
    DESCRIPTION
        "Parameter 'cause' in event ISDN.18"
    ::= { isdnEventObjects18 2 }

isdn18_interface OBJECT-TYPE
    SYNTAX DisplayString
    MAX-ACCESS accessible-for-notify
    STATUS current
    DESCRIPTION
        "Parameter 'interface' in event ISDN.18"
    ::= { isdnEventObjects18 3 }

isdnEventObjects19 OBJECT-IDENTITY
    STATUS current
    DESCRIPTION
        "Event ISDN.19
        REL message transmitted for the mentioned Q931 conversation."
    ::= { isdnEventsGroup 19 }

isdn19_call_ref OBJECT-TYPE
    SYNTAX Integer32
    MAX-ACCESS accessible-for-notify
    STATUS current
    DESCRIPTION
        "Parameter 'call_ref' in event ISDN.19"
    ::= { isdnEventObjects19 1 }

isdn19_cause OBJECT-TYPE
    SYNTAX Integer32
    MAX-ACCESS accessible-for-notify
    STATUS current
    DESCRIPTION
        "Parameter 'cause' in event ISDN.19"
    ::= { isdnEventObjects19 2 }

isdn19_interface OBJECT-TYPE
    SYNTAX DisplayString
    MAX-ACCESS accessible-for-notify
    STATUS current
    DESCRIPTION
        "Parameter 'interface' in event ISDN.19"
    ::= { isdnEventObjects19 3 }

isdnEventObjects20 OBJECT-IDENTITY
    STATUS current
    DESCRIPTION
        "Event ISDN.20
        REL COM message transmitted for the mentioned Q931 conversation."
    ::= { isdnEventsGroup 20 }

isdn20_call_ref OBJECT-TYPE
    SYNTAX Integer32
    MAX-ACCESS accessible-for-notify
    STATUS current
    DESCRIPTION
        "Parameter 'call_ref' in event ISDN.20"
    ::= { isdnEventObjects20 1 }

isdn20_cause OBJECT-TYPE
    SYNTAX Integer32
    MAX-ACCESS accessible-for-notify
    STATUS current
    DESCRIPTION
        "Parameter 'cause' in event ISDN.20"
    ::= { isdnEventObjects20 2 }

isdn20_interface OBJECT-TYPE
    SYNTAX DisplayString
    MAX-ACCESS accessible-for-notify
    STATUS current
    DESCRIPTION
        "Parameter 'interface' in event ISDN.20"
    ::= { isdnEventObjects20 3 }

isdnEventObjects21 OBJECT-IDENTITY
    STATUS current
    DESCRIPTION
        "Event ISDN.21
        SETUP message transmitted for the mentioned Q931 conversation."
    ::= { isdnEventsGroup 21 }

isdn21_call_ref OBJECT-TYPE
    SYNTAX Integer32
    MAX-ACCESS accessible-for-notify
    STATUS current
    DESCRIPTION
        "Parameter 'call_ref' in event ISDN.21"
    ::= { isdnEventObjects21 1 }

isdn21_called_num OBJECT-TYPE
    SYNTAX DisplayString
    MAX-ACCESS accessible-for-notify
    STATUS current
    DESCRIPTION
        "Parameter 'called_num' in event ISDN.21"
    ::= { isdnEventObjects21 2 }

isdn21_interface OBJECT-TYPE
    SYNTAX DisplayString
    MAX-ACCESS accessible-for-notify
    STATUS current
    DESCRIPTION
        "Parameter 'interface' in event ISDN.21"
    ::= { isdnEventObjects21 3 }

isdnEventObjects22 OBJECT-IDENTITY
    STATUS current
    DESCRIPTION
        "Event ISDN.22
        STATUS message transmitted for the mentioned Q931 conversation."
    ::= { isdnEventsGroup 22 }

isdn22_call_ref OBJECT-TYPE
    SYNTAX Integer32
    MAX-ACCESS accessible-for-notify
    STATUS current
    DESCRIPTION
        "Parameter 'call_ref' in event ISDN.22"
    ::= { isdnEventObjects22 1 }

isdn22_status OBJECT-TYPE
    SYNTAX Integer32
    MAX-ACCESS accessible-for-notify
    STATUS current
    DESCRIPTION
        "Parameter 'status' in event ISDN.22"
    ::= { isdnEventObjects22 2 }

isdn22_interface OBJECT-TYPE
    SYNTAX DisplayString
    MAX-ACCESS accessible-for-notify
    STATUS current
    DESCRIPTION
        "Parameter 'interface' in event ISDN.22"
    ::= { isdnEventObjects22 3 }

isdnEventObjects23 OBJECT-IDENTITY
    STATUS current
    DESCRIPTION
        "Event ISDN.23
        message transmitted contents."
    ::= { isdnEventsGroup 23 }

isdn23_frame_tx OBJECT-TYPE
    SYNTAX DisplayString
    MAX-ACCESS accessible-for-notify
    STATUS current
    DESCRIPTION
        "Parameter 'frame_tx' in event ISDN.23"
    ::= { isdnEventObjects23 1 }

isdn23_interface OBJECT-TYPE
    SYNTAX DisplayString
    MAX-ACCESS accessible-for-notify
    STATUS current
    DESCRIPTION
        "Parameter 'interface' in event ISDN.23"
    ::= { isdnEventObjects23 2 }

isdnEventObjects24 OBJECT-IDENTITY
    STATUS current
    DESCRIPTION
        "Event ISDN.24
        message received contents."
    ::= { isdnEventsGroup 24 }

isdn24_frame_rx OBJECT-TYPE
    SYNTAX DisplayString
    MAX-ACCESS accessible-for-notify
    STATUS current
    DESCRIPTION
        "Parameter 'frame_rx' in event ISDN.24"
    ::= { isdnEventObjects24 1 }

isdn24_interface OBJECT-TYPE
    SYNTAX DisplayString
    MAX-ACCESS accessible-for-notify
    STATUS current
    DESCRIPTION
        "Parameter 'interface' in event ISDN.24"
    ::= { isdnEventObjects24 2 }

isdnEventObjects25 OBJECT-IDENTITY
    STATUS current
    DESCRIPTION
        "Event ISDN.25
        RESTART message received."
    ::= { isdnEventsGroup 25 }

isdn25_restart_ind OBJECT-TYPE
    SYNTAX Integer32
    MAX-ACCESS accessible-for-notify
    STATUS current
    DESCRIPTION
        "Parameter 'restart_ind' in event ISDN.25"
    ::= { isdnEventObjects25 1 }

isdn25_channel_id OBJECT-TYPE
    SYNTAX DisplayString
    MAX-ACCESS accessible-for-notify
    STATUS current
    DESCRIPTION
        "Parameter 'channel_id' in event ISDN.25"
    ::= { isdnEventObjects25 2 }

isdn25_interface OBJECT-TYPE
    SYNTAX DisplayString
    MAX-ACCESS accessible-for-notify
    STATUS current
    DESCRIPTION
        "Parameter 'interface' in event ISDN.25"
    ::= { isdnEventObjects25 3 }

isdnEventObjects26 OBJECT-IDENTITY
    STATUS current
    DESCRIPTION
        "Event ISDN.26
        A RESTART ACK message has been transmitted."
    ::= { isdnEventsGroup 26 }

isdn26_interface OBJECT-TYPE
    SYNTAX DisplayString
    MAX-ACCESS accessible-for-notify
    STATUS current
    DESCRIPTION
        "Parameter 'interface' in event ISDN.26"
    ::= { isdnEventObjects26 1 }

isdnEventObjects27 OBJECT-IDENTITY
    STATUS current
    DESCRIPTION
        "Event ISDN.27
        An INFO message has been transmited in order to initialize SPID."
    ::= { isdnEventsGroup 27 }

isdn27_call_ref OBJECT-TYPE
    SYNTAX Integer32
    MAX-ACCESS accessible-for-notify
    STATUS current
    DESCRIPTION
        "Parameter 'call_ref' in event ISDN.27"
    ::= { isdnEventObjects27 1 }

isdn27_spid OBJECT-TYPE
    SYNTAX DisplayString
    MAX-ACCESS accessible-for-notify
    STATUS current
    DESCRIPTION
        "Parameter 'spid' in event ISDN.27"
    ::= { isdnEventObjects27 2 }

isdn27_interface OBJECT-TYPE
    SYNTAX DisplayString
    MAX-ACCESS accessible-for-notify
    STATUS current
    DESCRIPTION
        "Parameter 'interface' in event ISDN.27"
    ::= { isdnEventObjects27 3 }

isdnEventObjects28 OBJECT-IDENTITY
    STATUS current
    DESCRIPTION
        "Event ISDN.28
        SPEED is being sending to the network."
    ::= { isdnEventsGroup 28 }

isdn28_spid OBJECT-TYPE
    SYNTAX DisplayString
    MAX-ACCESS accessible-for-notify
    STATUS current
    DESCRIPTION
        "Parameter 'spid' in event ISDN.28"
    ::= { isdnEventObjects28 1 }

isdn28_interface OBJECT-TYPE
    SYNTAX DisplayString
    MAX-ACCESS accessible-for-notify
    STATUS current
    DESCRIPTION
        "Parameter 'interface' in event ISDN.28"
    ::= { isdnEventObjects28 2 }

isdnEventObjects29 OBJECT-IDENTITY
    STATUS current
    DESCRIPTION
        "Event ISDN.29
        An INFO message has been received acknowing successfully SPID initialize."
    ::= { isdnEventsGroup 29 }

isdn29_spid OBJECT-TYPE
    SYNTAX DisplayString
    MAX-ACCESS accessible-for-notify
    STATUS current
    DESCRIPTION
        "Parameter 'spid' in event ISDN.29"
    ::= { isdnEventObjects29 1 }

isdn29_interface OBJECT-TYPE
    SYNTAX DisplayString
    MAX-ACCESS accessible-for-notify
    STATUS current
    DESCRIPTION
        "Parameter 'interface' in event ISDN.29"
    ::= { isdnEventObjects29 2 }

isdnEventObjects30 OBJECT-IDENTITY
    STATUS current
    DESCRIPTION
        "Event ISDN.30
        An INFO message has been received with indicated cause."
    ::= { isdnEventsGroup 30 }

isdn30_spid OBJECT-TYPE
    SYNTAX DisplayString
    MAX-ACCESS accessible-for-notify
    STATUS current
    DESCRIPTION
        "Parameter 'spid' in event ISDN.30"
    ::= { isdnEventObjects30 1 }

isdn30_cause OBJECT-TYPE
    SYNTAX Integer32
    MAX-ACCESS accessible-for-notify
    STATUS current
    DESCRIPTION
        "Parameter 'cause' in event ISDN.30"
    ::= { isdnEventObjects30 2 }

isdn30_interface OBJECT-TYPE
    SYNTAX DisplayString
    MAX-ACCESS accessible-for-notify
    STATUS current
    DESCRIPTION
        "Parameter 'interface' in event ISDN.30"
    ::= { isdnEventObjects30 3 }

isdnEventObjects31 OBJECT-IDENTITY
    STATUS current
    DESCRIPTION
        "Event ISDN.31
        A CALL PROCEEDING message has been transmitted."
    ::= { isdnEventsGroup 31 }

isdn31_call_ref OBJECT-TYPE
    SYNTAX Integer32
    MAX-ACCESS accessible-for-notify
    STATUS current
    DESCRIPTION
        "Parameter 'call_ref' in event ISDN.31"
    ::= { isdnEventObjects31 1 }

isdn31_interface OBJECT-TYPE
    SYNTAX DisplayString
    MAX-ACCESS accessible-for-notify
    STATUS current
    DESCRIPTION
        "Parameter 'interface' in event ISDN.31"
    ::= { isdnEventObjects31 2 }

isdnEventObjects32 OBJECT-IDENTITY
    STATUS current
    DESCRIPTION
        "Event ISDN.32
        An ALERTING message has been transmitted."
    ::= { isdnEventsGroup 32 }

isdn32_call_ref OBJECT-TYPE
    SYNTAX Integer32
    MAX-ACCESS accessible-for-notify
    STATUS current
    DESCRIPTION
        "Parameter 'call_ref' in event ISDN.32"
    ::= { isdnEventObjects32 1 }

isdn32_interface OBJECT-TYPE
    SYNTAX DisplayString
    MAX-ACCESS accessible-for-notify
    STATUS current
    DESCRIPTION
        "Parameter 'interface' in event ISDN.32"
    ::= { isdnEventObjects32 2 }

isdnEventObjects33 OBJECT-IDENTITY
    STATUS current
    DESCRIPTION
        "Event ISDN.33
        A SETUP_ACK message has been transmitted."
    ::= { isdnEventsGroup 33 }

isdn33_call_ref OBJECT-TYPE
    SYNTAX Integer32
    MAX-ACCESS accessible-for-notify
    STATUS current
    DESCRIPTION
        "Parameter 'call_ref' in event ISDN.33"
    ::= { isdnEventObjects33 1 }

isdn33_interface OBJECT-TYPE
    SYNTAX DisplayString
    MAX-ACCESS accessible-for-notify
    STATUS current
    DESCRIPTION
        "Parameter 'interface' in event ISDN.33"
    ::= { isdnEventObjects33 2 }

isdnEventObjects34 OBJECT-IDENTITY
    STATUS current
    DESCRIPTION
        "Event ISDN.34
        SETUP ACK message received for the mentioned Q931 conversation."
    ::= { isdnEventsGroup 34 }

isdn34_call_ref OBJECT-TYPE
    SYNTAX Integer32
    MAX-ACCESS accessible-for-notify
    STATUS current
    DESCRIPTION
        "Parameter 'call_ref' in event ISDN.34"
    ::= { isdnEventObjects34 1 }

isdn34_interface OBJECT-TYPE
    SYNTAX DisplayString
    MAX-ACCESS accessible-for-notify
    STATUS current
    DESCRIPTION
        "Parameter 'interface' in event ISDN.34"
    ::= { isdnEventObjects34 2 }

isdnEventObjects35 OBJECT-IDENTITY
    STATUS current
    DESCRIPTION
        "Event ISDN.35
        FACILITY message received for the mentioned Q931 conversation."
    ::= { isdnEventsGroup 35 }

isdn35_call_ref OBJECT-TYPE
    SYNTAX Integer32
    MAX-ACCESS accessible-for-notify
    STATUS current
    DESCRIPTION
        "Parameter 'call_ref' in event ISDN.35"
    ::= { isdnEventObjects35 1 }

isdn35_interface OBJECT-TYPE
    SYNTAX DisplayString
    MAX-ACCESS accessible-for-notify
    STATUS current
    DESCRIPTION
        "Parameter 'interface' in event ISDN.35"
    ::= { isdnEventObjects35 2 }

isdnEventObjects36 OBJECT-IDENTITY
    STATUS current
    DESCRIPTION
        "Event ISDN.36
        NOTIFY message received for the mentioned Q931 conversation."
    ::= { isdnEventsGroup 36 }

isdn36_call_ref OBJECT-TYPE
    SYNTAX Integer32
    MAX-ACCESS accessible-for-notify
    STATUS current
    DESCRIPTION
        "Parameter 'call_ref' in event ISDN.36"
    ::= { isdnEventObjects36 1 }

isdn36_interface OBJECT-TYPE
    SYNTAX DisplayString
    MAX-ACCESS accessible-for-notify
    STATUS current
    DESCRIPTION
        "Parameter 'interface' in event ISDN.36"
    ::= { isdnEventObjects36 2 }

isdnEventObjects37 OBJECT-IDENTITY
    STATUS current
    DESCRIPTION
        "Event ISDN.37
        Display information elements."
    ::= { isdnEventsGroup 37 }

isdn37_sense OBJECT-TYPE
    SYNTAX DisplayString
    MAX-ACCESS accessible-for-notify
    STATUS current
    DESCRIPTION
        "Parameter 'sense' in event ISDN.37"
    ::= { isdnEventObjects37 1 }

isdn37_type OBJECT-TYPE
    SYNTAX DisplayString
    MAX-ACCESS accessible-for-notify
    STATUS current
    DESCRIPTION
        "Parameter 'type' in event ISDN.37"
    ::= { isdnEventObjects37 2 }

isdn37_length OBJECT-TYPE
    SYNTAX Integer32
    MAX-ACCESS accessible-for-notify
    STATUS current
    DESCRIPTION
        "Parameter 'length' in event ISDN.37"
    ::= { isdnEventObjects37 3 }

isdn37_data OBJECT-TYPE
    SYNTAX DisplayString
    MAX-ACCESS accessible-for-notify
    STATUS current
    DESCRIPTION
        "Parameter 'data' in event ISDN.37"
    ::= { isdnEventObjects37 4 }

isdnEventObjects38 OBJECT-IDENTITY
    STATUS current
    DESCRIPTION
        "Event ISDN.38
        An MAN_INFO message has been transmited in order to initialize SPID."
    ::= { isdnEventsGroup 38 }

isdn38_call_ref OBJECT-TYPE
    SYNTAX Integer32
    MAX-ACCESS accessible-for-notify
    STATUS current
    DESCRIPTION
        "Parameter 'call_ref' in event ISDN.38"
    ::= { isdnEventObjects38 1 }

isdn38_usid OBJECT-TYPE
    SYNTAX Integer32
    MAX-ACCESS accessible-for-notify
    STATUS current
    DESCRIPTION
        "Parameter 'usid' in event ISDN.38"
    ::= { isdnEventObjects38 2 }

isdn38_tid OBJECT-TYPE
    SYNTAX Integer32
    MAX-ACCESS accessible-for-notify
    STATUS current
    DESCRIPTION
        "Parameter 'tid' in event ISDN.38"
    ::= { isdnEventObjects38 3 }

isdn38_interfaces OBJECT-TYPE
    SYNTAX DisplayString
    MAX-ACCESS accessible-for-notify
    STATUS current
    DESCRIPTION
        "Parameter 'interfaces' in event ISDN.38"
    ::= { isdnEventObjects38 4 }

isdnEventObjects39 OBJECT-IDENTITY
    STATUS current
    DESCRIPTION
        "Event ISDN.39
        Indicated interface is not available due to physical and/or LAPD problems"
    ::= { isdnEventsGroup 39 }

isdn39_interface OBJECT-TYPE
    SYNTAX DisplayString
    MAX-ACCESS accessible-for-notify
    STATUS current
    DESCRIPTION
        "Parameter 'interface' in event ISDN.39"
    ::= { isdnEventObjects39 1 }

isdnEventObjects40 OBJECT-IDENTITY
    STATUS current
    DESCRIPTION
        "Event ISDN.40
        Indicated interface is available to make calls. This means that physcal level is active and LAPD is established"
    ::= { isdnEventsGroup 40 }

isdn40_interface OBJECT-TYPE
    SYNTAX DisplayString
    MAX-ACCESS accessible-for-notify
    STATUS current
    DESCRIPTION
        "Parameter 'interface' in event ISDN.40"
    ::= { isdnEventObjects40 1 }

isdnEventObjects41 OBJECT-IDENTITY
    STATUS current
    DESCRIPTION
        "Event ISDN.41
        An PROGRESS message has been transmitted."
    ::= { isdnEventsGroup 41 }

isdn41_call_ref OBJECT-TYPE
    SYNTAX Integer32
    MAX-ACCESS accessible-for-notify
    STATUS current
    DESCRIPTION
        "Parameter 'call_ref' in event ISDN.41"
    ::= { isdnEventObjects41 1 }

isdn41_interface OBJECT-TYPE
    SYNTAX DisplayString
    MAX-ACCESS accessible-for-notify
    STATUS current
    DESCRIPTION
        "Parameter 'interface' in event ISDN.41"
    ::= { isdnEventObjects41 2 }


isdnNotification1 NOTIFICATION-TYPE
    OBJECTS { 
              isdn1_call_ref, 
              isdn1_interface 
            }
    STATUS current
    DESCRIPTION
        "Notification of Event ISDN.1

        Message: 'An ALERTING message has been received with Call Reference $1 interface $2'

        Parameters list:
              $1: isdn1_call_ref
              $2: isdn1_interface

        ALERTING message received for the mentioned Q931 conversation."
    ::= { isdnNotificationsPrefix 1 }

isdnNotification2 NOTIFICATION-TYPE
    OBJECTS { 
              isdn2_call_ref, 
              isdn2_interface 
            }
    STATUS current
    DESCRIPTION
        "Notification of Event ISDN.2

        Message: 'A CONN ACK message has been received with Call Reference $1 interface $2'

        Parameters list:
              $1: isdn2_call_ref
              $2: isdn2_interface

        CONN ACK message received for the mentioned Q931 conversation."
    ::= { isdnNotificationsPrefix 2 }

isdnNotification3 NOTIFICATION-TYPE
    OBJECTS { 
              isdn3_call_ref, 
              isdn3_interface 
            }
    STATUS current
    DESCRIPTION
        "Notification of Event ISDN.3

        Message: 'A CONN message has been received with Call Reference $1 interface $2'

        Parameters list:
              $1: isdn3_call_ref
              $2: isdn3_interface

        CONN message received for the mentioned Q931 conversation."
    ::= { isdnNotificationsPrefix 3 }

isdnNotification4 NOTIFICATION-TYPE
    OBJECTS { 
              isdn4_call_ref, 
              isdn4_chan,
              isdn4_interface 
            }
    STATUS current
    DESCRIPTION
        "Notification of Event ISDN.4

        Message: 'A CALL PROC message has been received with Call Reference $1 assigning B channel $2e $3'

        Parameters list:
              $1: isdn4_call_ref
              $2: isdn4_chan
              $3: isdn4_interface

        CALL PROC message received for the mentioned Q931 conversation."
    ::= { isdnNotificationsPrefix 4 }

isdnNotification5 NOTIFICATION-TYPE
    OBJECTS { 
              isdn5_call_ref, 
              isdn5_cause,
              isdn5_cost,
              isdn5_interface 
            }
    STATUS current
    DESCRIPTION
        "Notification of Event ISDN.5

        Message: 'A DISC message has been received with Call Reference $1, Cause $2 and Cost $3 interface $4'

        Parameters list:
              $1: isdn5_call_ref
              $2: isdn5_cause
              $3: isdn5_cost
              $4: isdn5_interface

        DISC message received for the mentioned Q931 conversation."
    ::= { isdnNotificationsPrefix 5 }

isdnNotification6 NOTIFICATION-TYPE
    OBJECTS { 
              isdn6_call_ref, 
              isdn6_interface 
            }
    STATUS current
    DESCRIPTION
        "Notification of Event ISDN.6

        Message: 'A INFO message has been received with Call Reference $1 interface $2'

        Parameters list:
              $1: isdn6_call_ref
              $2: isdn6_interface

        INFO message received for the mentioned Q931 conversation."
    ::= { isdnNotificationsPrefix 6 }

isdnNotification7 NOTIFICATION-TYPE
    OBJECTS { 
              isdn7_call_ref, 
              isdn7_interface 
            }
    STATUS current
    DESCRIPTION
        "Notification of Event ISDN.7

        Message: 'A PROGR message has been received with Call Reference $1 interface $2'

        Parameters list:
              $1: isdn7_call_ref
              $2: isdn7_interface

        PROGR message received for the mentioned Q931 conversation."
    ::= { isdnNotificationsPrefix 7 }

isdnNotification8 NOTIFICATION-TYPE
    OBJECTS { 
              isdn8_call_ref, 
              isdn8_cause,
              isdn8_cost,
              isdn8_interface 
            }
    STATUS current
    DESCRIPTION
        "Notification of Event ISDN.8

        Message: 'A RELEASE message has been received with Call Reference $1, Cause $2 and Cost $3 interface $4'

        Parameters list:
              $1: isdn8_call_ref
              $2: isdn8_cause
              $3: isdn8_cost
              $4: isdn8_interface

        RELEASE message received for the mentioned Q931 conversation."
    ::= { isdnNotificationsPrefix 8 }

isdnNotification9 NOTIFICATION-TYPE
    OBJECTS { 
              isdn9_call_ref, 
              isdn9_cause,
              isdn9_cost,
              isdn9_interface 
            }
    STATUS current
    DESCRIPTION
        "Notification of Event ISDN.9

        Message: 'A REL COMPLETE message has been received with Call Reference $1, Cause $2 and Cost $3 interface $4'

        Parameters list:
              $1: isdn9_call_ref
              $2: isdn9_cause
              $3: isdn9_cost
              $4: isdn9_interface

        REL COMPLETE message received for the mentioned Q931 conversation."
    ::= { isdnNotificationsPrefix 9 }

isdnNotification10 NOTIFICATION-TYPE
    OBJECTS { 
              isdn10_call_ref, 
              isdn10_interface 
            }
    STATUS current
    DESCRIPTION
        "Notification of Event ISDN.10

        Message: 'A STATUS message has been received with Call Reference $1 interface $2'

        Parameters list:
              $1: isdn10_call_ref
              $2: isdn10_interface

        STATUS message received for the mentioned Q931 conversation."
    ::= { isdnNotificationsPrefix 10 }

isdnNotification11 NOTIFICATION-TYPE
    OBJECTS { 
              isdn11_call_ref, 
              isdn11_chan,
              isdn11_caller_num,
              isdn11_interface 
            }
    STATUS current
    DESCRIPTION
        "Notification of Event ISDN.11

        Message: 'A SETUP message has been received with Call Reference $1, assigning B channel $2 and with Calling Number $3 interface $4'

        Parameters list:
              $1: isdn11_call_ref
              $2: isdn11_chan
              $3: isdn11_caller_num
              $4: isdn11_interface

        SETUP message received for the mentioned Q931 conversation."
    ::= { isdnNotificationsPrefix 11 }

isdnNotification12 NOTIFICATION-TYPE
    OBJECTS { 
              isdn12_called, 
              isdn12_caller,
              isdn12_interface 
            }
    STATUS current
    DESCRIPTION
        "Notification of Event ISDN.12

        Message: 'An incoming call has been established Called:$1  Caller $2 interface $3'

        Parameters list:
              $1: isdn12_called
              $2: isdn12_caller
              $3: isdn12_interface

        An incoming call has been established."
    ::= { isdnNotificationsPrefix 12 }

isdnNotification13 NOTIFICATION-TYPE
    OBJECTS { 
              isdn13_called, 
              isdn13_caller,
              isdn13_interface 
            }
    STATUS current
    DESCRIPTION
        "Notification of Event ISDN.13

        Message: 'An outgoing call has been established Called:$1  Caller $2 interface $3'

        Parameters list:
              $1: isdn13_called
              $2: isdn13_caller
              $3: isdn13_interface

        An outgoing call has been established."
    ::= { isdnNotificationsPrefix 13 }

isdnNotification14 NOTIFICATION-TYPE
    OBJECTS { 
              isdn14_called, 
              isdn14_caller,
              isdn14_interface 
            }
    STATUS current
    DESCRIPTION
        "Notification of Event ISDN.14

        Message: 'An incoming call has been released Called:$1  Caller $2 interface $3'

        Parameters list:
              $1: isdn14_called
              $2: isdn14_caller
              $3: isdn14_interface

        An incoming call has been released."
    ::= { isdnNotificationsPrefix 14 }

isdnNotification15 NOTIFICATION-TYPE
    OBJECTS { 
              isdn15_called, 
              isdn15_caller,
              isdn15_interface 
            }
    STATUS current
    DESCRIPTION
        "Notification of Event ISDN.15

        Message: 'An outgoing call has been released Called:$1  Caller $2 interface $3'

        Parameters list:
              $1: isdn15_called
              $2: isdn15_caller
              $3: isdn15_interface

        An outgoing call has been released."
    ::= { isdnNotificationsPrefix 15 }

isdnNotification16 NOTIFICATION-TYPE
    OBJECTS { 
              isdn16_call_ref, 
              isdn16_chan,
              isdn16_interface 
            }
    STATUS current
    DESCRIPTION
        "Notification of Event ISDN.16

        Message: 'A CONN message has been transmitted with Call Reference $1, confirming B channel $2 interface $3'

        Parameters list:
              $1: isdn16_call_ref
              $2: isdn16_chan
              $3: isdn16_interface

        CONN message transmitted for the mentioned Q931 conversation."
    ::= { isdnNotificationsPrefix 16 }

isdnNotification17 NOTIFICATION-TYPE
    OBJECTS { 
              isdn17_call_ref, 
              isdn17_interface 
            }
    STATUS current
    DESCRIPTION
        "Notification of Event ISDN.17

        Message: 'A CONN ACK message has been transmitted with Call Reference $1 interface $2'

        Parameters list:
              $1: isdn17_call_ref
              $2: isdn17_interface

        CONN ACK message transmitted for the mentioned Q931 conversation."
    ::= { isdnNotificationsPrefix 17 }

isdnNotification18 NOTIFICATION-TYPE
    OBJECTS { 
              isdn18_call_ref, 
              isdn18_cause,
              isdn18_interface 
            }
    STATUS current
    DESCRIPTION
        "Notification of Event ISDN.18

        Message: 'A DISC message has been transmitted with Call Reference $1, and Cause $2 interface $3'

        Parameters list:
              $1: isdn18_call_ref
              $2: isdn18_cause
              $3: isdn18_interface

        DISC message transmitted for the mentioned Q931 conversation."
    ::= { isdnNotificationsPrefix 18 }

isdnNotification19 NOTIFICATION-TYPE
    OBJECTS { 
              isdn19_call_ref, 
              isdn19_cause,
              isdn19_interface 
            }
    STATUS current
    DESCRIPTION
        "Notification of Event ISDN.19

        Message: 'A REL message has been transmitted with Call Reference $1, and Cause $2 interface $3'

        Parameters list:
              $1: isdn19_call_ref
              $2: isdn19_cause
              $3: isdn19_interface

        REL message transmitted for the mentioned Q931 conversation."
    ::= { isdnNotificationsPrefix 19 }

isdnNotification20 NOTIFICATION-TYPE
    OBJECTS { 
              isdn20_call_ref, 
              isdn20_cause,
              isdn20_interface 
            }
    STATUS current
    DESCRIPTION
        "Notification of Event ISDN.20

        Message: 'A REL COM message has been transmitted with Call Reference $1, and Cause $2 interface $3'

        Parameters list:
              $1: isdn20_call_ref
              $2: isdn20_cause
              $3: isdn20_interface

        REL COM message transmitted for the mentioned Q931 conversation."
    ::= { isdnNotificationsPrefix 20 }

isdnNotification21 NOTIFICATION-TYPE
    OBJECTS { 
              isdn21_call_ref, 
              isdn21_called_num,
              isdn21_interface 
            }
    STATUS current
    DESCRIPTION
        "Notification of Event ISDN.21

        Message: 'A SETUP message has been transmitted with Call Reference $1, and Called Number $2 interface $3'

        Parameters list:
              $1: isdn21_call_ref
              $2: isdn21_called_num
              $3: isdn21_interface

        SETUP message transmitted for the mentioned Q931 conversation."
    ::= { isdnNotificationsPrefix 21 }

isdnNotification22 NOTIFICATION-TYPE
    OBJECTS { 
              isdn22_call_ref, 
              isdn22_status,
              isdn22_interface 
            }
    STATUS current
    DESCRIPTION
        "Notification of Event ISDN.22

        Message: 'A STATUS message has been transmitted with Call Reference $1, indicating Status $2 interface $3'

        Parameters list:
              $1: isdn22_call_ref
              $2: isdn22_status
              $3: isdn22_interface

        STATUS message transmitted for the mentioned Q931 conversation."
    ::= { isdnNotificationsPrefix 22 }

isdnNotification23 NOTIFICATION-TYPE
    OBJECTS { 
              isdn23_frame_tx, 
              isdn23_interface 
            }
    STATUS current
    DESCRIPTION
        "Notification of Event ISDN.23

        Message: 'Sent FRAME: $1 interface $2'

        Parameters list:
              $1: isdn23_frame_tx
              $2: isdn23_interface

        message transmitted contents."
    ::= { isdnNotificationsPrefix 23 }

isdnNotification24 NOTIFICATION-TYPE
    OBJECTS { 
              isdn24_frame_rx, 
              isdn24_interface 
            }
    STATUS current
    DESCRIPTION
        "Notification of Event ISDN.24

        Message: 'Received FRAME: $1 interface $2'

        Parameters list:
              $1: isdn24_frame_rx
              $2: isdn24_interface

        message received contents."
    ::= { isdnNotificationsPrefix 24 }

isdnNotification25 NOTIFICATION-TYPE
    OBJECTS { 
              isdn25_restart_ind, 
              isdn25_channel_id,
              isdn25_interface 
            }
    STATUS current
    DESCRIPTION
        "Notification of Event ISDN.25

        Message: 'A RESTART message has been received with class $1  $2 interface $3'

        Parameters list:
              $1: isdn25_restart_ind
              $2: isdn25_channel_id
              $3: isdn25_interface

        RESTART message received."
    ::= { isdnNotificationsPrefix 25 }

isdnNotification26 NOTIFICATION-TYPE
    OBJECTS { 
              isdn26_interface 
            }
    STATUS current
    DESCRIPTION
        "Notification of Event ISDN.26

        Message: 'A RESTART ACK message has been transmitted interface $1'

        Parameters list:
              $1: isdn26_interface

        A RESTART ACK message has been transmitted."
    ::= { isdnNotificationsPrefix 26 }

isdnNotification27 NOTIFICATION-TYPE
    OBJECTS { 
              isdn27_call_ref, 
              isdn27_spid,
              isdn27_interface 
            }
    STATUS current
    DESCRIPTION
        "Notification of Event ISDN.27

        Message: 'An INFO message has been transmited with Call Reference $1 SPID $2 interface $3'

        Parameters list:
              $1: isdn27_call_ref
              $2: isdn27_spid
              $3: isdn27_interface

        An INFO message has been transmited in order to initialize SPID."
    ::= { isdnNotificationsPrefix 27 }

isdnNotification28 NOTIFICATION-TYPE
    OBJECTS { 
              isdn28_spid, 
              isdn28_interface 
            }
    STATUS current
    DESCRIPTION
        "Notification of Event ISDN.28

        Message: 'An INFO message has been transmited with SPID n— $1 interface $2'

        Parameters list:
              $1: isdn28_spid
              $2: isdn28_interface

        SPEED is being sending to the network."
    ::= { isdnNotificationsPrefix 28 }

isdnNotification29 NOTIFICATION-TYPE
    OBJECTS { 
              isdn29_spid, 
              isdn29_interface 
            }
    STATUS current
    DESCRIPTION
        "Notification of Event ISDN.29

        Message: 'An INFO message has been received acknowing successfully SPID $1 initialize interface $2'

        Parameters list:
              $1: isdn29_spid
              $2: isdn29_interface

        An INFO message has been received acknowing successfully SPID initialize."
    ::= { isdnNotificationsPrefix 29 }

isdnNotification30 NOTIFICATION-TYPE
    OBJECTS { 
              isdn30_spid, 
              isdn30_cause,
              isdn30_interface 
            }
    STATUS current
    DESCRIPTION
        "Notification of Event ISDN.30

        Message: 'An INFO message has been received for SPID $1 with cause $2 interface $3'

        Parameters list:
              $1: isdn30_spid
              $2: isdn30_cause
              $3: isdn30_interface

        An INFO message has been received with indicated cause."
    ::= { isdnNotificationsPrefix 30 }

isdnNotification31 NOTIFICATION-TYPE
    OBJECTS { 
              isdn31_call_ref, 
              isdn31_interface 
            }
    STATUS current
    DESCRIPTION
        "Notification of Event ISDN.31

        Message: 'A CALL PROCEEDING message has been transmitted   Call Ref $1 interface $2'

        Parameters list:
              $1: isdn31_call_ref
              $2: isdn31_interface

        A CALL PROCEEDING message has been transmitted."
    ::= { isdnNotificationsPrefix 31 }

isdnNotification32 NOTIFICATION-TYPE
    OBJECTS { 
              isdn32_call_ref, 
              isdn32_interface 
            }
    STATUS current
    DESCRIPTION
        "Notification of Event ISDN.32

        Message: 'A ALERTING message has been transmitted   Call Ref $1 interface $2'

        Parameters list:
              $1: isdn32_call_ref
              $2: isdn32_interface

        An ALERTING message has been transmitted."
    ::= { isdnNotificationsPrefix 32 }

isdnNotification33 NOTIFICATION-TYPE
    OBJECTS { 
              isdn33_call_ref, 
              isdn33_interface 
            }
    STATUS current
    DESCRIPTION
        "Notification of Event ISDN.33

        Message: 'A SETUP_ACK message has been transmitted   Call Ref $1 interface $2'

        Parameters list:
              $1: isdn33_call_ref
              $2: isdn33_interface

        A SETUP_ACK message has been transmitted."
    ::= { isdnNotificationsPrefix 33 }

isdnNotification34 NOTIFICATION-TYPE
    OBJECTS { 
              isdn34_call_ref, 
              isdn34_interface 
            }
    STATUS current
    DESCRIPTION
        "Notification of Event ISDN.34

        Message: 'A SETUP ACK message has been received with Call Reference $1 interface $2'

        Parameters list:
              $1: isdn34_call_ref
              $2: isdn34_interface

        SETUP ACK message received for the mentioned Q931 conversation."
    ::= { isdnNotificationsPrefix 34 }

isdnNotification35 NOTIFICATION-TYPE
    OBJECTS { 
              isdn35_call_ref, 
              isdn35_interface 
            }
    STATUS current
    DESCRIPTION
        "Notification of Event ISDN.35

        Message: 'A FACILITY message has been received with Call Reference $1 interface $2'

        Parameters list:
              $1: isdn35_call_ref
              $2: isdn35_interface

        FACILITY message received for the mentioned Q931 conversation."
    ::= { isdnNotificationsPrefix 35 }

isdnNotification36 NOTIFICATION-TYPE
    OBJECTS { 
              isdn36_call_ref, 
              isdn36_interface 
            }
    STATUS current
    DESCRIPTION
        "Notification of Event ISDN.36

        Message: 'A NOTIFY message has been received with Call Reference $1 interface $2'

        Parameters list:
              $1: isdn36_call_ref
              $2: isdn36_interface

        NOTIFY message received for the mentioned Q931 conversation."
    ::= { isdnNotificationsPrefix 36 }

isdnNotification37 NOTIFICATION-TYPE
    OBJECTS { 
              isdn37_sense, 
              isdn37_type,
              isdn37_length,
              isdn37_data 
            }
    STATUS current
    DESCRIPTION
        "Notification of Event ISDN.37

        Message: 'Info Element: Sense $1, Type $2, Len $3, Value: $4'

        Parameters list:
              $1: isdn37_sense
              $2: isdn37_type
              $3: isdn37_length
              $4: isdn37_data

        Display information elements."
    ::= { isdnNotificationsPrefix 37 }

isdnNotification38 NOTIFICATION-TYPE
    OBJECTS { 
              isdn38_call_ref, 
              isdn38_usid,
              isdn38_tid,
              isdn38_interfaces 
            }
    STATUS current
    DESCRIPTION
        "Notification of Event ISDN.38

        Message: 'An MAN_INFO message has been transmited with Call Reference $1  USID:$2 TID:$3 interface $4'

        Parameters list:
              $1: isdn38_call_ref
              $2: isdn38_usid
              $3: isdn38_tid
              $4: isdn38_interfaces

        An MAN_INFO message has been transmited in order to initialize SPID."
    ::= { isdnNotificationsPrefix 38 }

isdnNotification39 NOTIFICATION-TYPE
    OBJECTS { 
              isdn39_interface 
            }
    STATUS current
    DESCRIPTION
        "Notification of Event ISDN.39

        Message: 'Interface is NOT available to make calls $1'

        Parameters list:
              $1: isdn39_interface

        Indicated interface is not available due to physical and/or LAPD problems"
    ::= { isdnNotificationsPrefix 39 }

isdnNotification40 NOTIFICATION-TYPE
    OBJECTS { 
              isdn40_interface 
            }
    STATUS current
    DESCRIPTION
        "Notification of Event ISDN.40

        Message: 'Interface is available to make calls $1'

        Parameters list:
              $1: isdn40_interface

        Indicated interface is available to make calls. This means that physcal level is active and LAPD is established"
    ::= { isdnNotificationsPrefix 40 }

isdnNotification41 NOTIFICATION-TYPE
    OBJECTS { 
              isdn41_call_ref, 
              isdn41_interface 
            }
    STATUS current
    DESCRIPTION
        "Notification of Event ISDN.41

        Message: 'A PROGRESS message has been transmitted   Call Ref $1 interface $2'

        Parameters list:
              $1: isdn41_call_ref
              $2: isdn41_interface

        An PROGRESS message has been transmitted."
    ::= { isdnNotificationsPrefix 41 }


END
