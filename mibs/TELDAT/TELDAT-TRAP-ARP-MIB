-- file automatically created


TELDAT-TRAP-ARP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


arpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ARP event subsystem."
    REVISION "201401200930Z"
    DESCRIPTION "Initial implementation"
        ::= { telEventTraps 5 }


arpEventsGroup	OBJECT IDENTIFIER	::= { arpTrapsMIB 1 }

arpNotifications	OBJECT IDENTIFIER	::= { arpTrapsMIB 2 }
arpNotificationsPrefix	OBJECT IDENTIFIER	::= { arpNotifications 0 }

arpEventObjects1 OBJECT-IDENTITY
    STATUS current
    DESCRIPTION
        "Event ARP.1
        A packet was discarded because the queue of pending ARP packets
        to process is too long. This means the number of received ARP packets
        is so high that they cannot be processed."
    ::= { arpEventsGroup 1 }

arp1_interface OBJECT-TYPE
    SYNTAX DisplayString
    MAX-ACCESS accessible-for-notify
    STATUS current
    DESCRIPTION
        "Parameter 'interface' in event ARP.1"
    ::= { arpEventObjects1 1 }

arpEventObjects2 OBJECT-IDENTITY
    STATUS current
    DESCRIPTION
        "Event ARP.2
        An ARP packet of the type indicated has just arrived for processing."
    ::= { arpEventsGroup 2 }

arp2_operation_type OBJECT-TYPE
    SYNTAX Integer32
    MAX-ACCESS accessible-for-notify
    STATUS current
    DESCRIPTION
        "Parameter 'operation_type' in event ARP.2"
    ::= { arpEventObjects2 1 }

arp2_hardware_type OBJECT-TYPE
    SYNTAX Integer32
    MAX-ACCESS accessible-for-notify
    STATUS current
    DESCRIPTION
        "Parameter 'hardware_type' in event ARP.2"
    ::= { arpEventObjects2 2 }

arp2_protocol_type OBJECT-TYPE
    SYNTAX Integer32
    MAX-ACCESS accessible-for-notify
    STATUS current
    DESCRIPTION
        "Parameter 'protocol_type' in event ARP.2"
    ::= { arpEventObjects2 3 }

arp2_interface OBJECT-TYPE
    SYNTAX DisplayString
    MAX-ACCESS accessible-for-notify
    STATUS current
    DESCRIPTION
        "Parameter 'interface' in event ARP.2"
    ::= { arpEventObjects2 4 }

arpEventObjects3 OBJECT-IDENTITY
    STATUS current
    DESCRIPTION
        "Event ARP.3
        An ARP reply is being sent as the result of a request for a translation
        from another host."
    ::= { arpEventsGroup 3 }

arp3_hardware_type OBJECT-TYPE
    SYNTAX Integer32
    MAX-ACCESS accessible-for-notify
    STATUS current
    DESCRIPTION
        "Parameter 'hardware_type' in event ARP.3"
    ::= { arpEventObjects3 1 }

arp3_protocol_type OBJECT-TYPE
    SYNTAX Integer32
    MAX-ACCESS accessible-for-notify
    STATUS current
    DESCRIPTION
        "Parameter 'protocol_type' in event ARP.3"
    ::= { arpEventObjects3 2 }

arp3_interface OBJECT-TYPE
    SYNTAX DisplayString
    MAX-ACCESS accessible-for-notify
    STATUS current
    DESCRIPTION
        "Parameter 'interface' in event ARP.3"
    ::= { arpEventObjects3 3 }

arpEventObjects4 OBJECT-IDENTITY
    STATUS current
    DESCRIPTION
        "Event ARP.4
        A translation cache entry timed out (which was not used or refreshed
        recently) has been deleted."
    ::= { arpEventsGroup 4 }

arp4_hardware_type OBJECT-TYPE
    SYNTAX Integer32
    MAX-ACCESS accessible-for-notify
    STATUS current
    DESCRIPTION
        "Parameter 'hardware_type' in event ARP.4"
    ::= { arpEventObjects4 1 }

arp4_protocol_type OBJECT-TYPE
    SYNTAX Integer32
    MAX-ACCESS accessible-for-notify
    STATUS current
    DESCRIPTION
        "Parameter 'protocol_type' in event ARP.4"
    ::= { arpEventObjects4 2 }

arp4_interface OBJECT-TYPE
    SYNTAX DisplayString
    MAX-ACCESS accessible-for-notify
    STATUS current
    DESCRIPTION
        "Parameter 'interface' in event ARP.4"
    ::= { arpEventObjects4 3 }

arpEventObjects5 OBJECT-IDENTITY
    STATUS current
    DESCRIPTION
        "Event ARP.5
        An ARP translation request is being sent as a result of the transmission
        of a frame to another host. As the host address is unknown, the ARP
        address resolution process is started broadcasting an ARP request."
    ::= { arpEventsGroup 5 }

arp5_hardware_type OBJECT-TYPE
    SYNTAX Integer32
    MAX-ACCESS accessible-for-notify
    STATUS current
    DESCRIPTION
        "Parameter 'hardware_type' in event ARP.5"
    ::= { arpEventObjects5 1 }

arp5_protocol_type OBJECT-TYPE
    SYNTAX Integer32
    MAX-ACCESS accessible-for-notify
    STATUS current
    DESCRIPTION
        "Parameter 'protocol_type' in event ARP.5"
    ::= { arpEventObjects5 2 }

arp5_interface OBJECT-TYPE
    SYNTAX DisplayString
    MAX-ACCESS accessible-for-notify
    STATUS current
    DESCRIPTION
        "Parameter 'interface' in event ARP.5"
    ::= { arpEventObjects5 3 }

arpEventObjects6 OBJECT-IDENTITY
    STATUS current
    DESCRIPTION
        "Event ARP.6
        An ARP translation request is being sent as the result of
        the auto-refresh mechanism: the refresh timer for a dynamic entry is
        going to expire. When available, this request is sent directly to the
        MAC address in the current translation instead of a broadcast to all
        hosts."
    ::= { arpEventsGroup 6 }

arp6_hardware_type OBJECT-TYPE
    SYNTAX Integer32
    MAX-ACCESS accessible-for-notify
    STATUS current
    DESCRIPTION
        "Parameter 'hardware_type' in event ARP.6"
    ::= { arpEventObjects6 1 }

arp6_protocol_type OBJECT-TYPE
    SYNTAX Integer32
    MAX-ACCESS accessible-for-notify
    STATUS current
    DESCRIPTION
        "Parameter 'protocol_type' in event ARP.6"
    ::= { arpEventObjects6 2 }

arp6_interface OBJECT-TYPE
    SYNTAX DisplayString
    MAX-ACCESS accessible-for-notify
    STATUS current
    DESCRIPTION
        "Parameter 'interface' in event ARP.6"
    ::= { arpEventObjects6 3 }

arpEventObjects7 OBJECT-IDENTITY
    STATUS current
    DESCRIPTION
        "Event ARP.7
        During the input processing of an ARP packet, the router did not have
        memory available to make a new dynamic ARP entry for the given protocol."
    ::= { arpEventsGroup 7 }

arp7_protocol_type OBJECT-TYPE
    SYNTAX Integer32
    MAX-ACCESS accessible-for-notify
    STATUS current
    DESCRIPTION
        "Parameter 'protocol_type' in event ARP.7"
    ::= { arpEventObjects7 1 }

arp7_interface OBJECT-TYPE
    SYNTAX DisplayString
    MAX-ACCESS accessible-for-notify
    STATUS current
    DESCRIPTION
        "Parameter 'interface' in event ARP.7"
    ::= { arpEventObjects7 2 }

arpEventObjects8 OBJECT-IDENTITY
    STATUS current
    DESCRIPTION
        "Event ARP.8
        An ARP packet of the type indicated has just arrived for processing."
    ::= { arpEventsGroup 8 }

arp8_operation_type OBJECT-TYPE
    SYNTAX DisplayString
    MAX-ACCESS accessible-for-notify
    STATUS current
    DESCRIPTION
        "Parameter 'operation_type' in event ARP.8"
    ::= { arpEventObjects8 1 }

arp8_src_address OBJECT-TYPE
    SYNTAX IpAddress
    MAX-ACCESS accessible-for-notify
    STATUS current
    DESCRIPTION
        "Parameter 'src_address' in event ARP.8"
    ::= { arpEventObjects8 2 }

arp8_dest_address OBJECT-TYPE
    SYNTAX IpAddress
    MAX-ACCESS accessible-for-notify
    STATUS current
    DESCRIPTION
        "Parameter 'dest_address' in event ARP.8"
    ::= { arpEventObjects8 3 }

arp8_interface OBJECT-TYPE
    SYNTAX DisplayString
    MAX-ACCESS accessible-for-notify
    STATUS current
    DESCRIPTION
        "Parameter 'interface' in event ARP.8"
    ::= { arpEventObjects8 4 }

arpEventObjects9 OBJECT-IDENTITY
    STATUS current
    DESCRIPTION
        "Event ARP.9
        An ARP reply is being sent as the result of a request for a translation
        from another host."
    ::= { arpEventsGroup 9 }

arp9_operation_type OBJECT-TYPE
    SYNTAX DisplayString
    MAX-ACCESS accessible-for-notify
    STATUS current
    DESCRIPTION
        "Parameter 'operation_type' in event ARP.9"
    ::= { arpEventObjects9 1 }

arp9_src_address OBJECT-TYPE
    SYNTAX IpAddress
    MAX-ACCESS accessible-for-notify
    STATUS current
    DESCRIPTION
        "Parameter 'src_address' in event ARP.9"
    ::= { arpEventObjects9 2 }

arp9_dest_address OBJECT-TYPE
    SYNTAX IpAddress
    MAX-ACCESS accessible-for-notify
    STATUS current
    DESCRIPTION
        "Parameter 'dest_address' in event ARP.9"
    ::= { arpEventObjects9 3 }

arp9_interface OBJECT-TYPE
    SYNTAX DisplayString
    MAX-ACCESS accessible-for-notify
    STATUS current
    DESCRIPTION
        "Parameter 'interface' in event ARP.9"
    ::= { arpEventObjects9 4 }

arpEventObjects10 OBJECT-IDENTITY
    STATUS current
    DESCRIPTION
        "Event ARP.10
        An ARP packet has been dropped while it was being sent out."
    ::= { arpEventsGroup 10 }

arp10_operation_type OBJECT-TYPE
    SYNTAX DisplayString
    MAX-ACCESS accessible-for-notify
    STATUS current
    DESCRIPTION
        "Parameter 'operation_type' in event ARP.10"
    ::= { arpEventObjects10 1 }

arp10_protocol_type OBJECT-TYPE
    SYNTAX Integer32
    MAX-ACCESS accessible-for-notify
    STATUS current
    DESCRIPTION
        "Parameter 'protocol_type' in event ARP.10"
    ::= { arpEventObjects10 2 }

arp10_interface OBJECT-TYPE
    SYNTAX DisplayString
    MAX-ACCESS accessible-for-notify
    STATUS current
    DESCRIPTION
        "Parameter 'interface' in event ARP.10"
    ::= { arpEventObjects10 3 }

arpEventObjects11 OBJECT-IDENTITY
    STATUS current
    DESCRIPTION
        "Event ARP.11
        Auto-refresh process was launched as a result of using an entry near its
        expiration time."
    ::= { arpEventsGroup 11 }

arp11_hardware_type OBJECT-TYPE
    SYNTAX Integer32
    MAX-ACCESS accessible-for-notify
    STATUS current
    DESCRIPTION
        "Parameter 'hardware_type' in event ARP.11"
    ::= { arpEventObjects11 1 }

arp11_protocol_type OBJECT-TYPE
    SYNTAX Integer32
    MAX-ACCESS accessible-for-notify
    STATUS current
    DESCRIPTION
        "Parameter 'protocol_type' in event ARP.11"
    ::= { arpEventObjects11 2 }

arp11_protocol_address OBJECT-TYPE
    SYNTAX DisplayString
    MAX-ACCESS accessible-for-notify
    STATUS current
    DESCRIPTION
        "Parameter 'protocol_address' in event ARP.11"
    ::= { arpEventObjects11 3 }

arp11_interface OBJECT-TYPE
    SYNTAX DisplayString
    MAX-ACCESS accessible-for-notify
    STATUS current
    DESCRIPTION
        "Parameter 'interface' in event ARP.11"
    ::= { arpEventObjects11 4 }

arpEventObjects12 OBJECT-IDENTITY
    STATUS current
    DESCRIPTION
        "Event ARP.12
        Hardware address has been cleared from protocol caches. This may be due
        to hardware address learning, refresh process, network failure, or
        configuration changes."
    ::= { arpEventsGroup 12 }

arp12_hardware_type OBJECT-TYPE
    SYNTAX Integer32
    MAX-ACCESS accessible-for-notify
    STATUS current
    DESCRIPTION
        "Parameter 'hardware_type' in event ARP.12"
    ::= { arpEventObjects12 1 }

arp12_protocol_type OBJECT-TYPE
    SYNTAX Integer32
    MAX-ACCESS accessible-for-notify
    STATUS current
    DESCRIPTION
        "Parameter 'protocol_type' in event ARP.12"
    ::= { arpEventObjects12 2 }

arp12_protocol_address OBJECT-TYPE
    SYNTAX DisplayString
    MAX-ACCESS accessible-for-notify
    STATUS current
    DESCRIPTION
        "Parameter 'protocol_address' in event ARP.12"
    ::= { arpEventObjects12 3 }

arp12_interface OBJECT-TYPE
    SYNTAX DisplayString
    MAX-ACCESS accessible-for-notify
    STATUS current
    DESCRIPTION
        "Parameter 'interface' in event ARP.12"
    ::= { arpEventObjects12 4 }

arpEventObjects13 OBJECT-IDENTITY
    STATUS current
    DESCRIPTION
        "Event ARP.13
        An ARP request is being sent for an address translation of another host."
    ::= { arpEventsGroup 13 }

arp13_operation_type OBJECT-TYPE
    SYNTAX DisplayString
    MAX-ACCESS accessible-for-notify
    STATUS current
    DESCRIPTION
        "Parameter 'operation_type' in event ARP.13"
    ::= { arpEventObjects13 1 }

arp13_src_address OBJECT-TYPE
    SYNTAX IpAddress
    MAX-ACCESS accessible-for-notify
    STATUS current
    DESCRIPTION
        "Parameter 'src_address' in event ARP.13"
    ::= { arpEventObjects13 2 }

arp13_dest_address OBJECT-TYPE
    SYNTAX IpAddress
    MAX-ACCESS accessible-for-notify
    STATUS current
    DESCRIPTION
        "Parameter 'dest_address' in event ARP.13"
    ::= { arpEventObjects13 3 }

arp13_interface OBJECT-TYPE
    SYNTAX DisplayString
    MAX-ACCESS accessible-for-notify
    STATUS current
    DESCRIPTION
        "Parameter 'interface' in event ARP.13"
    ::= { arpEventObjects13 4 }

arpEventObjects14 OBJECT-IDENTITY
    STATUS current
    DESCRIPTION
        "Event ARP.14
        An ARP translation request is being sent as the result of the 
        auto-refresh mechanism for this IP and mac address."
    ::= { arpEventsGroup 14 }

arp14_mac_address OBJECT-TYPE
    SYNTAX DisplayString
    MAX-ACCESS accessible-for-notify
    STATUS current
    DESCRIPTION
        "Parameter 'mac_address' in event ARP.14"
    ::= { arpEventObjects14 1 }

arp14_ip_address OBJECT-TYPE
    SYNTAX IpAddress
    MAX-ACCESS accessible-for-notify
    STATUS current
    DESCRIPTION
        "Parameter 'ip_address' in event ARP.14"
    ::= { arpEventObjects14 2 }

arp14_interface OBJECT-TYPE
    SYNTAX DisplayString
    MAX-ACCESS accessible-for-notify
    STATUS current
    DESCRIPTION
        "Parameter 'interface' in event ARP.14"
    ::= { arpEventObjects14 3 }

arpEventObjects15 OBJECT-IDENTITY
    STATUS current
    DESCRIPTION
        "Event ARP.15
        A translation cache entry timed out with this IP and mac address has 
        been deleted."
    ::= { arpEventsGroup 15 }

arp15_mac_address OBJECT-TYPE
    SYNTAX DisplayString
    MAX-ACCESS accessible-for-notify
    STATUS current
    DESCRIPTION
        "Parameter 'mac_address' in event ARP.15"
    ::= { arpEventObjects15 1 }

arp15_ip_address OBJECT-TYPE
    SYNTAX IpAddress
    MAX-ACCESS accessible-for-notify
    STATUS current
    DESCRIPTION
        "Parameter 'ip_address' in event ARP.15"
    ::= { arpEventObjects15 2 }

arp15_interface OBJECT-TYPE
    SYNTAX DisplayString
    MAX-ACCESS accessible-for-notify
    STATUS current
    DESCRIPTION
        "Parameter 'interface' in event ARP.15"
    ::= { arpEventObjects15 3 }

arpEventObjects16 OBJECT-IDENTITY
    STATUS current
    DESCRIPTION
        "Event ARP.16
        An ARP translation is being setup this IP and mac address."
    ::= { arpEventsGroup 16 }

arp16_mac_address OBJECT-TYPE
    SYNTAX DisplayString
    MAX-ACCESS accessible-for-notify
    STATUS current
    DESCRIPTION
        "Parameter 'mac_address' in event ARP.16"
    ::= { arpEventObjects16 1 }

arp16_ip_address OBJECT-TYPE
    SYNTAX IpAddress
    MAX-ACCESS accessible-for-notify
    STATUS current
    DESCRIPTION
        "Parameter 'ip_address' in event ARP.16"
    ::= { arpEventObjects16 2 }

arp16_interface OBJECT-TYPE
    SYNTAX DisplayString
    MAX-ACCESS accessible-for-notify
    STATUS current
    DESCRIPTION
        "Parameter 'interface' in event ARP.16"
    ::= { arpEventObjects16 3 }

arpEventObjects17 OBJECT-IDENTITY
    STATUS current
    DESCRIPTION
        "Event ARP.17
        An ARP translation mac address is being changed for this IP."
    ::= { arpEventsGroup 17 }

arp17_mac_address_old OBJECT-TYPE
    SYNTAX DisplayString
    MAX-ACCESS accessible-for-notify
    STATUS current
    DESCRIPTION
        "Parameter 'mac_address_old' in event ARP.17"
    ::= { arpEventObjects17 1 }

arp17_mac_address_new OBJECT-TYPE
    SYNTAX DisplayString
    MAX-ACCESS accessible-for-notify
    STATUS current
    DESCRIPTION
        "Parameter 'mac_address_new' in event ARP.17"
    ::= { arpEventObjects17 2 }

arp17_ip_address OBJECT-TYPE
    SYNTAX IpAddress
    MAX-ACCESS accessible-for-notify
    STATUS current
    DESCRIPTION
        "Parameter 'ip_address' in event ARP.17"
    ::= { arpEventObjects17 3 }

arp17_interface OBJECT-TYPE
    SYNTAX DisplayString
    MAX-ACCESS accessible-for-notify
    STATUS current
    DESCRIPTION
        "Parameter 'interface' in event ARP.17"
    ::= { arpEventObjects17 4 }

arpEventObjects18 OBJECT-IDENTITY
    STATUS current
    DESCRIPTION
        "Event ARP.18
        An ARP packet was received with a local address. The received mac and IP
        addresses are shown, as well as the interface."
    ::= { arpEventsGroup 18 }

arp18_mac_address OBJECT-TYPE
    SYNTAX DisplayString
    MAX-ACCESS accessible-for-notify
    STATUS current
    DESCRIPTION
        "Parameter 'mac_address' in event ARP.18"
    ::= { arpEventObjects18 1 }

arp18_ip_address OBJECT-TYPE
    SYNTAX IpAddress
    MAX-ACCESS accessible-for-notify
    STATUS current
    DESCRIPTION
        "Parameter 'ip_address' in event ARP.18"
    ::= { arpEventObjects18 2 }

arp18_interface OBJECT-TYPE
    SYNTAX DisplayString
    MAX-ACCESS accessible-for-notify
    STATUS current
    DESCRIPTION
        "Parameter 'interface' in event ARP.18"
    ::= { arpEventObjects18 3 }


arpNotification1 NOTIFICATION-TYPE
    OBJECTS { 
              arp1_interface 
            }
    STATUS current
    DESCRIPTION
        "Notification of Event ARP.1

        Message: 'Queue overflow on interface $1'

        Parameters list:
              $1: arp1_interface

        A packet was discarded because the queue of pending ARP packets
        to process is too long. This means the number of received ARP packets
        is so high that they cannot be processed."
    ::= { arpNotificationsPrefix 1 }

arpNotification2 NOTIFICATION-TYPE
    OBJECTS { 
              arp2_operation_type, 
              arp2_hardware_type,
              arp2_protocol_type,
              arp2_interface 
            }
    STATUS current
    DESCRIPTION
        "Notification of Event ARP.2

        Message: 'Packet received $1 $2 $3 interface $4'

        Parameters list:
              $1: arp2_operation_type
              $2: arp2_hardware_type
              $3: arp2_protocol_type
              $4: arp2_interface

        An ARP packet of the type indicated has just arrived for processing."
    ::= { arpNotificationsPrefix 2 }

arpNotification3 NOTIFICATION-TYPE
    OBJECTS { 
              arp3_hardware_type, 
              arp3_protocol_type,
              arp3_interface 
            }
    STATUS current
    DESCRIPTION
        "Notification of Event ARP.3

        Message: 'Reply sent $1 $2 interface $3'

        Parameters list:
              $1: arp3_hardware_type
              $2: arp3_protocol_type
              $3: arp3_interface

        An ARP reply is being sent as the result of a request for a translation
        from another host."
    ::= { arpNotificationsPrefix 3 }

arpNotification4 NOTIFICATION-TYPE
    OBJECTS { 
              arp4_hardware_type, 
              arp4_protocol_type,
              arp4_interface 
            }
    STATUS current
    DESCRIPTION
        "Notification of Event ARP.4

        Message: 'Deleting translation entry $1 $2 interface $3'

        Parameters list:
              $1: arp4_hardware_type
              $2: arp4_protocol_type
              $3: arp4_interface

        A translation cache entry timed out (which was not used or refreshed
        recently) has been deleted."
    ::= { arpNotificationsPrefix 4 }

arpNotification5 NOTIFICATION-TYPE
    OBJECTS { 
              arp5_hardware_type, 
              arp5_protocol_type,
              arp5_interface 
            }
    STATUS current
    DESCRIPTION
        "Notification of Event ARP.5

        Message: 'Translation request sent ARP $1 $2 interface $3'

        Parameters list:
              $1: arp5_hardware_type
              $2: arp5_protocol_type
              $3: arp5_interface

        An ARP translation request is being sent as a result of the transmission
        of a frame to another host. As the host address is unknown, the ARP
        address resolution process is started broadcasting an ARP request."
    ::= { arpNotificationsPrefix 5 }

arpNotification6 NOTIFICATION-TYPE
    OBJECTS { 
              arp6_hardware_type, 
              arp6_protocol_type,
              arp6_interface 
            }
    STATUS current
    DESCRIPTION
        "Notification of Event ARP.6

        Message: 'Auto-refresh $1 $2 interface $3'

        Parameters list:
              $1: arp6_hardware_type
              $2: arp6_protocol_type
              $3: arp6_interface

        An ARP translation request is being sent as the result of
        the auto-refresh mechanism: the refresh timer for a dynamic entry is
        going to expire. When available, this request is sent directly to the
        MAC address in the current translation instead of a broadcast to all
        hosts."
    ::= { arpNotificationsPrefix 6 }

arpNotification7 NOTIFICATION-TYPE
    OBJECTS { 
              arp7_protocol_type, 
              arp7_interface 
            }
    STATUS current
    DESCRIPTION
        "Notification of Event ARP.7

        Message: 'No memory for entry, protocol $1 interface $2'

        Parameters list:
              $1: arp7_protocol_type
              $2: arp7_interface

        During the input processing of an ARP packet, the router did not have
        memory available to make a new dynamic ARP entry for the given protocol."
    ::= { arpNotificationsPrefix 7 }

arpNotification8 NOTIFICATION-TYPE
    OBJECTS { 
              arp8_operation_type, 
              arp8_src_address,
              arp8_dest_address,
              arp8_interface 
            }
    STATUS current
    DESCRIPTION
        "Notification of Event ARP.8

        Message: 'Packet received, type $1, for IP protocol from $2 to $3 interface $4'

        Parameters list:
              $1: arp8_operation_type
              $2: arp8_src_address
              $3: arp8_dest_address
              $4: arp8_interface

        An ARP packet of the type indicated has just arrived for processing."
    ::= { arpNotificationsPrefix 8 }

arpNotification9 NOTIFICATION-TYPE
    OBJECTS { 
              arp9_operation_type, 
              arp9_src_address,
              arp9_dest_address,
              arp9_interface 
            }
    STATUS current
    DESCRIPTION
        "Notification of Event ARP.9

        Message: 'Reply sent, type $1, for IP protocol from $2 to $3 interface $4'

        Parameters list:
              $1: arp9_operation_type
              $2: arp9_src_address
              $3: arp9_dest_address
              $4: arp9_interface

        An ARP reply is being sent as the result of a request for a translation
        from another host."
    ::= { arpNotificationsPrefix 9 }

arpNotification10 NOTIFICATION-TYPE
    OBJECTS { 
              arp10_operation_type, 
              arp10_protocol_type,
              arp10_interface 
            }
    STATUS current
    DESCRIPTION
        "Notification of Event ARP.10

        Message: 'Packet sent dropped, type $1, protocol $2 interface $3'

        Parameters list:
              $1: arp10_operation_type
              $2: arp10_protocol_type
              $3: arp10_interface

        An ARP packet has been dropped while it was being sent out."
    ::= { arpNotificationsPrefix 10 }

arpNotification11 NOTIFICATION-TYPE
    OBJECTS { 
              arp11_hardware_type, 
              arp11_protocol_type,
              arp11_protocol_address,
              arp11_interface 
            }
    STATUS current
    DESCRIPTION
        "Notification of Event ARP.11

        Message: 'Auto-refresh process launched $1 $2 $3 interface $4'

        Parameters list:
              $1: arp11_hardware_type
              $2: arp11_protocol_type
              $3: arp11_protocol_address
              $4: arp11_interface

        Auto-refresh process was launched as a result of using an entry near its
        expiration time."
    ::= { arpNotificationsPrefix 11 }

arpNotification12 NOTIFICATION-TYPE
    OBJECTS { 
              arp12_hardware_type, 
              arp12_protocol_type,
              arp12_protocol_address,
              arp12_interface 
            }
    STATUS current
    DESCRIPTION
        "Notification of Event ARP.12

        Message: 'Cache cleared $1 $2 $3 interface $4'

        Parameters list:
              $1: arp12_hardware_type
              $2: arp12_protocol_type
              $3: arp12_protocol_address
              $4: arp12_interface

        Hardware address has been cleared from protocol caches. This may be due
        to hardware address learning, refresh process, network failure, or
        configuration changes."
    ::= { arpNotificationsPrefix 12 }

arpNotification13 NOTIFICATION-TYPE
    OBJECTS { 
              arp13_operation_type, 
              arp13_src_address,
              arp13_dest_address,
              arp13_interface 
            }
    STATUS current
    DESCRIPTION
        "Notification of Event ARP.13

        Message: 'Request sent, type $1, for IP protocol from $2 to $3 interface $4'

        Parameters list:
              $1: arp13_operation_type
              $2: arp13_src_address
              $3: arp13_dest_address
              $4: arp13_interface

        An ARP request is being sent for an address translation of another host."
    ::= { arpNotificationsPrefix 13 }

arpNotification14 NOTIFICATION-TYPE
    OBJECTS { 
              arp14_mac_address, 
              arp14_ip_address,
              arp14_interface 
            }
    STATUS current
    DESCRIPTION
        "Notification of Event ARP.14

        Message: 'Refresh request sent for mac $1 associated with IP $2 interface $3'

        Parameters list:
              $1: arp14_mac_address
              $2: arp14_ip_address
              $3: arp14_interface

        An ARP translation request is being sent as the result of the 
        auto-refresh mechanism for this IP and mac address."
    ::= { arpNotificationsPrefix 14 }

arpNotification15 NOTIFICATION-TYPE
    OBJECTS { 
              arp15_mac_address, 
              arp15_ip_address,
              arp15_interface 
            }
    STATUS current
    DESCRIPTION
        "Notification of Event ARP.15

        Message: 'Deleting translation entry with mac $1 and IP $2 interface $3'

        Parameters list:
              $1: arp15_mac_address
              $2: arp15_ip_address
              $3: arp15_interface

        A translation cache entry timed out with this IP and mac address has 
        been deleted."
    ::= { arpNotificationsPrefix 15 }

arpNotification16 NOTIFICATION-TYPE
    OBJECTS { 
              arp16_mac_address, 
              arp16_ip_address,
              arp16_interface 
            }
    STATUS current
    DESCRIPTION
        "Notification of Event ARP.16

        Message: 'New entry mac $1 associated with IP $2 interface $3'

        Parameters list:
              $1: arp16_mac_address
              $2: arp16_ip_address
              $3: arp16_interface

        An ARP translation is being setup this IP and mac address."
    ::= { arpNotificationsPrefix 16 }

arpNotification17 NOTIFICATION-TYPE
    OBJECTS { 
              arp17_mac_address_old, 
              arp17_mac_address_new,
              arp17_ip_address,
              arp17_interface 
            }
    STATUS current
    DESCRIPTION
        "Notification of Event ARP.17

        Message: 'Change entry mac $1 to $2 associated with IP $3 interface $4'

        Parameters list:
              $1: arp17_mac_address_old
              $2: arp17_mac_address_new
              $3: arp17_ip_address
              $4: arp17_interface

        An ARP translation mac address is being changed for this IP."
    ::= { arpNotificationsPrefix 17 }

arpNotification18 NOTIFICATION-TYPE
    OBJECTS { 
              arp18_mac_address, 
              arp18_ip_address,
              arp18_interface 
            }
    STATUS current
    DESCRIPTION
        "Notification of Event ARP.18

        Message: 'Duplicated address received from mac $1 with IP $2 interface $3'

        Parameters list:
              $1: arp18_mac_address
              $2: arp18_ip_address
              $3: arp18_interface

        An ARP packet was received with a local address. The received mac and IP
        addresses are shown, as well as the interface."
    ::= { arpNotificationsPrefix 18 }


END
