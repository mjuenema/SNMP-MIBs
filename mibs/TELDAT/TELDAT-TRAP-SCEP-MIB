-- file automatically created


TELDAT-TRAP-SCEP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


scepTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SCEP event subsystem."
    REVISION "201401200930Z"
    DESCRIPTION "Initial implementation"
        ::= { telEventTraps 147 }


scepEventsGroup	OBJECT IDENTIFIER	::= { scepTrapsMIB 1 }

scepNotifications	OBJECT IDENTIFIER	::= { scepTrapsMIB 2 }
scepNotificationsPrefix	OBJECT IDENTIFIER	::= { scepNotifications 0 }

scepEventObjects1 OBJECT-IDENTITY
    STATUS current
    DESCRIPTION
        "Event SCEP.1
        Request SCEP in progress. First step to success depends on whether tcp
        establishes connection."
    ::= { scepEventsGroup 1 }

scep1_request_type OBJECT-TYPE
    SYNTAX DisplayString
    MAX-ACCESS accessible-for-notify
    STATUS current
    DESCRIPTION
        "Parameter 'request_type' in event SCEP.1"
    ::= { scepEventObjects1 1 }

scep1_server_ip_address OBJECT-TYPE
    SYNTAX IpAddress
    MAX-ACCESS accessible-for-notify
    STATUS current
    DESCRIPTION
        "Parameter 'server_ip_address' in event SCEP.1"
    ::= { scepEventObjects1 2 }

scepEventObjects2 OBJECT-IDENTITY
    STATUS current
    DESCRIPTION
        "Event SCEP.2
        Reset session SCEP by application or client SCEP, in a normal way (app),
        aborting (app), by error (client), or by timeout (app or client)."
    ::= { scepEventsGroup 2 }

scep2_reason OBJECT-TYPE
    SYNTAX DisplayString
    MAX-ACCESS accessible-for-notify
    STATUS current
    DESCRIPTION
        "Parameter 'reason' in event SCEP.2"
    ::= { scepEventObjects2 1 }

scep2_app_or_client OBJECT-TYPE
    SYNTAX DisplayString
    MAX-ACCESS accessible-for-notify
    STATUS current
    DESCRIPTION
        "Parameter 'app_or_client' in event SCEP.2"
    ::= { scepEventObjects2 2 }

scepEventObjects3 OBJECT-IDENTITY
    STATUS current
    DESCRIPTION
        "Event SCEP.3
        Session SCEP with server closed."
    ::= { scepEventsGroup 3 }

scep3_server_ip_address OBJECT-TYPE
    SYNTAX IpAddress
    MAX-ACCESS accessible-for-notify
    STATUS current
    DESCRIPTION
        "Parameter 'server_ip_address' in event SCEP.3"
    ::= { scepEventObjects3 1 }

scepEventObjects4 OBJECT-IDENTITY
    STATUS current
    DESCRIPTION
        "Event SCEP.4
        Received message."
    ::= { scepEventsGroup 4 }

scep4_msg OBJECT-TYPE
    SYNTAX DisplayString
    MAX-ACCESS accessible-for-notify
    STATUS current
    DESCRIPTION
        "Parameter 'msg' in event SCEP.4"
    ::= { scepEventObjects4 1 }

scepEventObjects5 OBJECT-IDENTITY
    STATUS current
    DESCRIPTION
        "Event SCEP.5
        Message to be sent."
    ::= { scepEventsGroup 5 }

scep5_msg OBJECT-TYPE
    SYNTAX DisplayString
    MAX-ACCESS accessible-for-notify
    STATUS current
    DESCRIPTION
        "Parameter 'msg' in event SCEP.5"
    ::= { scepEventObjects5 1 }

scepEventObjects6 OBJECT-IDENTITY
    STATUS current
    DESCRIPTION
        "Event SCEP.6
        Session SCEP with server whose IP address is shown has just been opened."
    ::= { scepEventsGroup 6 }

scep6_server_ip_address OBJECT-TYPE
    SYNTAX IpAddress
    MAX-ACCESS accessible-for-notify
    STATUS current
    DESCRIPTION
        "Parameter 'server_ip_address' in event SCEP.6"
    ::= { scepEventObjects6 1 }

scepEventObjects9 OBJECT-IDENTITY
    STATUS current
    DESCRIPTION
        "Event SCEP.9
        A http header has been received with error description."
    ::= { scepEventsGroup 9 }

scep9_Error_description OBJECT-TYPE
    SYNTAX DisplayString
    MAX-ACCESS accessible-for-notify
    STATUS current
    DESCRIPTION
        "Parameter 'Error_description' in event SCEP.9"
    ::= { scepEventObjects9 1 }

scepEventObjects10 OBJECT-IDENTITY
    STATUS current
    DESCRIPTION
        "Event SCEP.10
        Processed information (whose type is shown) is not valid."
    ::= { scepEventsGroup 10 }

scep10_information_txt OBJECT-TYPE
    SYNTAX DisplayString
    MAX-ACCESS accessible-for-notify
    STATUS current
    DESCRIPTION
        "Parameter 'information_txt' in event SCEP.10"
    ::= { scepEventObjects10 1 }

scepEventObjects11 OBJECT-IDENTITY
    STATUS current
    DESCRIPTION
        "Event SCEP.11
        Internal error while processing information whose type is shown."
    ::= { scepEventsGroup 11 }

scep11_information_txt OBJECT-TYPE
    SYNTAX DisplayString
    MAX-ACCESS accessible-for-notify
    STATUS current
    DESCRIPTION
        "Parameter 'information_txt' in event SCEP.11"
    ::= { scepEventObjects11 1 }

scepEventObjects12 OBJECT-IDENTITY
    STATUS current
    DESCRIPTION
        "Event SCEP.12
        Server SCEP has closed its session."
    ::= { scepEventsGroup 12 }

scep12_server_ip_address OBJECT-TYPE
    SYNTAX IpAddress
    MAX-ACCESS accessible-for-notify
    STATUS current
    DESCRIPTION
        "Parameter 'server_ip_address' in event SCEP.12"
    ::= { scepEventObjects12 1 }

scepEventObjects13 OBJECT-IDENTITY
    STATUS current
    DESCRIPTION
        "Event SCEP.13
        Message SCEPReq completely sent to the indicated server."
    ::= { scepEventsGroup 13 }

scep13_server_ip_address OBJECT-TYPE
    SYNTAX IpAddress
    MAX-ACCESS accessible-for-notify
    STATUS current
    DESCRIPTION
        "Parameter 'server_ip_address' in event SCEP.13"
    ::= { scepEventObjects13 1 }

scepEventObjects14 OBJECT-IDENTITY
    STATUS current
    DESCRIPTION
        "Event SCEP.14
        The message response to receive is bytes_to_read long."
    ::= { scepEventsGroup 14 }

scep14_bytes_to_read OBJECT-TYPE
    SYNTAX Integer32
    MAX-ACCESS accessible-for-notify
    STATUS current
    DESCRIPTION
        "Parameter 'bytes_to_read' in event SCEP.14"
    ::= { scepEventObjects14 1 }

scepEventObjects15 OBJECT-IDENTITY
    STATUS current
    DESCRIPTION
        "Event SCEP.15
        It is shown the number of bytes read until now."
    ::= { scepEventsGroup 15 }

scep15_bytes_read OBJECT-TYPE
    SYNTAX Integer32
    MAX-ACCESS accessible-for-notify
    STATUS current
    DESCRIPTION
        "Parameter 'bytes_read' in event SCEP.15"
    ::= { scepEventObjects15 1 }


scepNotification1 NOTIFICATION-TYPE
    OBJECTS { 
              scep1_request_type, 
              scep1_server_ip_address 
            }
    STATUS current
    DESCRIPTION
        "Notification of Event SCEP.1

        Message: 'Request type $1 (destination $2) in progress'

        Parameters list:
              $1: scep1_request_type
              $2: scep1_server_ip_address

        Request SCEP in progress. First step to success depends on whether tcp
        establishes connection."
    ::= { scepNotificationsPrefix 1 }

scepNotification2 NOTIFICATION-TYPE
    OBJECTS { 
              scep2_reason, 
              scep2_app_or_client 
            }
    STATUS current
    DESCRIPTION
        "Notification of Event SCEP.2

        Message: 'Reset session SCEP (reason $1) by $2'

        Parameters list:
              $1: scep2_reason
              $2: scep2_app_or_client

        Reset session SCEP by application or client SCEP, in a normal way (app),
        aborting (app), by error (client), or by timeout (app or client)."
    ::= { scepNotificationsPrefix 2 }

scepNotification3 NOTIFICATION-TYPE
    OBJECTS { 
              scep3_server_ip_address 
            }
    STATUS current
    DESCRIPTION
        "Notification of Event SCEP.3

        Message: 'Session SCEP (destination $1) closed'

        Parameters list:
              $1: scep3_server_ip_address

        Session SCEP with server closed."
    ::= { scepNotificationsPrefix 3 }

scepNotification4 NOTIFICATION-TYPE
    OBJECTS { 
              scep4_msg 
            }
    STATUS current
    DESCRIPTION
        "Notification of Event SCEP.4

        Message: 'Received message $1'

        Parameters list:
              $1: scep4_msg

        Received message."
    ::= { scepNotificationsPrefix 4 }

scepNotification5 NOTIFICATION-TYPE
    OBJECTS { 
              scep5_msg 
            }
    STATUS current
    DESCRIPTION
        "Notification of Event SCEP.5

        Message: 'Send message: $1'

        Parameters list:
              $1: scep5_msg

        Message to be sent."
    ::= { scepNotificationsPrefix 5 }

scepNotification6 NOTIFICATION-TYPE
    OBJECTS { 
              scep6_server_ip_address 
            }
    STATUS current
    DESCRIPTION
        "Notification of Event SCEP.6

        Message: 'Session SCEP (destination $1) opened'

        Parameters list:
              $1: scep6_server_ip_address

        Session SCEP with server whose IP address is shown has just been opened."
    ::= { scepNotificationsPrefix 6 }

scepNotification7 NOTIFICATION-TYPE
    STATUS current
    DESCRIPTION
        "Notification of Event SCEP.7

        Message: 'Header no type http'

        Header received is no a valid http header."
    ::= { scepNotificationsPrefix 7 }

scepNotification8 NOTIFICATION-TYPE
    STATUS current
    DESCRIPTION
        "Notification of Event SCEP.8

        Message: 'No content length received'

        There is no content length received, or it is 0."
    ::= { scepNotificationsPrefix 8 }

scepNotification9 NOTIFICATION-TYPE
    OBJECTS { 
              scep9_Error_description 
            }
    STATUS current
    DESCRIPTION
        "Notification of Event SCEP.9

        Message: 'Http hdr received. Error: $1'

        Parameters list:
              $1: scep9_Error_description

        A http header has been received with error description."
    ::= { scepNotificationsPrefix 9 }

scepNotification10 NOTIFICATION-TYPE
    OBJECTS { 
              scep10_information_txt 
            }
    STATUS current
    DESCRIPTION
        "Notification of Event SCEP.10

        Message: 'Invalid information $1'

        Parameters list:
              $1: scep10_information_txt

        Processed information (whose type is shown) is not valid."
    ::= { scepNotificationsPrefix 10 }

scepNotification11 NOTIFICATION-TYPE
    OBJECTS { 
              scep11_information_txt 
            }
    STATUS current
    DESCRIPTION
        "Notification of Event SCEP.11

        Message: 'Error while processing $1'

        Parameters list:
              $1: scep11_information_txt

        Internal error while processing information whose type is shown."
    ::= { scepNotificationsPrefix 11 }

scepNotification12 NOTIFICATION-TYPE
    OBJECTS { 
              scep12_server_ip_address 
            }
    STATUS current
    DESCRIPTION
        "Notification of Event SCEP.12

        Message: 'Server session SCEP (from $1) closed'

        Parameters list:
              $1: scep12_server_ip_address

        Server SCEP has closed its session."
    ::= { scepNotificationsPrefix 12 }

scepNotification13 NOTIFICATION-TYPE
    OBJECTS { 
              scep13_server_ip_address 
            }
    STATUS current
    DESCRIPTION
        "Notification of Event SCEP.13

        Message: 'Message SCEPReq sent to $1'

        Parameters list:
              $1: scep13_server_ip_address

        Message SCEPReq completely sent to the indicated server."
    ::= { scepNotificationsPrefix 13 }

scepNotification14 NOTIFICATION-TYPE
    OBJECTS { 
              scep14_bytes_to_read 
            }
    STATUS current
    DESCRIPTION
        "Notification of Event SCEP.14

        Message: 'Bytes from server to read: $1'

        Parameters list:
              $1: scep14_bytes_to_read

        The message response to receive is bytes_to_read long."
    ::= { scepNotificationsPrefix 14 }

scepNotification15 NOTIFICATION-TYPE
    OBJECTS { 
              scep15_bytes_read 
            }
    STATUS current
    DESCRIPTION
        "Notification of Event SCEP.15

        Message: 'Bytes read: $1'

        Parameters list:
              $1: scep15_bytes_read

        It is shown the number of bytes read until now."
    ::= { scepNotificationsPrefix 15 }

scepNotification16 NOTIFICATION-TYPE
    STATUS current
    DESCRIPTION
        "Notification of Event SCEP.16

        Message: 'SCEP process aborted by user'

        SCEP process is aborted because user introduced an Abort command
        from console."
    ::= { scepNotificationsPrefix 16 }

scepNotification17 NOTIFICATION-TYPE
    STATUS current
    DESCRIPTION
        "Notification of Event SCEP.17

        Message: 'Message dropped by abort command'

        A message was in parsing process while an Abort command was issued, so
        when parsing finished, the message was discarded."
    ::= { scepNotificationsPrefix 17 }


END
