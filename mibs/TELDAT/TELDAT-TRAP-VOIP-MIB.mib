-- file automatically created


TELDAT-TRAP-VOIP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


voipTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the VOIP event subsystem."
    REVISION "201401200930Z"
    DESCRIPTION "Initial implementation"
        ::= { telEventTraps 174 }


voipEventsGroup	OBJECT IDENTIFIER	::= { voipTrapsMIB 1 }

voipNotifications	OBJECT IDENTIFIER	::= { voipTrapsMIB 2 }
voipNotificationsPrefix	OBJECT IDENTIFIER	::= { voipNotifications 0 }

voipEventObjects1 OBJECT-IDENTITY
    STATUS current
    DESCRIPTION
        "Event VOIP.1
        Report actions, status and error related to VoIP initialization process."
    ::= { voipEventsGroup 1 }

voip1_text OBJECT-TYPE
    SYNTAX DisplayString
    MAX-ACCESS accessible-for-notify
    STATUS current
    DESCRIPTION
        "Parameter 'text' in event VOIP.1"
    ::= { voipEventObjects1 1 }

voipEventObjects2 OBJECT-IDENTITY
    STATUS current
    DESCRIPTION
        "Event VOIP.2
        Report actions, status and error related to a VoIP card placed in interface."
    ::= { voipEventsGroup 2 }

voip2_text OBJECT-TYPE
    SYNTAX DisplayString
    MAX-ACCESS accessible-for-notify
    STATUS current
    DESCRIPTION
        "Parameter 'text' in event VOIP.2"
    ::= { voipEventObjects2 1 }

voip2_interface OBJECT-TYPE
    SYNTAX DisplayString
    MAX-ACCESS accessible-for-notify
    STATUS current
    DESCRIPTION
        "Parameter 'interface' in event VOIP.2"
    ::= { voipEventObjects2 2 }

voipEventObjects3 OBJECT-IDENTITY
    STATUS current
    DESCRIPTION
        "Event VOIP.3
        An event has been received on indicated interface and line."
    ::= { voipEventsGroup 3 }

voip3_Event OBJECT-TYPE
    SYNTAX DisplayString
    MAX-ACCESS accessible-for-notify
    STATUS current
    DESCRIPTION
        "Parameter 'Event' in event VOIP.3"
    ::= { voipEventObjects3 1 }

voip3_parameter OBJECT-TYPE
    SYNTAX DisplayString
    MAX-ACCESS accessible-for-notify
    STATUS current
    DESCRIPTION
        "Parameter 'parameter' in event VOIP.3"
    ::= { voipEventObjects3 2 }

voip3_interface OBJECT-TYPE
    SYNTAX DisplayString
    MAX-ACCESS accessible-for-notify
    STATUS current
    DESCRIPTION
        "Parameter 'interface' in event VOIP.3"
    ::= { voipEventObjects3 3 }

voip3_line OBJECT-TYPE
    SYNTAX Integer32
    MAX-ACCESS accessible-for-notify
    STATUS current
    DESCRIPTION
        "Parameter 'line' in event VOIP.3"
    ::= { voipEventObjects3 4 }

voipEventObjects4 OBJECT-IDENTITY
    STATUS current
    DESCRIPTION
        "Event VOIP.4
        Line state has changed."
    ::= { voipEventsGroup 4 }

voip4_Event OBJECT-TYPE
    SYNTAX DisplayString
    MAX-ACCESS accessible-for-notify
    STATUS current
    DESCRIPTION
        "Parameter 'Event' in event VOIP.4"
    ::= { voipEventObjects4 1 }

voip4_interface OBJECT-TYPE
    SYNTAX DisplayString
    MAX-ACCESS accessible-for-notify
    STATUS current
    DESCRIPTION
        "Parameter 'interface' in event VOIP.4"
    ::= { voipEventObjects4 2 }

voip4_line OBJECT-TYPE
    SYNTAX Integer32
    MAX-ACCESS accessible-for-notify
    STATUS current
    DESCRIPTION
        "Parameter 'line' in event VOIP.4"
    ::= { voipEventObjects4 3 }

voipEventObjects5 OBJECT-IDENTITY
    STATUS current
    DESCRIPTION
        "Event VOIP.5
        Frequently Time Out Events."
    ::= { voipEventsGroup 5 }

voip5_Type OBJECT-TYPE
    SYNTAX DisplayString
    MAX-ACCESS accessible-for-notify
    STATUS current
    DESCRIPTION
        "Parameter 'Type' in event VOIP.5"
    ::= { voipEventObjects5 1 }

voip5_Reason OBJECT-TYPE
    SYNTAX DisplayString
    MAX-ACCESS accessible-for-notify
    STATUS current
    DESCRIPTION
        "Parameter 'Reason' in event VOIP.5"
    ::= { voipEventObjects5 2 }

voip5_interface OBJECT-TYPE
    SYNTAX DisplayString
    MAX-ACCESS accessible-for-notify
    STATUS current
    DESCRIPTION
        "Parameter 'interface' in event VOIP.5"
    ::= { voipEventObjects5 3 }

voip5_line OBJECT-TYPE
    SYNTAX Integer32
    MAX-ACCESS accessible-for-notify
    STATUS current
    DESCRIPTION
        "Parameter 'line' in event VOIP.5"
    ::= { voipEventObjects5 4 }

voipEventObjects6 OBJECT-IDENTITY
    STATUS current
    DESCRIPTION
        "Event VOIP.6
        Unfrequently Time Out Events."
    ::= { voipEventsGroup 6 }

voip6_Type OBJECT-TYPE
    SYNTAX DisplayString
    MAX-ACCESS accessible-for-notify
    STATUS current
    DESCRIPTION
        "Parameter 'Type' in event VOIP.6"
    ::= { voipEventObjects6 1 }

voip6_Reason OBJECT-TYPE
    SYNTAX DisplayString
    MAX-ACCESS accessible-for-notify
    STATUS current
    DESCRIPTION
        "Parameter 'Reason' in event VOIP.6"
    ::= { voipEventObjects6 2 }

voip6_interface OBJECT-TYPE
    SYNTAX DisplayString
    MAX-ACCESS accessible-for-notify
    STATUS current
    DESCRIPTION
        "Parameter 'interface' in event VOIP.6"
    ::= { voipEventObjects6 3 }

voip6_line OBJECT-TYPE
    SYNTAX Integer32
    MAX-ACCESS accessible-for-notify
    STATUS current
    DESCRIPTION
        "Parameter 'line' in event VOIP.6"
    ::= { voipEventObjects6 4 }

voipEventObjects7 OBJECT-IDENTITY
    STATUS current
    DESCRIPTION
        "Event VOIP.7
        Report E&M actions, status and error."
    ::= { voipEventsGroup 7 }

voip7_text OBJECT-TYPE
    SYNTAX DisplayString
    MAX-ACCESS accessible-for-notify
    STATUS current
    DESCRIPTION
        "Parameter 'text' in event VOIP.7"
    ::= { voipEventObjects7 1 }

voip7_interface OBJECT-TYPE
    SYNTAX DisplayString
    MAX-ACCESS accessible-for-notify
    STATUS current
    DESCRIPTION
        "Parameter 'interface' in event VOIP.7"
    ::= { voipEventObjects7 2 }

voip7_line OBJECT-TYPE
    SYNTAX Integer32
    MAX-ACCESS accessible-for-notify
    STATUS current
    DESCRIPTION
        "Parameter 'line' in event VOIP.7"
    ::= { voipEventObjects7 3 }

voipEventObjects8 OBJECT-IDENTITY
    STATUS current
    DESCRIPTION
        "Event VOIP.8
        Report PBX service related events, status and error."
    ::= { voipEventsGroup 8 }

voip8_description OBJECT-TYPE
    SYNTAX DisplayString
    MAX-ACCESS accessible-for-notify
    STATUS current
    DESCRIPTION
        "Parameter 'description' in event VOIP.8"
    ::= { voipEventObjects8 1 }

voip8_number OBJECT-TYPE
    SYNTAX DisplayString
    MAX-ACCESS accessible-for-notify
    STATUS current
    DESCRIPTION
        "Parameter 'number' in event VOIP.8"
    ::= { voipEventObjects8 2 }

voip8_interface OBJECT-TYPE
    SYNTAX DisplayString
    MAX-ACCESS accessible-for-notify
    STATUS current
    DESCRIPTION
        "Parameter 'interface' in event VOIP.8"
    ::= { voipEventObjects8 3 }

voip8_line OBJECT-TYPE
    SYNTAX Integer32
    MAX-ACCESS accessible-for-notify
    STATUS current
    DESCRIPTION
        "Parameter 'line' in event VOIP.8"
    ::= { voipEventObjects8 4 }

voipEventObjects9 OBJECT-IDENTITY
    STATUS current
    DESCRIPTION
        "Event VOIP.9
        Report NSLA related events, status and error."
    ::= { voipEventsGroup 9 }

voip9_description OBJECT-TYPE
    SYNTAX DisplayString
    MAX-ACCESS accessible-for-notify
    STATUS current
    DESCRIPTION
        "Parameter 'description' in event VOIP.9"
    ::= { voipEventObjects9 1 }

voip9_item OBJECT-TYPE
    SYNTAX DisplayString
    MAX-ACCESS accessible-for-notify
    STATUS current
    DESCRIPTION
        "Parameter 'item' in event VOIP.9"
    ::= { voipEventObjects9 2 }

voip9_active OBJECT-TYPE
    SYNTAX DisplayString
    MAX-ACCESS accessible-for-notify
    STATUS current
    DESCRIPTION
        "Parameter 'active' in event VOIP.9"
    ::= { voipEventObjects9 3 }

voipEventObjects10 OBJECT-IDENTITY
    STATUS current
    DESCRIPTION
        "Event VOIP.10
        Report ISDN/cellular command"
    ::= { voipEventsGroup 10 }

voip10_command OBJECT-TYPE
    SYNTAX DisplayString
    MAX-ACCESS accessible-for-notify
    STATUS current
    DESCRIPTION
        "Parameter 'command' in event VOIP.10"
    ::= { voipEventObjects10 1 }

voip10_interface OBJECT-TYPE
    SYNTAX DisplayString
    MAX-ACCESS accessible-for-notify
    STATUS current
    DESCRIPTION
        "Parameter 'interface' in event VOIP.10"
    ::= { voipEventObjects10 2 }

voip10_line OBJECT-TYPE
    SYNTAX Integer32
    MAX-ACCESS accessible-for-notify
    STATUS current
    DESCRIPTION
        "Parameter 'line' in event VOIP.10"
    ::= { voipEventObjects10 3 }

voipEventObjects11 OBJECT-IDENTITY
    STATUS current
    DESCRIPTION
        "Event VOIP.11
        Report ISDN/cellular events"
    ::= { voipEventsGroup 11 }

voip11_event OBJECT-TYPE
    SYNTAX DisplayString
    MAX-ACCESS accessible-for-notify
    STATUS current
    DESCRIPTION
        "Parameter 'event' in event VOIP.11"
    ::= { voipEventObjects11 1 }

voip11_interface OBJECT-TYPE
    SYNTAX DisplayString
    MAX-ACCESS accessible-for-notify
    STATUS current
    DESCRIPTION
        "Parameter 'interface' in event VOIP.11"
    ::= { voipEventObjects11 2 }

voip11_line OBJECT-TYPE
    SYNTAX Integer32
    MAX-ACCESS accessible-for-notify
    STATUS current
    DESCRIPTION
        "Parameter 'line' in event VOIP.11"
    ::= { voipEventObjects11 3 }

voipEventObjects12 OBJECT-IDENTITY
    STATUS current
    DESCRIPTION
        "Event VOIP.12
        Report ISDN/cellular status and error"
    ::= { voipEventsGroup 12 }

voip12_str OBJECT-TYPE
    SYNTAX DisplayString
    MAX-ACCESS accessible-for-notify
    STATUS current
    DESCRIPTION
        "Parameter 'str' in event VOIP.12"
    ::= { voipEventObjects12 1 }

voip12_interface OBJECT-TYPE
    SYNTAX DisplayString
    MAX-ACCESS accessible-for-notify
    STATUS current
    DESCRIPTION
        "Parameter 'interface' in event VOIP.12"
    ::= { voipEventObjects12 2 }

voip12_line OBJECT-TYPE
    SYNTAX Integer32
    MAX-ACCESS accessible-for-notify
    STATUS current
    DESCRIPTION
        "Parameter 'line' in event VOIP.12"
    ::= { voipEventObjects12 3 }

voipEventObjects13 OBJECT-IDENTITY
    STATUS current
    DESCRIPTION
        "Event VOIP.13
        Report voip errors"
    ::= { voipEventsGroup 13 }

voip13_str OBJECT-TYPE
    SYNTAX DisplayString
    MAX-ACCESS accessible-for-notify
    STATUS current
    DESCRIPTION
        "Parameter 'str' in event VOIP.13"
    ::= { voipEventObjects13 1 }

voip13_interface OBJECT-TYPE
    SYNTAX DisplayString
    MAX-ACCESS accessible-for-notify
    STATUS current
    DESCRIPTION
        "Parameter 'interface' in event VOIP.13"
    ::= { voipEventObjects13 2 }

voip13_line OBJECT-TYPE
    SYNTAX Integer32
    MAX-ACCESS accessible-for-notify
    STATUS current
    DESCRIPTION
        "Parameter 'line' in event VOIP.13"
    ::= { voipEventObjects13 3 }

voipEventObjects14 OBJECT-IDENTITY
    STATUS current
    DESCRIPTION
        "Event VOIP.14
        Report events related to voice messages"
    ::= { voipEventsGroup 14 }

voip14_loc-index OBJECT-TYPE
    SYNTAX Integer32
    MAX-ACCESS accessible-for-notify
    STATUS current
    DESCRIPTION
        "Parameter 'loc-index' in event VOIP.14"
    ::= { voipEventObjects14 1 }

voip14_event OBJECT-TYPE
    SYNTAX DisplayString
    MAX-ACCESS accessible-for-notify
    STATUS current
    DESCRIPTION
        "Parameter 'event' in event VOIP.14"
    ::= { voipEventObjects14 2 }


voipNotification1 NOTIFICATION-TYPE
    OBJECTS { 
              voip1_text 
            }
    STATUS current
    DESCRIPTION
        "Notification of Event VOIP.1

        Message: 'Report $1'

        Parameters list:
              $1: voip1_text

        Report actions, status and error related to VoIP initialization process."
    ::= { voipNotificationsPrefix 1 }

voipNotification2 NOTIFICATION-TYPE
    OBJECTS { 
              voip2_text, 
              voip2_interface 
            }
    STATUS current
    DESCRIPTION
        "Notification of Event VOIP.2

        Message: 'Error $1 ifc $2'

        Parameters list:
              $1: voip2_text
              $2: voip2_interface

        Report actions, status and error related to a VoIP card placed in interface."
    ::= { voipNotificationsPrefix 2 }

voipNotification3 NOTIFICATION-TYPE
    OBJECTS { 
              voip3_Event, 
              voip3_parameter,
              voip3_interface,
              voip3_line 
            }
    STATUS current
    DESCRIPTION
        "Notification of Event VOIP.3

        Message: 'Event: $1 $2 line $3-$4'

        Parameters list:
              $1: voip3_Event
              $2: voip3_parameter
              $3: voip3_interface
              $4: voip3_line

        An event has been received on indicated interface and line."
    ::= { voipNotificationsPrefix 3 }

voipNotification4 NOTIFICATION-TYPE
    OBJECTS { 
              voip4_Event, 
              voip4_interface,
              voip4_line 
            }
    STATUS current
    DESCRIPTION
        "Notification of Event VOIP.4

        Message: 'State terminal changed to $1 line $2-$3'

        Parameters list:
              $1: voip4_Event
              $2: voip4_interface
              $3: voip4_line

        Line state has changed."
    ::= { voipNotificationsPrefix 4 }

voipNotification5 NOTIFICATION-TYPE
    OBJECTS { 
              voip5_Type, 
              voip5_Reason,
              voip5_interface,
              voip5_line 
            }
    STATUS current
    DESCRIPTION
        "Notification of Event VOIP.5

        Message: 'Time Out (type: $1 by $2) ln $3-$4'

        Parameters list:
              $1: voip5_Type
              $2: voip5_Reason
              $3: voip5_interface
              $4: voip5_line

        Frequently Time Out Events."
    ::= { voipNotificationsPrefix 5 }

voipNotification6 NOTIFICATION-TYPE
    OBJECTS { 
              voip6_Type, 
              voip6_Reason,
              voip6_interface,
              voip6_line 
            }
    STATUS current
    DESCRIPTION
        "Notification of Event VOIP.6

        Message: 'Time Out (typ: $1 by $2) line $3-$4'

        Parameters list:
              $1: voip6_Type
              $2: voip6_Reason
              $3: voip6_interface
              $4: voip6_line

        Unfrequently Time Out Events."
    ::= { voipNotificationsPrefix 6 }

voipNotification7 NOTIFICATION-TYPE
    OBJECTS { 
              voip7_text, 
              voip7_interface,
              voip7_line 
            }
    STATUS current
    DESCRIPTION
        "Notification of Event VOIP.7

        Message: 'E&M: $1 line $2-$3'

        Parameters list:
              $1: voip7_text
              $2: voip7_interface
              $3: voip7_line

        Report E&M actions, status and error."
    ::= { voipNotificationsPrefix 7 }

voipNotification8 NOTIFICATION-TYPE
    OBJECTS { 
              voip8_description, 
              voip8_number,
              voip8_interface,
              voip8_line 
            }
    STATUS current
    DESCRIPTION
        "Notification of Event VOIP.8

        Message: 'PBX: $1 $2 line $3-$4'

        Parameters list:
              $1: voip8_description
              $2: voip8_number
              $3: voip8_interface
              $4: voip8_line

        Report PBX service related events, status and error."
    ::= { voipNotificationsPrefix 8 }

voipNotification9 NOTIFICATION-TYPE
    OBJECTS { 
              voip9_description, 
              voip9_item,
              voip9_active 
            }
    STATUS current
    DESCRIPTION
        "Notification of Event VOIP.9

        Message: 'NSLA: $1 $2 $3'

        Parameters list:
              $1: voip9_description
              $2: voip9_item
              $3: voip9_active

        Report NSLA related events, status and error."
    ::= { voipNotificationsPrefix 9 }

voipNotification10 NOTIFICATION-TYPE
    OBJECTS { 
              voip10_command, 
              voip10_interface,
              voip10_line 
            }
    STATUS current
    DESCRIPTION
        "Notification of Event VOIP.10

        Message: 'DIAL: command $1 line $2-$3'

        Parameters list:
              $1: voip10_command
              $2: voip10_interface
              $3: voip10_line

        Report ISDN/cellular command"
    ::= { voipNotificationsPrefix 10 }

voipNotification11 NOTIFICATION-TYPE
    OBJECTS { 
              voip11_event, 
              voip11_interface,
              voip11_line 
            }
    STATUS current
    DESCRIPTION
        "Notification of Event VOIP.11

        Message: 'DIAL: event $1 line $2-$3'

        Parameters list:
              $1: voip11_event
              $2: voip11_interface
              $3: voip11_line

        Report ISDN/cellular events"
    ::= { voipNotificationsPrefix 11 }

voipNotification12 NOTIFICATION-TYPE
    OBJECTS { 
              voip12_str, 
              voip12_interface,
              voip12_line 
            }
    STATUS current
    DESCRIPTION
        "Notification of Event VOIP.12

        Message: 'DIAL: $1 line $2-$3'

        Parameters list:
              $1: voip12_str
              $2: voip12_interface
              $3: voip12_line

        Report ISDN/cellular status and error"
    ::= { voipNotificationsPrefix 12 }

voipNotification13 NOTIFICATION-TYPE
    OBJECTS { 
              voip13_str, 
              voip13_interface,
              voip13_line 
            }
    STATUS current
    DESCRIPTION
        "Notification of Event VOIP.13

        Message: 'Error: $1 line $2-$3'

        Parameters list:
              $1: voip13_str
              $2: voip13_interface
              $3: voip13_line

        Report voip errors"
    ::= { voipNotificationsPrefix 13 }

voipNotification14 NOTIFICATION-TYPE
    OBJECTS { 
              voip14_loc-index, 
              voip14_event 
            }
    STATUS current
    DESCRIPTION
        "Notification of Event VOIP.14

        Message: 'Voice message $1: $2'

        Parameters list:
              $1: voip14_loc-index
              $2: voip14_event

        Report events related to voice messages"
    ::= { voipNotificationsPrefix 14 }


END
