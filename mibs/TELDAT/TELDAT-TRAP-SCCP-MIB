-- file automatically created


TELDAT-TRAP-SCCP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


sccpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SCCP event subsystem."
    REVISION "201401200930Z"
    DESCRIPTION "Initial implementation"
        ::= { telEventTraps 210 }


sccpEventsGroup	OBJECT IDENTIFIER	::= { sccpTrapsMIB 1 }

sccpNotifications	OBJECT IDENTIFIER	::= { sccpTrapsMIB 2 }
sccpNotificationsPrefix	OBJECT IDENTIFIER	::= { sccpNotifications 0 }

sccpEventObjects1 OBJECT-IDENTITY
    STATUS current
    DESCRIPTION
        "Event SCCP.1
        Event related with tcp connection."
    ::= { sccpEventsGroup 1 }

sccp1_state OBJECT-TYPE
    SYNTAX DisplayString
    MAX-ACCESS accessible-for-notify
    STATUS current
    DESCRIPTION
        "Parameter 'state' in event SCCP.1"
    ::= { sccpEventObjects1 1 }

sccp1_ip OBJECT-TYPE
    SYNTAX IpAddress
    MAX-ACCESS accessible-for-notify
    STATUS current
    DESCRIPTION
        "Parameter 'ip' in event SCCP.1"
    ::= { sccpEventObjects1 2 }

sccp1_port OBJECT-TYPE
    SYNTAX Integer32
    MAX-ACCESS accessible-for-notify
    STATUS current
    DESCRIPTION
        "Parameter 'port' in event SCCP.1"
    ::= { sccpEventObjects1 3 }

sccpEventObjects2 OBJECT-IDENTITY
    STATUS current
    DESCRIPTION
        "Event SCCP.2
        Message transmitted."
    ::= { sccpEventsGroup 2 }

sccp2_message OBJECT-TYPE
    SYNTAX DisplayString
    MAX-ACCESS accessible-for-notify
    STATUS current
    DESCRIPTION
        "Parameter 'message' in event SCCP.2"
    ::= { sccpEventObjects2 1 }

sccp2_ip OBJECT-TYPE
    SYNTAX IpAddress
    MAX-ACCESS accessible-for-notify
    STATUS current
    DESCRIPTION
        "Parameter 'ip' in event SCCP.2"
    ::= { sccpEventObjects2 2 }

sccp2_port OBJECT-TYPE
    SYNTAX Integer32
    MAX-ACCESS accessible-for-notify
    STATUS current
    DESCRIPTION
        "Parameter 'port' in event SCCP.2"
    ::= { sccpEventObjects2 3 }

sccpEventObjects3 OBJECT-IDENTITY
    STATUS current
    DESCRIPTION
        "Event SCCP.3
        Message received."
    ::= { sccpEventsGroup 3 }

sccp3_message OBJECT-TYPE
    SYNTAX DisplayString
    MAX-ACCESS accessible-for-notify
    STATUS current
    DESCRIPTION
        "Parameter 'message' in event SCCP.3"
    ::= { sccpEventObjects3 1 }

sccp3_ip OBJECT-TYPE
    SYNTAX IpAddress
    MAX-ACCESS accessible-for-notify
    STATUS current
    DESCRIPTION
        "Parameter 'ip' in event SCCP.3"
    ::= { sccpEventObjects3 2 }

sccp3_port OBJECT-TYPE
    SYNTAX Integer32
    MAX-ACCESS accessible-for-notify
    STATUS current
    DESCRIPTION
        "Parameter 'port' in event SCCP.3"
    ::= { sccpEventObjects3 3 }

sccpEventObjects4 OBJECT-IDENTITY
    STATUS current
    DESCRIPTION
        "Event SCCP.4
        Warning related with message processing."
    ::= { sccpEventsGroup 4 }

sccp4_description OBJECT-TYPE
    SYNTAX DisplayString
    MAX-ACCESS accessible-for-notify
    STATUS current
    DESCRIPTION
        "Parameter 'description' in event SCCP.4"
    ::= { sccpEventObjects4 1 }

sccp4_ip OBJECT-TYPE
    SYNTAX IpAddress
    MAX-ACCESS accessible-for-notify
    STATUS current
    DESCRIPTION
        "Parameter 'ip' in event SCCP.4"
    ::= { sccpEventObjects4 2 }

sccp4_port OBJECT-TYPE
    SYNTAX Integer32
    MAX-ACCESS accessible-for-notify
    STATUS current
    DESCRIPTION
        "Parameter 'port' in event SCCP.4"
    ::= { sccpEventObjects4 3 }

sccpEventObjects5 OBJECT-IDENTITY
    STATUS current
    DESCRIPTION
        "Event SCCP.5
        Error related with message processing."
    ::= { sccpEventsGroup 5 }

sccp5_description OBJECT-TYPE
    SYNTAX DisplayString
    MAX-ACCESS accessible-for-notify
    STATUS current
    DESCRIPTION
        "Parameter 'description' in event SCCP.5"
    ::= { sccpEventObjects5 1 }

sccp5_ip OBJECT-TYPE
    SYNTAX IpAddress
    MAX-ACCESS accessible-for-notify
    STATUS current
    DESCRIPTION
        "Parameter 'ip' in event SCCP.5"
    ::= { sccpEventObjects5 2 }

sccp5_port OBJECT-TYPE
    SYNTAX Integer32
    MAX-ACCESS accessible-for-notify
    STATUS current
    DESCRIPTION
        "Parameter 'port' in event SCCP.5"
    ::= { sccpEventObjects5 3 }

sccpEventObjects6 OBJECT-IDENTITY
    STATUS current
    DESCRIPTION
        "Event SCCP.6
        SCCP daemon went up or down."
    ::= { sccpEventsGroup 6 }

sccp6_state OBJECT-TYPE
    SYNTAX DisplayString
    MAX-ACCESS accessible-for-notify
    STATUS current
    DESCRIPTION
        "Parameter 'state' in event SCCP.6"
    ::= { sccpEventObjects6 1 }

sccpEventObjects7 OBJECT-IDENTITY
    STATUS current
    DESCRIPTION
        "Event SCCP.7
        Line state changed"
    ::= { sccpEventsGroup 7 }

sccp7_line OBJECT-TYPE
    SYNTAX DisplayString
    MAX-ACCESS accessible-for-notify
    STATUS current
    DESCRIPTION
        "Parameter 'line' in event SCCP.7"
    ::= { sccpEventObjects7 1 }

sccp7_state OBJECT-TYPE
    SYNTAX DisplayString
    MAX-ACCESS accessible-for-notify
    STATUS current
    DESCRIPTION
        "Parameter 'state' in event SCCP.7"
    ::= { sccpEventObjects7 2 }

sccp7_ip OBJECT-TYPE
    SYNTAX IpAddress
    MAX-ACCESS accessible-for-notify
    STATUS current
    DESCRIPTION
        "Parameter 'ip' in event SCCP.7"
    ::= { sccpEventObjects7 3 }

sccp7_port OBJECT-TYPE
    SYNTAX Integer32
    MAX-ACCESS accessible-for-notify
    STATUS current
    DESCRIPTION
        "Parameter 'port' in event SCCP.7"
    ::= { sccpEventObjects7 4 }

sccpEventObjects8 OBJECT-IDENTITY
    STATUS current
    DESCRIPTION
        "Event SCCP.8
        Digit received."
    ::= { sccpEventsGroup 8 }

sccp8_digit OBJECT-TYPE
    SYNTAX Integer32
    MAX-ACCESS accessible-for-notify
    STATUS current
    DESCRIPTION
        "Parameter 'digit' in event SCCP.8"
    ::= { sccpEventObjects8 1 }

sccp8_line OBJECT-TYPE
    SYNTAX DisplayString
    MAX-ACCESS accessible-for-notify
    STATUS current
    DESCRIPTION
        "Parameter 'line' in event SCCP.8"
    ::= { sccpEventObjects8 2 }

sccp8_ip OBJECT-TYPE
    SYNTAX IpAddress
    MAX-ACCESS accessible-for-notify
    STATUS current
    DESCRIPTION
        "Parameter 'ip' in event SCCP.8"
    ::= { sccpEventObjects8 3 }

sccp8_port OBJECT-TYPE
    SYNTAX Integer32
    MAX-ACCESS accessible-for-notify
    STATUS current
    DESCRIPTION
        "Parameter 'port' in event SCCP.8"
    ::= { sccpEventObjects8 4 }


sccpNotification1 NOTIFICATION-TYPE
    OBJECTS { 
              sccp1_state, 
              sccp1_ip,
              sccp1_port 
            }
    STATUS current
    DESCRIPTION
        "Notification of Event SCCP.1

        Message: 'Connection $1 $2:$3'

        Parameters list:
              $1: sccp1_state
              $2: sccp1_ip
              $3: sccp1_port

        Event related with tcp connection."
    ::= { sccpNotificationsPrefix 1 }

sccpNotification2 NOTIFICATION-TYPE
    OBJECTS { 
              sccp2_message, 
              sccp2_ip,
              sccp2_port 
            }
    STATUS current
    DESCRIPTION
        "Notification of Event SCCP.2

        Message: 'Message $1 transmitted connection $2:$3'

        Parameters list:
              $1: sccp2_message
              $2: sccp2_ip
              $3: sccp2_port

        Message transmitted."
    ::= { sccpNotificationsPrefix 2 }

sccpNotification3 NOTIFICATION-TYPE
    OBJECTS { 
              sccp3_message, 
              sccp3_ip,
              sccp3_port 
            }
    STATUS current
    DESCRIPTION
        "Notification of Event SCCP.3

        Message: 'Message $1 received connection $2:$3'

        Parameters list:
              $1: sccp3_message
              $2: sccp3_ip
              $3: sccp3_port

        Message received."
    ::= { sccpNotificationsPrefix 3 }

sccpNotification4 NOTIFICATION-TYPE
    OBJECTS { 
              sccp4_description, 
              sccp4_ip,
              sccp4_port 
            }
    STATUS current
    DESCRIPTION
        "Notification of Event SCCP.4

        Message: 'Warning $1 connection $2:$3'

        Parameters list:
              $1: sccp4_description
              $2: sccp4_ip
              $3: sccp4_port

        Warning related with message processing."
    ::= { sccpNotificationsPrefix 4 }

sccpNotification5 NOTIFICATION-TYPE
    OBJECTS { 
              sccp5_description, 
              sccp5_ip,
              sccp5_port 
            }
    STATUS current
    DESCRIPTION
        "Notification of Event SCCP.5

        Message: 'Error $1 connection $2:$3'

        Parameters list:
              $1: sccp5_description
              $2: sccp5_ip
              $3: sccp5_port

        Error related with message processing."
    ::= { sccpNotificationsPrefix 5 }

sccpNotification6 NOTIFICATION-TYPE
    OBJECTS { 
              sccp6_state 
            }
    STATUS current
    DESCRIPTION
        "Notification of Event SCCP.6

        Message: 'Core $1'

        Parameters list:
              $1: sccp6_state

        SCCP daemon went up or down."
    ::= { sccpNotificationsPrefix 6 }

sccpNotification7 NOTIFICATION-TYPE
    OBJECTS { 
              sccp7_line, 
              sccp7_state,
              sccp7_ip,
              sccp7_port 
            }
    STATUS current
    DESCRIPTION
        "Notification of Event SCCP.7

        Message: 'Line $1->$2 $3:$4'

        Parameters list:
              $1: sccp7_line
              $2: sccp7_state
              $3: sccp7_ip
              $4: sccp7_port

        Line state changed"
    ::= { sccpNotificationsPrefix 7 }

sccpNotification8 NOTIFICATION-TYPE
    OBJECTS { 
              sccp8_digit, 
              sccp8_line,
              sccp8_ip,
              sccp8_port 
            }
    STATUS current
    DESCRIPTION
        "Notification of Event SCCP.8

        Message: 'Digit $1 line $2 from $3:$4'

        Parameters list:
              $1: sccp8_digit
              $2: sccp8_line
              $3: sccp8_ip
              $4: sccp8_port

        Digit received."
    ::= { sccpNotificationsPrefix 8 }


END
