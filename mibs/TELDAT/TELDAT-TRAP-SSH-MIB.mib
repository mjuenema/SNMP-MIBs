-- file automatically created


TELDAT-TRAP-SSH-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


sshTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SSH event subsystem."
    REVISION "201401200930Z"
    DESCRIPTION "Initial implementation"
        ::= { telEventTraps 215 }


sshEventsGroup	OBJECT IDENTIFIER	::= { sshTrapsMIB 1 }

sshNotifications	OBJECT IDENTIFIER	::= { sshTrapsMIB 2 }
sshNotificationsPrefix	OBJECT IDENTIFIER	::= { sshNotifications 0 }

sshEventObjects2 OBJECT-IDENTITY
    STATUS current
    DESCRIPTION
        "Event SSH.2
        Verbose info from a global SSH function."
    ::= { sshEventsGroup 2 }

ssh2_description OBJECT-TYPE
    SYNTAX DisplayString
    MAX-ACCESS accessible-for-notify
    STATUS current
    DESCRIPTION
        "Parameter 'description' in event SSH.2"
    ::= { sshEventObjects2 1 }

sshEventObjects3 OBJECT-IDENTITY
    STATUS current
    DESCRIPTION
        "Event SSH.3
        Error found in a global SSH function."
    ::= { sshEventsGroup 3 }

ssh3_description OBJECT-TYPE
    SYNTAX DisplayString
    MAX-ACCESS accessible-for-notify
    STATUS current
    DESCRIPTION
        "Parameter 'description' in event SSH.3"
    ::= { sshEventObjects3 1 }

sshEventObjects4 OBJECT-IDENTITY
    STATUS current
    DESCRIPTION
        "Event SSH.4
        Event related to task creation/deletion."
    ::= { sshEventsGroup 4 }

ssh4_description OBJECT-TYPE
    SYNTAX DisplayString
    MAX-ACCESS accessible-for-notify
    STATUS current
    DESCRIPTION
        "Parameter 'description' in event SSH.4"
    ::= { sshEventObjects4 1 }

ssh4_task OBJECT-TYPE
    SYNTAX DisplayString
    MAX-ACCESS accessible-for-notify
    STATUS current
    DESCRIPTION
        "Parameter 'task' in event SSH.4"
    ::= { sshEventObjects4 2 }

sshEventObjects5 OBJECT-IDENTITY
    STATUS current
    DESCRIPTION
        "Event SSH.5
        Error related to task creation/deletion."
    ::= { sshEventsGroup 5 }

ssh5_error OBJECT-TYPE
    SYNTAX DisplayString
    MAX-ACCESS accessible-for-notify
    STATUS current
    DESCRIPTION
        "Parameter 'error' in event SSH.5"
    ::= { sshEventObjects5 1 }

ssh5_task OBJECT-TYPE
    SYNTAX DisplayString
    MAX-ACCESS accessible-for-notify
    STATUS current
    DESCRIPTION
        "Parameter 'task' in event SSH.5"
    ::= { sshEventObjects5 2 }

sshEventObjects6 OBJECT-IDENTITY
    STATUS current
    DESCRIPTION
        "Event SSH.6
        Event related to server initialization."
    ::= { sshEventsGroup 6 }

ssh6_description OBJECT-TYPE
    SYNTAX DisplayString
    MAX-ACCESS accessible-for-notify
    STATUS current
    DESCRIPTION
        "Parameter 'description' in event SSH.6"
    ::= { sshEventObjects6 1 }

sshEventObjects7 OBJECT-IDENTITY
    STATUS current
    DESCRIPTION
        "Event SSH.7
        Error related to server initialization."
    ::= { sshEventsGroup 7 }

ssh7_description OBJECT-TYPE
    SYNTAX DisplayString
    MAX-ACCESS accessible-for-notify
    STATUS current
    DESCRIPTION
        "Parameter 'description' in event SSH.7"
    ::= { sshEventObjects7 1 }

sshEventObjects8 OBJECT-IDENTITY
    STATUS current
    DESCRIPTION
        "Event SSH.8
        Verbose event related to server initialization."
    ::= { sshEventsGroup 8 }

ssh8_description OBJECT-TYPE
    SYNTAX DisplayString
    MAX-ACCESS accessible-for-notify
    STATUS current
    DESCRIPTION
        "Parameter 'description' in event SSH.8"
    ::= { sshEventObjects8 1 }

sshEventObjects9 OBJECT-IDENTITY
    STATUS current
    DESCRIPTION
        "Event SSH.9
        Event related to hostkey loading/generation."
    ::= { sshEventsGroup 9 }

ssh9_hostkey-type OBJECT-TYPE
    SYNTAX DisplayString
    MAX-ACCESS accessible-for-notify
    STATUS current
    DESCRIPTION
        "Parameter 'hostkey-type' in event SSH.9"
    ::= { sshEventObjects9 1 }

ssh9_description OBJECT-TYPE
    SYNTAX DisplayString
    MAX-ACCESS accessible-for-notify
    STATUS current
    DESCRIPTION
        "Parameter 'description' in event SSH.9"
    ::= { sshEventObjects9 2 }

sshEventObjects10 OBJECT-IDENTITY
    STATUS current
    DESCRIPTION
        "Event SSH.10
        Warning: Hostkey not found in config."
    ::= { sshEventsGroup 10 }

ssh10_hostkey-type OBJECT-TYPE
    SYNTAX DisplayString
    MAX-ACCESS accessible-for-notify
    STATUS current
    DESCRIPTION
        "Parameter 'hostkey-type' in event SSH.10"
    ::= { sshEventObjects10 1 }

sshEventObjects11 OBJECT-IDENTITY
    STATUS current
    DESCRIPTION
        "Event SSH.11
        Verbose information about key generation process."
    ::= { sshEventsGroup 11 }

ssh11_description OBJECT-TYPE
    SYNTAX DisplayString
    MAX-ACCESS accessible-for-notify
    STATUS current
    DESCRIPTION
        "Parameter 'description' in event SSH.11"
    ::= { sshEventObjects11 1 }

sshEventObjects12 OBJECT-IDENTITY
    STATUS current
    DESCRIPTION
        "Event SSH.12
        Error found during key generation process."
    ::= { sshEventsGroup 12 }

ssh12_description OBJECT-TYPE
    SYNTAX DisplayString
    MAX-ACCESS accessible-for-notify
    STATUS current
    DESCRIPTION
        "Parameter 'description' in event SSH.12"
    ::= { sshEventObjects12 1 }

sshEventObjects15 OBJECT-IDENTITY
    STATUS current
    DESCRIPTION
        "Event SSH.15
        Important! Event related to a new connection with user id info."
    ::= { sshEventsGroup 15 }

ssh15_userid OBJECT-TYPE
    SYNTAX Integer32
    MAX-ACCESS accessible-for-notify
    STATUS current
    DESCRIPTION
        "Parameter 'userid' in event SSH.15"
    ::= { sshEventObjects15 1 }

ssh15_srvadd OBJECT-TYPE
    SYNTAX IpAddress
    MAX-ACCESS accessible-for-notify
    STATUS current
    DESCRIPTION
        "Parameter 'srvadd' in event SSH.15"
    ::= { sshEventObjects15 2 }

ssh15_srvport OBJECT-TYPE
    SYNTAX Integer32
    MAX-ACCESS accessible-for-notify
    STATUS current
    DESCRIPTION
        "Parameter 'srvport' in event SSH.15"
    ::= { sshEventObjects15 3 }

ssh15_cliadd OBJECT-TYPE
    SYNTAX IpAddress
    MAX-ACCESS accessible-for-notify
    STATUS current
    DESCRIPTION
        "Parameter 'cliadd' in event SSH.15"
    ::= { sshEventObjects15 4 }

ssh15_cliport OBJECT-TYPE
    SYNTAX Integer32
    MAX-ACCESS accessible-for-notify
    STATUS current
    DESCRIPTION
        "Parameter 'cliport' in event SSH.15"
    ::= { sshEventObjects15 5 }

sshEventObjects16 OBJECT-IDENTITY
    STATUS current
    DESCRIPTION
        "Event SSH.16
        A new connection was refused because of the reason"
    ::= { sshEventsGroup 16 }

ssh16_cliadd OBJECT-TYPE
    SYNTAX IpAddress
    MAX-ACCESS accessible-for-notify
    STATUS current
    DESCRIPTION
        "Parameter 'cliadd' in event SSH.16"
    ::= { sshEventObjects16 1 }

ssh16_cliport OBJECT-TYPE
    SYNTAX Integer32
    MAX-ACCESS accessible-for-notify
    STATUS current
    DESCRIPTION
        "Parameter 'cliport' in event SSH.16"
    ::= { sshEventObjects16 2 }

ssh16_reason OBJECT-TYPE
    SYNTAX DisplayString
    MAX-ACCESS accessible-for-notify
    STATUS current
    DESCRIPTION
        "Parameter 'reason' in event SSH.16"
    ::= { sshEventObjects16 3 }

sshEventObjects17 OBJECT-IDENTITY
    STATUS current
    DESCRIPTION
        "Event SSH.17
        Event related to a connection closing"
    ::= { sshEventsGroup 17 }

ssh17_userid OBJECT-TYPE
    SYNTAX Integer32
    MAX-ACCESS accessible-for-notify
    STATUS current
    DESCRIPTION
        "Parameter 'userid' in event SSH.17"
    ::= { sshEventObjects17 1 }

ssh17_srvadd OBJECT-TYPE
    SYNTAX IpAddress
    MAX-ACCESS accessible-for-notify
    STATUS current
    DESCRIPTION
        "Parameter 'srvadd' in event SSH.17"
    ::= { sshEventObjects17 2 }

ssh17_srvport OBJECT-TYPE
    SYNTAX Integer32
    MAX-ACCESS accessible-for-notify
    STATUS current
    DESCRIPTION
        "Parameter 'srvport' in event SSH.17"
    ::= { sshEventObjects17 3 }

ssh17_cliadd OBJECT-TYPE
    SYNTAX IpAddress
    MAX-ACCESS accessible-for-notify
    STATUS current
    DESCRIPTION
        "Parameter 'cliadd' in event SSH.17"
    ::= { sshEventObjects17 4 }

ssh17_cliport OBJECT-TYPE
    SYNTAX Integer32
    MAX-ACCESS accessible-for-notify
    STATUS current
    DESCRIPTION
        "Parameter 'cliport' in event SSH.17"
    ::= { sshEventObjects17 5 }

sshEventObjects18 OBJECT-IDENTITY
    STATUS current
    DESCRIPTION
        "Event SSH.18
        Verbose information about the connection."
    ::= { sshEventsGroup 18 }

ssh18_userid OBJECT-TYPE
    SYNTAX Integer32
    MAX-ACCESS accessible-for-notify
    STATUS current
    DESCRIPTION
        "Parameter 'userid' in event SSH.18"
    ::= { sshEventObjects18 1 }

ssh18_description OBJECT-TYPE
    SYNTAX DisplayString
    MAX-ACCESS accessible-for-notify
    STATUS current
    DESCRIPTION
        "Parameter 'description' in event SSH.18"
    ::= { sshEventObjects18 2 }

sshEventObjects19 OBJECT-IDENTITY
    STATUS current
    DESCRIPTION
        "Event SSH.19
        Error related to version incompatibility."
    ::= { sshEventsGroup 19 }

ssh19_userid OBJECT-TYPE
    SYNTAX Integer32
    MAX-ACCESS accessible-for-notify
    STATUS current
    DESCRIPTION
        "Parameter 'userid' in event SSH.19"
    ::= { sshEventObjects19 1 }

ssh19_description OBJECT-TYPE
    SYNTAX DisplayString
    MAX-ACCESS accessible-for-notify
    STATUS current
    DESCRIPTION
        "Parameter 'description' in event SSH.19"
    ::= { sshEventObjects19 2 }

sshEventObjects21 OBJECT-IDENTITY
    STATUS current
    DESCRIPTION
        "Event SSH.21
        SSH message received."
    ::= { sshEventsGroup 21 }

ssh21_userid OBJECT-TYPE
    SYNTAX Integer32
    MAX-ACCESS accessible-for-notify
    STATUS current
    DESCRIPTION
        "Parameter 'userid' in event SSH.21"
    ::= { sshEventObjects21 1 }

ssh21_msg-number OBJECT-TYPE
    SYNTAX Integer32
    MAX-ACCESS accessible-for-notify
    STATUS current
    DESCRIPTION
        "Parameter 'msg-number' in event SSH.21"
    ::= { sshEventObjects21 2 }

sshEventObjects22 OBJECT-IDENTITY
    STATUS current
    DESCRIPTION
        "Event SSH.22
        SSH message sent."
    ::= { sshEventsGroup 22 }

ssh22_userid OBJECT-TYPE
    SYNTAX Integer32
    MAX-ACCESS accessible-for-notify
    STATUS current
    DESCRIPTION
        "Parameter 'userid' in event SSH.22"
    ::= { sshEventObjects22 1 }

ssh22_msg-number OBJECT-TYPE
    SYNTAX Integer32
    MAX-ACCESS accessible-for-notify
    STATUS current
    DESCRIPTION
        "Parameter 'msg-number' in event SSH.22"
    ::= { sshEventObjects22 2 }

sshEventObjects23 OBJECT-IDENTITY
    STATUS current
    DESCRIPTION
        "Event SSH.23
        Message expected from peer."
    ::= { sshEventsGroup 23 }

ssh23_userid OBJECT-TYPE
    SYNTAX Integer32
    MAX-ACCESS accessible-for-notify
    STATUS current
    DESCRIPTION
        "Parameter 'userid' in event SSH.23"
    ::= { sshEventObjects23 1 }

ssh23_msg-number OBJECT-TYPE
    SYNTAX Integer32
    MAX-ACCESS accessible-for-notify
    STATUS current
    DESCRIPTION
        "Parameter 'msg-number' in event SSH.23"
    ::= { sshEventObjects23 2 }

sshEventObjects24 OBJECT-IDENTITY
    STATUS current
    DESCRIPTION
        "Event SSH.24
        Disconnection message received with reason code and explanation."
    ::= { sshEventsGroup 24 }

ssh24_userid OBJECT-TYPE
    SYNTAX Integer32
    MAX-ACCESS accessible-for-notify
    STATUS current
    DESCRIPTION
        "Parameter 'userid' in event SSH.24"
    ::= { sshEventObjects24 1 }

ssh24_reason-code OBJECT-TYPE
    SYNTAX Integer32
    MAX-ACCESS accessible-for-notify
    STATUS current
    DESCRIPTION
        "Parameter 'reason-code' in event SSH.24"
    ::= { sshEventObjects24 2 }

ssh24_description OBJECT-TYPE
    SYNTAX DisplayString
    MAX-ACCESS accessible-for-notify
    STATUS current
    DESCRIPTION
        "Parameter 'description' in event SSH.24"
    ::= { sshEventObjects24 3 }

sshEventObjects25 OBJECT-IDENTITY
    STATUS current
    DESCRIPTION
        "Event SSH.25
        Disconnection message sent with reason code and explanation."
    ::= { sshEventsGroup 25 }

ssh25_userid OBJECT-TYPE
    SYNTAX Integer32
    MAX-ACCESS accessible-for-notify
    STATUS current
    DESCRIPTION
        "Parameter 'userid' in event SSH.25"
    ::= { sshEventObjects25 1 }

ssh25_reason-code OBJECT-TYPE
    SYNTAX Integer32
    MAX-ACCESS accessible-for-notify
    STATUS current
    DESCRIPTION
        "Parameter 'reason-code' in event SSH.25"
    ::= { sshEventObjects25 2 }

ssh25_description OBJECT-TYPE
    SYNTAX DisplayString
    MAX-ACCESS accessible-for-notify
    STATUS current
    DESCRIPTION
        "Parameter 'description' in event SSH.25"
    ::= { sshEventObjects25 3 }

sshEventObjects26 OBJECT-IDENTITY
    STATUS current
    DESCRIPTION
        "Event SSH.26
        An ignore message has been rcvd/sent."
    ::= { sshEventsGroup 26 }

ssh26_userid OBJECT-TYPE
    SYNTAX Integer32
    MAX-ACCESS accessible-for-notify
    STATUS current
    DESCRIPTION
        "Parameter 'userid' in event SSH.26"
    ::= { sshEventObjects26 1 }

ssh26_description OBJECT-TYPE
    SYNTAX DisplayString
    MAX-ACCESS accessible-for-notify
    STATUS current
    DESCRIPTION
        "Parameter 'description' in event SSH.26"
    ::= { sshEventObjects26 2 }

sshEventObjects27 OBJECT-IDENTITY
    STATUS current
    DESCRIPTION
        "Event SSH.27
        A not implemented message has been received."
    ::= { sshEventsGroup 27 }

ssh27_userid OBJECT-TYPE
    SYNTAX Integer32
    MAX-ACCESS accessible-for-notify
    STATUS current
    DESCRIPTION
        "Parameter 'userid' in event SSH.27"
    ::= { sshEventObjects27 1 }

ssh27_direction OBJECT-TYPE
    SYNTAX DisplayString
    MAX-ACCESS accessible-for-notify
    STATUS current
    DESCRIPTION
        "Parameter 'direction' in event SSH.27"
    ::= { sshEventObjects27 2 }

sshEventObjects28 OBJECT-IDENTITY
    STATUS current
    DESCRIPTION
        "Event SSH.28
        Debug message rcvd/sent with debug info."
    ::= { sshEventsGroup 28 }

ssh28_userid OBJECT-TYPE
    SYNTAX Integer32
    MAX-ACCESS accessible-for-notify
    STATUS current
    DESCRIPTION
        "Parameter 'userid' in event SSH.28"
    ::= { sshEventObjects28 1 }

ssh28_rcvd-sent OBJECT-TYPE
    SYNTAX DisplayString
    MAX-ACCESS accessible-for-notify
    STATUS current
    DESCRIPTION
        "Parameter 'rcvd-sent' in event SSH.28"
    ::= { sshEventObjects28 2 }

ssh28_description OBJECT-TYPE
    SYNTAX DisplayString
    MAX-ACCESS accessible-for-notify
    STATUS current
    DESCRIPTION
        "Parameter 'description' in event SSH.28"
    ::= { sshEventObjects28 3 }

sshEventObjects31 OBJECT-IDENTITY
    STATUS current
    DESCRIPTION
        "Event SSH.31
        KEX proposal sent from server to client"
    ::= { sshEventsGroup 31 }

ssh31_userid OBJECT-TYPE
    SYNTAX Integer32
    MAX-ACCESS accessible-for-notify
    STATUS current
    DESCRIPTION
        "Parameter 'userid' in event SSH.31"
    ::= { sshEventObjects31 1 }

ssh31_proposal OBJECT-TYPE
    SYNTAX DisplayString
    MAX-ACCESS accessible-for-notify
    STATUS current
    DESCRIPTION
        "Parameter 'proposal' in event SSH.31"
    ::= { sshEventObjects31 2 }

sshEventObjects32 OBJECT-IDENTITY
    STATUS current
    DESCRIPTION
        "Event SSH.32
        KEX proposal sent from client to server"
    ::= { sshEventsGroup 32 }

ssh32_userid OBJECT-TYPE
    SYNTAX Integer32
    MAX-ACCESS accessible-for-notify
    STATUS current
    DESCRIPTION
        "Parameter 'userid' in event SSH.32"
    ::= { sshEventObjects32 1 }

ssh32_proposal OBJECT-TYPE
    SYNTAX DisplayString
    MAX-ACCESS accessible-for-notify
    STATUS current
    DESCRIPTION
        "Parameter 'proposal' in event SSH.32"
    ::= { sshEventObjects32 2 }

sshEventObjects33 OBJECT-IDENTITY
    STATUS current
    DESCRIPTION
        "Event SSH.33
        KEX decision made after comparing kexinit messages."
    ::= { sshEventsGroup 33 }

ssh33_userid OBJECT-TYPE
    SYNTAX Integer32
    MAX-ACCESS accessible-for-notify
    STATUS current
    DESCRIPTION
        "Parameter 'userid' in event SSH.33"
    ::= { sshEventObjects33 1 }

ssh33_decision OBJECT-TYPE
    SYNTAX DisplayString
    MAX-ACCESS accessible-for-notify
    STATUS current
    DESCRIPTION
        "Parameter 'decision' in event SSH.33"
    ::= { sshEventObjects33 2 }

sshEventObjects34 OBJECT-IDENTITY
    STATUS current
    DESCRIPTION
        "Event SSH.34
        Event related to verbose information about KEX."
    ::= { sshEventsGroup 34 }

ssh34_userid OBJECT-TYPE
    SYNTAX Integer32
    MAX-ACCESS accessible-for-notify
    STATUS current
    DESCRIPTION
        "Parameter 'userid' in event SSH.34"
    ::= { sshEventObjects34 1 }

ssh34_description OBJECT-TYPE
    SYNTAX DisplayString
    MAX-ACCESS accessible-for-notify
    STATUS current
    DESCRIPTION
        "Parameter 'description' in event SSH.34"
    ::= { sshEventObjects34 2 }

sshEventObjects35 OBJECT-IDENTITY
    STATUS current
    DESCRIPTION
        "Event SSH.35
        Event related to an error found during KEX."
    ::= { sshEventsGroup 35 }

ssh35_userid OBJECT-TYPE
    SYNTAX Integer32
    MAX-ACCESS accessible-for-notify
    STATUS current
    DESCRIPTION
        "Parameter 'userid' in event SSH.35"
    ::= { sshEventObjects35 1 }

ssh35_description OBJECT-TYPE
    SYNTAX DisplayString
    MAX-ACCESS accessible-for-notify
    STATUS current
    DESCRIPTION
        "Parameter 'description' in event SSH.35"
    ::= { sshEventObjects35 2 }

sshEventObjects36 OBJECT-IDENTITY
    STATUS current
    DESCRIPTION
        "Event SSH.36
        Diffie-Hellman message of a certain type has been received/sent."
    ::= { sshEventsGroup 36 }

ssh36_userid OBJECT-TYPE
    SYNTAX Integer32
    MAX-ACCESS accessible-for-notify
    STATUS current
    DESCRIPTION
        "Parameter 'userid' in event SSH.36"
    ::= { sshEventObjects36 1 }

ssh36_description OBJECT-TYPE
    SYNTAX DisplayString
    MAX-ACCESS accessible-for-notify
    STATUS current
    DESCRIPTION
        "Parameter 'description' in event SSH.36"
    ::= { sshEventObjects36 2 }

ssh36_direction OBJECT-TYPE
    SYNTAX DisplayString
    MAX-ACCESS accessible-for-notify
    STATUS current
    DESCRIPTION
        "Parameter 'direction' in event SSH.36"
    ::= { sshEventObjects36 3 }

sshEventObjects37 OBJECT-IDENTITY
    STATUS current
    DESCRIPTION
        "Event SSH.37
        SSHv1 Key Exchange message has been received/sent."
    ::= { sshEventsGroup 37 }

ssh37_userid OBJECT-TYPE
    SYNTAX Integer32
    MAX-ACCESS accessible-for-notify
    STATUS current
    DESCRIPTION
        "Parameter 'userid' in event SSH.37"
    ::= { sshEventObjects37 1 }

ssh37_direction OBJECT-TYPE
    SYNTAX DisplayString
    MAX-ACCESS accessible-for-notify
    STATUS current
    DESCRIPTION
        "Parameter 'direction' in event SSH.37"
    ::= { sshEventObjects37 2 }

ssh37_description OBJECT-TYPE
    SYNTAX DisplayString
    MAX-ACCESS accessible-for-notify
    STATUS current
    DESCRIPTION
        "Parameter 'description' in event SSH.37"
    ::= { sshEventObjects37 3 }

sshEventObjects38 OBJECT-IDENTITY
    STATUS current
    DESCRIPTION
        "Event SSH.38
        New keys are about to be used from now on."
    ::= { sshEventsGroup 38 }

ssh38_userid OBJECT-TYPE
    SYNTAX Integer32
    MAX-ACCESS accessible-for-notify
    STATUS current
    DESCRIPTION
        "Parameter 'userid' in event SSH.38"
    ::= { sshEventObjects38 1 }

ssh38_direction OBJECT-TYPE
    SYNTAX DisplayString
    MAX-ACCESS accessible-for-notify
    STATUS current
    DESCRIPTION
        "Parameter 'direction' in event SSH.38"
    ::= { sshEventObjects38 2 }

sshEventObjects39 OBJECT-IDENTITY
    STATUS current
    DESCRIPTION
        "Event SSH.39
        Periodic rekeying process after a period."
    ::= { sshEventsGroup 39 }

ssh39_userid OBJECT-TYPE
    SYNTAX Integer32
    MAX-ACCESS accessible-for-notify
    STATUS current
    DESCRIPTION
        "Parameter 'userid' in event SSH.39"
    ::= { sshEventObjects39 1 }

sshEventObjects41 OBJECT-IDENTITY
    STATUS current
    DESCRIPTION
        "Event SSH.41
        Service request name and direction."
    ::= { sshEventsGroup 41 }

ssh41_userid OBJECT-TYPE
    SYNTAX Integer32
    MAX-ACCESS accessible-for-notify
    STATUS current
    DESCRIPTION
        "Parameter 'userid' in event SSH.41"
    ::= { sshEventObjects41 1 }

ssh41_service OBJECT-TYPE
    SYNTAX DisplayString
    MAX-ACCESS accessible-for-notify
    STATUS current
    DESCRIPTION
        "Parameter 'service' in event SSH.41"
    ::= { sshEventObjects41 2 }

ssh41_direction OBJECT-TYPE
    SYNTAX DisplayString
    MAX-ACCESS accessible-for-notify
    STATUS current
    DESCRIPTION
        "Parameter 'direction' in event SSH.41"
    ::= { sshEventObjects41 3 }

sshEventObjects42 OBJECT-IDENTITY
    STATUS current
    DESCRIPTION
        "Event SSH.42
        Service request received/sent has not been accepted."
    ::= { sshEventsGroup 42 }

ssh42_userid OBJECT-TYPE
    SYNTAX Integer32
    MAX-ACCESS accessible-for-notify
    STATUS current
    DESCRIPTION
        "Parameter 'userid' in event SSH.42"
    ::= { sshEventObjects42 1 }

ssh42_service OBJECT-TYPE
    SYNTAX DisplayString
    MAX-ACCESS accessible-for-notify
    STATUS current
    DESCRIPTION
        "Parameter 'service' in event SSH.42"
    ::= { sshEventObjects42 2 }

sshEventObjects43 OBJECT-IDENTITY
    STATUS current
    DESCRIPTION
        "Event SSH.43
        Userauth request received/sent with parameters."
    ::= { sshEventsGroup 43 }

ssh43_userid OBJECT-TYPE
    SYNTAX Integer32
    MAX-ACCESS accessible-for-notify
    STATUS current
    DESCRIPTION
        "Parameter 'userid' in event SSH.43"
    ::= { sshEventObjects43 1 }

ssh43_direction OBJECT-TYPE
    SYNTAX DisplayString
    MAX-ACCESS accessible-for-notify
    STATUS current
    DESCRIPTION
        "Parameter 'direction' in event SSH.43"
    ::= { sshEventObjects43 2 }

ssh43_username OBJECT-TYPE
    SYNTAX DisplayString
    MAX-ACCESS accessible-for-notify
    STATUS current
    DESCRIPTION
        "Parameter 'username' in event SSH.43"
    ::= { sshEventObjects43 3 }

ssh43_service OBJECT-TYPE
    SYNTAX DisplayString
    MAX-ACCESS accessible-for-notify
    STATUS current
    DESCRIPTION
        "Parameter 'service' in event SSH.43"
    ::= { sshEventObjects43 4 }

ssh43_method OBJECT-TYPE
    SYNTAX DisplayString
    MAX-ACCESS accessible-for-notify
    STATUS current
    DESCRIPTION
        "Parameter 'method' in event SSH.43"
    ::= { sshEventObjects43 5 }

sshEventObjects44 OBJECT-IDENTITY
    STATUS current
    DESCRIPTION
        "Event SSH.44
        Register of userauth attempt and failures."
    ::= { sshEventsGroup 44 }

ssh44_userid OBJECT-TYPE
    SYNTAX Integer32
    MAX-ACCESS accessible-for-notify
    STATUS current
    DESCRIPTION
        "Parameter 'userid' in event SSH.44"
    ::= { sshEventObjects44 1 }

ssh44_attempt OBJECT-TYPE
    SYNTAX Integer32
    MAX-ACCESS accessible-for-notify
    STATUS current
    DESCRIPTION
        "Parameter 'attempt' in event SSH.44"
    ::= { sshEventObjects44 2 }

ssh44_failures OBJECT-TYPE
    SYNTAX Integer32
    MAX-ACCESS accessible-for-notify
    STATUS current
    DESCRIPTION
        "Parameter 'failures' in event SSH.44"
    ::= { sshEventObjects44 3 }

sshEventObjects45 OBJECT-IDENTITY
    STATUS current
    DESCRIPTION
        "Event SSH.45
        Userauth request postponed/accepted."
    ::= { sshEventsGroup 45 }

ssh45_userid OBJECT-TYPE
    SYNTAX Integer32
    MAX-ACCESS accessible-for-notify
    STATUS current
    DESCRIPTION
        "Parameter 'userid' in event SSH.45"
    ::= { sshEventObjects45 1 }

ssh45_operation OBJECT-TYPE
    SYNTAX DisplayString
    MAX-ACCESS accessible-for-notify
    STATUS current
    DESCRIPTION
        "Parameter 'operation' in event SSH.45"
    ::= { sshEventObjects45 2 }

sshEventObjects46 OBJECT-IDENTITY
    STATUS current
    DESCRIPTION
        "Event SSH.46
        Userauth request denied indicating available methods."
    ::= { sshEventsGroup 46 }

ssh46_userid OBJECT-TYPE
    SYNTAX Integer32
    MAX-ACCESS accessible-for-notify
    STATUS current
    DESCRIPTION
        "Parameter 'userid' in event SSH.46"
    ::= { sshEventObjects46 1 }

ssh46_methods OBJECT-TYPE
    SYNTAX DisplayString
    MAX-ACCESS accessible-for-notify
    STATUS current
    DESCRIPTION
        "Parameter 'methods' in event SSH.46"
    ::= { sshEventObjects46 2 }

sshEventObjects47 OBJECT-IDENTITY
    STATUS current
    DESCRIPTION
        "Event SSH.47
        Event related to information about SSHv1 authentication."
    ::= { sshEventsGroup 47 }

ssh47_userid OBJECT-TYPE
    SYNTAX Integer32
    MAX-ACCESS accessible-for-notify
    STATUS current
    DESCRIPTION
        "Parameter 'userid' in event SSH.47"
    ::= { sshEventObjects47 1 }

ssh47_description OBJECT-TYPE
    SYNTAX DisplayString
    MAX-ACCESS accessible-for-notify
    STATUS current
    DESCRIPTION
        "Parameter 'description' in event SSH.47"
    ::= { sshEventObjects47 2 }

sshEventObjects48 OBJECT-IDENTITY
    STATUS current
    DESCRIPTION
        "Event SSH.48
        Event related to further information about authentication."
    ::= { sshEventsGroup 48 }

ssh48_userid OBJECT-TYPE
    SYNTAX Integer32
    MAX-ACCESS accessible-for-notify
    STATUS current
    DESCRIPTION
        "Parameter 'userid' in event SSH.48"
    ::= { sshEventObjects48 1 }

ssh48_description OBJECT-TYPE
    SYNTAX DisplayString
    MAX-ACCESS accessible-for-notify
    STATUS current
    DESCRIPTION
        "Parameter 'description' in event SSH.48"
    ::= { sshEventObjects48 2 }

sshEventObjects49 OBJECT-IDENTITY
    STATUS current
    DESCRIPTION
        "Event SSH.49
        User authentication not completed before maximum allowed time expired."
    ::= { sshEventsGroup 49 }

ssh49_userid OBJECT-TYPE
    SYNTAX Integer32
    MAX-ACCESS accessible-for-notify
    STATUS current
    DESCRIPTION
        "Parameter 'userid' in event SSH.49"
    ::= { sshEventObjects49 1 }

sshEventObjects50 OBJECT-IDENTITY
    STATUS current
    DESCRIPTION
        "Event SSH.50
        Event related to an error found while user authentication."
    ::= { sshEventsGroup 50 }

ssh50_userid OBJECT-TYPE
    SYNTAX Integer32
    MAX-ACCESS accessible-for-notify
    STATUS current
    DESCRIPTION
        "Parameter 'userid' in event SSH.50"
    ::= { sshEventObjects50 1 }

ssh50_description OBJECT-TYPE
    SYNTAX DisplayString
    MAX-ACCESS accessible-for-notify
    STATUS current
    DESCRIPTION
        "Parameter 'description' in event SSH.50"
    ::= { sshEventObjects50 2 }

sshEventObjects51 OBJECT-IDENTITY
    STATUS current
    DESCRIPTION
        "Event SSH.51
        Banner message was received/sent."
    ::= { sshEventsGroup 51 }

ssh51_userid OBJECT-TYPE
    SYNTAX Integer32
    MAX-ACCESS accessible-for-notify
    STATUS current
    DESCRIPTION
        "Parameter 'userid' in event SSH.51"
    ::= { sshEventObjects51 1 }

ssh51_direction OBJECT-TYPE
    SYNTAX DisplayString
    MAX-ACCESS accessible-for-notify
    STATUS current
    DESCRIPTION
        "Parameter 'direction' in event SSH.51"
    ::= { sshEventObjects51 2 }

sshEventObjects54 OBJECT-IDENTITY
    STATUS current
    DESCRIPTION
        "Event SSH.54
        Global request was received/sent."
    ::= { sshEventsGroup 54 }

ssh54_userid OBJECT-TYPE
    SYNTAX Integer32
    MAX-ACCESS accessible-for-notify
    STATUS current
    DESCRIPTION
        "Parameter 'userid' in event SSH.54"
    ::= { sshEventObjects54 1 }

ssh54_request OBJECT-TYPE
    SYNTAX DisplayString
    MAX-ACCESS accessible-for-notify
    STATUS current
    DESCRIPTION
        "Parameter 'request' in event SSH.54"
    ::= { sshEventObjects54 2 }

ssh54_direction OBJECT-TYPE
    SYNTAX DisplayString
    MAX-ACCESS accessible-for-notify
    STATUS current
    DESCRIPTION
        "Parameter 'direction' in event SSH.54"
    ::= { sshEventObjects54 3 }

sshEventObjects55 OBJECT-IDENTITY
    STATUS current
    DESCRIPTION
        "Event SSH.55
        Global request was refused."
    ::= { sshEventsGroup 55 }

ssh55_userid OBJECT-TYPE
    SYNTAX Integer32
    MAX-ACCESS accessible-for-notify
    STATUS current
    DESCRIPTION
        "Parameter 'userid' in event SSH.55"
    ::= { sshEventObjects55 1 }

ssh55_request OBJECT-TYPE
    SYNTAX DisplayString
    MAX-ACCESS accessible-for-notify
    STATUS current
    DESCRIPTION
        "Parameter 'request' in event SSH.55"
    ::= { sshEventObjects55 2 }

sshEventObjects58 OBJECT-IDENTITY
    STATUS current
    DESCRIPTION
        "Event SSH.58
        Channel open message with sender parameters."
    ::= { sshEventsGroup 58 }

ssh58_userid OBJECT-TYPE
    SYNTAX Integer32
    MAX-ACCESS accessible-for-notify
    STATUS current
    DESCRIPTION
        "Parameter 'userid' in event SSH.58"
    ::= { sshEventObjects58 1 }

ssh58_direction OBJECT-TYPE
    SYNTAX DisplayString
    MAX-ACCESS accessible-for-notify
    STATUS current
    DESCRIPTION
        "Parameter 'direction' in event SSH.58"
    ::= { sshEventObjects58 2 }

ssh58_sndchan OBJECT-TYPE
    SYNTAX Integer32
    MAX-ACCESS accessible-for-notify
    STATUS current
    DESCRIPTION
        "Parameter 'sndchan' in event SSH.58"
    ::= { sshEventObjects58 3 }

ssh58_type OBJECT-TYPE
    SYNTAX DisplayString
    MAX-ACCESS accessible-for-notify
    STATUS current
    DESCRIPTION
        "Parameter 'type' in event SSH.58"
    ::= { sshEventObjects58 4 }

ssh58_win OBJECT-TYPE
    SYNTAX Integer32
    MAX-ACCESS accessible-for-notify
    STATUS current
    DESCRIPTION
        "Parameter 'win' in event SSH.58"
    ::= { sshEventObjects58 5 }

ssh58_maxpkt OBJECT-TYPE
    SYNTAX Integer32
    MAX-ACCESS accessible-for-notify
    STATUS current
    DESCRIPTION
        "Parameter 'maxpkt' in event SSH.58"
    ::= { sshEventObjects58 6 }

sshEventObjects59 OBJECT-IDENTITY
    STATUS current
    DESCRIPTION
        "Event SSH.59
        Association between channels and session for an authenticated connection."
    ::= { sshEventsGroup 59 }

ssh59_userid OBJECT-TYPE
    SYNTAX Integer32
    MAX-ACCESS accessible-for-notify
    STATUS current
    DESCRIPTION
        "Parameter 'userid' in event SSH.59"
    ::= { sshEventObjects59 1 }

ssh59_cliadd OBJECT-TYPE
    SYNTAX IpAddress
    MAX-ACCESS accessible-for-notify
    STATUS current
    DESCRIPTION
        "Parameter 'cliadd' in event SSH.59"
    ::= { sshEventObjects59 2 }

ssh59_cliport OBJECT-TYPE
    SYNTAX Integer32
    MAX-ACCESS accessible-for-notify
    STATUS current
    DESCRIPTION
        "Parameter 'cliport' in event SSH.59"
    ::= { sshEventObjects59 3 }

ssh59_srvadd OBJECT-TYPE
    SYNTAX IpAddress
    MAX-ACCESS accessible-for-notify
    STATUS current
    DESCRIPTION
        "Parameter 'srvadd' in event SSH.59"
    ::= { sshEventObjects59 4 }

ssh59_srvport OBJECT-TYPE
    SYNTAX Integer32
    MAX-ACCESS accessible-for-notify
    STATUS current
    DESCRIPTION
        "Parameter 'srvport' in event SSH.59"
    ::= { sshEventObjects59 5 }

ssh59_clichan OBJECT-TYPE
    SYNTAX Integer32
    MAX-ACCESS accessible-for-notify
    STATUS current
    DESCRIPTION
        "Parameter 'clichan' in event SSH.59"
    ::= { sshEventObjects59 6 }

ssh59_srvchan OBJECT-TYPE
    SYNTAX Integer32
    MAX-ACCESS accessible-for-notify
    STATUS current
    DESCRIPTION
        "Parameter 'srvchan' in event SSH.59"
    ::= { sshEventObjects59 7 }

ssh59_session OBJECT-TYPE
    SYNTAX Integer32
    MAX-ACCESS accessible-for-notify
    STATUS current
    DESCRIPTION
        "Parameter 'session' in event SSH.59"
    ::= { sshEventObjects59 8 }

sshEventObjects60 OBJECT-IDENTITY
    STATUS current
    DESCRIPTION
        "Event SSH.60
        Channel open confirmation message for receiver channel with sender parameters."
    ::= { sshEventsGroup 60 }

ssh60_userid OBJECT-TYPE
    SYNTAX Integer32
    MAX-ACCESS accessible-for-notify
    STATUS current
    DESCRIPTION
        "Parameter 'userid' in event SSH.60"
    ::= { sshEventObjects60 1 }

ssh60_direction OBJECT-TYPE
    SYNTAX DisplayString
    MAX-ACCESS accessible-for-notify
    STATUS current
    DESCRIPTION
        "Parameter 'direction' in event SSH.60"
    ::= { sshEventObjects60 2 }

ssh60_rcvchan OBJECT-TYPE
    SYNTAX Integer32
    MAX-ACCESS accessible-for-notify
    STATUS current
    DESCRIPTION
        "Parameter 'rcvchan' in event SSH.60"
    ::= { sshEventObjects60 3 }

ssh60_sndchan OBJECT-TYPE
    SYNTAX Integer32
    MAX-ACCESS accessible-for-notify
    STATUS current
    DESCRIPTION
        "Parameter 'sndchan' in event SSH.60"
    ::= { sshEventObjects60 4 }

ssh60_type OBJECT-TYPE
    SYNTAX DisplayString
    MAX-ACCESS accessible-for-notify
    STATUS current
    DESCRIPTION
        "Parameter 'type' in event SSH.60"
    ::= { sshEventObjects60 5 }

ssh60_win OBJECT-TYPE
    SYNTAX Integer32
    MAX-ACCESS accessible-for-notify
    STATUS current
    DESCRIPTION
        "Parameter 'win' in event SSH.60"
    ::= { sshEventObjects60 6 }

ssh60_maxpkt OBJECT-TYPE
    SYNTAX Integer32
    MAX-ACCESS accessible-for-notify
    STATUS current
    DESCRIPTION
        "Parameter 'maxpkt' in event SSH.60"
    ::= { sshEventObjects60 7 }

sshEventObjects61 OBJECT-IDENTITY
    STATUS current
    DESCRIPTION
        "Event SSH.61
        Channel open failure message for receiver channel."
    ::= { sshEventsGroup 61 }

ssh61_userid OBJECT-TYPE
    SYNTAX Integer32
    MAX-ACCESS accessible-for-notify
    STATUS current
    DESCRIPTION
        "Parameter 'userid' in event SSH.61"
    ::= { sshEventObjects61 1 }

ssh61_reason-code OBJECT-TYPE
    SYNTAX Integer32
    MAX-ACCESS accessible-for-notify
    STATUS current
    DESCRIPTION
        "Parameter 'reason-code' in event SSH.61"
    ::= { sshEventObjects61 2 }

ssh61_rcvchan OBJECT-TYPE
    SYNTAX Integer32
    MAX-ACCESS accessible-for-notify
    STATUS current
    DESCRIPTION
        "Parameter 'rcvchan' in event SSH.61"
    ::= { sshEventObjects61 3 }

ssh61_description OBJECT-TYPE
    SYNTAX DisplayString
    MAX-ACCESS accessible-for-notify
    STATUS current
    DESCRIPTION
        "Parameter 'description' in event SSH.61"
    ::= { sshEventObjects61 4 }

sshEventObjects62 OBJECT-IDENTITY
    STATUS current
    DESCRIPTION
        "Event SSH.62
        Client-alive message has been received/sent."
    ::= { sshEventsGroup 62 }

ssh62_userid OBJECT-TYPE
    SYNTAX Integer32
    MAX-ACCESS accessible-for-notify
    STATUS current
    DESCRIPTION
        "Parameter 'userid' in event SSH.62"
    ::= { sshEventObjects62 1 }

ssh62_direction OBJECT-TYPE
    SYNTAX DisplayString
    MAX-ACCESS accessible-for-notify
    STATUS current
    DESCRIPTION
        "Parameter 'direction' in event SSH.62"
    ::= { sshEventObjects62 2 }

sshEventObjects63 OBJECT-IDENTITY
    STATUS current
    DESCRIPTION
        "Event SSH.63
        Event related to authenticated SSHv1."
    ::= { sshEventsGroup 63 }

ssh63_userid OBJECT-TYPE
    SYNTAX Integer32
    MAX-ACCESS accessible-for-notify
    STATUS current
    DESCRIPTION
        "Parameter 'userid' in event SSH.63"
    ::= { sshEventObjects63 1 }

ssh63_description OBJECT-TYPE
    SYNTAX DisplayString
    MAX-ACCESS accessible-for-notify
    STATUS current
    DESCRIPTION
        "Parameter 'description' in event SSH.63"
    ::= { sshEventObjects63 2 }

sshEventObjects64 OBJECT-IDENTITY
    STATUS current
    DESCRIPTION
        "Event SSH.64
        Verbose information in authenticated connection."
    ::= { sshEventsGroup 64 }

ssh64_userid OBJECT-TYPE
    SYNTAX Integer32
    MAX-ACCESS accessible-for-notify
    STATUS current
    DESCRIPTION
        "Parameter 'userid' in event SSH.64"
    ::= { sshEventObjects64 1 }

ssh64_description OBJECT-TYPE
    SYNTAX DisplayString
    MAX-ACCESS accessible-for-notify
    STATUS current
    DESCRIPTION
        "Parameter 'description' in event SSH.64"
    ::= { sshEventObjects64 2 }

sshEventObjects65 OBJECT-IDENTITY
    STATUS current
    DESCRIPTION
        "Event SSH.65
        Error found in authenticated connection."
    ::= { sshEventsGroup 65 }

ssh65_userid OBJECT-TYPE
    SYNTAX Integer32
    MAX-ACCESS accessible-for-notify
    STATUS current
    DESCRIPTION
        "Parameter 'userid' in event SSH.65"
    ::= { sshEventObjects65 1 }

ssh65_description OBJECT-TYPE
    SYNTAX DisplayString
    MAX-ACCESS accessible-for-notify
    STATUS current
    DESCRIPTION
        "Parameter 'description' in event SSH.65"
    ::= { sshEventObjects65 2 }

sshEventObjects67 OBJECT-IDENTITY
    STATUS current
    DESCRIPTION
        "Event SSH.67
        Channel window adjust message received/sent indicating bytes to add."
    ::= { sshEventsGroup 67 }

ssh67_userid OBJECT-TYPE
    SYNTAX Integer32
    MAX-ACCESS accessible-for-notify
    STATUS current
    DESCRIPTION
        "Parameter 'userid' in event SSH.67"
    ::= { sshEventObjects67 1 }

ssh67_local_chan OBJECT-TYPE
    SYNTAX Integer32
    MAX-ACCESS accessible-for-notify
    STATUS current
    DESCRIPTION
        "Parameter 'local_chan' in event SSH.67"
    ::= { sshEventObjects67 2 }

ssh67_direction OBJECT-TYPE
    SYNTAX DisplayString
    MAX-ACCESS accessible-for-notify
    STATUS current
    DESCRIPTION
        "Parameter 'direction' in event SSH.67"
    ::= { sshEventObjects67 3 }

ssh67_bytes OBJECT-TYPE
    SYNTAX Integer32
    MAX-ACCESS accessible-for-notify
    STATUS current
    DESCRIPTION
        "Parameter 'bytes' in event SSH.67"
    ::= { sshEventObjects67 4 }

sshEventObjects68 OBJECT-IDENTITY
    STATUS current
    DESCRIPTION
        "Event SSH.68
        Channel data message received/sent."
    ::= { sshEventsGroup 68 }

ssh68_userid OBJECT-TYPE
    SYNTAX Integer32
    MAX-ACCESS accessible-for-notify
    STATUS current
    DESCRIPTION
        "Parameter 'userid' in event SSH.68"
    ::= { sshEventObjects68 1 }

ssh68_local_chan OBJECT-TYPE
    SYNTAX Integer32
    MAX-ACCESS accessible-for-notify
    STATUS current
    DESCRIPTION
        "Parameter 'local_chan' in event SSH.68"
    ::= { sshEventObjects68 2 }

ssh68_direction OBJECT-TYPE
    SYNTAX DisplayString
    MAX-ACCESS accessible-for-notify
    STATUS current
    DESCRIPTION
        "Parameter 'direction' in event SSH.68"
    ::= { sshEventObjects68 3 }

ssh68_len OBJECT-TYPE
    SYNTAX Integer32
    MAX-ACCESS accessible-for-notify
    STATUS current
    DESCRIPTION
        "Parameter 'len' in event SSH.68"
    ::= { sshEventObjects68 4 }

sshEventObjects69 OBJECT-IDENTITY
    STATUS current
    DESCRIPTION
        "Event SSH.69
        Extended channel data message received/sent."
    ::= { sshEventsGroup 69 }

ssh69_userid OBJECT-TYPE
    SYNTAX Integer32
    MAX-ACCESS accessible-for-notify
    STATUS current
    DESCRIPTION
        "Parameter 'userid' in event SSH.69"
    ::= { sshEventObjects69 1 }

ssh69_local_chan OBJECT-TYPE
    SYNTAX Integer32
    MAX-ACCESS accessible-for-notify
    STATUS current
    DESCRIPTION
        "Parameter 'local_chan' in event SSH.69"
    ::= { sshEventObjects69 2 }

ssh69_type OBJECT-TYPE
    SYNTAX Integer32
    MAX-ACCESS accessible-for-notify
    STATUS current
    DESCRIPTION
        "Parameter 'type' in event SSH.69"
    ::= { sshEventObjects69 3 }

ssh69_direction OBJECT-TYPE
    SYNTAX DisplayString
    MAX-ACCESS accessible-for-notify
    STATUS current
    DESCRIPTION
        "Parameter 'direction' in event SSH.69"
    ::= { sshEventObjects69 4 }

ssh69_len OBJECT-TYPE
    SYNTAX Integer32
    MAX-ACCESS accessible-for-notify
    STATUS current
    DESCRIPTION
        "Parameter 'len' in event SSH.69"
    ::= { sshEventObjects69 5 }

sshEventObjects70 OBJECT-IDENTITY
    STATUS current
    DESCRIPTION
        "Event SSH.70
        EOF message received/sent."
    ::= { sshEventsGroup 70 }

ssh70_userid OBJECT-TYPE
    SYNTAX Integer32
    MAX-ACCESS accessible-for-notify
    STATUS current
    DESCRIPTION
        "Parameter 'userid' in event SSH.70"
    ::= { sshEventObjects70 1 }

ssh70_local_chan OBJECT-TYPE
    SYNTAX Integer32
    MAX-ACCESS accessible-for-notify
    STATUS current
    DESCRIPTION
        "Parameter 'local_chan' in event SSH.70"
    ::= { sshEventObjects70 2 }

ssh70_direction OBJECT-TYPE
    SYNTAX DisplayString
    MAX-ACCESS accessible-for-notify
    STATUS current
    DESCRIPTION
        "Parameter 'direction' in event SSH.70"
    ::= { sshEventObjects70 3 }

sshEventObjects71 OBJECT-IDENTITY
    STATUS current
    DESCRIPTION
        "Event SSH.71
        Channel close message received/sent."
    ::= { sshEventsGroup 71 }

ssh71_userid OBJECT-TYPE
    SYNTAX Integer32
    MAX-ACCESS accessible-for-notify
    STATUS current
    DESCRIPTION
        "Parameter 'userid' in event SSH.71"
    ::= { sshEventObjects71 1 }

ssh71_local_chan OBJECT-TYPE
    SYNTAX Integer32
    MAX-ACCESS accessible-for-notify
    STATUS current
    DESCRIPTION
        "Parameter 'local_chan' in event SSH.71"
    ::= { sshEventObjects71 2 }

ssh71_direction OBJECT-TYPE
    SYNTAX DisplayString
    MAX-ACCESS accessible-for-notify
    STATUS current
    DESCRIPTION
        "Parameter 'direction' in event SSH.71"
    ::= { sshEventObjects71 3 }

sshEventObjects72 OBJECT-IDENTITY
    STATUS current
    DESCRIPTION
        "Event SSH.72
        Channel request message received/sent that may be confirmed, with extra data."
    ::= { sshEventsGroup 72 }

ssh72_userid OBJECT-TYPE
    SYNTAX Integer32
    MAX-ACCESS accessible-for-notify
    STATUS current
    DESCRIPTION
        "Parameter 'userid' in event SSH.72"
    ::= { sshEventObjects72 1 }

ssh72_local_chan OBJECT-TYPE
    SYNTAX Integer32
    MAX-ACCESS accessible-for-notify
    STATUS current
    DESCRIPTION
        "Parameter 'local_chan' in event SSH.72"
    ::= { sshEventObjects72 2 }

ssh72_request OBJECT-TYPE
    SYNTAX DisplayString
    MAX-ACCESS accessible-for-notify
    STATUS current
    DESCRIPTION
        "Parameter 'request' in event SSH.72"
    ::= { sshEventObjects72 3 }

ssh72_direction OBJECT-TYPE
    SYNTAX DisplayString
    MAX-ACCESS accessible-for-notify
    STATUS current
    DESCRIPTION
        "Parameter 'direction' in event SSH.72"
    ::= { sshEventObjects72 4 }

ssh72_confirm OBJECT-TYPE
    SYNTAX DisplayString
    MAX-ACCESS accessible-for-notify
    STATUS current
    DESCRIPTION
        "Parameter 'confirm' in event SSH.72"
    ::= { sshEventObjects72 5 }

ssh72_data OBJECT-TYPE
    SYNTAX DisplayString
    MAX-ACCESS accessible-for-notify
    STATUS current
    DESCRIPTION
        "Parameter 'data' in event SSH.72"
    ::= { sshEventObjects72 6 }

sshEventObjects73 OBJECT-IDENTITY
    STATUS current
    DESCRIPTION
        "Event SSH.73
        Channel failure message indicating that a previous request was refused."
    ::= { sshEventsGroup 73 }

ssh73_userid OBJECT-TYPE
    SYNTAX Integer32
    MAX-ACCESS accessible-for-notify
    STATUS current
    DESCRIPTION
        "Parameter 'userid' in event SSH.73"
    ::= { sshEventObjects73 1 }

ssh73_local_chan OBJECT-TYPE
    SYNTAX Integer32
    MAX-ACCESS accessible-for-notify
    STATUS current
    DESCRIPTION
        "Parameter 'local_chan' in event SSH.73"
    ::= { sshEventObjects73 2 }

ssh73_request OBJECT-TYPE
    SYNTAX DisplayString
    MAX-ACCESS accessible-for-notify
    STATUS current
    DESCRIPTION
        "Parameter 'request' in event SSH.73"
    ::= { sshEventObjects73 3 }

sshEventObjects74 OBJECT-IDENTITY
    STATUS current
    DESCRIPTION
        "Event SSH.74
        Event related to the allocation of a new pseudo-terminal."
    ::= { sshEventsGroup 74 }

ssh74_userid OBJECT-TYPE
    SYNTAX Integer32
    MAX-ACCESS accessible-for-notify
    STATUS current
    DESCRIPTION
        "Parameter 'userid' in event SSH.74"
    ::= { sshEventObjects74 1 }

ssh74_local_chan OBJECT-TYPE
    SYNTAX Integer32
    MAX-ACCESS accessible-for-notify
    STATUS current
    DESCRIPTION
        "Parameter 'local_chan' in event SSH.74"
    ::= { sshEventObjects74 2 }

sshEventObjects75 OBJECT-IDENTITY
    STATUS current
    DESCRIPTION
        "Event SSH.75
        Event related to the creation of a new console."
    ::= { sshEventsGroup 75 }

ssh75_userid OBJECT-TYPE
    SYNTAX Integer32
    MAX-ACCESS accessible-for-notify
    STATUS current
    DESCRIPTION
        "Parameter 'userid' in event SSH.75"
    ::= { sshEventObjects75 1 }

ssh75_local_chan OBJECT-TYPE
    SYNTAX Integer32
    MAX-ACCESS accessible-for-notify
    STATUS current
    DESCRIPTION
        "Parameter 'local_chan' in event SSH.75"
    ::= { sshEventObjects75 2 }

sshEventObjects76 OBJECT-IDENTITY
    STATUS current
    DESCRIPTION
        "Event SSH.76
        Event related to a SSHv1 channel."
    ::= { sshEventsGroup 76 }

ssh76_userid OBJECT-TYPE
    SYNTAX Integer32
    MAX-ACCESS accessible-for-notify
    STATUS current
    DESCRIPTION
        "Parameter 'userid' in event SSH.76"
    ::= { sshEventObjects76 1 }

ssh76_local_chan OBJECT-TYPE
    SYNTAX Integer32
    MAX-ACCESS accessible-for-notify
    STATUS current
    DESCRIPTION
        "Parameter 'local_chan' in event SSH.76"
    ::= { sshEventObjects76 2 }

ssh76_description OBJECT-TYPE
    SYNTAX DisplayString
    MAX-ACCESS accessible-for-notify
    STATUS current
    DESCRIPTION
        "Parameter 'description' in event SSH.76"
    ::= { sshEventObjects76 3 }

sshEventObjects77 OBJECT-IDENTITY
    STATUS current
    DESCRIPTION
        "Event SSH.77
        Verbose information about channel."
    ::= { sshEventsGroup 77 }

ssh77_userid OBJECT-TYPE
    SYNTAX Integer32
    MAX-ACCESS accessible-for-notify
    STATUS current
    DESCRIPTION
        "Parameter 'userid' in event SSH.77"
    ::= { sshEventObjects77 1 }

ssh77_local_chan OBJECT-TYPE
    SYNTAX Integer32
    MAX-ACCESS accessible-for-notify
    STATUS current
    DESCRIPTION
        "Parameter 'local_chan' in event SSH.77"
    ::= { sshEventObjects77 2 }

ssh77_description OBJECT-TYPE
    SYNTAX DisplayString
    MAX-ACCESS accessible-for-notify
    STATUS current
    DESCRIPTION
        "Parameter 'description' in event SSH.77"
    ::= { sshEventObjects77 3 }

sshEventObjects78 OBJECT-IDENTITY
    STATUS current
    DESCRIPTION
        "Event SSH.78
        Error found in channel."
    ::= { sshEventsGroup 78 }

ssh78_userid OBJECT-TYPE
    SYNTAX Integer32
    MAX-ACCESS accessible-for-notify
    STATUS current
    DESCRIPTION
        "Parameter 'userid' in event SSH.78"
    ::= { sshEventObjects78 1 }

ssh78_local_chan OBJECT-TYPE
    SYNTAX Integer32
    MAX-ACCESS accessible-for-notify
    STATUS current
    DESCRIPTION
        "Parameter 'local_chan' in event SSH.78"
    ::= { sshEventObjects78 2 }

ssh78_description OBJECT-TYPE
    SYNTAX DisplayString
    MAX-ACCESS accessible-for-notify
    STATUS current
    DESCRIPTION
        "Parameter 'description' in event SSH.78"
    ::= { sshEventObjects78 3 }


sshNotification1 NOTIFICATION-TYPE
    STATUS current
    DESCRIPTION
        "Notification of Event SSH.1

        Message: 'SSH server not enabled'

        SSH server not enabled in configuration."
    ::= { sshNotificationsPrefix 1 }

sshNotification2 NOTIFICATION-TYPE
    OBJECTS { 
              ssh2_description 
            }
    STATUS current
    DESCRIPTION
        "Notification of Event SSH.2

        Message: 'Global verbose: $1'

        Parameters list:
              $1: ssh2_description

        Verbose info from a global SSH function."
    ::= { sshNotificationsPrefix 2 }

sshNotification3 NOTIFICATION-TYPE
    OBJECTS { 
              ssh3_description 
            }
    STATUS current
    DESCRIPTION
        "Notification of Event SSH.3

        Message: 'Global error: $1'

        Parameters list:
              $1: ssh3_description

        Error found in a global SSH function."
    ::= { sshNotificationsPrefix 3 }

sshNotification4 NOTIFICATION-TYPE
    OBJECTS { 
              ssh4_description, 
              ssh4_task 
            }
    STATUS current
    DESCRIPTION
        "Notification of Event SSH.4

        Message: 'Task verbose: $1 $2'

        Parameters list:
              $1: ssh4_description
              $2: ssh4_task

        Event related to task creation/deletion."
    ::= { sshNotificationsPrefix 4 }

sshNotification5 NOTIFICATION-TYPE
    OBJECTS { 
              ssh5_error, 
              ssh5_task 
            }
    STATUS current
    DESCRIPTION
        "Notification of Event SSH.5

        Message: 'Task error: $1 $2'

        Parameters list:
              $1: ssh5_error
              $2: ssh5_task

        Error related to task creation/deletion."
    ::= { sshNotificationsPrefix 5 }

sshNotification6 NOTIFICATION-TYPE
    OBJECTS { 
              ssh6_description 
            }
    STATUS current
    DESCRIPTION
        "Notification of Event SSH.6

        Message: 'Server init: $1'

        Parameters list:
              $1: ssh6_description

        Event related to server initialization."
    ::= { sshNotificationsPrefix 6 }

sshNotification7 NOTIFICATION-TYPE
    OBJECTS { 
              ssh7_description 
            }
    STATUS current
    DESCRIPTION
        "Notification of Event SSH.7

        Message: 'Server init error: $1'

        Parameters list:
              $1: ssh7_description

        Error related to server initialization."
    ::= { sshNotificationsPrefix 7 }

sshNotification8 NOTIFICATION-TYPE
    OBJECTS { 
              ssh8_description 
            }
    STATUS current
    DESCRIPTION
        "Notification of Event SSH.8

        Message: 'Server init verbose: $1'

        Parameters list:
              $1: ssh8_description

        Verbose event related to server initialization."
    ::= { sshNotificationsPrefix 8 }

sshNotification9 NOTIFICATION-TYPE
    OBJECTS { 
              ssh9_hostkey-type, 
              ssh9_description 
            }
    STATUS current
    DESCRIPTION
        "Notification of Event SSH.9

        Message: 'Hostkey type $1: $2'

        Parameters list:
              $1: ssh9_hostkey-type
              $2: ssh9_description

        Event related to hostkey loading/generation."
    ::= { sshNotificationsPrefix 9 }

sshNotification10 NOTIFICATION-TYPE
    OBJECTS { 
              ssh10_hostkey-type 
            }
    STATUS current
    DESCRIPTION
        "Notification of Event SSH.10

        Message: 'Hostkey type $1: not found in config!'

        Parameters list:
              $1: ssh10_hostkey-type

        Warning: Hostkey not found in config."
    ::= { sshNotificationsPrefix 10 }

sshNotification11 NOTIFICATION-TYPE
    OBJECTS { 
              ssh11_description 
            }
    STATUS current
    DESCRIPTION
        "Notification of Event SSH.11

        Message: 'Key generation verbose: $1'

        Parameters list:
              $1: ssh11_description

        Verbose information about key generation process."
    ::= { sshNotificationsPrefix 11 }

sshNotification12 NOTIFICATION-TYPE
    OBJECTS { 
              ssh12_description 
            }
    STATUS current
    DESCRIPTION
        "Notification of Event SSH.12

        Message: 'Key generation error: $1'

        Parameters list:
              $1: ssh12_description

        Error found during key generation process."
    ::= { sshNotificationsPrefix 12 }

sshNotification13 NOTIFICATION-TYPE
    STATUS current
    DESCRIPTION
        "Notification of Event SSH.13

        Message: '----'

        Reserved for possible future use."
    ::= { sshNotificationsPrefix 13 }

sshNotification14 NOTIFICATION-TYPE
    STATUS current
    DESCRIPTION
        "Notification of Event SSH.14

        Message: '----'

        Reserved for possible future use."
    ::= { sshNotificationsPrefix 14 }

sshNotification15 NOTIFICATION-TYPE
    OBJECTS { 
              ssh15_userid, 
              ssh15_srvadd,
              ssh15_srvport,
              ssh15_cliadd,
              ssh15_cliport 
            }
    STATUS current
    DESCRIPTION
        "Notification of Event SSH.15

        Message: 'New connection!!! New user id is $1. Server: $2:$3 - Client: $4:$5'

        Parameters list:
              $1: ssh15_userid
              $2: ssh15_srvadd
              $3: ssh15_srvport
              $4: ssh15_cliadd
              $5: ssh15_cliport

        Important! Event related to a new connection with user id info."
    ::= { sshNotificationsPrefix 15 }

sshNotification16 NOTIFICATION-TYPE
    OBJECTS { 
              ssh16_cliadd, 
              ssh16_cliport,
              ssh16_reason 
            }
    STATUS current
    DESCRIPTION
        "Notification of Event SSH.16

        Message: 'New connection from $1:$2 refused: $3'

        Parameters list:
              $1: ssh16_cliadd
              $2: ssh16_cliport
              $3: ssh16_reason

        A new connection was refused because of the reason"
    ::= { sshNotificationsPrefix 16 }

sshNotification17 NOTIFICATION-TYPE
    OBJECTS { 
              ssh17_userid, 
              ssh17_srvadd,
              ssh17_srvport,
              ssh17_cliadd,
              ssh17_cliport 
            }
    STATUS current
    DESCRIPTION
        "Notification of Event SSH.17

        Message: 'U:$1. Connection closed!!! Server: $2:$3 - Client: $4:$5. User id free!'

        Parameters list:
              $1: ssh17_userid
              $2: ssh17_srvadd
              $3: ssh17_srvport
              $4: ssh17_cliadd
              $5: ssh17_cliport

        Event related to a connection closing"
    ::= { sshNotificationsPrefix 17 }

sshNotification18 NOTIFICATION-TYPE
    OBJECTS { 
              ssh18_userid, 
              ssh18_description 
            }
    STATUS current
    DESCRIPTION
        "Notification of Event SSH.18

        Message: 'U:$1. Connection verbose: $2'

        Parameters list:
              $1: ssh18_userid
              $2: ssh18_description

        Verbose information about the connection."
    ::= { sshNotificationsPrefix 18 }

sshNotification19 NOTIFICATION-TYPE
    OBJECTS { 
              ssh19_userid, 
              ssh19_description 
            }
    STATUS current
    DESCRIPTION
        "Notification of Event SSH.19

        Message: 'U:$1. Version incompatibility: $2'

        Parameters list:
              $1: ssh19_userid
              $2: ssh19_description

        Error related to version incompatibility."
    ::= { sshNotificationsPrefix 19 }

sshNotification20 NOTIFICATION-TYPE
    STATUS current
    DESCRIPTION
        "Notification of Event SSH.20

        Message: '----'

        Reserved for possible future use."
    ::= { sshNotificationsPrefix 20 }

sshNotification21 NOTIFICATION-TYPE
    OBJECTS { 
              ssh21_userid, 
              ssh21_msg-number 
            }
    STATUS current
    DESCRIPTION
        "Notification of Event SSH.21

        Message: 'U:$1. Message [$2] received'

        Parameters list:
              $1: ssh21_userid
              $2: ssh21_msg-number

        SSH message received."
    ::= { sshNotificationsPrefix 21 }

sshNotification22 NOTIFICATION-TYPE
    OBJECTS { 
              ssh22_userid, 
              ssh22_msg-number 
            }
    STATUS current
    DESCRIPTION
        "Notification of Event SSH.22

        Message: 'U:$1. Message [$2] sent'

        Parameters list:
              $1: ssh22_userid
              $2: ssh22_msg-number

        SSH message sent."
    ::= { sshNotificationsPrefix 22 }

sshNotification23 NOTIFICATION-TYPE
    OBJECTS { 
              ssh23_userid, 
              ssh23_msg-number 
            }
    STATUS current
    DESCRIPTION
        "Notification of Event SSH.23

        Message: 'U:$1. Message [$2] expected'

        Parameters list:
              $1: ssh23_userid
              $2: ssh23_msg-number

        Message expected from peer."
    ::= { sshNotificationsPrefix 23 }

sshNotification24 NOTIFICATION-TYPE
    OBJECTS { 
              ssh24_userid, 
              ssh24_reason-code,
              ssh24_description 
            }
    STATUS current
    DESCRIPTION
        "Notification of Event SSH.24

        Message: 'U:$1. Disconnection message (reason code: $2) received: $3'

        Parameters list:
              $1: ssh24_userid
              $2: ssh24_reason-code
              $3: ssh24_description

        Disconnection message received with reason code and explanation."
    ::= { sshNotificationsPrefix 24 }

sshNotification25 NOTIFICATION-TYPE
    OBJECTS { 
              ssh25_userid, 
              ssh25_reason-code,
              ssh25_description 
            }
    STATUS current
    DESCRIPTION
        "Notification of Event SSH.25

        Message: 'U:$1. Disconnection message (reason code:$2) sent: $3'

        Parameters list:
              $1: ssh25_userid
              $2: ssh25_reason-code
              $3: ssh25_description

        Disconnection message sent with reason code and explanation."
    ::= { sshNotificationsPrefix 25 }

sshNotification26 NOTIFICATION-TYPE
    OBJECTS { 
              ssh26_userid, 
              ssh26_description 
            }
    STATUS current
    DESCRIPTION
        "Notification of Event SSH.26

        Message: 'U:$1. Ignore message $2'

        Parameters list:
              $1: ssh26_userid
              $2: ssh26_description

        An ignore message has been rcvd/sent."
    ::= { sshNotificationsPrefix 26 }

sshNotification27 NOTIFICATION-TYPE
    OBJECTS { 
              ssh27_userid, 
              ssh27_direction 
            }
    STATUS current
    DESCRIPTION
        "Notification of Event SSH.27

        Message: 'U:$1. Unimplemented message $2'

        Parameters list:
              $1: ssh27_userid
              $2: ssh27_direction

        A not implemented message has been received."
    ::= { sshNotificationsPrefix 27 }

sshNotification28 NOTIFICATION-TYPE
    OBJECTS { 
              ssh28_userid, 
              ssh28_rcvd-sent,
              ssh28_description 
            }
    STATUS current
    DESCRIPTION
        "Notification of Event SSH.28

        Message: 'U:$1. Debug message $2: $3'

        Parameters list:
              $1: ssh28_userid
              $2: ssh28_rcvd-sent
              $3: ssh28_description

        Debug message rcvd/sent with debug info."
    ::= { sshNotificationsPrefix 28 }

sshNotification29 NOTIFICATION-TYPE
    STATUS current
    DESCRIPTION
        "Notification of Event SSH.29

        Message: '----'

        Reserved for possible future use."
    ::= { sshNotificationsPrefix 29 }

sshNotification30 NOTIFICATION-TYPE
    STATUS current
    DESCRIPTION
        "Notification of Event SSH.30

        Message: '----'

        Reserved for possible future use."
    ::= { sshNotificationsPrefix 30 }

sshNotification31 NOTIFICATION-TYPE
    OBJECTS { 
              ssh31_userid, 
              ssh31_proposal 
            }
    STATUS current
    DESCRIPTION
        "Notification of Event SSH.31

        Message: 'U:$1. Key Exchange. Kexinit server->client: $2'

        Parameters list:
              $1: ssh31_userid
              $2: ssh31_proposal

        KEX proposal sent from server to client"
    ::= { sshNotificationsPrefix 31 }

sshNotification32 NOTIFICATION-TYPE
    OBJECTS { 
              ssh32_userid, 
              ssh32_proposal 
            }
    STATUS current
    DESCRIPTION
        "Notification of Event SSH.32

        Message: 'U:$1. Key Exchange. Kexinit client->server: $2'

        Parameters list:
              $1: ssh32_userid
              $2: ssh32_proposal

        KEX proposal sent from client to server"
    ::= { sshNotificationsPrefix 32 }

sshNotification33 NOTIFICATION-TYPE
    OBJECTS { 
              ssh33_userid, 
              ssh33_decision 
            }
    STATUS current
    DESCRIPTION
        "Notification of Event SSH.33

        Message: 'U:$1. Key Exchange. Decision: $2'

        Parameters list:
              $1: ssh33_userid
              $2: ssh33_decision

        KEX decision made after comparing kexinit messages."
    ::= { sshNotificationsPrefix 33 }

sshNotification34 NOTIFICATION-TYPE
    OBJECTS { 
              ssh34_userid, 
              ssh34_description 
            }
    STATUS current
    DESCRIPTION
        "Notification of Event SSH.34

        Message: 'U:$1. Key Exchange. Verbose: $2'

        Parameters list:
              $1: ssh34_userid
              $2: ssh34_description

        Event related to verbose information about KEX."
    ::= { sshNotificationsPrefix 34 }

sshNotification35 NOTIFICATION-TYPE
    OBJECTS { 
              ssh35_userid, 
              ssh35_description 
            }
    STATUS current
    DESCRIPTION
        "Notification of Event SSH.35

        Message: 'U:$1. Key Exchange. Error: $2'

        Parameters list:
              $1: ssh35_userid
              $2: ssh35_description

        Event related to an error found during KEX."
    ::= { sshNotificationsPrefix 35 }

sshNotification36 NOTIFICATION-TYPE
    OBJECTS { 
              ssh36_userid, 
              ssh36_description,
              ssh36_direction 
            }
    STATUS current
    DESCRIPTION
        "Notification of Event SSH.36

        Message: 'U:$1. Key Exchange. Diffie-Hellman $2 $3'

        Parameters list:
              $1: ssh36_userid
              $2: ssh36_description
              $3: ssh36_direction

        Diffie-Hellman message of a certain type has been received/sent."
    ::= { sshNotificationsPrefix 36 }

sshNotification37 NOTIFICATION-TYPE
    OBJECTS { 
              ssh37_userid, 
              ssh37_direction,
              ssh37_description 
            }
    STATUS current
    DESCRIPTION
        "Notification of Event SSH.37

        Message: 'U:$1. Key Exchange. SSHv1: $2 $3'

        Parameters list:
              $1: ssh37_userid
              $2: ssh37_direction
              $3: ssh37_description

        SSHv1 Key Exchange message has been received/sent."
    ::= { sshNotificationsPrefix 37 }

sshNotification38 NOTIFICATION-TYPE
    OBJECTS { 
              ssh38_userid, 
              ssh38_direction 
            }
    STATUS current
    DESCRIPTION
        "Notification of Event SSH.38

        Message: 'U:$1. KEX. NEWKEYS message $2'

        Parameters list:
              $1: ssh38_userid
              $2: ssh38_direction

        New keys are about to be used from now on."
    ::= { sshNotificationsPrefix 38 }

sshNotification39 NOTIFICATION-TYPE
    OBJECTS { 
              ssh39_userid 
            }
    STATUS current
    DESCRIPTION
        "Notification of Event SSH.39

        Message: 'U:$1. KEX. Rekeying!'

        Parameters list:
              $1: ssh39_userid

        Periodic rekeying process after a period."
    ::= { sshNotificationsPrefix 39 }

sshNotification40 NOTIFICATION-TYPE
    STATUS current
    DESCRIPTION
        "Notification of Event SSH.40

        Message: '----'

        Reserved for possible future use."
    ::= { sshNotificationsPrefix 40 }

sshNotification41 NOTIFICATION-TYPE
    OBJECTS { 
              ssh41_userid, 
              ssh41_service,
              ssh41_direction 
            }
    STATUS current
    DESCRIPTION
        "Notification of Event SSH.41

        Message: 'U:$1. Service request $2 $3'

        Parameters list:
              $1: ssh41_userid
              $2: ssh41_service
              $3: ssh41_direction

        Service request name and direction."
    ::= { sshNotificationsPrefix 41 }

sshNotification42 NOTIFICATION-TYPE
    OBJECTS { 
              ssh42_userid, 
              ssh42_service 
            }
    STATUS current
    DESCRIPTION
        "Notification of Event SSH.42

        Message: 'U:$1. Service request $2 not accepted'

        Parameters list:
              $1: ssh42_userid
              $2: ssh42_service

        Service request received/sent has not been accepted."
    ::= { sshNotificationsPrefix 42 }

sshNotification43 NOTIFICATION-TYPE
    OBJECTS { 
              ssh43_userid, 
              ssh43_direction,
              ssh43_username,
              ssh43_service,
              ssh43_method 
            }
    STATUS current
    DESCRIPTION
        "Notification of Event SSH.43

        Message: 'U:$1. User authentication request $2: user $3 - service $4 - method $5'

        Parameters list:
              $1: ssh43_userid
              $2: ssh43_direction
              $3: ssh43_username
              $4: ssh43_service
              $5: ssh43_method

        Userauth request received/sent with parameters."
    ::= { sshNotificationsPrefix 43 }

sshNotification44 NOTIFICATION-TYPE
    OBJECTS { 
              ssh44_userid, 
              ssh44_attempt,
              ssh44_failures 
            }
    STATUS current
    DESCRIPTION
        "Notification of Event SSH.44

        Message: 'U:$1. User authentication attempt $2. Number of failures: $3'

        Parameters list:
              $1: ssh44_userid
              $2: ssh44_attempt
              $3: ssh44_failures

        Register of userauth attempt and failures."
    ::= { sshNotificationsPrefix 44 }

sshNotification45 NOTIFICATION-TYPE
    OBJECTS { 
              ssh45_userid, 
              ssh45_operation 
            }
    STATUS current
    DESCRIPTION
        "Notification of Event SSH.45

        Message: 'U:$1. User authentication request $2'

        Parameters list:
              $1: ssh45_userid
              $2: ssh45_operation

        Userauth request postponed/accepted."
    ::= { sshNotificationsPrefix 45 }

sshNotification46 NOTIFICATION-TYPE
    OBJECTS { 
              ssh46_userid, 
              ssh46_methods 
            }
    STATUS current
    DESCRIPTION
        "Notification of Event SSH.46

        Message: 'U:$1. User authentication request denied. Methods: $2'

        Parameters list:
              $1: ssh46_userid
              $2: ssh46_methods

        Userauth request denied indicating available methods."
    ::= { sshNotificationsPrefix 46 }

sshNotification47 NOTIFICATION-TYPE
    OBJECTS { 
              ssh47_userid, 
              ssh47_description 
            }
    STATUS current
    DESCRIPTION
        "Notification of Event SSH.47

        Message: 'U:$1. SSHv1 user authentication: $2'

        Parameters list:
              $1: ssh47_userid
              $2: ssh47_description

        Event related to information about SSHv1 authentication."
    ::= { sshNotificationsPrefix 47 }

sshNotification48 NOTIFICATION-TYPE
    OBJECTS { 
              ssh48_userid, 
              ssh48_description 
            }
    STATUS current
    DESCRIPTION
        "Notification of Event SSH.48

        Message: 'U:$1. User authentication verbose: $2'

        Parameters list:
              $1: ssh48_userid
              $2: ssh48_description

        Event related to further information about authentication."
    ::= { sshNotificationsPrefix 48 }

sshNotification49 NOTIFICATION-TYPE
    OBJECTS { 
              ssh49_userid 
            }
    STATUS current
    DESCRIPTION
        "Notification of Event SSH.49

        Message: 'U:$1. User authentication not completed before maximum allowed time expired!!'

        Parameters list:
              $1: ssh49_userid

        User authentication not completed before maximum allowed time expired."
    ::= { sshNotificationsPrefix 49 }

sshNotification50 NOTIFICATION-TYPE
    OBJECTS { 
              ssh50_userid, 
              ssh50_description 
            }
    STATUS current
    DESCRIPTION
        "Notification of Event SSH.50

        Message: 'U:$1. User authentication error: $2'

        Parameters list:
              $1: ssh50_userid
              $2: ssh50_description

        Event related to an error found while user authentication."
    ::= { sshNotificationsPrefix 50 }

sshNotification51 NOTIFICATION-TYPE
    OBJECTS { 
              ssh51_userid, 
              ssh51_direction 
            }
    STATUS current
    DESCRIPTION
        "Notification of Event SSH.51

        Message: 'U:$1. Banner message $2'

        Parameters list:
              $1: ssh51_userid
              $2: ssh51_direction

        Banner message was received/sent."
    ::= { sshNotificationsPrefix 51 }

sshNotification52 NOTIFICATION-TYPE
    STATUS current
    DESCRIPTION
        "Notification of Event SSH.52

        Message: '----'

        Reserved for possible future use."
    ::= { sshNotificationsPrefix 52 }

sshNotification53 NOTIFICATION-TYPE
    STATUS current
    DESCRIPTION
        "Notification of Event SSH.53

        Message: '----'

        Reserved for possible future use."
    ::= { sshNotificationsPrefix 53 }

sshNotification54 NOTIFICATION-TYPE
    OBJECTS { 
              ssh54_userid, 
              ssh54_request,
              ssh54_direction 
            }
    STATUS current
    DESCRIPTION
        "Notification of Event SSH.54

        Message: 'U:$1. Global request $2 $3'

        Parameters list:
              $1: ssh54_userid
              $2: ssh54_request
              $3: ssh54_direction

        Global request was received/sent."
    ::= { sshNotificationsPrefix 54 }

sshNotification55 NOTIFICATION-TYPE
    OBJECTS { 
              ssh55_userid, 
              ssh55_request 
            }
    STATUS current
    DESCRIPTION
        "Notification of Event SSH.55

        Message: 'U:$1. Global request $2 refused'

        Parameters list:
              $1: ssh55_userid
              $2: ssh55_request

        Global request was refused."
    ::= { sshNotificationsPrefix 55 }

sshNotification56 NOTIFICATION-TYPE
    STATUS current
    DESCRIPTION
        "Notification of Event SSH.56

        Message: '----'

        Reserved for possible future use."
    ::= { sshNotificationsPrefix 56 }

sshNotification57 NOTIFICATION-TYPE
    STATUS current
    DESCRIPTION
        "Notification of Event SSH.57

        Message: '----'

        Reserved for possible future use."
    ::= { sshNotificationsPrefix 57 }

sshNotification58 NOTIFICATION-TYPE
    OBJECTS { 
              ssh58_userid, 
              ssh58_direction,
              ssh58_sndchan,
              ssh58_type,
              ssh58_win,
              ssh58_maxpkt 
            }
    STATUS current
    DESCRIPTION
        "Notification of Event SSH.58

        Message: 'U:$1. Channel open $2: Sender_channel $3 - Type $4 - rcv_Window $5 - Max_packet $6'

        Parameters list:
              $1: ssh58_userid
              $2: ssh58_direction
              $3: ssh58_sndchan
              $4: ssh58_type
              $5: ssh58_win
              $6: ssh58_maxpkt

        Channel open message with sender parameters."
    ::= { sshNotificationsPrefix 58 }

sshNotification59 NOTIFICATION-TYPE
    OBJECTS { 
              ssh59_userid, 
              ssh59_cliadd,
              ssh59_cliport,
              ssh59_srvadd,
              ssh59_srvport,
              ssh59_clichan,
              ssh59_srvchan,
              ssh59_session 
            }
    STATUS current
    DESCRIPTION
        "Notification of Event SSH.59

        Message: 'U:$1. Socket c: $2:$3 -> s: $4:$5. Client_channel $6 - Server_channel $7 - Local_session $8'

        Parameters list:
              $1: ssh59_userid
              $2: ssh59_cliadd
              $3: ssh59_cliport
              $4: ssh59_srvadd
              $5: ssh59_srvport
              $6: ssh59_clichan
              $7: ssh59_srvchan
              $8: ssh59_session

        Association between channels and session for an authenticated connection."
    ::= { sshNotificationsPrefix 59 }

sshNotification60 NOTIFICATION-TYPE
    OBJECTS { 
              ssh60_userid, 
              ssh60_direction,
              ssh60_rcvchan,
              ssh60_sndchan,
              ssh60_type,
              ssh60_win,
              ssh60_maxpkt 
            }
    STATUS current
    DESCRIPTION
        "Notification of Event SSH.60

        Message: 'U:$1. Channel open confirmed $2: Receiver_channel $3 - Sender_channel $4 - Type $5 - rcv_Window $6 - Max_packet $7'

        Parameters list:
              $1: ssh60_userid
              $2: ssh60_direction
              $3: ssh60_rcvchan
              $4: ssh60_sndchan
              $5: ssh60_type
              $6: ssh60_win
              $7: ssh60_maxpkt

        Channel open confirmation message for receiver channel with sender parameters."
    ::= { sshNotificationsPrefix 60 }

sshNotification61 NOTIFICATION-TYPE
    OBJECTS { 
              ssh61_userid, 
              ssh61_reason-code,
              ssh61_rcvchan,
              ssh61_description 
            }
    STATUS current
    DESCRIPTION
        "Notification of Event SSH.61

        Message: 'U:$1. Channel open failure [$2] for rcvchan $3: $4'

        Parameters list:
              $1: ssh61_userid
              $2: ssh61_reason-code
              $3: ssh61_rcvchan
              $4: ssh61_description

        Channel open failure message for receiver channel."
    ::= { sshNotificationsPrefix 61 }

sshNotification62 NOTIFICATION-TYPE
    OBJECTS { 
              ssh62_userid, 
              ssh62_direction 
            }
    STATUS current
    DESCRIPTION
        "Notification of Event SSH.62

        Message: 'U:$1. Client-alive $2'

        Parameters list:
              $1: ssh62_userid
              $2: ssh62_direction

        Client-alive message has been received/sent."
    ::= { sshNotificationsPrefix 62 }

sshNotification63 NOTIFICATION-TYPE
    OBJECTS { 
              ssh63_userid, 
              ssh63_description 
            }
    STATUS current
    DESCRIPTION
        "Notification of Event SSH.63

        Message: 'U:$1. Authenticated SSHv1: $2'

        Parameters list:
              $1: ssh63_userid
              $2: ssh63_description

        Event related to authenticated SSHv1."
    ::= { sshNotificationsPrefix 63 }

sshNotification64 NOTIFICATION-TYPE
    OBJECTS { 
              ssh64_userid, 
              ssh64_description 
            }
    STATUS current
    DESCRIPTION
        "Notification of Event SSH.64

        Message: 'U:$1. Authenticated. Verbose: $2'

        Parameters list:
              $1: ssh64_userid
              $2: ssh64_description

        Verbose information in authenticated connection."
    ::= { sshNotificationsPrefix 64 }

sshNotification65 NOTIFICATION-TYPE
    OBJECTS { 
              ssh65_userid, 
              ssh65_description 
            }
    STATUS current
    DESCRIPTION
        "Notification of Event SSH.65

        Message: 'U:$1. Authenticated. Error: $2'

        Parameters list:
              $1: ssh65_userid
              $2: ssh65_description

        Error found in authenticated connection."
    ::= { sshNotificationsPrefix 65 }

sshNotification66 NOTIFICATION-TYPE
    STATUS current
    DESCRIPTION
        "Notification of Event SSH.66

        Message: '----'

        Reserved for possible future use."
    ::= { sshNotificationsPrefix 66 }

sshNotification67 NOTIFICATION-TYPE
    OBJECTS { 
              ssh67_userid, 
              ssh67_local_chan,
              ssh67_direction,
              ssh67_bytes 
            }
    STATUS current
    DESCRIPTION
        "Notification of Event SSH.67

        Message: 'U:$1.C:$2. Channel window adjust $3: $4 bytes'

        Parameters list:
              $1: ssh67_userid
              $2: ssh67_local_chan
              $3: ssh67_direction
              $4: ssh67_bytes

        Channel window adjust message received/sent indicating bytes to add."
    ::= { sshNotificationsPrefix 67 }

sshNotification68 NOTIFICATION-TYPE
    OBJECTS { 
              ssh68_userid, 
              ssh68_local_chan,
              ssh68_direction,
              ssh68_len 
            }
    STATUS current
    DESCRIPTION
        "Notification of Event SSH.68

        Message: 'U:$1.C:$2. Channel data $3 ($4 bytes)'

        Parameters list:
              $1: ssh68_userid
              $2: ssh68_local_chan
              $3: ssh68_direction
              $4: ssh68_len

        Channel data message received/sent."
    ::= { sshNotificationsPrefix 68 }

sshNotification69 NOTIFICATION-TYPE
    OBJECTS { 
              ssh69_userid, 
              ssh69_local_chan,
              ssh69_type,
              ssh69_direction,
              ssh69_len 
            }
    STATUS current
    DESCRIPTION
        "Notification of Event SSH.69

        Message: 'U:$1.C:$2. Extended channel data [type $3] $4 ($5 bytes)'

        Parameters list:
              $1: ssh69_userid
              $2: ssh69_local_chan
              $3: ssh69_type
              $4: ssh69_direction
              $5: ssh69_len

        Extended channel data message received/sent."
    ::= { sshNotificationsPrefix 69 }

sshNotification70 NOTIFICATION-TYPE
    OBJECTS { 
              ssh70_userid, 
              ssh70_local_chan,
              ssh70_direction 
            }
    STATUS current
    DESCRIPTION
        "Notification of Event SSH.70

        Message: 'U:$1.C:$2. EOF $3'

        Parameters list:
              $1: ssh70_userid
              $2: ssh70_local_chan
              $3: ssh70_direction

        EOF message received/sent."
    ::= { sshNotificationsPrefix 70 }

sshNotification71 NOTIFICATION-TYPE
    OBJECTS { 
              ssh71_userid, 
              ssh71_local_chan,
              ssh71_direction 
            }
    STATUS current
    DESCRIPTION
        "Notification of Event SSH.71

        Message: 'U:$1.C:$2. Channel close $3'

        Parameters list:
              $1: ssh71_userid
              $2: ssh71_local_chan
              $3: ssh71_direction

        Channel close message received/sent."
    ::= { sshNotificationsPrefix 71 }

sshNotification72 NOTIFICATION-TYPE
    OBJECTS { 
              ssh72_userid, 
              ssh72_local_chan,
              ssh72_request,
              ssh72_direction,
              ssh72_confirm,
              ssh72_data 
            }
    STATUS current
    DESCRIPTION
        "Notification of Event SSH.72

        Message: 'U:$1.C:$2. Channel request $3 $4. Confirm: $5. Data: $6'

        Parameters list:
              $1: ssh72_userid
              $2: ssh72_local_chan
              $3: ssh72_request
              $4: ssh72_direction
              $5: ssh72_confirm
              $6: ssh72_data

        Channel request message received/sent that may be confirmed, with extra data."
    ::= { sshNotificationsPrefix 72 }

sshNotification73 NOTIFICATION-TYPE
    OBJECTS { 
              ssh73_userid, 
              ssh73_local_chan,
              ssh73_request 
            }
    STATUS current
    DESCRIPTION
        "Notification of Event SSH.73

        Message: 'U:$1.C:$2. Channel request $3 failed'

        Parameters list:
              $1: ssh73_userid
              $2: ssh73_local_chan
              $3: ssh73_request

        Channel failure message indicating that a previous request was refused."
    ::= { sshNotificationsPrefix 73 }

sshNotification74 NOTIFICATION-TYPE
    OBJECTS { 
              ssh74_userid, 
              ssh74_local_chan 
            }
    STATUS current
    DESCRIPTION
        "Notification of Event SSH.74

        Message: 'U:$1.C:$2. New pty allocated'

        Parameters list:
              $1: ssh74_userid
              $2: ssh74_local_chan

        Event related to the allocation of a new pseudo-terminal."
    ::= { sshNotificationsPrefix 74 }

sshNotification75 NOTIFICATION-TYPE
    OBJECTS { 
              ssh75_userid, 
              ssh75_local_chan 
            }
    STATUS current
    DESCRIPTION
        "Notification of Event SSH.75

        Message: 'U:$1.C:$2. New console created'

        Parameters list:
              $1: ssh75_userid
              $2: ssh75_local_chan

        Event related to the creation of a new console."
    ::= { sshNotificationsPrefix 75 }

sshNotification76 NOTIFICATION-TYPE
    OBJECTS { 
              ssh76_userid, 
              ssh76_local_chan,
              ssh76_description 
            }
    STATUS current
    DESCRIPTION
        "Notification of Event SSH.76

        Message: 'U:$1.C:$2. SSHv1: $3'

        Parameters list:
              $1: ssh76_userid
              $2: ssh76_local_chan
              $3: ssh76_description

        Event related to a SSHv1 channel."
    ::= { sshNotificationsPrefix 76 }

sshNotification77 NOTIFICATION-TYPE
    OBJECTS { 
              ssh77_userid, 
              ssh77_local_chan,
              ssh77_description 
            }
    STATUS current
    DESCRIPTION
        "Notification of Event SSH.77

        Message: 'U:$1.C:$2. Channel verbose: $3'

        Parameters list:
              $1: ssh77_userid
              $2: ssh77_local_chan
              $3: ssh77_description

        Verbose information about channel."
    ::= { sshNotificationsPrefix 77 }

sshNotification78 NOTIFICATION-TYPE
    OBJECTS { 
              ssh78_userid, 
              ssh78_local_chan,
              ssh78_description 
            }
    STATUS current
    DESCRIPTION
        "Notification of Event SSH.78

        Message: 'U:$1.C:$2. Channel error: $3'

        Parameters list:
              $1: ssh78_userid
              $2: ssh78_local_chan
              $3: ssh78_description

        Error found in channel."
    ::= { sshNotificationsPrefix 78 }


END
