-- file automatically created


TELDAT-TRAP-NAPT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


naptTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NAPT event subsystem."
    REVISION "201401200930Z"
    DESCRIPTION "Initial implementation"
        ::= { telEventTraps 154 }


naptEventsGroup	OBJECT IDENTIFIER	::= { naptTrapsMIB 1 }

naptNotifications	OBJECT IDENTIFIER	::= { naptTrapsMIB 2 }
naptNotificationsPrefix	OBJECT IDENTIFIER	::= { naptNotifications 0 }

naptEventObjects1 OBJECT-IDENTITY
    STATUS current
    DESCRIPTION
        "Event NAPT.1
        NAPT for outgoing IP packet."
    ::= { naptEventsGroup 1 }

napt1_internal_ip OBJECT-TYPE
    SYNTAX IpAddress
    MAX-ACCESS accessible-for-notify
    STATUS current
    DESCRIPTION
        "Parameter 'internal_ip' in event NAPT.1"
    ::= { naptEventObjects1 1 }

napt1_internal_port OBJECT-TYPE
    SYNTAX Integer32
    MAX-ACCESS accessible-for-notify
    STATUS current
    DESCRIPTION
        "Parameter 'internal_port' in event NAPT.1"
    ::= { naptEventObjects1 2 }

napt1_external_ip OBJECT-TYPE
    SYNTAX IpAddress
    MAX-ACCESS accessible-for-notify
    STATUS current
    DESCRIPTION
        "Parameter 'external_ip' in event NAPT.1"
    ::= { naptEventObjects1 3 }

napt1_external_port OBJECT-TYPE
    SYNTAX Integer32
    MAX-ACCESS accessible-for-notify
    STATUS current
    DESCRIPTION
        "Parameter 'external_port' in event NAPT.1"
    ::= { naptEventObjects1 4 }

naptEventObjects2 OBJECT-IDENTITY
    STATUS current
    DESCRIPTION
        "Event NAPT.2
        NAPT for incoming IP packet."
    ::= { naptEventsGroup 2 }

napt2_external_ip OBJECT-TYPE
    SYNTAX IpAddress
    MAX-ACCESS accessible-for-notify
    STATUS current
    DESCRIPTION
        "Parameter 'external_ip' in event NAPT.2"
    ::= { naptEventObjects2 1 }

napt2_external_port OBJECT-TYPE
    SYNTAX Integer32
    MAX-ACCESS accessible-for-notify
    STATUS current
    DESCRIPTION
        "Parameter 'external_port' in event NAPT.2"
    ::= { naptEventObjects2 2 }

napt2_internal_ip OBJECT-TYPE
    SYNTAX IpAddress
    MAX-ACCESS accessible-for-notify
    STATUS current
    DESCRIPTION
        "Parameter 'internal_ip' in event NAPT.2"
    ::= { naptEventObjects2 3 }

napt2_internal_port OBJECT-TYPE
    SYNTAX Integer32
    MAX-ACCESS accessible-for-notify
    STATUS current
    DESCRIPTION
        "Parameter 'internal_port' in event NAPT.2"
    ::= { naptEventObjects2 4 }

naptEventObjects3 OBJECT-IDENTITY
    STATUS current
    DESCRIPTION
        "Event NAPT.3
        Translation for outgoing ICMP packet."
    ::= { naptEventsGroup 3 }

napt3_internal_ip OBJECT-TYPE
    SYNTAX IpAddress
    MAX-ACCESS accessible-for-notify
    STATUS current
    DESCRIPTION
        "Parameter 'internal_ip' in event NAPT.3"
    ::= { naptEventObjects3 1 }

napt3_internal_ident OBJECT-TYPE
    SYNTAX Integer32
    MAX-ACCESS accessible-for-notify
    STATUS current
    DESCRIPTION
        "Parameter 'internal_ident' in event NAPT.3"
    ::= { naptEventObjects3 2 }

napt3_external_ip OBJECT-TYPE
    SYNTAX IpAddress
    MAX-ACCESS accessible-for-notify
    STATUS current
    DESCRIPTION
        "Parameter 'external_ip' in event NAPT.3"
    ::= { naptEventObjects3 3 }

napt3_external_ident OBJECT-TYPE
    SYNTAX Integer32
    MAX-ACCESS accessible-for-notify
    STATUS current
    DESCRIPTION
        "Parameter 'external_ident' in event NAPT.3"
    ::= { naptEventObjects3 4 }

naptEventObjects4 OBJECT-IDENTITY
    STATUS current
    DESCRIPTION
        "Event NAPT.4
        Translation for incoming ICMP packet."
    ::= { naptEventsGroup 4 }

napt4_external_ip OBJECT-TYPE
    SYNTAX IpAddress
    MAX-ACCESS accessible-for-notify
    STATUS current
    DESCRIPTION
        "Parameter 'external_ip' in event NAPT.4"
    ::= { naptEventObjects4 1 }

napt4_external_ident OBJECT-TYPE
    SYNTAX Integer32
    MAX-ACCESS accessible-for-notify
    STATUS current
    DESCRIPTION
        "Parameter 'external_ident' in event NAPT.4"
    ::= { naptEventObjects4 2 }

napt4_internal_ip OBJECT-TYPE
    SYNTAX IpAddress
    MAX-ACCESS accessible-for-notify
    STATUS current
    DESCRIPTION
        "Parameter 'internal_ip' in event NAPT.4"
    ::= { naptEventObjects4 3 }

napt4_internal_ident OBJECT-TYPE
    SYNTAX Integer32
    MAX-ACCESS accessible-for-notify
    STATUS current
    DESCRIPTION
        "Parameter 'internal_ident' in event NAPT.4"
    ::= { naptEventObjects4 4 }

naptEventObjects7 OBJECT-IDENTITY
    STATUS current
    DESCRIPTION
        "Event NAPT.7
        Received TCP packet with bad TCP checksum."
    ::= { naptEventsGroup 7 }

napt7_internal_ip OBJECT-TYPE
    SYNTAX IpAddress
    MAX-ACCESS accessible-for-notify
    STATUS current
    DESCRIPTION
        "Parameter 'internal_ip' in event NAPT.7"
    ::= { naptEventObjects7 1 }

napt7_internal_port OBJECT-TYPE
    SYNTAX Integer32
    MAX-ACCESS accessible-for-notify
    STATUS current
    DESCRIPTION
        "Parameter 'internal_port' in event NAPT.7"
    ::= { naptEventObjects7 2 }

napt7_external_ip OBJECT-TYPE
    SYNTAX IpAddress
    MAX-ACCESS accessible-for-notify
    STATUS current
    DESCRIPTION
        "Parameter 'external_ip' in event NAPT.7"
    ::= { naptEventObjects7 3 }

napt7_external_port OBJECT-TYPE
    SYNTAX Integer32
    MAX-ACCESS accessible-for-notify
    STATUS current
    DESCRIPTION
        "Parameter 'external_port' in event NAPT.7"
    ::= { naptEventObjects7 4 }

napt7_sequence OBJECT-TYPE
    SYNTAX Integer32
    MAX-ACCESS accessible-for-notify
    STATUS current
    DESCRIPTION
        "Parameter 'sequence' in event NAPT.7"
    ::= { naptEventObjects7 5 }

napt7_ack_sequence OBJECT-TYPE
    SYNTAX Integer32
    MAX-ACCESS accessible-for-notify
    STATUS current
    DESCRIPTION
        "Parameter 'ack_sequence' in event NAPT.7"
    ::= { naptEventObjects7 6 }

naptEventObjects8 OBJECT-IDENTITY
    STATUS current
    DESCRIPTION
        "Event NAPT.8
        It is not allowed to do NAPT in some firewalling cases: RIP, OSPF..."
    ::= { naptEventsGroup 8 }

napt8_Drop_noNaptto OBJECT-TYPE
    SYNTAX DisplayString
    MAX-ACCESS accessible-for-notify
    STATUS current
    DESCRIPTION
        "Parameter 'Drop_noNaptto' in event NAPT.8"
    ::= { naptEventObjects8 1 }

napt8_packet_type OBJECT-TYPE
    SYNTAX DisplayString
    MAX-ACCESS accessible-for-notify
    STATUS current
    DESCRIPTION
        "Parameter 'packet_type' in event NAPT.8"
    ::= { naptEventObjects8 2 }

naptEventObjects9 OBJECT-IDENTITY
    STATUS current
    DESCRIPTION
        "Event NAPT.9
        Sent TCP SYNC."
    ::= { naptEventsGroup 9 }

napt9_application OBJECT-TYPE
    SYNTAX DisplayString
    MAX-ACCESS accessible-for-notify
    STATUS current
    DESCRIPTION
        "Parameter 'application' in event NAPT.9"
    ::= { naptEventObjects9 1 }

napt9_source_ip OBJECT-TYPE
    SYNTAX IpAddress
    MAX-ACCESS accessible-for-notify
    STATUS current
    DESCRIPTION
        "Parameter 'source_ip' in event NAPT.9"
    ::= { naptEventObjects9 2 }

napt9_source_port OBJECT-TYPE
    SYNTAX Integer32
    MAX-ACCESS accessible-for-notify
    STATUS current
    DESCRIPTION
        "Parameter 'source_port' in event NAPT.9"
    ::= { naptEventObjects9 3 }

napt9_target_ip OBJECT-TYPE
    SYNTAX IpAddress
    MAX-ACCESS accessible-for-notify
    STATUS current
    DESCRIPTION
        "Parameter 'target_ip' in event NAPT.9"
    ::= { naptEventObjects9 4 }

napt9_target_port OBJECT-TYPE
    SYNTAX Integer32
    MAX-ACCESS accessible-for-notify
    STATUS current
    DESCRIPTION
        "Parameter 'target_port' in event NAPT.9"
    ::= { naptEventObjects9 5 }

napt9_sequence OBJECT-TYPE
    SYNTAX Integer32
    MAX-ACCESS accessible-for-notify
    STATUS current
    DESCRIPTION
        "Parameter 'sequence' in event NAPT.9"
    ::= { naptEventObjects9 6 }

napt9_ack_sequence OBJECT-TYPE
    SYNTAX Integer32
    MAX-ACCESS accessible-for-notify
    STATUS current
    DESCRIPTION
        "Parameter 'ack_sequence' in event NAPT.9"
    ::= { naptEventObjects9 7 }

naptEventObjects10 OBJECT-IDENTITY
    STATUS current
    DESCRIPTION
        "Event NAPT.10
        Received or sent TCP FIN/RST."
    ::= { naptEventsGroup 10 }

napt10_application OBJECT-TYPE
    SYNTAX DisplayString
    MAX-ACCESS accessible-for-notify
    STATUS current
    DESCRIPTION
        "Parameter 'application' in event NAPT.10"
    ::= { naptEventObjects10 1 }

napt10_source_ip OBJECT-TYPE
    SYNTAX IpAddress
    MAX-ACCESS accessible-for-notify
    STATUS current
    DESCRIPTION
        "Parameter 'source_ip' in event NAPT.10"
    ::= { naptEventObjects10 2 }

napt10_source_port OBJECT-TYPE
    SYNTAX Integer32
    MAX-ACCESS accessible-for-notify
    STATUS current
    DESCRIPTION
        "Parameter 'source_port' in event NAPT.10"
    ::= { naptEventObjects10 3 }

napt10_target_ip OBJECT-TYPE
    SYNTAX IpAddress
    MAX-ACCESS accessible-for-notify
    STATUS current
    DESCRIPTION
        "Parameter 'target_ip' in event NAPT.10"
    ::= { naptEventObjects10 4 }

napt10_target_port OBJECT-TYPE
    SYNTAX Integer32
    MAX-ACCESS accessible-for-notify
    STATUS current
    DESCRIPTION
        "Parameter 'target_port' in event NAPT.10"
    ::= { naptEventObjects10 5 }

naptEventObjects11 OBJECT-IDENTITY
    STATUS current
    DESCRIPTION
        "Event NAPT.11
        Received bad IP header field."
    ::= { naptEventsGroup 11 }

napt11_IP_field OBJECT-TYPE
    SYNTAX DisplayString
    MAX-ACCESS accessible-for-notify
    STATUS current
    DESCRIPTION
        "Parameter 'IP_field' in event NAPT.11"
    ::= { naptEventObjects11 1 }

napt11_field_value OBJECT-TYPE
    SYNTAX Integer32
    MAX-ACCESS accessible-for-notify
    STATUS current
    DESCRIPTION
        "Parameter 'field_value' in event NAPT.11"
    ::= { naptEventObjects11 2 }

naptEventObjects12 OBJECT-IDENTITY
    STATUS current
    DESCRIPTION
        "Event NAPT.12
        Received a packet that does not match any IP connection."
    ::= { naptEventsGroup 12 }

napt12_target_address OBJECT-TYPE
    SYNTAX IpAddress
    MAX-ACCESS accessible-for-notify
    STATUS current
    DESCRIPTION
        "Parameter 'target_address' in event NAPT.12"
    ::= { naptEventObjects12 1 }

naptEventObjects13 OBJECT-IDENTITY
    STATUS current
    DESCRIPTION
        "Event NAPT.13
        NAPT entry or ICMP identifier timeout."
    ::= { naptEventsGroup 13 }

napt13_type OBJECT-TYPE
    SYNTAX DisplayString
    MAX-ACCESS accessible-for-notify
    STATUS current
    DESCRIPTION
        "Parameter 'type' in event NAPT.13"
    ::= { naptEventObjects13 1 }

napt13_source_ip OBJECT-TYPE
    SYNTAX IpAddress
    MAX-ACCESS accessible-for-notify
    STATUS current
    DESCRIPTION
        "Parameter 'source_ip' in event NAPT.13"
    ::= { naptEventObjects13 2 }

napt13_source_port OBJECT-TYPE
    SYNTAX Integer32
    MAX-ACCESS accessible-for-notify
    STATUS current
    DESCRIPTION
        "Parameter 'source_port' in event NAPT.13"
    ::= { naptEventObjects13 3 }

napt13_source_napted_ip OBJECT-TYPE
    SYNTAX IpAddress
    MAX-ACCESS accessible-for-notify
    STATUS current
    DESCRIPTION
        "Parameter 'source_napted_ip' in event NAPT.13"
    ::= { naptEventObjects13 4 }

napt13_source_napted_port OBJECT-TYPE
    SYNTAX Integer32
    MAX-ACCESS accessible-for-notify
    STATUS current
    DESCRIPTION
        "Parameter 'source_napted_port' in event NAPT.13"
    ::= { naptEventObjects13 5 }

naptEventObjects14 OBJECT-IDENTITY
    STATUS current
    DESCRIPTION
        "Event NAPT.14
        Received IP packet for an unused external port."
    ::= { naptEventsGroup 14 }

napt14_target_port OBJECT-TYPE
    SYNTAX Integer32
    MAX-ACCESS accessible-for-notify
    STATUS current
    DESCRIPTION
        "Parameter 'target_port' in event NAPT.14"
    ::= { naptEventObjects14 1 }

naptEventObjects15 OBJECT-IDENTITY
    STATUS current
    DESCRIPTION
        "Event NAPT.15
        Received ICMP packet for an unused external identifier."
    ::= { naptEventsGroup 15 }

napt15_target_identifier OBJECT-TYPE
    SYNTAX Integer32
    MAX-ACCESS accessible-for-notify
    STATUS current
    DESCRIPTION
        "Parameter 'target_identifier' in event NAPT.15"
    ::= { naptEventObjects15 1 }

naptEventObjects16 OBJECT-IDENTITY
    STATUS current
    DESCRIPTION
        "Event NAPT.16
        Host exceeds max allowed NAPT entries."
    ::= { naptEventsGroup 16 }

napt16_ip_address OBJECT-TYPE
    SYNTAX IpAddress
    MAX-ACCESS accessible-for-notify
    STATUS current
    DESCRIPTION
        "Parameter 'ip_address' in event NAPT.16"
    ::= { naptEventObjects16 1 }

naptEventObjects17 OBJECT-IDENTITY
    STATUS current
    DESCRIPTION
        "Event NAPT.17
        NAPT for PPTP traces."
    ::= { naptEventsGroup 17 }

napt17_description OBJECT-TYPE
    SYNTAX DisplayString
    MAX-ACCESS accessible-for-notify
    STATUS current
    DESCRIPTION
        "Parameter 'description' in event NAPT.17"
    ::= { naptEventObjects17 1 }

naptEventObjects18 OBJECT-IDENTITY
    STATUS current
    DESCRIPTION
        "Event NAPT.18
        NAPT for an incoming fragment (without port translation)."
    ::= { naptEventsGroup 18 }

napt18_external_ip OBJECT-TYPE
    SYNTAX IpAddress
    MAX-ACCESS accessible-for-notify
    STATUS current
    DESCRIPTION
        "Parameter 'external_ip' in event NAPT.18"
    ::= { naptEventObjects18 1 }

napt18_internal_ip OBJECT-TYPE
    SYNTAX IpAddress
    MAX-ACCESS accessible-for-notify
    STATUS current
    DESCRIPTION
        "Parameter 'internal_ip' in event NAPT.18"
    ::= { naptEventObjects18 2 }

napt18_fragment_indication OBJECT-TYPE
    SYNTAX DisplayString
    MAX-ACCESS accessible-for-notify
    STATUS current
    DESCRIPTION
        "Parameter 'fragment_indication' in event NAPT.18"
    ::= { naptEventObjects18 3 }

naptEventObjects19 OBJECT-IDENTITY
    STATUS current
    DESCRIPTION
        "Event NAPT.19
        Dropping outgoing packet that does not match any IP connection."
    ::= { naptEventsGroup 19 }

napt19_source_ip OBJECT-TYPE
    SYNTAX IpAddress
    MAX-ACCESS accessible-for-notify
    STATUS current
    DESCRIPTION
        "Parameter 'source_ip' in event NAPT.19"
    ::= { naptEventObjects19 1 }

napt19_destination_ip OBJECT-TYPE
    SYNTAX IpAddress
    MAX-ACCESS accessible-for-notify
    STATUS current
    DESCRIPTION
        "Parameter 'destination_ip' in event NAPT.19"
    ::= { naptEventObjects19 2 }

naptEventObjects20 OBJECT-IDENTITY
    STATUS current
    DESCRIPTION
        "Event NAPT.20
        It is not allowed to do incoming/outgoing NAPT to locally originated
        packets. No translation is performed."
    ::= { naptEventsGroup 20 }

napt20_incoming_outcoming OBJECT-TYPE
    SYNTAX DisplayString
    MAX-ACCESS accessible-for-notify
    STATUS current
    DESCRIPTION
        "Parameter 'incoming_outcoming' in event NAPT.20"
    ::= { naptEventObjects20 1 }

napt20_source_ip OBJECT-TYPE
    SYNTAX IpAddress
    MAX-ACCESS accessible-for-notify
    STATUS current
    DESCRIPTION
        "Parameter 'source_ip' in event NAPT.20"
    ::= { naptEventObjects20 2 }

napt20_destination_ip OBJECT-TYPE
    SYNTAX IpAddress
    MAX-ACCESS accessible-for-notify
    STATUS current
    DESCRIPTION
        "Parameter 'destination_ip' in event NAPT.20"
    ::= { naptEventObjects20 3 }

naptEventObjects21 OBJECT-IDENTITY
    STATUS current
    DESCRIPTION
        "Event NAPT.21
        Assignated destination address is not accesible. Packets are dropped."
    ::= { naptEventsGroup 21 }

napt21_source_ip OBJECT-TYPE
    SYNTAX IpAddress
    MAX-ACCESS accessible-for-notify
    STATUS current
    DESCRIPTION
        "Parameter 'source_ip' in event NAPT.21"
    ::= { naptEventObjects21 1 }

napt21_destination_ip OBJECT-TYPE
    SYNTAX IpAddress
    MAX-ACCESS accessible-for-notify
    STATUS current
    DESCRIPTION
        "Parameter 'destination_ip' in event NAPT.21"
    ::= { naptEventObjects21 2 }

napt21_assignated_destination_ip OBJECT-TYPE
    SYNTAX IpAddress
    MAX-ACCESS accessible-for-notify
    STATUS current
    DESCRIPTION
        "Parameter 'assignated_destination_ip' in event NAPT.21"
    ::= { naptEventObjects21 3 }

naptEventObjects22 OBJECT-IDENTITY
    STATUS current
    DESCRIPTION
        "Event NAPT.22
        Virtual destination NAPT for outgoing IP packet."
    ::= { naptEventsGroup 22 }

napt22_virtual_dest_ip OBJECT-TYPE
    SYNTAX IpAddress
    MAX-ACCESS accessible-for-notify
    STATUS current
    DESCRIPTION
        "Parameter 'virtual_dest_ip' in event NAPT.22"
    ::= { naptEventObjects22 1 }

napt22_virtual_dest_port OBJECT-TYPE
    SYNTAX Integer32
    MAX-ACCESS accessible-for-notify
    STATUS current
    DESCRIPTION
        "Parameter 'virtual_dest_port' in event NAPT.22"
    ::= { naptEventObjects22 2 }

napt22_new_dest_ip OBJECT-TYPE
    SYNTAX IpAddress
    MAX-ACCESS accessible-for-notify
    STATUS current
    DESCRIPTION
        "Parameter 'new_dest_ip' in event NAPT.22"
    ::= { naptEventObjects22 3 }

napt22_new_dest_port OBJECT-TYPE
    SYNTAX Integer32
    MAX-ACCESS accessible-for-notify
    STATUS current
    DESCRIPTION
        "Parameter 'new_dest_port' in event NAPT.22"
    ::= { naptEventObjects22 4 }

naptEventObjects23 OBJECT-IDENTITY
    STATUS current
    DESCRIPTION
        "Event NAPT.23
        Virtual destination NAPT for incoming IP packet."
    ::= { naptEventsGroup 23 }

napt23_new_dest_ip OBJECT-TYPE
    SYNTAX IpAddress
    MAX-ACCESS accessible-for-notify
    STATUS current
    DESCRIPTION
        "Parameter 'new_dest_ip' in event NAPT.23"
    ::= { naptEventObjects23 1 }

napt23_new_dest_port OBJECT-TYPE
    SYNTAX Integer32
    MAX-ACCESS accessible-for-notify
    STATUS current
    DESCRIPTION
        "Parameter 'new_dest_port' in event NAPT.23"
    ::= { naptEventObjects23 2 }

napt23_virtual_dest_ip OBJECT-TYPE
    SYNTAX IpAddress
    MAX-ACCESS accessible-for-notify
    STATUS current
    DESCRIPTION
        "Parameter 'virtual_dest_ip' in event NAPT.23"
    ::= { naptEventObjects23 3 }

napt23_virtual_dest_port OBJECT-TYPE
    SYNTAX Integer32
    MAX-ACCESS accessible-for-notify
    STATUS current
    DESCRIPTION
        "Parameter 'virtual_dest_port' in event NAPT.23"
    ::= { naptEventObjects23 4 }

naptEventObjects24 OBJECT-IDENTITY
    STATUS current
    DESCRIPTION
        "Event NAPT.24
        Dropping or passing through without NAPT an incoming packet
        that does not match any IP connection."
    ::= { naptEventsGroup 24 }

napt24_Drop_noNAPTto OBJECT-TYPE
    SYNTAX DisplayString
    MAX-ACCESS accessible-for-notify
    STATUS current
    DESCRIPTION
        "Parameter 'Drop_noNAPTto' in event NAPT.24"
    ::= { naptEventObjects24 1 }

napt24_source_ip OBJECT-TYPE
    SYNTAX IpAddress
    MAX-ACCESS accessible-for-notify
    STATUS current
    DESCRIPTION
        "Parameter 'source_ip' in event NAPT.24"
    ::= { naptEventObjects24 2 }

napt24_destination_ip OBJECT-TYPE
    SYNTAX IpAddress
    MAX-ACCESS accessible-for-notify
    STATUS current
    DESCRIPTION
        "Parameter 'destination_ip' in event NAPT.24"
    ::= { naptEventObjects24 3 }

naptEventObjects25 OBJECT-IDENTITY
    STATUS current
    DESCRIPTION
        "Event NAPT.25
        Creating or deleting NAPT fragmentation entry."
    ::= { naptEventsGroup 25 }

napt25_action OBJECT-TYPE
    SYNTAX DisplayString
    MAX-ACCESS accessible-for-notify
    STATUS current
    DESCRIPTION
        "Parameter 'action' in event NAPT.25"
    ::= { naptEventObjects25 1 }

napt25_fragmentation_entry OBJECT-TYPE
    SYNTAX Integer32
    MAX-ACCESS accessible-for-notify
    STATUS current
    DESCRIPTION
        "Parameter 'fragmentation_entry' in event NAPT.25"
    ::= { naptEventObjects25 2 }

napt25_ip_id OBJECT-TYPE
    SYNTAX Integer32
    MAX-ACCESS accessible-for-notify
    STATUS current
    DESCRIPTION
        "Parameter 'ip_id' in event NAPT.25"
    ::= { naptEventObjects25 3 }

napt25_ip_address OBJECT-TYPE
    SYNTAX IpAddress
    MAX-ACCESS accessible-for-notify
    STATUS current
    DESCRIPTION
        "Parameter 'ip_address' in event NAPT.25"
    ::= { naptEventObjects25 4 }

naptEventObjects26 OBJECT-IDENTITY
    STATUS current
    DESCRIPTION
        "Event NAPT.26
        Action done to a packet by a fragmentation entry."
    ::= { naptEventsGroup 26 }

napt26_action OBJECT-TYPE
    SYNTAX DisplayString
    MAX-ACCESS accessible-for-notify
    STATUS current
    DESCRIPTION
        "Parameter 'action' in event NAPT.26"
    ::= { naptEventObjects26 1 }

napt26_fragmentation_entry OBJECT-TYPE
    SYNTAX Integer32
    MAX-ACCESS accessible-for-notify
    STATUS current
    DESCRIPTION
        "Parameter 'fragmentation_entry' in event NAPT.26"
    ::= { naptEventObjects26 2 }

napt26_ip_id OBJECT-TYPE
    SYNTAX Integer32
    MAX-ACCESS accessible-for-notify
    STATUS current
    DESCRIPTION
        "Parameter 'ip_id' in event NAPT.26"
    ::= { naptEventObjects26 3 }

napt26_ip_address OBJECT-TYPE
    SYNTAX IpAddress
    MAX-ACCESS accessible-for-notify
    STATUS current
    DESCRIPTION
        "Parameter 'ip_address' in event NAPT.26"
    ::= { naptEventObjects26 4 }

napt26_ip_offset OBJECT-TYPE
    SYNTAX Integer32
    MAX-ACCESS accessible-for-notify
    STATUS current
    DESCRIPTION
        "Parameter 'ip_offset' in event NAPT.26"
    ::= { naptEventObjects26 5 }

naptEventObjects27 OBJECT-IDENTITY
    STATUS current
    DESCRIPTION
        "Event NAPT.27
        An incoming packet matching a NAPT entry with virtual dest active
        has been droped because its source address was diferent from
        the assigned destination."
    ::= { naptEventsGroup 27 }

napt27_source_ip OBJECT-TYPE
    SYNTAX IpAddress
    MAX-ACCESS accessible-for-notify
    STATUS current
    DESCRIPTION
        "Parameter 'source_ip' in event NAPT.27"
    ::= { naptEventObjects27 1 }

napt27_destination_ip OBJECT-TYPE
    SYNTAX IpAddress
    MAX-ACCESS accessible-for-notify
    STATUS current
    DESCRIPTION
        "Parameter 'destination_ip' in event NAPT.27"
    ::= { naptEventObjects27 2 }

napt27_assignated_destination_ip OBJECT-TYPE
    SYNTAX IpAddress
    MAX-ACCESS accessible-for-notify
    STATUS current
    DESCRIPTION
        "Parameter 'assignated_destination_ip' in event NAPT.27"
    ::= { naptEventObjects27 3 }

napt27_src_address OBJECT-TYPE
    SYNTAX IpAddress
    MAX-ACCESS accessible-for-notify
    STATUS current
    DESCRIPTION
        "Parameter 'src_address' in event NAPT.27"
    ::= { naptEventObjects27 4 }

naptEventObjects28 OBJECT-IDENTITY
    STATUS current
    DESCRIPTION
        "Event NAPT.28
        An incoming packet has been drop or past through without NAPT because
        its destination port is out of the range of NAPT ports."
    ::= { naptEventsGroup 28 }

napt28_Drop_noNAPTto OBJECT-TYPE
    SYNTAX DisplayString
    MAX-ACCESS accessible-for-notify
    STATUS current
    DESCRIPTION
        "Parameter 'Drop_noNAPTto' in event NAPT.28"
    ::= { naptEventObjects28 1 }

napt28_source_ip OBJECT-TYPE
    SYNTAX IpAddress
    MAX-ACCESS accessible-for-notify
    STATUS current
    DESCRIPTION
        "Parameter 'source_ip' in event NAPT.28"
    ::= { naptEventObjects28 2 }

napt28_source_port OBJECT-TYPE
    SYNTAX Integer32
    MAX-ACCESS accessible-for-notify
    STATUS current
    DESCRIPTION
        "Parameter 'source_port' in event NAPT.28"
    ::= { naptEventObjects28 3 }

napt28_destination_ip OBJECT-TYPE
    SYNTAX IpAddress
    MAX-ACCESS accessible-for-notify
    STATUS current
    DESCRIPTION
        "Parameter 'destination_ip' in event NAPT.28"
    ::= { naptEventObjects28 4 }

napt28_destination_port OBJECT-TYPE
    SYNTAX Integer32
    MAX-ACCESS accessible-for-notify
    STATUS current
    DESCRIPTION
        "Parameter 'destination_port' in event NAPT.28"
    ::= { naptEventObjects28 5 }

naptEventObjects29 OBJECT-IDENTITY
    STATUS current
    DESCRIPTION
        "Event NAPT.29
        The MSS value of an outgoing TCP SYN packet has been adjusted."
    ::= { naptEventsGroup 29 }

napt29_source_ip OBJECT-TYPE
    SYNTAX IpAddress
    MAX-ACCESS accessible-for-notify
    STATUS current
    DESCRIPTION
        "Parameter 'source_ip' in event NAPT.29"
    ::= { naptEventObjects29 1 }

napt29_source_port OBJECT-TYPE
    SYNTAX Integer32
    MAX-ACCESS accessible-for-notify
    STATUS current
    DESCRIPTION
        "Parameter 'source_port' in event NAPT.29"
    ::= { naptEventObjects29 2 }

napt29_destination_ip OBJECT-TYPE
    SYNTAX IpAddress
    MAX-ACCESS accessible-for-notify
    STATUS current
    DESCRIPTION
        "Parameter 'destination_ip' in event NAPT.29"
    ::= { naptEventObjects29 3 }

napt29_destination_port OBJECT-TYPE
    SYNTAX Integer32
    MAX-ACCESS accessible-for-notify
    STATUS current
    DESCRIPTION
        "Parameter 'destination_port' in event NAPT.29"
    ::= { naptEventObjects29 4 }

napt29_old_mss OBJECT-TYPE
    SYNTAX Integer32
    MAX-ACCESS accessible-for-notify
    STATUS current
    DESCRIPTION
        "Parameter 'old_mss' in event NAPT.29"
    ::= { naptEventObjects29 5 }

napt29_new_mss OBJECT-TYPE
    SYNTAX Integer32
    MAX-ACCESS accessible-for-notify
    STATUS current
    DESCRIPTION
        "Parameter 'new_mss' in event NAPT.29"
    ::= { naptEventObjects29 6 }

naptEventObjects30 OBJECT-IDENTITY
    STATUS current
    DESCRIPTION
        "Event NAPT.30
        An incoming packet matching a NAPT entry with virtual destination active
        has been droped because its source port was diferent from the assigned
        destination port."
    ::= { naptEventsGroup 30 }

napt30_source_ip OBJECT-TYPE
    SYNTAX IpAddress
    MAX-ACCESS accessible-for-notify
    STATUS current
    DESCRIPTION
        "Parameter 'source_ip' in event NAPT.30"
    ::= { naptEventObjects30 1 }

napt30_source_port OBJECT-TYPE
    SYNTAX Integer32
    MAX-ACCESS accessible-for-notify
    STATUS current
    DESCRIPTION
        "Parameter 'source_port' in event NAPT.30"
    ::= { naptEventObjects30 2 }

napt30_destination_ip OBJECT-TYPE
    SYNTAX IpAddress
    MAX-ACCESS accessible-for-notify
    STATUS current
    DESCRIPTION
        "Parameter 'destination_ip' in event NAPT.30"
    ::= { naptEventObjects30 3 }

napt30_destination_port OBJECT-TYPE
    SYNTAX Integer32
    MAX-ACCESS accessible-for-notify
    STATUS current
    DESCRIPTION
        "Parameter 'destination_port' in event NAPT.30"
    ::= { naptEventObjects30 4 }

napt30_assignated_destination_port OBJECT-TYPE
    SYNTAX Integer32
    MAX-ACCESS accessible-for-notify
    STATUS current
    DESCRIPTION
        "Parameter 'assignated_destination_port' in event NAPT.30"
    ::= { naptEventObjects30 5 }

napt30_src_port OBJECT-TYPE
    SYNTAX Integer32
    MAX-ACCESS accessible-for-notify
    STATUS current
    DESCRIPTION
        "Parameter 'src_port' in event NAPT.30"
    ::= { naptEventObjects30 6 }


naptNotification1 NOTIFICATION-TYPE
    OBJECTS { 
              napt1_internal_ip, 
              napt1_internal_port,
              napt1_external_ip,
              napt1_external_port 
            }
    STATUS current
    DESCRIPTION
        "Notification of Event NAPT.1

        Message: 'Out ($1:$2 => $3:$4)'

        Parameters list:
              $1: napt1_internal_ip
              $2: napt1_internal_port
              $3: napt1_external_ip
              $4: napt1_external_port

        NAPT for outgoing IP packet."
    ::= { naptNotificationsPrefix 1 }

naptNotification2 NOTIFICATION-TYPE
    OBJECTS { 
              napt2_external_ip, 
              napt2_external_port,
              napt2_internal_ip,
              napt2_internal_port 
            }
    STATUS current
    DESCRIPTION
        "Notification of Event NAPT.2

        Message: 'In ($1:$2 => $3:$4)'

        Parameters list:
              $1: napt2_external_ip
              $2: napt2_external_port
              $3: napt2_internal_ip
              $4: napt2_internal_port

        NAPT for incoming IP packet."
    ::= { naptNotificationsPrefix 2 }

naptNotification3 NOTIFICATION-TYPE
    OBJECTS { 
              napt3_internal_ip, 
              napt3_internal_ident,
              napt3_external_ip,
              napt3_external_ident 
            }
    STATUS current
    DESCRIPTION
        "Notification of Event NAPT.3

        Message: 'Out ($1[$2] => $3[$4])'

        Parameters list:
              $1: napt3_internal_ip
              $2: napt3_internal_ident
              $3: napt3_external_ip
              $4: napt3_external_ident

        Translation for outgoing ICMP packet."
    ::= { naptNotificationsPrefix 3 }

naptNotification4 NOTIFICATION-TYPE
    OBJECTS { 
              napt4_external_ip, 
              napt4_external_ident,
              napt4_internal_ip,
              napt4_internal_ident 
            }
    STATUS current
    DESCRIPTION
        "Notification of Event NAPT.4

        Message: 'In ($1[$2] => $3[$4])'

        Parameters list:
              $1: napt4_external_ip
              $2: napt4_external_ident
              $3: napt4_internal_ip
              $4: napt4_internal_ident

        Translation for incoming ICMP packet."
    ::= { naptNotificationsPrefix 4 }

naptNotification5 NOTIFICATION-TYPE
    STATUS current
    DESCRIPTION
        "Notification of Event NAPT.5

        Message: 'No NAPT entries free'

        Unable to find NAPT entries free (all of them are used)."
    ::= { naptNotificationsPrefix 5 }

naptNotification6 NOTIFICATION-TYPE
    STATUS current
    DESCRIPTION
        "Notification of Event NAPT.6

        Message: 'No ICMP identifiers free'

        Unable to find ICMP identifiers free (all of them are used)."
    ::= { naptNotificationsPrefix 6 }

naptNotification7 NOTIFICATION-TYPE
    OBJECTS { 
              napt7_internal_ip, 
              napt7_internal_port,
              napt7_external_ip,
              napt7_external_port,
              napt7_sequence,
              napt7_ack_sequence 
            }
    STATUS current
    DESCRIPTION
        "Notification of Event NAPT.7

        Message: 'Bad TCP checksum ($1:$2 -> $3:$4) seq $5, ack $6'

        Parameters list:
              $1: napt7_internal_ip
              $2: napt7_internal_port
              $3: napt7_external_ip
              $4: napt7_external_port
              $5: napt7_sequence
              $6: napt7_ack_sequence

        Received TCP packet with bad TCP checksum."
    ::= { naptNotificationsPrefix 7 }

naptNotification8 NOTIFICATION-TYPE
    OBJECTS { 
              napt8_Drop_noNaptto, 
              napt8_packet_type 
            }
    STATUS current
    DESCRIPTION
        "Notification of Event NAPT.8

        Message: '$1 $2 packet'

        Parameters list:
              $1: napt8_Drop_noNaptto
              $2: napt8_packet_type

        It is not allowed to do NAPT in some firewalling cases: RIP, OSPF..."
    ::= { naptNotificationsPrefix 8 }

naptNotification9 NOTIFICATION-TYPE
    OBJECTS { 
              napt9_application, 
              napt9_source_ip,
              napt9_source_port,
              napt9_target_ip,
              napt9_target_port,
              napt9_sequence,
              napt9_ack_sequence 
            }
    STATUS current
    DESCRIPTION
        "Notification of Event NAPT.9

        Message: '[$1]TCP SYNC ($2:$3 -> $4:$5) seq:$6, ack:$7'

        Parameters list:
              $1: napt9_application
              $2: napt9_source_ip
              $3: napt9_source_port
              $4: napt9_target_ip
              $5: napt9_target_port
              $6: napt9_sequence
              $7: napt9_ack_sequence

        Sent TCP SYNC."
    ::= { naptNotificationsPrefix 9 }

naptNotification10 NOTIFICATION-TYPE
    OBJECTS { 
              napt10_application, 
              napt10_source_ip,
              napt10_source_port,
              napt10_target_ip,
              napt10_target_port 
            }
    STATUS current
    DESCRIPTION
        "Notification of Event NAPT.10

        Message: '[$1]TCP FIN/RST ($2:$3 -> $4:$5)'

        Parameters list:
              $1: napt10_application
              $2: napt10_source_ip
              $3: napt10_source_port
              $4: napt10_target_ip
              $5: napt10_target_port

        Received or sent TCP FIN/RST."
    ::= { naptNotificationsPrefix 10 }

naptNotification11 NOTIFICATION-TYPE
    OBJECTS { 
              napt11_IP_field, 
              napt11_field_value 
            }
    STATUS current
    DESCRIPTION
        "Notification of Event NAPT.11

        Message: 'Bad IP $1 0x$2'

        Parameters list:
              $1: napt11_IP_field
              $2: napt11_field_value

        Received bad IP header field."
    ::= { naptNotificationsPrefix 11 }

naptNotification12 NOTIFICATION-TYPE
    OBJECTS { 
              napt12_target_address 
            }
    STATUS current
    DESCRIPTION
        "Notification of Event NAPT.12

        Message: 'In $1 does not match external IP'

        Parameters list:
              $1: napt12_target_address

        Received a packet that does not match any IP connection."
    ::= { naptNotificationsPrefix 12 }

naptNotification13 NOTIFICATION-TYPE
    OBJECTS { 
              napt13_type, 
              napt13_source_ip,
              napt13_source_port,
              napt13_source_napted_ip,
              napt13_source_napted_port 
            }
    STATUS current
    DESCRIPTION
        "Notification of Event NAPT.13

        Message: '[$1] timeout ($2:$3 => $4:$5)'

        Parameters list:
              $1: napt13_type
              $2: napt13_source_ip
              $3: napt13_source_port
              $4: napt13_source_napted_ip
              $5: napt13_source_napted_port

        NAPT entry or ICMP identifier timeout."
    ::= { naptNotificationsPrefix 13 }

naptNotification14 NOTIFICATION-TYPE
    OBJECTS { 
              napt14_target_port 
            }
    STATUS current
    DESCRIPTION
        "Notification of Event NAPT.14

        Message: 'In unknown PORT $1'

        Parameters list:
              $1: napt14_target_port

        Received IP packet for an unused external port."
    ::= { naptNotificationsPrefix 14 }

naptNotification15 NOTIFICATION-TYPE
    OBJECTS { 
              napt15_target_identifier 
            }
    STATUS current
    DESCRIPTION
        "Notification of Event NAPT.15

        Message: 'In unknown IDENT $1'

        Parameters list:
              $1: napt15_target_identifier

        Received ICMP packet for an unused external identifier."
    ::= { naptNotificationsPrefix 15 }

naptNotification16 NOTIFICATION-TYPE
    OBJECTS { 
              napt16_ip_address 
            }
    STATUS current
    DESCRIPTION
        "Notification of Event NAPT.16

        Message: 'Out $1 exceeds max allowed entries'

        Parameters list:
              $1: napt16_ip_address

        Host exceeds max allowed NAPT entries."
    ::= { naptNotificationsPrefix 16 }

naptNotification17 NOTIFICATION-TYPE
    OBJECTS { 
              napt17_description 
            }
    STATUS current
    DESCRIPTION
        "Notification of Event NAPT.17

        Message: 'PPTP: $1'

        Parameters list:
              $1: napt17_description

        NAPT for PPTP traces."
    ::= { naptNotificationsPrefix 17 }

naptNotification18 NOTIFICATION-TYPE
    OBJECTS { 
              napt18_external_ip, 
              napt18_internal_ip,
              napt18_fragment_indication 
            }
    STATUS current
    DESCRIPTION
        "Notification of Event NAPT.18

        Message: 'In ($1 => $2) $3'

        Parameters list:
              $1: napt18_external_ip
              $2: napt18_internal_ip
              $3: napt18_fragment_indication

        NAPT for an incoming fragment (without port translation)."
    ::= { naptNotificationsPrefix 18 }

naptNotification19 NOTIFICATION-TYPE
    OBJECTS { 
              napt19_source_ip, 
              napt19_destination_ip 
            }
    STATUS current
    DESCRIPTION
        "Notification of Event NAPT.19

        Message: 'Dropping outgoing packet ($1 -> $2) due to connection unknown'

        Parameters list:
              $1: napt19_source_ip
              $2: napt19_destination_ip

        Dropping outgoing packet that does not match any IP connection."
    ::= { naptNotificationsPrefix 19 }

naptNotification20 NOTIFICATION-TYPE
    OBJECTS { 
              napt20_incoming_outcoming, 
              napt20_source_ip,
              napt20_destination_ip 
            }
    STATUS current
    DESCRIPTION
        "Notification of Event NAPT.20

        Message: '$1 packet ($2 -> $3) was locally generated, no NAPT is performed'

        Parameters list:
              $1: napt20_incoming_outcoming
              $2: napt20_source_ip
              $3: napt20_destination_ip

        It is not allowed to do incoming/outgoing NAPT to locally originated
        packets. No translation is performed."
    ::= { naptNotificationsPrefix 20 }

naptNotification21 NOTIFICATION-TYPE
    OBJECTS { 
              napt21_source_ip, 
              napt21_destination_ip,
              napt21_assignated_destination_ip 
            }
    STATUS current
    DESCRIPTION
        "Notification of Event NAPT.21

        Message: 'Dropping virtual destination outgoing packet ($1 -> $2) due to assigned destination is inactive ($3)'

        Parameters list:
              $1: napt21_source_ip
              $2: napt21_destination_ip
              $3: napt21_assignated_destination_ip

        Assignated destination address is not accesible. Packets are dropped."
    ::= { naptNotificationsPrefix 21 }

naptNotification22 NOTIFICATION-TYPE
    OBJECTS { 
              napt22_virtual_dest_ip, 
              napt22_virtual_dest_port,
              napt22_new_dest_ip,
              napt22_new_dest_port 
            }
    STATUS current
    DESCRIPTION
        "Notification of Event NAPT.22

        Message: 'Out virtual destination ($1:$2 => $3:$4)'

        Parameters list:
              $1: napt22_virtual_dest_ip
              $2: napt22_virtual_dest_port
              $3: napt22_new_dest_ip
              $4: napt22_new_dest_port

        Virtual destination NAPT for outgoing IP packet."
    ::= { naptNotificationsPrefix 22 }

naptNotification23 NOTIFICATION-TYPE
    OBJECTS { 
              napt23_new_dest_ip, 
              napt23_new_dest_port,
              napt23_virtual_dest_ip,
              napt23_virtual_dest_port 
            }
    STATUS current
    DESCRIPTION
        "Notification of Event NAPT.23

        Message: 'Incoming virtual destination ($1:$2 => $3:$4)'

        Parameters list:
              $1: napt23_new_dest_ip
              $2: napt23_new_dest_port
              $3: napt23_virtual_dest_ip
              $4: napt23_virtual_dest_port

        Virtual destination NAPT for incoming IP packet."
    ::= { naptNotificationsPrefix 23 }

naptNotification24 NOTIFICATION-TYPE
    OBJECTS { 
              napt24_Drop_noNAPTto, 
              napt24_source_ip,
              napt24_destination_ip 
            }
    STATUS current
    DESCRIPTION
        "Notification of Event NAPT.24

        Message: '$1 Incoming packet ($2 -> $3) due to connection unknown'

        Parameters list:
              $1: napt24_Drop_noNAPTto
              $2: napt24_source_ip
              $3: napt24_destination_ip

        Dropping or passing through without NAPT an incoming packet
        that does not match any IP connection."
    ::= { naptNotificationsPrefix 24 }

naptNotification25 NOTIFICATION-TYPE
    OBJECTS { 
              napt25_action, 
              napt25_fragmentation_entry,
              napt25_ip_id,
              napt25_ip_address 
            }
    STATUS current
    DESCRIPTION
        "Notification of Event NAPT.25

        Message: '$1: Fragmentation entry 0X$2 ip fragmentation id $3 ip address $4'

        Parameters list:
              $1: napt25_action
              $2: napt25_fragmentation_entry
              $3: napt25_ip_id
              $4: napt25_ip_address

        Creating or deleting NAPT fragmentation entry."
    ::= { naptNotificationsPrefix 25 }

naptNotification26 NOTIFICATION-TYPE
    OBJECTS { 
              napt26_action, 
              napt26_fragmentation_entry,
              napt26_ip_id,
              napt26_ip_address,
              napt26_ip_offset 
            }
    STATUS current
    DESCRIPTION
        "Notification of Event NAPT.26

        Message: '$1: Fragmentation entry 0X$2 ip fragmentation id $3 ip address $4 ip header offset $5'

        Parameters list:
              $1: napt26_action
              $2: napt26_fragmentation_entry
              $3: napt26_ip_id
              $4: napt26_ip_address
              $5: napt26_ip_offset

        Action done to a packet by a fragmentation entry."
    ::= { naptNotificationsPrefix 26 }

naptNotification27 NOTIFICATION-TYPE
    OBJECTS { 
              napt27_source_ip, 
              napt27_destination_ip,
              napt27_assignated_destination_ip,
              napt27_src_address 
            }
    STATUS current
    DESCRIPTION
        "Notification of Event NAPT.27

        Message: 'Dropping virtual destination incoming packet ($1 -> $2), assigned destination ($3) not equal to source ($4)'

        Parameters list:
              $1: napt27_source_ip
              $2: napt27_destination_ip
              $3: napt27_assignated_destination_ip
              $4: napt27_src_address

        An incoming packet matching a NAPT entry with virtual dest active
        has been droped because its source address was diferent from
        the assigned destination."
    ::= { naptNotificationsPrefix 27 }

naptNotification28 NOTIFICATION-TYPE
    OBJECTS { 
              napt28_Drop_noNAPTto, 
              napt28_source_ip,
              napt28_source_port,
              napt28_destination_ip,
              napt28_destination_port 
            }
    STATUS current
    DESCRIPTION
        "Notification of Event NAPT.28

        Message: '$1 incoming packet ($2:$3 -> $4:$5) with no napt destination port'

        Parameters list:
              $1: napt28_Drop_noNAPTto
              $2: napt28_source_ip
              $3: napt28_source_port
              $4: napt28_destination_ip
              $5: napt28_destination_port

        An incoming packet has been drop or past through without NAPT because
        its destination port is out of the range of NAPT ports."
    ::= { naptNotificationsPrefix 28 }

naptNotification29 NOTIFICATION-TYPE
    OBJECTS { 
              napt29_source_ip, 
              napt29_source_port,
              napt29_destination_ip,
              napt29_destination_port,
              napt29_old_mss,
              napt29_new_mss 
            }
    STATUS current
    DESCRIPTION
        "Notification of Event NAPT.29

        Message: 'TCP SYN MSS Adjusted ($1:$2 -> $3:$4) ($5 => $6)'

        Parameters list:
              $1: napt29_source_ip
              $2: napt29_source_port
              $3: napt29_destination_ip
              $4: napt29_destination_port
              $5: napt29_old_mss
              $6: napt29_new_mss

        The MSS value of an outgoing TCP SYN packet has been adjusted."
    ::= { naptNotificationsPrefix 29 }

naptNotification30 NOTIFICATION-TYPE
    OBJECTS { 
              napt30_source_ip, 
              napt30_source_port,
              napt30_destination_ip,
              napt30_destination_port,
              napt30_assignated_destination_port,
              napt30_src_port 
            }
    STATUS current
    DESCRIPTION
        "Notification of Event NAPT.30

        Message: 'Dropping virtual destination incoming packet ($1:$2 -> $3:$4), assigned destination port ($5) not equal to source port ($6)'

        Parameters list:
              $1: napt30_source_ip
              $2: napt30_source_port
              $3: napt30_destination_ip
              $4: napt30_destination_port
              $5: napt30_assignated_destination_port
              $6: napt30_src_port

        An incoming packet matching a NAPT entry with virtual destination active
        has been droped because its source port was diferent from the assigned
        destination port."
    ::= { naptNotificationsPrefix 30 }


END
