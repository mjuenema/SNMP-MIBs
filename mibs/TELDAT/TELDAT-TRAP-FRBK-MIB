-- file automatically created


TELDAT-TRAP-FRBK-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


frbkTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the FRBK event subsystem."
    REVISION "201401200930Z"
    DESCRIPTION "Initial implementation"
        ::= { telEventTraps 114 }


frbkEventsGroup	OBJECT IDENTIFIER	::= { frbkTrapsMIB 1 }

frbkNotifications	OBJECT IDENTIFIER	::= { frbkTrapsMIB 2 }
frbkNotificationsPrefix	OBJECT IDENTIFIER	::= { frbkNotifications 0 }

frbkEventObjects1 OBJECT-IDENTITY
    STATUS current
    DESCRIPTION
        "Event FRBK.1
        A PVC switched to backup state."
    ::= { frbkEventsGroup 1 }

frbk1_circuit OBJECT-TYPE
    SYNTAX Integer32
    MAX-ACCESS accessible-for-notify
    STATUS current
    DESCRIPTION
        "Parameter 'circuit' in event FRBK.1"
    ::= { frbkEventObjects1 1 }

frbk1_ifc_name OBJECT-TYPE
    SYNTAX DisplayString
    MAX-ACCESS accessible-for-notify
    STATUS current
    DESCRIPTION
        "Parameter 'ifc_name' in event FRBK.1"
    ::= { frbkEventObjects1 2 }

frbkEventObjects2 OBJECT-IDENTITY
    STATUS current
    DESCRIPTION
        "Event FRBK.2
        A PVC returns from backup state to active state."
    ::= { frbkEventsGroup 2 }

frbk2_circuit OBJECT-TYPE
    SYNTAX Integer32
    MAX-ACCESS accessible-for-notify
    STATUS current
    DESCRIPTION
        "Parameter 'circuit' in event FRBK.2"
    ::= { frbkEventObjects2 1 }

frbk2_ifc_name OBJECT-TYPE
    SYNTAX DisplayString
    MAX-ACCESS accessible-for-notify
    STATUS current
    DESCRIPTION
        "Parameter 'ifc_name' in event FRBK.2"
    ::= { frbkEventObjects2 2 }

frbkEventObjects3 OBJECT-IDENTITY
    STATUS current
    DESCRIPTION
        "Event FRBK.3
        All PVCs in backup state are forced to return to active state whenever
        it is possible."
    ::= { frbkEventsGroup 3 }

frbk3_ifc_name OBJECT-TYPE
    SYNTAX DisplayString
    MAX-ACCESS accessible-for-notify
    STATUS current
    DESCRIPTION
        "Parameter 'ifc_name' in event FRBK.3"
    ::= { frbkEventObjects3 1 }

frbkEventObjects4 OBJECT-IDENTITY
    STATUS current
    DESCRIPTION
        "Event FRBK.4
        When backup timer expires all circuits can switch to normal operation
        (if it is possible)."
    ::= { frbkEventsGroup 4 }

frbk4_ifc_name OBJECT-TYPE
    SYNTAX DisplayString
    MAX-ACCESS accessible-for-notify
    STATUS current
    DESCRIPTION
        "Parameter 'ifc_name' in event FRBK.4"
    ::= { frbkEventObjects4 1 }

frbkEventObjects5 OBJECT-IDENTITY
    STATUS current
    DESCRIPTION
        "Event FRBK.5
        All traffic which normally goes through Frame Relay interface must be
        routered through the associated backup interface over ISDN."
    ::= { frbkEventsGroup 5 }

frbk5_ifc_name OBJECT-TYPE
    SYNTAX DisplayString
    MAX-ACCESS accessible-for-notify
    STATUS current
    DESCRIPTION
        "Parameter 'ifc_name' in event FRBK.5"
    ::= { frbkEventObjects5 1 }

frbk5_isdn_ifc_name OBJECT-TYPE
    SYNTAX DisplayString
    MAX-ACCESS accessible-for-notify
    STATUS current
    DESCRIPTION
        "Parameter 'isdn_ifc_name' in event FRBK.5"
    ::= { frbkEventObjects5 2 }

frbkEventObjects6 OBJECT-IDENTITY
    STATUS current
    DESCRIPTION
        "Event FRBK.6
        Frame Relay interface (primary link) has recovered: it is active and
        operative again, so the secondary link automatically disconnects and
        traffic stops being transmitted through the ISDN backup interface."
    ::= { frbkEventsGroup 6 }

frbk6_ifc_name OBJECT-TYPE
    SYNTAX DisplayString
    MAX-ACCESS accessible-for-notify
    STATUS current
    DESCRIPTION
        "Parameter 'ifc_name' in event FRBK.6"
    ::= { frbkEventObjects6 1 }

frbk6_isdn_ifc_name OBJECT-TYPE
    SYNTAX DisplayString
    MAX-ACCESS accessible-for-notify
    STATUS current
    DESCRIPTION
        "Parameter 'isdn_ifc_name' in event FRBK.6"
    ::= { frbkEventObjects6 2 }

frbkEventObjects7 OBJECT-IDENTITY
    STATUS current
    DESCRIPTION
        "Event FRBK.7
        A PVC switched to backup state."
    ::= { frbkEventsGroup 7 }

frbk7_circuit OBJECT-TYPE
    SYNTAX Integer32
    MAX-ACCESS accessible-for-notify
    STATUS current
    DESCRIPTION
        "Parameter 'circuit' in event FRBK.7"
    ::= { frbkEventObjects7 1 }

frbk7_ifc_name OBJECT-TYPE
    SYNTAX DisplayString
    MAX-ACCESS accessible-for-notify
    STATUS current
    DESCRIPTION
        "Parameter 'ifc_name' in event FRBK.7"
    ::= { frbkEventObjects7 2 }

frbk7_isdn_ifc_name OBJECT-TYPE
    SYNTAX DisplayString
    MAX-ACCESS accessible-for-notify
    STATUS current
    DESCRIPTION
        "Parameter 'isdn_ifc_name' in event FRBK.7"
    ::= { frbkEventObjects7 3 }

frbkEventObjects8 OBJECT-IDENTITY
    STATUS current
    DESCRIPTION
        "Event FRBK.8
        A PVC returns from backup state to active state."
    ::= { frbkEventsGroup 8 }

frbk8_circuit OBJECT-TYPE
    SYNTAX Integer32
    MAX-ACCESS accessible-for-notify
    STATUS current
    DESCRIPTION
        "Parameter 'circuit' in event FRBK.8"
    ::= { frbkEventObjects8 1 }

frbk8_ifc_name OBJECT-TYPE
    SYNTAX DisplayString
    MAX-ACCESS accessible-for-notify
    STATUS current
    DESCRIPTION
        "Parameter 'ifc_name' in event FRBK.8"
    ::= { frbkEventObjects8 2 }

frbk8_isdn_ifc_name OBJECT-TYPE
    SYNTAX DisplayString
    MAX-ACCESS accessible-for-notify
    STATUS current
    DESCRIPTION
        "Parameter 'isdn_ifc_name' in event FRBK.8"
    ::= { frbkEventObjects8 3 }


frbkNotification1 NOTIFICATION-TYPE
    OBJECTS { 
              frbk1_circuit, 
              frbk1_circuit,
              frbk1_ifc_name 
            }
    STATUS current
    DESCRIPTION
        "Notification of Event FRBK.1

        Message: 'Backup-PVC, PVC=$1 PVCBackup=$2, on interface $3'

        Parameters list:
              $1: frbk1_circuit
              $2: frbk1_circuit
              $3: frbk1_ifc_name

        A PVC switched to backup state."
    ::= { frbkNotificationsPrefix 1 }

frbkNotification2 NOTIFICATION-TYPE
    OBJECTS { 
              frbk2_circuit, 
              frbk2_circuit,
              frbk2_ifc_name 
            }
    STATUS current
    DESCRIPTION
        "Notification of Event FRBK.2

        Message: 'Return Backup-PVC, PVC=$1 PVCBackup= $2, on interface $3'

        Parameters list:
              $1: frbk2_circuit
              $2: frbk2_circuit
              $3: frbk2_ifc_name

        A PVC returns from backup state to active state."
    ::= { frbkNotificationsPrefix 2 }

frbkNotification3 NOTIFICATION-TYPE
    OBJECTS { 
              frbk3_ifc_name 
            }
    STATUS current
    DESCRIPTION
        "Notification of Event FRBK.3

        Message: 'Return command Backup PVC, on interface $1'

        Parameters list:
              $1: frbk3_ifc_name

        All PVCs in backup state are forced to return to active state whenever
        it is possible."
    ::= { frbkNotificationsPrefix 3 }

frbkNotification4 NOTIFICATION-TYPE
    OBJECTS { 
              frbk4_ifc_name 
            }
    STATUS current
    DESCRIPTION
        "Notification of Event FRBK.4

        Message: 'Tiemout Backup PVC, on interface $1'

        Parameters list:
              $1: frbk4_ifc_name

        When backup timer expires all circuits can switch to normal operation
        (if it is possible)."
    ::= { frbkNotificationsPrefix 4 }

frbkNotification5 NOTIFICATION-TYPE
    OBJECTS { 
              frbk5_ifc_name, 
              frbk5_isdn_ifc_name 
            }
    STATUS current
    DESCRIPTION
        "Notification of Event FRBK.5

        Message: 'ISDN Backup, FR interface $1, RDSI interface $2'

        Parameters list:
              $1: frbk5_ifc_name
              $2: frbk5_isdn_ifc_name

        All traffic which normally goes through Frame Relay interface must be
        routered through the associated backup interface over ISDN."
    ::= { frbkNotificationsPrefix 5 }

frbkNotification6 NOTIFICATION-TYPE
    OBJECTS { 
              frbk6_ifc_name, 
              frbk6_isdn_ifc_name 
            }
    STATUS current
    DESCRIPTION
        "Notification of Event FRBK.6

        Message: 'Return ISDN Backup, FR interface $1, RDSI interface $2'

        Parameters list:
              $1: frbk6_ifc_name
              $2: frbk6_isdn_ifc_name

        Frame Relay interface (primary link) has recovered: it is active and
        operative again, so the secondary link automatically disconnects and
        traffic stops being transmitted through the ISDN backup interface."
    ::= { frbkNotificationsPrefix 6 }

frbkNotification7 NOTIFICATION-TYPE
    OBJECTS { 
              frbk7_circuit, 
              frbk7_circuit,
              frbk7_ifc_name,
              frbk7_isdn_ifc_name 
            }
    STATUS current
    DESCRIPTION
        "Notification of Event FRBK.7

        Message: 'ISDN Backup, PVC=$1 PVCBackup-ISDN=$2, FR interface $3 RDSI interface $4'

        Parameters list:
              $1: frbk7_circuit
              $2: frbk7_circuit
              $3: frbk7_ifc_name
              $4: frbk7_isdn_ifc_name

        A PVC switched to backup state."
    ::= { frbkNotificationsPrefix 7 }

frbkNotification8 NOTIFICATION-TYPE
    OBJECTS { 
              frbk8_circuit, 
              frbk8_circuit,
              frbk8_ifc_name,
              frbk8_isdn_ifc_name 
            }
    STATUS current
    DESCRIPTION
        "Notification of Event FRBK.8

        Message: 'Return ISDN-Backup, PVC=$1 PVCBackup-ISDN = $2, FR interface $3 RDSI interface $4'

        Parameters list:
              $1: frbk8_circuit
              $2: frbk8_circuit
              $3: frbk8_ifc_name
              $4: frbk8_isdn_ifc_name

        A PVC returns from backup state to active state."
    ::= { frbkNotificationsPrefix 8 }


END
