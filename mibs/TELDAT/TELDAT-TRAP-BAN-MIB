-- file automatically created


TELDAT-TRAP-BAN-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


banTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BAN event subsystem."
    REVISION "201401200930Z"
    DESCRIPTION "Initial implementation"
        ::= { telEventTraps 109 }


banEventsGroup	OBJECT IDENTIFIER	::= { banTrapsMIB 1 }

banNotifications	OBJECT IDENTIFIER	::= { banTrapsMIB 2 }
banNotificationsPrefix	OBJECT IDENTIFIER	::= { banNotifications 0 }

banEventObjects1 OBJECT-IDENTITY
    STATUS current
    DESCRIPTION
        "Event BAN.1
        I_frame packet. Direction is 'in' or 'out' of the router. Shows the
        bridge port number. Shows the full RIF (routing information field) of
        the packet. Shows up to 20 bytes of the packet after the SSAP field.
        The length is the amount of data in the packet after the SSAP field in
        the packet."
    ::= { banEventsGroup 1 }

ban1_direction OBJECT-TYPE
    SYNTAX DisplayString
    MAX-ACCESS accessible-for-notify
    STATUS current
    DESCRIPTION
        "Parameter 'direction' in event BAN.1"
    ::= { banEventObjects1 1 }

ban1_bridge_port OBJECT-TYPE
    SYNTAX Integer32
    MAX-ACCESS accessible-for-notify
    STATUS current
    DESCRIPTION
        "Parameter 'bridge_port' in event BAN.1"
    ::= { banEventObjects1 2 }

ban1_len OBJECT-TYPE
    SYNTAX Integer32
    MAX-ACCESS accessible-for-notify
    STATUS current
    DESCRIPTION
        "Parameter 'len' in event BAN.1"
    ::= { banEventObjects1 3 }

ban1_source_mac_address OBJECT-TYPE
    SYNTAX DisplayString
    MAX-ACCESS accessible-for-notify
    STATUS current
    DESCRIPTION
        "Parameter 'source_mac_address' in event BAN.1"
    ::= { banEventObjects1 4 }

ban1_dest_mac_address OBJECT-TYPE
    SYNTAX DisplayString
    MAX-ACCESS accessible-for-notify
    STATUS current
    DESCRIPTION
        "Parameter 'dest_mac_address' in event BAN.1"
    ::= { banEventObjects1 5 }

ban1_source_sap OBJECT-TYPE
    SYNTAX Integer32
    MAX-ACCESS accessible-for-notify
    STATUS current
    DESCRIPTION
        "Parameter 'source_sap' in event BAN.1"
    ::= { banEventObjects1 6 }

ban1_dest_sap OBJECT-TYPE
    SYNTAX Integer32
    MAX-ACCESS accessible-for-notify
    STATUS current
    DESCRIPTION
        "Parameter 'dest_sap' in event BAN.1"
    ::= { banEventObjects1 7 }

ban1_rif_data OBJECT-TYPE
    SYNTAX DisplayString
    MAX-ACCESS accessible-for-notify
    STATUS current
    DESCRIPTION
        "Parameter 'rif_data' in event BAN.1"
    ::= { banEventObjects1 8 }

banEventObjects2 OBJECT-IDENTITY
    STATUS current
    DESCRIPTION
        "Event BAN.2
        RR packet."
    ::= { banEventsGroup 2 }

ban2_direction OBJECT-TYPE
    SYNTAX DisplayString
    MAX-ACCESS accessible-for-notify
    STATUS current
    DESCRIPTION
        "Parameter 'direction' in event BAN.2"
    ::= { banEventObjects2 1 }

ban2_bridge_port OBJECT-TYPE
    SYNTAX Integer32
    MAX-ACCESS accessible-for-notify
    STATUS current
    DESCRIPTION
        "Parameter 'bridge_port' in event BAN.2"
    ::= { banEventObjects2 2 }

ban2_len OBJECT-TYPE
    SYNTAX Integer32
    MAX-ACCESS accessible-for-notify
    STATUS current
    DESCRIPTION
        "Parameter 'len' in event BAN.2"
    ::= { banEventObjects2 3 }

ban2_source_mac_address OBJECT-TYPE
    SYNTAX DisplayString
    MAX-ACCESS accessible-for-notify
    STATUS current
    DESCRIPTION
        "Parameter 'source_mac_address' in event BAN.2"
    ::= { banEventObjects2 4 }

ban2_dest_mac_address OBJECT-TYPE
    SYNTAX DisplayString
    MAX-ACCESS accessible-for-notify
    STATUS current
    DESCRIPTION
        "Parameter 'dest_mac_address' in event BAN.2"
    ::= { banEventObjects2 5 }

ban2_source_sap OBJECT-TYPE
    SYNTAX Integer32
    MAX-ACCESS accessible-for-notify
    STATUS current
    DESCRIPTION
        "Parameter 'source_sap' in event BAN.2"
    ::= { banEventObjects2 6 }

ban2_dest_sap OBJECT-TYPE
    SYNTAX Integer32
    MAX-ACCESS accessible-for-notify
    STATUS current
    DESCRIPTION
        "Parameter 'dest_sap' in event BAN.2"
    ::= { banEventObjects2 7 }

ban2_rif_data OBJECT-TYPE
    SYNTAX DisplayString
    MAX-ACCESS accessible-for-notify
    STATUS current
    DESCRIPTION
        "Parameter 'rif_data' in event BAN.2"
    ::= { banEventObjects2 8 }

banEventObjects3 OBJECT-IDENTITY
    STATUS current
    DESCRIPTION
        "Event BAN.3
        The configured BAN bridge port is not a bridge port."
    ::= { banEventsGroup 3 }

ban3_bridge_port OBJECT-TYPE
    SYNTAX Integer32
    MAX-ACCESS accessible-for-notify
    STATUS current
    DESCRIPTION
        "Parameter 'bridge_port' in event BAN.3"
    ::= { banEventObjects3 1 }

banEventObjects4 OBJECT-IDENTITY
    STATUS current
    DESCRIPTION
        "Event BAN.4
        The configured BAN bridge port has been initialized from a BAN point of view."
    ::= { banEventsGroup 4 }

ban4_bridge_port OBJECT-TYPE
    SYNTAX Integer32
    MAX-ACCESS accessible-for-notify
    STATUS current
    DESCRIPTION
        "Parameter 'bridge_port' in event BAN.4"
    ::= { banEventObjects4 1 }

banEventObjects5 OBJECT-IDENTITY
    STATUS current
    DESCRIPTION
        "Event BAN.5
        Every frame sent by the NCP must match the configured Boundary Node
        Identifier (BNI) MAC address."
    ::= { banEventsGroup 5 }

ban5_source_mac_address OBJECT-TYPE
    SYNTAX DisplayString
    MAX-ACCESS accessible-for-notify
    STATUS current
    DESCRIPTION
        "Parameter 'source_mac_address' in event BAN.5"
    ::= { banEventObjects5 1 }

ban5_dest_mac_address OBJECT-TYPE
    SYNTAX DisplayString
    MAX-ACCESS accessible-for-notify
    STATUS current
    DESCRIPTION
        "Parameter 'dest_mac_address' in event BAN.5"
    ::= { banEventObjects5 2 }

ban5_bni_mac OBJECT-TYPE
    SYNTAX DisplayString
    MAX-ACCESS accessible-for-notify
    STATUS current
    DESCRIPTION
        "Parameter 'bni_mac' in event BAN.5"
    ::= { banEventObjects5 3 }

ban5_bridge_port OBJECT-TYPE
    SYNTAX Integer32
    MAX-ACCESS accessible-for-notify
    STATUS current
    DESCRIPTION
        "Parameter 'bridge_port' in event BAN.5"
    ::= { banEventObjects5 4 }

banEventObjects6 OBJECT-IDENTITY
    STATUS current
    DESCRIPTION
        "Event BAN.6
        The configured BAN bridge port is not a Frame Relay DLCI bridge port."
    ::= { banEventsGroup 6 }

ban6_bridge_port OBJECT-TYPE
    SYNTAX Integer32
    MAX-ACCESS accessible-for-notify
    STATUS current
    DESCRIPTION
        "Parameter 'bridge_port' in event BAN.6"
    ::= { banEventObjects6 1 }

banEventObjects8 OBJECT-IDENTITY
    STATUS current
    DESCRIPTION
        "Event BAN.8
        The outgoing frame was filtered by BAN because it was NOT an RFC 1490
        bridged Token-Ring frame, without preserved FCS, which is OUI type 9.
        This is the only type of frame expected by the NCP. Another bridge type
        frame is being sent: 1 and 7 are Ethernet, 2 and 8 are 802.4, 3 is
        Token-Ring with FCS, 4 and 10 are FDDI, 11 is 802.6, 14 is
        802.1d Hello BPDU, 15 is SRB Hello BPDU."
    ::= { banEventsGroup 8 }

ban8_bridge_port OBJECT-TYPE
    SYNTAX Integer32
    MAX-ACCESS accessible-for-notify
    STATUS current
    DESCRIPTION
        "Parameter 'bridge_port' in event BAN.8"
    ::= { banEventObjects8 1 }

ban8_oui_type OBJECT-TYPE
    SYNTAX Integer32
    MAX-ACCESS accessible-for-notify
    STATUS current
    DESCRIPTION
        "Parameter 'oui_type' in event BAN.8"
    ::= { banEventObjects8 2 }

banEventObjects9 OBJECT-IDENTITY
    STATUS current
    DESCRIPTION
        "Event BAN.9
        The outgoing frame was filtered by BAN because the frame's destination
        address did not equal the BAN DLCI address. This is done to protect
        the NCP."
    ::= { banEventsGroup 9 }

ban9_source_mac_address OBJECT-TYPE
    SYNTAX DisplayString
    MAX-ACCESS accessible-for-notify
    STATUS current
    DESCRIPTION
        "Parameter 'source_mac_address' in event BAN.9"
    ::= { banEventObjects9 1 }

ban9_dest_mac_address OBJECT-TYPE
    SYNTAX DisplayString
    MAX-ACCESS accessible-for-notify
    STATUS current
    DESCRIPTION
        "Parameter 'dest_mac_address' in event BAN.9"
    ::= { banEventObjects9 2 }

ban9_bridge_port OBJECT-TYPE
    SYNTAX Integer32
    MAX-ACCESS accessible-for-notify
    STATUS current
    DESCRIPTION
        "Parameter 'bridge_port' in event BAN.9"
    ::= { banEventObjects9 3 }

ban9_ban_dlci_address OBJECT-TYPE
    SYNTAX DisplayString
    MAX-ACCESS accessible-for-notify
    STATUS current
    DESCRIPTION
        "Parameter 'ban_dlci_address' in event BAN.9"
    ::= { banEventObjects9 4 }

banEventObjects10 OBJECT-IDENTITY
    STATUS current
    DESCRIPTION
        "Event BAN.10
        The BAN bridge port behavior is being dynamically forced to transparent
        bridging off, spanning tree off. This is required for BAN."
    ::= { banEventsGroup 10 }

ban10_bridge_port OBJECT-TYPE
    SYNTAX Integer32
    MAX-ACCESS accessible-for-notify
    STATUS current
    DESCRIPTION
        "Parameter 'bridge_port' in event BAN.10"
    ::= { banEventObjects10 1 }

banEventObjects11 OBJECT-IDENTITY
    STATUS current
    DESCRIPTION
        "Event BAN.11
        The BAN bridge port is configured for DLSw terminated. However, DLSw
        is not in this build."
    ::= { banEventsGroup 11 }

ban11_bridge_port OBJECT-TYPE
    SYNTAX Integer32
    MAX-ACCESS accessible-for-notify
    STATUS current
    DESCRIPTION
        "Parameter 'bridge_port' in event BAN.11"
    ::= { banEventObjects11 1 }

banEventObjects13 OBJECT-IDENTITY
    STATUS current
    DESCRIPTION
        "Event BAN.13
        The outgoing frame was filtered by BAN because the BAN port is set to
        DLSw switching, but the frame was not a DLSw frame since the DLSw
        source routing segment and bridge number were not in the RIF (routing
        information field) of the frame. This is done to protect the NCP."
    ::= { banEventsGroup 13 }

ban13_source_mac_address OBJECT-TYPE
    SYNTAX DisplayString
    MAX-ACCESS accessible-for-notify
    STATUS current
    DESCRIPTION
        "Parameter 'source_mac_address' in event BAN.13"
    ::= { banEventObjects13 1 }

ban13_dest_mac_address OBJECT-TYPE
    SYNTAX DisplayString
    MAX-ACCESS accessible-for-notify
    STATUS current
    DESCRIPTION
        "Parameter 'dest_mac_address' in event BAN.13"
    ::= { banEventObjects13 2 }

ban13_bridge_port OBJECT-TYPE
    SYNTAX Integer32
    MAX-ACCESS accessible-for-notify
    STATUS current
    DESCRIPTION
        "Parameter 'bridge_port' in event BAN.13"
    ::= { banEventObjects13 3 }

ban13_segment_ban OBJECT-TYPE
    SYNTAX Integer32
    MAX-ACCESS accessible-for-notify
    STATUS current
    DESCRIPTION
        "Parameter 'segment_ban' in event BAN.13"
    ::= { banEventObjects13 4 }

ban13_rif_data OBJECT-TYPE
    SYNTAX DisplayString
    MAX-ACCESS accessible-for-notify
    STATUS current
    DESCRIPTION
        "Parameter 'rif_data' in event BAN.13"
    ::= { banEventObjects13 5 }

banEventObjects14 OBJECT-IDENTITY
    STATUS current
    DESCRIPTION
        "Event BAN.14
        RNR packet."
    ::= { banEventsGroup 14 }

ban14_direction OBJECT-TYPE
    SYNTAX DisplayString
    MAX-ACCESS accessible-for-notify
    STATUS current
    DESCRIPTION
        "Parameter 'direction' in event BAN.14"
    ::= { banEventObjects14 1 }

ban14_bridge_port OBJECT-TYPE
    SYNTAX Integer32
    MAX-ACCESS accessible-for-notify
    STATUS current
    DESCRIPTION
        "Parameter 'bridge_port' in event BAN.14"
    ::= { banEventObjects14 2 }

ban14_len OBJECT-TYPE
    SYNTAX Integer32
    MAX-ACCESS accessible-for-notify
    STATUS current
    DESCRIPTION
        "Parameter 'len' in event BAN.14"
    ::= { banEventObjects14 3 }

ban14_source_mac_address OBJECT-TYPE
    SYNTAX DisplayString
    MAX-ACCESS accessible-for-notify
    STATUS current
    DESCRIPTION
        "Parameter 'source_mac_address' in event BAN.14"
    ::= { banEventObjects14 4 }

ban14_dest_mac_address OBJECT-TYPE
    SYNTAX DisplayString
    MAX-ACCESS accessible-for-notify
    STATUS current
    DESCRIPTION
        "Parameter 'dest_mac_address' in event BAN.14"
    ::= { banEventObjects14 5 }

ban14_source_sap OBJECT-TYPE
    SYNTAX Integer32
    MAX-ACCESS accessible-for-notify
    STATUS current
    DESCRIPTION
        "Parameter 'source_sap' in event BAN.14"
    ::= { banEventObjects14 6 }

ban14_dest_sap OBJECT-TYPE
    SYNTAX Integer32
    MAX-ACCESS accessible-for-notify
    STATUS current
    DESCRIPTION
        "Parameter 'dest_sap' in event BAN.14"
    ::= { banEventObjects14 7 }

ban14_rif_data OBJECT-TYPE
    SYNTAX DisplayString
    MAX-ACCESS accessible-for-notify
    STATUS current
    DESCRIPTION
        "Parameter 'rif_data' in event BAN.14"
    ::= { banEventObjects14 8 }

banEventObjects15 OBJECT-IDENTITY
    STATUS current
    DESCRIPTION
        "Event BAN.15
        REJ packet."
    ::= { banEventsGroup 15 }

ban15_direction OBJECT-TYPE
    SYNTAX DisplayString
    MAX-ACCESS accessible-for-notify
    STATUS current
    DESCRIPTION
        "Parameter 'direction' in event BAN.15"
    ::= { banEventObjects15 1 }

ban15_bridge_port OBJECT-TYPE
    SYNTAX Integer32
    MAX-ACCESS accessible-for-notify
    STATUS current
    DESCRIPTION
        "Parameter 'bridge_port' in event BAN.15"
    ::= { banEventObjects15 2 }

ban15_len OBJECT-TYPE
    SYNTAX Integer32
    MAX-ACCESS accessible-for-notify
    STATUS current
    DESCRIPTION
        "Parameter 'len' in event BAN.15"
    ::= { banEventObjects15 3 }

ban15_source_mac_address OBJECT-TYPE
    SYNTAX DisplayString
    MAX-ACCESS accessible-for-notify
    STATUS current
    DESCRIPTION
        "Parameter 'source_mac_address' in event BAN.15"
    ::= { banEventObjects15 4 }

ban15_dest_mac_address OBJECT-TYPE
    SYNTAX DisplayString
    MAX-ACCESS accessible-for-notify
    STATUS current
    DESCRIPTION
        "Parameter 'dest_mac_address' in event BAN.15"
    ::= { banEventObjects15 5 }

ban15_source_sap OBJECT-TYPE
    SYNTAX Integer32
    MAX-ACCESS accessible-for-notify
    STATUS current
    DESCRIPTION
        "Parameter 'source_sap' in event BAN.15"
    ::= { banEventObjects15 6 }

ban15_dest_sap OBJECT-TYPE
    SYNTAX Integer32
    MAX-ACCESS accessible-for-notify
    STATUS current
    DESCRIPTION
        "Parameter 'dest_sap' in event BAN.15"
    ::= { banEventObjects15 7 }

ban15_rif_data OBJECT-TYPE
    SYNTAX DisplayString
    MAX-ACCESS accessible-for-notify
    STATUS current
    DESCRIPTION
        "Parameter 'rif_data' in event BAN.15"
    ::= { banEventObjects15 8 }

banEventObjects16 OBJECT-IDENTITY
    STATUS current
    DESCRIPTION
        "Event BAN.16
        TEST_C (Test command) packet."
    ::= { banEventsGroup 16 }

ban16_direction OBJECT-TYPE
    SYNTAX DisplayString
    MAX-ACCESS accessible-for-notify
    STATUS current
    DESCRIPTION
        "Parameter 'direction' in event BAN.16"
    ::= { banEventObjects16 1 }

ban16_bridge_port OBJECT-TYPE
    SYNTAX Integer32
    MAX-ACCESS accessible-for-notify
    STATUS current
    DESCRIPTION
        "Parameter 'bridge_port' in event BAN.16"
    ::= { banEventObjects16 2 }

ban16_len OBJECT-TYPE
    SYNTAX Integer32
    MAX-ACCESS accessible-for-notify
    STATUS current
    DESCRIPTION
        "Parameter 'len' in event BAN.16"
    ::= { banEventObjects16 3 }

ban16_source_mac_address OBJECT-TYPE
    SYNTAX DisplayString
    MAX-ACCESS accessible-for-notify
    STATUS current
    DESCRIPTION
        "Parameter 'source_mac_address' in event BAN.16"
    ::= { banEventObjects16 4 }

ban16_dest_mac_address OBJECT-TYPE
    SYNTAX DisplayString
    MAX-ACCESS accessible-for-notify
    STATUS current
    DESCRIPTION
        "Parameter 'dest_mac_address' in event BAN.16"
    ::= { banEventObjects16 5 }

ban16_source_sap OBJECT-TYPE
    SYNTAX Integer32
    MAX-ACCESS accessible-for-notify
    STATUS current
    DESCRIPTION
        "Parameter 'source_sap' in event BAN.16"
    ::= { banEventObjects16 6 }

ban16_dest_sap OBJECT-TYPE
    SYNTAX Integer32
    MAX-ACCESS accessible-for-notify
    STATUS current
    DESCRIPTION
        "Parameter 'dest_sap' in event BAN.16"
    ::= { banEventObjects16 7 }

ban16_rif_data OBJECT-TYPE
    SYNTAX DisplayString
    MAX-ACCESS accessible-for-notify
    STATUS current
    DESCRIPTION
        "Parameter 'rif_data' in event BAN.16"
    ::= { banEventObjects16 8 }

banEventObjects17 OBJECT-IDENTITY
    STATUS current
    DESCRIPTION
        "Event BAN.17
        TEST_R (Test response) packet."
    ::= { banEventsGroup 17 }

ban17_direction OBJECT-TYPE
    SYNTAX DisplayString
    MAX-ACCESS accessible-for-notify
    STATUS current
    DESCRIPTION
        "Parameter 'direction' in event BAN.17"
    ::= { banEventObjects17 1 }

ban17_bridge_port OBJECT-TYPE
    SYNTAX Integer32
    MAX-ACCESS accessible-for-notify
    STATUS current
    DESCRIPTION
        "Parameter 'bridge_port' in event BAN.17"
    ::= { banEventObjects17 2 }

ban17_len OBJECT-TYPE
    SYNTAX Integer32
    MAX-ACCESS accessible-for-notify
    STATUS current
    DESCRIPTION
        "Parameter 'len' in event BAN.17"
    ::= { banEventObjects17 3 }

ban17_source_mac_address OBJECT-TYPE
    SYNTAX DisplayString
    MAX-ACCESS accessible-for-notify
    STATUS current
    DESCRIPTION
        "Parameter 'source_mac_address' in event BAN.17"
    ::= { banEventObjects17 4 }

ban17_dest_mac_address OBJECT-TYPE
    SYNTAX DisplayString
    MAX-ACCESS accessible-for-notify
    STATUS current
    DESCRIPTION
        "Parameter 'dest_mac_address' in event BAN.17"
    ::= { banEventObjects17 5 }

ban17_source_sap OBJECT-TYPE
    SYNTAX Integer32
    MAX-ACCESS accessible-for-notify
    STATUS current
    DESCRIPTION
        "Parameter 'source_sap' in event BAN.17"
    ::= { banEventObjects17 6 }

ban17_dest_sap OBJECT-TYPE
    SYNTAX Integer32
    MAX-ACCESS accessible-for-notify
    STATUS current
    DESCRIPTION
        "Parameter 'dest_sap' in event BAN.17"
    ::= { banEventObjects17 7 }

ban17_rif_data OBJECT-TYPE
    SYNTAX DisplayString
    MAX-ACCESS accessible-for-notify
    STATUS current
    DESCRIPTION
        "Parameter 'rif_data' in event BAN.17"
    ::= { banEventObjects17 8 }

banEventObjects18 OBJECT-IDENTITY
    STATUS current
    DESCRIPTION
        "Event BAN.18
        XID_C (XID command) packet."
    ::= { banEventsGroup 18 }

ban18_direction OBJECT-TYPE
    SYNTAX DisplayString
    MAX-ACCESS accessible-for-notify
    STATUS current
    DESCRIPTION
        "Parameter 'direction' in event BAN.18"
    ::= { banEventObjects18 1 }

ban18_bridge_port OBJECT-TYPE
    SYNTAX Integer32
    MAX-ACCESS accessible-for-notify
    STATUS current
    DESCRIPTION
        "Parameter 'bridge_port' in event BAN.18"
    ::= { banEventObjects18 2 }

ban18_len OBJECT-TYPE
    SYNTAX Integer32
    MAX-ACCESS accessible-for-notify
    STATUS current
    DESCRIPTION
        "Parameter 'len' in event BAN.18"
    ::= { banEventObjects18 3 }

ban18_source_mac_address OBJECT-TYPE
    SYNTAX DisplayString
    MAX-ACCESS accessible-for-notify
    STATUS current
    DESCRIPTION
        "Parameter 'source_mac_address' in event BAN.18"
    ::= { banEventObjects18 4 }

ban18_dest_mac_address OBJECT-TYPE
    SYNTAX DisplayString
    MAX-ACCESS accessible-for-notify
    STATUS current
    DESCRIPTION
        "Parameter 'dest_mac_address' in event BAN.18"
    ::= { banEventObjects18 5 }

ban18_source_sap OBJECT-TYPE
    SYNTAX Integer32
    MAX-ACCESS accessible-for-notify
    STATUS current
    DESCRIPTION
        "Parameter 'source_sap' in event BAN.18"
    ::= { banEventObjects18 6 }

ban18_dest_sap OBJECT-TYPE
    SYNTAX Integer32
    MAX-ACCESS accessible-for-notify
    STATUS current
    DESCRIPTION
        "Parameter 'dest_sap' in event BAN.18"
    ::= { banEventObjects18 7 }

ban18_rif_data OBJECT-TYPE
    SYNTAX DisplayString
    MAX-ACCESS accessible-for-notify
    STATUS current
    DESCRIPTION
        "Parameter 'rif_data' in event BAN.18"
    ::= { banEventObjects18 8 }

banEventObjects19 OBJECT-IDENTITY
    STATUS current
    DESCRIPTION
        "Event BAN.19
        XID_R (XID response) packet."
    ::= { banEventsGroup 19 }

ban19_direction OBJECT-TYPE
    SYNTAX DisplayString
    MAX-ACCESS accessible-for-notify
    STATUS current
    DESCRIPTION
        "Parameter 'direction' in event BAN.19"
    ::= { banEventObjects19 1 }

ban19_bridge_port OBJECT-TYPE
    SYNTAX Integer32
    MAX-ACCESS accessible-for-notify
    STATUS current
    DESCRIPTION
        "Parameter 'bridge_port' in event BAN.19"
    ::= { banEventObjects19 2 }

ban19_len OBJECT-TYPE
    SYNTAX Integer32
    MAX-ACCESS accessible-for-notify
    STATUS current
    DESCRIPTION
        "Parameter 'len' in event BAN.19"
    ::= { banEventObjects19 3 }

ban19_source_mac_address OBJECT-TYPE
    SYNTAX DisplayString
    MAX-ACCESS accessible-for-notify
    STATUS current
    DESCRIPTION
        "Parameter 'source_mac_address' in event BAN.19"
    ::= { banEventObjects19 4 }

ban19_dest_mac_address OBJECT-TYPE
    SYNTAX DisplayString
    MAX-ACCESS accessible-for-notify
    STATUS current
    DESCRIPTION
        "Parameter 'dest_mac_address' in event BAN.19"
    ::= { banEventObjects19 5 }

ban19_source_sap OBJECT-TYPE
    SYNTAX Integer32
    MAX-ACCESS accessible-for-notify
    STATUS current
    DESCRIPTION
        "Parameter 'source_sap' in event BAN.19"
    ::= { banEventObjects19 6 }

ban19_dest_sap OBJECT-TYPE
    SYNTAX Integer32
    MAX-ACCESS accessible-for-notify
    STATUS current
    DESCRIPTION
        "Parameter 'dest_sap' in event BAN.19"
    ::= { banEventObjects19 7 }

ban19_rif_data OBJECT-TYPE
    SYNTAX DisplayString
    MAX-ACCESS accessible-for-notify
    STATUS current
    DESCRIPTION
        "Parameter 'rif_data' in event BAN.19"
    ::= { banEventObjects19 8 }

banEventObjects20 OBJECT-IDENTITY
    STATUS current
    DESCRIPTION
        "Event BAN.20
        SABME packet."
    ::= { banEventsGroup 20 }

ban20_direction OBJECT-TYPE
    SYNTAX DisplayString
    MAX-ACCESS accessible-for-notify
    STATUS current
    DESCRIPTION
        "Parameter 'direction' in event BAN.20"
    ::= { banEventObjects20 1 }

ban20_bridge_port OBJECT-TYPE
    SYNTAX Integer32
    MAX-ACCESS accessible-for-notify
    STATUS current
    DESCRIPTION
        "Parameter 'bridge_port' in event BAN.20"
    ::= { banEventObjects20 2 }

ban20_len OBJECT-TYPE
    SYNTAX Integer32
    MAX-ACCESS accessible-for-notify
    STATUS current
    DESCRIPTION
        "Parameter 'len' in event BAN.20"
    ::= { banEventObjects20 3 }

ban20_source_mac_address OBJECT-TYPE
    SYNTAX DisplayString
    MAX-ACCESS accessible-for-notify
    STATUS current
    DESCRIPTION
        "Parameter 'source_mac_address' in event BAN.20"
    ::= { banEventObjects20 4 }

ban20_dest_mac_address OBJECT-TYPE
    SYNTAX DisplayString
    MAX-ACCESS accessible-for-notify
    STATUS current
    DESCRIPTION
        "Parameter 'dest_mac_address' in event BAN.20"
    ::= { banEventObjects20 5 }

ban20_source_sap OBJECT-TYPE
    SYNTAX Integer32
    MAX-ACCESS accessible-for-notify
    STATUS current
    DESCRIPTION
        "Parameter 'source_sap' in event BAN.20"
    ::= { banEventObjects20 6 }

ban20_dest_sap OBJECT-TYPE
    SYNTAX Integer32
    MAX-ACCESS accessible-for-notify
    STATUS current
    DESCRIPTION
        "Parameter 'dest_sap' in event BAN.20"
    ::= { banEventObjects20 7 }

ban20_rif_data OBJECT-TYPE
    SYNTAX DisplayString
    MAX-ACCESS accessible-for-notify
    STATUS current
    DESCRIPTION
        "Parameter 'rif_data' in event BAN.20"
    ::= { banEventObjects20 8 }

banEventObjects21 OBJECT-IDENTITY
    STATUS current
    DESCRIPTION
        "Event BAN.21
        UA packet."
    ::= { banEventsGroup 21 }

ban21_direction OBJECT-TYPE
    SYNTAX DisplayString
    MAX-ACCESS accessible-for-notify
    STATUS current
    DESCRIPTION
        "Parameter 'direction' in event BAN.21"
    ::= { banEventObjects21 1 }

ban21_bridge_port OBJECT-TYPE
    SYNTAX Integer32
    MAX-ACCESS accessible-for-notify
    STATUS current
    DESCRIPTION
        "Parameter 'bridge_port' in event BAN.21"
    ::= { banEventObjects21 2 }

ban21_len OBJECT-TYPE
    SYNTAX Integer32
    MAX-ACCESS accessible-for-notify
    STATUS current
    DESCRIPTION
        "Parameter 'len' in event BAN.21"
    ::= { banEventObjects21 3 }

ban21_source_mac_address OBJECT-TYPE
    SYNTAX DisplayString
    MAX-ACCESS accessible-for-notify
    STATUS current
    DESCRIPTION
        "Parameter 'source_mac_address' in event BAN.21"
    ::= { banEventObjects21 4 }

ban21_dest_mac_address OBJECT-TYPE
    SYNTAX DisplayString
    MAX-ACCESS accessible-for-notify
    STATUS current
    DESCRIPTION
        "Parameter 'dest_mac_address' in event BAN.21"
    ::= { banEventObjects21 5 }

ban21_source_sap OBJECT-TYPE
    SYNTAX Integer32
    MAX-ACCESS accessible-for-notify
    STATUS current
    DESCRIPTION
        "Parameter 'source_sap' in event BAN.21"
    ::= { banEventObjects21 6 }

ban21_dest_sap OBJECT-TYPE
    SYNTAX Integer32
    MAX-ACCESS accessible-for-notify
    STATUS current
    DESCRIPTION
        "Parameter 'dest_sap' in event BAN.21"
    ::= { banEventObjects21 7 }

ban21_rif_data OBJECT-TYPE
    SYNTAX DisplayString
    MAX-ACCESS accessible-for-notify
    STATUS current
    DESCRIPTION
        "Parameter 'rif_data' in event BAN.21"
    ::= { banEventObjects21 8 }

banEventObjects22 OBJECT-IDENTITY
    STATUS current
    DESCRIPTION
        "Event BAN.22
        DM packet."
    ::= { banEventsGroup 22 }

ban22_direction OBJECT-TYPE
    SYNTAX DisplayString
    MAX-ACCESS accessible-for-notify
    STATUS current
    DESCRIPTION
        "Parameter 'direction' in event BAN.22"
    ::= { banEventObjects22 1 }

ban22_bridge_port OBJECT-TYPE
    SYNTAX Integer32
    MAX-ACCESS accessible-for-notify
    STATUS current
    DESCRIPTION
        "Parameter 'bridge_port' in event BAN.22"
    ::= { banEventObjects22 2 }

ban22_len OBJECT-TYPE
    SYNTAX Integer32
    MAX-ACCESS accessible-for-notify
    STATUS current
    DESCRIPTION
        "Parameter 'len' in event BAN.22"
    ::= { banEventObjects22 3 }

ban22_source_mac_address OBJECT-TYPE
    SYNTAX DisplayString
    MAX-ACCESS accessible-for-notify
    STATUS current
    DESCRIPTION
        "Parameter 'source_mac_address' in event BAN.22"
    ::= { banEventObjects22 4 }

ban22_dest_mac_address OBJECT-TYPE
    SYNTAX DisplayString
    MAX-ACCESS accessible-for-notify
    STATUS current
    DESCRIPTION
        "Parameter 'dest_mac_address' in event BAN.22"
    ::= { banEventObjects22 5 }

ban22_source_sap OBJECT-TYPE
    SYNTAX Integer32
    MAX-ACCESS accessible-for-notify
    STATUS current
    DESCRIPTION
        "Parameter 'source_sap' in event BAN.22"
    ::= { banEventObjects22 6 }

ban22_dest_sap OBJECT-TYPE
    SYNTAX Integer32
    MAX-ACCESS accessible-for-notify
    STATUS current
    DESCRIPTION
        "Parameter 'dest_sap' in event BAN.22"
    ::= { banEventObjects22 7 }

ban22_rif_data OBJECT-TYPE
    SYNTAX DisplayString
    MAX-ACCESS accessible-for-notify
    STATUS current
    DESCRIPTION
        "Parameter 'rif_data' in event BAN.22"
    ::= { banEventObjects22 8 }

banEventObjects23 OBJECT-IDENTITY
    STATUS current
    DESCRIPTION
        "Event BAN.23
        DISC packet."
    ::= { banEventsGroup 23 }

ban23_direction OBJECT-TYPE
    SYNTAX DisplayString
    MAX-ACCESS accessible-for-notify
    STATUS current
    DESCRIPTION
        "Parameter 'direction' in event BAN.23"
    ::= { banEventObjects23 1 }

ban23_bridge_port OBJECT-TYPE
    SYNTAX Integer32
    MAX-ACCESS accessible-for-notify
    STATUS current
    DESCRIPTION
        "Parameter 'bridge_port' in event BAN.23"
    ::= { banEventObjects23 2 }

ban23_len OBJECT-TYPE
    SYNTAX Integer32
    MAX-ACCESS accessible-for-notify
    STATUS current
    DESCRIPTION
        "Parameter 'len' in event BAN.23"
    ::= { banEventObjects23 3 }

ban23_source_mac_address OBJECT-TYPE
    SYNTAX DisplayString
    MAX-ACCESS accessible-for-notify
    STATUS current
    DESCRIPTION
        "Parameter 'source_mac_address' in event BAN.23"
    ::= { banEventObjects23 4 }

ban23_dest_mac_address OBJECT-TYPE
    SYNTAX DisplayString
    MAX-ACCESS accessible-for-notify
    STATUS current
    DESCRIPTION
        "Parameter 'dest_mac_address' in event BAN.23"
    ::= { banEventObjects23 5 }

ban23_source_sap OBJECT-TYPE
    SYNTAX Integer32
    MAX-ACCESS accessible-for-notify
    STATUS current
    DESCRIPTION
        "Parameter 'source_sap' in event BAN.23"
    ::= { banEventObjects23 6 }

ban23_dest_sap OBJECT-TYPE
    SYNTAX Integer32
    MAX-ACCESS accessible-for-notify
    STATUS current
    DESCRIPTION
        "Parameter 'dest_sap' in event BAN.23"
    ::= { banEventObjects23 7 }

ban23_rif_data OBJECT-TYPE
    SYNTAX DisplayString
    MAX-ACCESS accessible-for-notify
    STATUS current
    DESCRIPTION
        "Parameter 'rif_data' in event BAN.23"
    ::= { banEventObjects23 8 }

banEventObjects24 OBJECT-IDENTITY
    STATUS current
    DESCRIPTION
        "Event BAN.24
        FRMR packet."
    ::= { banEventsGroup 24 }

ban24_direction OBJECT-TYPE
    SYNTAX DisplayString
    MAX-ACCESS accessible-for-notify
    STATUS current
    DESCRIPTION
        "Parameter 'direction' in event BAN.24"
    ::= { banEventObjects24 1 }

ban24_bridge_port OBJECT-TYPE
    SYNTAX Integer32
    MAX-ACCESS accessible-for-notify
    STATUS current
    DESCRIPTION
        "Parameter 'bridge_port' in event BAN.24"
    ::= { banEventObjects24 2 }

ban24_len OBJECT-TYPE
    SYNTAX Integer32
    MAX-ACCESS accessible-for-notify
    STATUS current
    DESCRIPTION
        "Parameter 'len' in event BAN.24"
    ::= { banEventObjects24 3 }

ban24_source_mac_address OBJECT-TYPE
    SYNTAX DisplayString
    MAX-ACCESS accessible-for-notify
    STATUS current
    DESCRIPTION
        "Parameter 'source_mac_address' in event BAN.24"
    ::= { banEventObjects24 4 }

ban24_dest_mac_address OBJECT-TYPE
    SYNTAX DisplayString
    MAX-ACCESS accessible-for-notify
    STATUS current
    DESCRIPTION
        "Parameter 'dest_mac_address' in event BAN.24"
    ::= { banEventObjects24 5 }

ban24_source_sap OBJECT-TYPE
    SYNTAX Integer32
    MAX-ACCESS accessible-for-notify
    STATUS current
    DESCRIPTION
        "Parameter 'source_sap' in event BAN.24"
    ::= { banEventObjects24 6 }

ban24_dest_sap OBJECT-TYPE
    SYNTAX Integer32
    MAX-ACCESS accessible-for-notify
    STATUS current
    DESCRIPTION
        "Parameter 'dest_sap' in event BAN.24"
    ::= { banEventObjects24 7 }

ban24_rif_data OBJECT-TYPE
    SYNTAX DisplayString
    MAX-ACCESS accessible-for-notify
    STATUS current
    DESCRIPTION
        "Parameter 'rif_data' in event BAN.24"
    ::= { banEventObjects24 8 }

banEventObjects25 OBJECT-IDENTITY
    STATUS current
    DESCRIPTION
        "Event BAN.25
        Other packet than those specifically called out above. Look at the data
        shown to determine exactly what type of frame it is."
    ::= { banEventsGroup 25 }

ban25_direction OBJECT-TYPE
    SYNTAX DisplayString
    MAX-ACCESS accessible-for-notify
    STATUS current
    DESCRIPTION
        "Parameter 'direction' in event BAN.25"
    ::= { banEventObjects25 1 }

ban25_bridge_port OBJECT-TYPE
    SYNTAX Integer32
    MAX-ACCESS accessible-for-notify
    STATUS current
    DESCRIPTION
        "Parameter 'bridge_port' in event BAN.25"
    ::= { banEventObjects25 2 }

ban25_len OBJECT-TYPE
    SYNTAX Integer32
    MAX-ACCESS accessible-for-notify
    STATUS current
    DESCRIPTION
        "Parameter 'len' in event BAN.25"
    ::= { banEventObjects25 3 }

ban25_source_mac_address OBJECT-TYPE
    SYNTAX DisplayString
    MAX-ACCESS accessible-for-notify
    STATUS current
    DESCRIPTION
        "Parameter 'source_mac_address' in event BAN.25"
    ::= { banEventObjects25 4 }

ban25_dest_mac_address OBJECT-TYPE
    SYNTAX DisplayString
    MAX-ACCESS accessible-for-notify
    STATUS current
    DESCRIPTION
        "Parameter 'dest_mac_address' in event BAN.25"
    ::= { banEventObjects25 5 }

ban25_source_sap OBJECT-TYPE
    SYNTAX Integer32
    MAX-ACCESS accessible-for-notify
    STATUS current
    DESCRIPTION
        "Parameter 'source_sap' in event BAN.25"
    ::= { banEventObjects25 6 }

ban25_dest_sap OBJECT-TYPE
    SYNTAX Integer32
    MAX-ACCESS accessible-for-notify
    STATUS current
    DESCRIPTION
        "Parameter 'dest_sap' in event BAN.25"
    ::= { banEventObjects25 7 }

ban25_rif_data OBJECT-TYPE
    SYNTAX DisplayString
    MAX-ACCESS accessible-for-notify
    STATUS current
    DESCRIPTION
        "Parameter 'rif_data' in event BAN.25"
    ::= { banEventObjects25 8 }

banEventObjects26 OBJECT-IDENTITY
    STATUS current
    DESCRIPTION
        "Event BAN.26
        All frames are being dropped. The port has been configured for DLSw
        termination, but DLSw is not running."
    ::= { banEventsGroup 26 }

ban26_bridge_port OBJECT-TYPE
    SYNTAX Integer32
    MAX-ACCESS accessible-for-notify
    STATUS current
    DESCRIPTION
        "Parameter 'bridge_port' in event BAN.26"
    ::= { banEventObjects26 1 }

banEventObjects27 OBJECT-IDENTITY
    STATUS current
    DESCRIPTION
        "Event BAN.27
        The configured BAN bridge port is not a source routing bridge port."
    ::= { banEventsGroup 27 }

ban27_bridge_port OBJECT-TYPE
    SYNTAX Integer32
    MAX-ACCESS accessible-for-notify
    STATUS current
    DESCRIPTION
        "Parameter 'bridge_port' in event BAN.27"
    ::= { banEventObjects27 1 }

banEventObjects28 OBJECT-IDENTITY
    STATUS current
    DESCRIPTION
        "Event BAN.28
        All bridged frames, in and out, are being dropped. The BAN port did not
        initialize."
    ::= { banEventsGroup 28 }

ban28_bridge_port OBJECT-TYPE
    SYNTAX Integer32
    MAX-ACCESS accessible-for-notify
    STATUS current
    DESCRIPTION
        "Parameter 'bridge_port' in event BAN.28"
    ::= { banEventObjects28 1 }

banEventObjects29 OBJECT-IDENTITY
    STATUS current
    DESCRIPTION
        "Event BAN.29
        When SR-TB conversion is enabled on the bridge, the BAN DLCI MAC address
        of the bridging DLCI must be unique. This restriction does not apply if
        SR-TB is disabled."
    ::= { banEventsGroup 29 }

ban29_bridge_port OBJECT-TYPE
    SYNTAX Integer32
    MAX-ACCESS accessible-for-notify
    STATUS current
    DESCRIPTION
        "Parameter 'bridge_port' in event BAN.29"
    ::= { banEventObjects29 1 }

ban29_ban_dlci_address OBJECT-TYPE
    SYNTAX DisplayString
    MAX-ACCESS accessible-for-notify
    STATUS current
    DESCRIPTION
        "Parameter 'ban_dlci_address' in event BAN.29"
    ::= { banEventObjects29 2 }


banNotification1 NOTIFICATION-TYPE
    OBJECTS { 
              ban1_direction, 
              ban1_bridge_port,
              ban1_len,
              ban1_source_mac_address,
              ban1_dest_mac_address,
              ban1_source_sap,
              ban1_dest_sap,
              ban1_rif_data 
            }
    STATUS current
    DESCRIPTION
        "Notification of Event BAN.1

        Message: 'T$1:I-FRAME port=$2 len=$3 $4->$5 $6->$7 $8'

        Parameters list:
              $1: ban1_direction
              $2: ban1_bridge_port
              $3: ban1_len
              $4: ban1_source_mac_address
              $5: ban1_dest_mac_address
              $6: ban1_source_sap
              $7: ban1_dest_sap
              $8: ban1_rif_data

        I_frame packet. Direction is 'in' or 'out' of the router. Shows the
        bridge port number. Shows the full RIF (routing information field) of
        the packet. Shows up to 20 bytes of the packet after the SSAP field.
        The length is the amount of data in the packet after the SSAP field in
        the packet."
    ::= { banNotificationsPrefix 1 }

banNotification2 NOTIFICATION-TYPE
    OBJECTS { 
              ban2_direction, 
              ban2_bridge_port,
              ban2_len,
              ban2_source_mac_address,
              ban2_dest_mac_address,
              ban2_source_sap,
              ban2_dest_sap,
              ban2_rif_data 
            }
    STATUS current
    DESCRIPTION
        "Notification of Event BAN.2

        Message: 'T$1:RR port=$2 len=$3 $4->$5 $6->$7 $8'

        Parameters list:
              $1: ban2_direction
              $2: ban2_bridge_port
              $3: ban2_len
              $4: ban2_source_mac_address
              $5: ban2_dest_mac_address
              $6: ban2_source_sap
              $7: ban2_dest_sap
              $8: ban2_rif_data

        RR packet."
    ::= { banNotificationsPrefix 2 }

banNotification3 NOTIFICATION-TYPE
    OBJECTS { 
              ban3_bridge_port 
            }
    STATUS current
    DESCRIPTION
        "Notification of Event BAN.3

        Message: 'port $1 is not a bridge port'

        Parameters list:
              $1: ban3_bridge_port

        The configured BAN bridge port is not a bridge port."
    ::= { banNotificationsPrefix 3 }

banNotification4 NOTIFICATION-TYPE
    OBJECTS { 
              ban4_bridge_port 
            }
    STATUS current
    DESCRIPTION
        "Notification of Event BAN.4

        Message: 'port $1 initialized'

        Parameters list:
              $1: ban4_bridge_port

        The configured BAN bridge port has been initialized from a BAN point of view."
    ::= { banNotificationsPrefix 4 }

banNotification5 NOTIFICATION-TYPE
    OBJECTS { 
              ban5_source_mac_address, 
              ban5_dest_mac_address,
              ban5_bni_mac,
              ban5_bridge_port 
            }
    STATUS current
    DESCRIPTION
        "Notification of Event BAN.5

        Message: 'frame dropped $1->$2, not BNI source address $3, port $4'

        Parameters list:
              $1: ban5_source_mac_address
              $2: ban5_dest_mac_address
              $3: ban5_bni_mac
              $4: ban5_bridge_port

        Every frame sent by the NCP must match the configured Boundary Node
        Identifier (BNI) MAC address."
    ::= { banNotificationsPrefix 5 }

banNotification6 NOTIFICATION-TYPE
    OBJECTS { 
              ban6_bridge_port 
            }
    STATUS current
    DESCRIPTION
        "Notification of Event BAN.6

        Message: 'port $1 is not a Frame Relay bridge port'

        Parameters list:
              $1: ban6_bridge_port

        The configured BAN bridge port is not a Frame Relay DLCI bridge port."
    ::= { banNotificationsPrefix 6 }

banNotification7 NOTIFICATION-TYPE
    STATUS current
    DESCRIPTION
        "Notification of Event BAN.7

        Message: '---'

        Reserved for possible future use."
    ::= { banNotificationsPrefix 7 }

banNotification8 NOTIFICATION-TYPE
    OBJECTS { 
              ban8_bridge_port, 
              ban8_oui_type 
            }
    STATUS current
    DESCRIPTION
        "Notification of Event BAN.8

        Message: 'frame filtered, port $1, OUI bridge type $2'

        Parameters list:
              $1: ban8_bridge_port
              $2: ban8_oui_type

        The outgoing frame was filtered by BAN because it was NOT an RFC 1490
        bridged Token-Ring frame, without preserved FCS, which is OUI type 9.
        This is the only type of frame expected by the NCP. Another bridge type
        frame is being sent: 1 and 7 are Ethernet, 2 and 8 are 802.4, 3 is
        Token-Ring with FCS, 4 and 10 are FDDI, 11 is 802.6, 14 is
        802.1d Hello BPDU, 15 is SRB Hello BPDU."
    ::= { banNotificationsPrefix 8 }

banNotification9 NOTIFICATION-TYPE
    OBJECTS { 
              ban9_source_mac_address, 
              ban9_dest_mac_address,
              ban9_bridge_port,
              ban9_ban_dlci_address 
            }
    STATUS current
    DESCRIPTION
        "Notification of Event BAN.9

        Message: 'frame filtered $1->$2, port $3, da not BAN DLCI address $4'

        Parameters list:
              $1: ban9_source_mac_address
              $2: ban9_dest_mac_address
              $3: ban9_bridge_port
              $4: ban9_ban_dlci_address

        The outgoing frame was filtered by BAN because the frame's destination
        address did not equal the BAN DLCI address. This is done to protect
        the NCP."
    ::= { banNotificationsPrefix 9 }

banNotification10 NOTIFICATION-TYPE
    OBJECTS { 
              ban10_bridge_port 
            }
    STATUS current
    DESCRIPTION
        "Notification of Event BAN.10

        Message: 'port $1 forcing: TB,STP off'

        Parameters list:
              $1: ban10_bridge_port

        The BAN bridge port behavior is being dynamically forced to transparent
        bridging off, spanning tree off. This is required for BAN."
    ::= { banNotificationsPrefix 10 }

banNotification11 NOTIFICATION-TYPE
    OBJECTS { 
              ban11_bridge_port 
            }
    STATUS current
    DESCRIPTION
        "Notification of Event BAN.11

        Message: 'port $1 DLSw term but DLSw is not in the build'

        Parameters list:
              $1: ban11_bridge_port

        The BAN bridge port is configured for DLSw terminated. However, DLSw
        is not in this build."
    ::= { banNotificationsPrefix 11 }

banNotification12 NOTIFICATION-TYPE
    STATUS current
    DESCRIPTION
        "Notification of Event BAN.12

        Message: '---'

        Reserved for possible future use."
    ::= { banNotificationsPrefix 12 }

banNotification13 NOTIFICATION-TYPE
    OBJECTS { 
              ban13_source_mac_address, 
              ban13_dest_mac_address,
              ban13_bridge_port,
              ban13_segment_ban,
              ban13_rif_data 
            }
    STATUS current
    DESCRIPTION
        "Notification of Event BAN.13

        Message: 'frame filtered $1->$2, port $3, DLSw snbn $4 not in RIF $5'

        Parameters list:
              $1: ban13_source_mac_address
              $2: ban13_dest_mac_address
              $3: ban13_bridge_port
              $4: ban13_segment_ban
              $5: ban13_rif_data

        The outgoing frame was filtered by BAN because the BAN port is set to
        DLSw switching, but the frame was not a DLSw frame since the DLSw
        source routing segment and bridge number were not in the RIF (routing
        information field) of the frame. This is done to protect the NCP."
    ::= { banNotificationsPrefix 13 }

banNotification14 NOTIFICATION-TYPE
    OBJECTS { 
              ban14_direction, 
              ban14_bridge_port,
              ban14_len,
              ban14_source_mac_address,
              ban14_dest_mac_address,
              ban14_source_sap,
              ban14_dest_sap,
              ban14_rif_data 
            }
    STATUS current
    DESCRIPTION
        "Notification of Event BAN.14

        Message: 'T$1:RNR port=$2 len=$3 $4->$5 $6->$7 $8'

        Parameters list:
              $1: ban14_direction
              $2: ban14_bridge_port
              $3: ban14_len
              $4: ban14_source_mac_address
              $5: ban14_dest_mac_address
              $6: ban14_source_sap
              $7: ban14_dest_sap
              $8: ban14_rif_data

        RNR packet."
    ::= { banNotificationsPrefix 14 }

banNotification15 NOTIFICATION-TYPE
    OBJECTS { 
              ban15_direction, 
              ban15_bridge_port,
              ban15_len,
              ban15_source_mac_address,
              ban15_dest_mac_address,
              ban15_source_sap,
              ban15_dest_sap,
              ban15_rif_data 
            }
    STATUS current
    DESCRIPTION
        "Notification of Event BAN.15

        Message: 'T$1:REJ port=$2 len=$3 $4->$5 $6->$7 $8'

        Parameters list:
              $1: ban15_direction
              $2: ban15_bridge_port
              $3: ban15_len
              $4: ban15_source_mac_address
              $5: ban15_dest_mac_address
              $6: ban15_source_sap
              $7: ban15_dest_sap
              $8: ban15_rif_data

        REJ packet."
    ::= { banNotificationsPrefix 15 }

banNotification16 NOTIFICATION-TYPE
    OBJECTS { 
              ban16_direction, 
              ban16_bridge_port,
              ban16_len,
              ban16_source_mac_address,
              ban16_dest_mac_address,
              ban16_source_sap,
              ban16_dest_sap,
              ban16_rif_data 
            }
    STATUS current
    DESCRIPTION
        "Notification of Event BAN.16

        Message: 'T$1:TST_C port=$2 len=$3 $4->$5 $6->$7 $8'

        Parameters list:
              $1: ban16_direction
              $2: ban16_bridge_port
              $3: ban16_len
              $4: ban16_source_mac_address
              $5: ban16_dest_mac_address
              $6: ban16_source_sap
              $7: ban16_dest_sap
              $8: ban16_rif_data

        TEST_C (Test command) packet."
    ::= { banNotificationsPrefix 16 }

banNotification17 NOTIFICATION-TYPE
    OBJECTS { 
              ban17_direction, 
              ban17_bridge_port,
              ban17_len,
              ban17_source_mac_address,
              ban17_dest_mac_address,
              ban17_source_sap,
              ban17_dest_sap,
              ban17_rif_data 
            }
    STATUS current
    DESCRIPTION
        "Notification of Event BAN.17

        Message: 'T$1:TST_R port=$2 len=$3 $4->$5 $6->$7 $8'

        Parameters list:
              $1: ban17_direction
              $2: ban17_bridge_port
              $3: ban17_len
              $4: ban17_source_mac_address
              $5: ban17_dest_mac_address
              $6: ban17_source_sap
              $7: ban17_dest_sap
              $8: ban17_rif_data

        TEST_R (Test response) packet."
    ::= { banNotificationsPrefix 17 }

banNotification18 NOTIFICATION-TYPE
    OBJECTS { 
              ban18_direction, 
              ban18_bridge_port,
              ban18_len,
              ban18_source_mac_address,
              ban18_dest_mac_address,
              ban18_source_sap,
              ban18_dest_sap,
              ban18_rif_data 
            }
    STATUS current
    DESCRIPTION
        "Notification of Event BAN.18

        Message: 'T$1:XID_C port=$2 len=$3 $4->$5 $6->$7 $8'

        Parameters list:
              $1: ban18_direction
              $2: ban18_bridge_port
              $3: ban18_len
              $4: ban18_source_mac_address
              $5: ban18_dest_mac_address
              $6: ban18_source_sap
              $7: ban18_dest_sap
              $8: ban18_rif_data

        XID_C (XID command) packet."
    ::= { banNotificationsPrefix 18 }

banNotification19 NOTIFICATION-TYPE
    OBJECTS { 
              ban19_direction, 
              ban19_bridge_port,
              ban19_len,
              ban19_source_mac_address,
              ban19_dest_mac_address,
              ban19_source_sap,
              ban19_dest_sap,
              ban19_rif_data 
            }
    STATUS current
    DESCRIPTION
        "Notification of Event BAN.19

        Message: 'T$1:XID_R port=$2 len=$3 $4->$5 $6->$7 $8'

        Parameters list:
              $1: ban19_direction
              $2: ban19_bridge_port
              $3: ban19_len
              $4: ban19_source_mac_address
              $5: ban19_dest_mac_address
              $6: ban19_source_sap
              $7: ban19_dest_sap
              $8: ban19_rif_data

        XID_R (XID response) packet."
    ::= { banNotificationsPrefix 19 }

banNotification20 NOTIFICATION-TYPE
    OBJECTS { 
              ban20_direction, 
              ban20_bridge_port,
              ban20_len,
              ban20_source_mac_address,
              ban20_dest_mac_address,
              ban20_source_sap,
              ban20_dest_sap,
              ban20_rif_data 
            }
    STATUS current
    DESCRIPTION
        "Notification of Event BAN.20

        Message: 'T$1:SABME port=$2 len=$3 $4->$5 $6->$7 $8'

        Parameters list:
              $1: ban20_direction
              $2: ban20_bridge_port
              $3: ban20_len
              $4: ban20_source_mac_address
              $5: ban20_dest_mac_address
              $6: ban20_source_sap
              $7: ban20_dest_sap
              $8: ban20_rif_data

        SABME packet."
    ::= { banNotificationsPrefix 20 }

banNotification21 NOTIFICATION-TYPE
    OBJECTS { 
              ban21_direction, 
              ban21_bridge_port,
              ban21_len,
              ban21_source_mac_address,
              ban21_dest_mac_address,
              ban21_source_sap,
              ban21_dest_sap,
              ban21_rif_data 
            }
    STATUS current
    DESCRIPTION
        "Notification of Event BAN.21

        Message: 'T$1:UA port=$2 len=$3 $4->$5 $6->$7 $8'

        Parameters list:
              $1: ban21_direction
              $2: ban21_bridge_port
              $3: ban21_len
              $4: ban21_source_mac_address
              $5: ban21_dest_mac_address
              $6: ban21_source_sap
              $7: ban21_dest_sap
              $8: ban21_rif_data

        UA packet."
    ::= { banNotificationsPrefix 21 }

banNotification22 NOTIFICATION-TYPE
    OBJECTS { 
              ban22_direction, 
              ban22_bridge_port,
              ban22_len,
              ban22_source_mac_address,
              ban22_dest_mac_address,
              ban22_source_sap,
              ban22_dest_sap,
              ban22_rif_data 
            }
    STATUS current
    DESCRIPTION
        "Notification of Event BAN.22

        Message: 'T$1:DM port=$2 len=$3 $4->$5 $6->$7 $8'

        Parameters list:
              $1: ban22_direction
              $2: ban22_bridge_port
              $3: ban22_len
              $4: ban22_source_mac_address
              $5: ban22_dest_mac_address
              $6: ban22_source_sap
              $7: ban22_dest_sap
              $8: ban22_rif_data

        DM packet."
    ::= { banNotificationsPrefix 22 }

banNotification23 NOTIFICATION-TYPE
    OBJECTS { 
              ban23_direction, 
              ban23_bridge_port,
              ban23_len,
              ban23_source_mac_address,
              ban23_dest_mac_address,
              ban23_source_sap,
              ban23_dest_sap,
              ban23_rif_data 
            }
    STATUS current
    DESCRIPTION
        "Notification of Event BAN.23

        Message: 'T$1:DISC port=$2 len=$3 $4->$5 $6->$7 $8'

        Parameters list:
              $1: ban23_direction
              $2: ban23_bridge_port
              $3: ban23_len
              $4: ban23_source_mac_address
              $5: ban23_dest_mac_address
              $6: ban23_source_sap
              $7: ban23_dest_sap
              $8: ban23_rif_data

        DISC packet."
    ::= { banNotificationsPrefix 23 }

banNotification24 NOTIFICATION-TYPE
    OBJECTS { 
              ban24_direction, 
              ban24_bridge_port,
              ban24_len,
              ban24_source_mac_address,
              ban24_dest_mac_address,
              ban24_source_sap,
              ban24_dest_sap,
              ban24_rif_data 
            }
    STATUS current
    DESCRIPTION
        "Notification of Event BAN.24

        Message: 'T$1:FRMR port=$2 len=$3 $4->$5 $6->$7 $8'

        Parameters list:
              $1: ban24_direction
              $2: ban24_bridge_port
              $3: ban24_len
              $4: ban24_source_mac_address
              $5: ban24_dest_mac_address
              $6: ban24_source_sap
              $7: ban24_dest_sap
              $8: ban24_rif_data

        FRMR packet."
    ::= { banNotificationsPrefix 24 }

banNotification25 NOTIFICATION-TYPE
    OBJECTS { 
              ban25_direction, 
              ban25_bridge_port,
              ban25_len,
              ban25_source_mac_address,
              ban25_dest_mac_address,
              ban25_source_sap,
              ban25_dest_sap,
              ban25_rif_data 
            }
    STATUS current
    DESCRIPTION
        "Notification of Event BAN.25

        Message: 'T$1:OTHER port=$2 len=$3 $4->$5 $6->$7 $8'

        Parameters list:
              $1: ban25_direction
              $2: ban25_bridge_port
              $3: ban25_len
              $4: ban25_source_mac_address
              $5: ban25_dest_mac_address
              $6: ban25_source_sap
              $7: ban25_dest_sap
              $8: ban25_rif_data

        Other packet than those specifically called out above. Look at the data
        shown to determine exactly what type of frame it is."
    ::= { banNotificationsPrefix 25 }

banNotification26 NOTIFICATION-TYPE
    OBJECTS { 
              ban26_bridge_port 
            }
    STATUS current
    DESCRIPTION
        "Notification of Event BAN.26

        Message: 'frame dropped, port $1, port is DLSw term, but DLSw is not initialized'

        Parameters list:
              $1: ban26_bridge_port

        All frames are being dropped. The port has been configured for DLSw
        termination, but DLSw is not running."
    ::= { banNotificationsPrefix 26 }

banNotification27 NOTIFICATION-TYPE
    OBJECTS { 
              ban27_bridge_port 
            }
    STATUS current
    DESCRIPTION
        "Notification of Event BAN.27

        Message: 'port $1 is not a source routing bridge port'

        Parameters list:
              $1: ban27_bridge_port

        The configured BAN bridge port is not a source routing bridge port."
    ::= { banNotificationsPrefix 27 }

banNotification28 NOTIFICATION-TYPE
    OBJECTS { 
              ban28_bridge_port 
            }
    STATUS current
    DESCRIPTION
        "Notification of Event BAN.28

        Message: 'frame dropped, port $1, port is not initialized'

        Parameters list:
              $1: ban28_bridge_port

        All bridged frames, in and out, are being dropped. The BAN port did not
        initialize."
    ::= { banNotificationsPrefix 28 }

banNotification29 NOTIFICATION-TYPE
    OBJECTS { 
              ban29_bridge_port, 
              ban29_ban_dlci_address 
            }
    STATUS current
    DESCRIPTION
        "Notification of Event BAN.29

        Message: 'port $1, BAN DLCI address $2 is a duplicate with SR-TB enabled'

        Parameters list:
              $1: ban29_bridge_port
              $2: ban29_ban_dlci_address

        When SR-TB conversion is enabled on the bridge, the BAN DLCI MAC address
        of the bridging DLCI must be unique. This restriction does not apply if
        SR-TB is disabled."
    ::= { banNotificationsPrefix 29 }


END
