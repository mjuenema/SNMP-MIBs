-- file automatically created


TELDAT-TRAP-G104-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


g104TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the G104 event subsystem."
    REVISION "201401200930Z"
    DESCRIPTION "Initial implementation"
        ::= { telEventTraps 228 }


g104EventsGroup	OBJECT IDENTIFIER	::= { g104TrapsMIB 1 }

g104Notifications	OBJECT IDENTIFIER	::= { g104TrapsMIB 2 }
g104NotificationsPrefix	OBJECT IDENTIFIER	::= { g104Notifications 0 }

g104EventObjects1 OBJECT-IDENTITY
    STATUS current
    DESCRIPTION
        "Event G104.1
        A TCP Packet has been received."
    ::= { g104EventsGroup 1 }

g1041_message_type OBJECT-TYPE
    SYNTAX DisplayString
    MAX-ACCESS accessible-for-notify
    STATUS current
    DESCRIPTION
        "Parameter 'message_type' in event G104.1"
    ::= { g104EventObjects1 1 }

g1041_bytes OBJECT-TYPE
    SYNTAX Integer32
    MAX-ACCESS accessible-for-notify
    STATUS current
    DESCRIPTION
        "Parameter 'bytes' in event G104.1"
    ::= { g104EventObjects1 2 }

g1041_foreign_host OBJECT-TYPE
    SYNTAX IpAddress
    MAX-ACCESS accessible-for-notify
    STATUS current
    DESCRIPTION
        "Parameter 'foreign_host' in event G104.1"
    ::= { g104EventObjects1 3 }

g1041_remote_port OBJECT-TYPE
    SYNTAX Integer32
    MAX-ACCESS accessible-for-notify
    STATUS current
    DESCRIPTION
        "Parameter 'remote_port' in event G104.1"
    ::= { g104EventObjects1 4 }

g104EventObjects2 OBJECT-IDENTITY
    STATUS current
    DESCRIPTION
        "Event G104.2
        The TCP session has been closed."
    ::= { g104EventsGroup 2 }

g1042_foreign_host OBJECT-TYPE
    SYNTAX IpAddress
    MAX-ACCESS accessible-for-notify
    STATUS current
    DESCRIPTION
        "Parameter 'foreign_host' in event G104.2"
    ::= { g104EventObjects2 1 }

g1042_remote_port OBJECT-TYPE
    SYNTAX Integer32
    MAX-ACCESS accessible-for-notify
    STATUS current
    DESCRIPTION
        "Parameter 'remote_port' in event G104.2"
    ::= { g104EventObjects2 2 }

g104EventObjects3 OBJECT-IDENTITY
    STATUS current
    DESCRIPTION
        "Event G104.3
        The TCP session has been closed by the Remote end."
    ::= { g104EventsGroup 3 }

g1043_foreign_host OBJECT-TYPE
    SYNTAX IpAddress
    MAX-ACCESS accessible-for-notify
    STATUS current
    DESCRIPTION
        "Parameter 'foreign_host' in event G104.3"
    ::= { g104EventObjects3 1 }

g1043_remote_port OBJECT-TYPE
    SYNTAX Integer32
    MAX-ACCESS accessible-for-notify
    STATUS current
    DESCRIPTION
        "Parameter 'remote_port' in event G104.3"
    ::= { g104EventObjects3 2 }

g104EventObjects4 OBJECT-IDENTITY
    STATUS current
    DESCRIPTION
        "Event G104.4
        The TCP session has been opened by the Remote end."
    ::= { g104EventsGroup 4 }

g1044_remote_ip OBJECT-TYPE
    SYNTAX IpAddress
    MAX-ACCESS accessible-for-notify
    STATUS current
    DESCRIPTION
        "Parameter 'remote_ip' in event G104.4"
    ::= { g104EventObjects4 1 }

g1044_remote_port OBJECT-TYPE
    SYNTAX Integer32
    MAX-ACCESS accessible-for-notify
    STATUS current
    DESCRIPTION
        "Parameter 'remote_port' in event G104.4"
    ::= { g104EventObjects4 2 }

g104EventObjects5 OBJECT-IDENTITY
    STATUS current
    DESCRIPTION
        "Event G104.5
        A packet was lost, due TCP Tx overrun error."
    ::= { g104EventsGroup 5 }

g1045_cc_address OBJECT-TYPE
    SYNTAX IpAddress
    MAX-ACCESS accessible-for-notify
    STATUS current
    DESCRIPTION
        "Parameter 'cc_address' in event G104.5"
    ::= { g104EventObjects5 1 }

g104EventObjects6 OBJECT-IDENTITY
    STATUS current
    DESCRIPTION
        "Event G104.6
        A packet was lost, due TCP is closed."
    ::= { g104EventsGroup 6 }

g1046_cc_address OBJECT-TYPE
    SYNTAX IpAddress
    MAX-ACCESS accessible-for-notify
    STATUS current
    DESCRIPTION
        "Parameter 'cc_address' in event G104.6"
    ::= { g104EventObjects6 1 }

g104EventObjects7 OBJECT-IDENTITY
    STATUS current
    DESCRIPTION
        "Event G104.7
        TCP generic event was occurred."
    ::= { g104EventsGroup 7 }

g1047_event OBJECT-TYPE
    SYNTAX DisplayString
    MAX-ACCESS accessible-for-notify
    STATUS current
    DESCRIPTION
        "Parameter 'event' in event G104.7"
    ::= { g104EventObjects7 1 }

g1047_ip OBJECT-TYPE
    SYNTAX IpAddress
    MAX-ACCESS accessible-for-notify
    STATUS current
    DESCRIPTION
        "Parameter 'ip' in event G104.7"
    ::= { g104EventObjects7 2 }

g1047_port OBJECT-TYPE
    SYNTAX Integer32
    MAX-ACCESS accessible-for-notify
    STATUS current
    DESCRIPTION
        "Parameter 'port' in event G104.7"
    ::= { g104EventObjects7 3 }

g104EventObjects8 OBJECT-IDENTITY
    STATUS current
    DESCRIPTION
        "Event G104.8
        An input TCP session has been rejet."
    ::= { g104EventsGroup 8 }

g1048_event OBJECT-TYPE
    SYNTAX DisplayString
    MAX-ACCESS accessible-for-notify
    STATUS current
    DESCRIPTION
        "Parameter 'event' in event G104.8"
    ::= { g104EventObjects8 1 }

g1048_ip OBJECT-TYPE
    SYNTAX IpAddress
    MAX-ACCESS accessible-for-notify
    STATUS current
    DESCRIPTION
        "Parameter 'ip' in event G104.8"
    ::= { g104EventObjects8 2 }

g1048_port OBJECT-TYPE
    SYNTAX Integer32
    MAX-ACCESS accessible-for-notify
    STATUS current
    DESCRIPTION
        "Parameter 'port' in event G104.8"
    ::= { g104EventObjects8 3 }

g104EventObjects9 OBJECT-IDENTITY
    STATUS current
    DESCRIPTION
        "Event G104.9
        Trying to send TCP an I frame to Control Center."
    ::= { g104EventsGroup 9 }

g1049_ns OBJECT-TYPE
    SYNTAX Integer32
    MAX-ACCESS accessible-for-notify
    STATUS current
    DESCRIPTION
        "Parameter 'ns' in event G104.9"
    ::= { g104EventObjects9 1 }

g1049_nr OBJECT-TYPE
    SYNTAX Integer32
    MAX-ACCESS accessible-for-notify
    STATUS current
    DESCRIPTION
        "Parameter 'nr' in event G104.9"
    ::= { g104EventObjects9 2 }

g1049_cc_address OBJECT-TYPE
    SYNTAX IpAddress
    MAX-ACCESS accessible-for-notify
    STATUS current
    DESCRIPTION
        "Parameter 'cc_address' in event G104.9"
    ::= { g104EventObjects9 3 }

g1049_bytes OBJECT-TYPE
    SYNTAX Integer32
    MAX-ACCESS accessible-for-notify
    STATUS current
    DESCRIPTION
        "Parameter 'bytes' in event G104.9"
    ::= { g104EventObjects9 4 }

g104EventObjects10 OBJECT-IDENTITY
    STATUS current
    DESCRIPTION
        "Event G104.10
        Detailed Data send to TCP session."
    ::= { g104EventsGroup 10 }

g10410_ip_address OBJECT-TYPE
    SYNTAX IpAddress
    MAX-ACCESS accessible-for-notify
    STATUS current
    DESCRIPTION
        "Parameter 'ip_address' in event G104.10"
    ::= { g104EventObjects10 1 }

g10410_lenght OBJECT-TYPE
    SYNTAX Integer32
    MAX-ACCESS accessible-for-notify
    STATUS current
    DESCRIPTION
        "Parameter 'lenght' in event G104.10"
    ::= { g104EventObjects10 2 }

g10410_hex_data OBJECT-TYPE
    SYNTAX DisplayString
    MAX-ACCESS accessible-for-notify
    STATUS current
    DESCRIPTION
        "Parameter 'hex_data' in event G104.10"
    ::= { g104EventObjects10 3 }

g104EventObjects11 OBJECT-IDENTITY
    STATUS current
    DESCRIPTION
        "Event G104.11
        Detailed Data received from TCP session."
    ::= { g104EventsGroup 11 }

g10411_ip_address OBJECT-TYPE
    SYNTAX IpAddress
    MAX-ACCESS accessible-for-notify
    STATUS current
    DESCRIPTION
        "Parameter 'ip_address' in event G104.11"
    ::= { g104EventObjects11 1 }

g10411_lenght OBJECT-TYPE
    SYNTAX Integer32
    MAX-ACCESS accessible-for-notify
    STATUS current
    DESCRIPTION
        "Parameter 'lenght' in event G104.11"
    ::= { g104EventObjects11 2 }

g10411_hex_data OBJECT-TYPE
    SYNTAX DisplayString
    MAX-ACCESS accessible-for-notify
    STATUS current
    DESCRIPTION
        "Parameter 'hex_data' in event G104.11"
    ::= { g104EventObjects11 3 }

g104EventObjects12 OBJECT-IDENTITY
    STATUS current
    DESCRIPTION
        "Event G104.12
        Agent IEC-104 protocol START on specified channel."
    ::= { g104EventsGroup 12 }

g10412_agent OBJECT-TYPE
    SYNTAX DisplayString
    MAX-ACCESS accessible-for-notify
    STATUS current
    DESCRIPTION
        "Parameter 'agent' in event G104.12"
    ::= { g104EventObjects12 1 }

g10412_channel OBJECT-TYPE
    SYNTAX Integer32
    MAX-ACCESS accessible-for-notify
    STATUS current
    DESCRIPTION
        "Parameter 'channel' in event G104.12"
    ::= { g104EventObjects12 2 }

g104EventObjects13 OBJECT-IDENTITY
    STATUS current
    DESCRIPTION
        "Event G104.13
        Agent IEC-104 protocol STOPPED on specified channel."
    ::= { g104EventsGroup 13 }

g10413_agent OBJECT-TYPE
    SYNTAX DisplayString
    MAX-ACCESS accessible-for-notify
    STATUS current
    DESCRIPTION
        "Parameter 'agent' in event G104.13"
    ::= { g104EventObjects13 1 }

g10413_channel OBJECT-TYPE
    SYNTAX Integer32
    MAX-ACCESS accessible-for-notify
    STATUS current
    DESCRIPTION
        "Parameter 'channel' in event G104.13"
    ::= { g104EventObjects13 2 }

g104EventObjects14 OBJECT-IDENTITY
    STATUS current
    DESCRIPTION
        "Event G104.14
        Agent IEC-104 start running."
    ::= { g104EventsGroup 14 }

g10414_agent OBJECT-TYPE
    SYNTAX DisplayString
    MAX-ACCESS accessible-for-notify
    STATUS current
    DESCRIPTION
        "Parameter 'agent' in event G104.14"
    ::= { g104EventObjects14 1 }

g104EventObjects15 OBJECT-IDENTITY
    STATUS current
    DESCRIPTION
        "Event G104.15
        Agent IEC-104 stop."
    ::= { g104EventsGroup 15 }

g10415_agent OBJECT-TYPE
    SYNTAX DisplayString
    MAX-ACCESS accessible-for-notify
    STATUS current
    DESCRIPTION
        "Parameter 'agent' in event G104.15"
    ::= { g104EventObjects15 1 }

g104EventObjects16 OBJECT-IDENTITY
    STATUS current
    DESCRIPTION
        "Event G104.16
        An I frame has been received from TCP."
    ::= { g104EventsGroup 16 }

g10416_ns OBJECT-TYPE
    SYNTAX Integer32
    MAX-ACCESS accessible-for-notify
    STATUS current
    DESCRIPTION
        "Parameter 'ns' in event G104.16"
    ::= { g104EventObjects16 1 }

g10416_nr OBJECT-TYPE
    SYNTAX Integer32
    MAX-ACCESS accessible-for-notify
    STATUS current
    DESCRIPTION
        "Parameter 'nr' in event G104.16"
    ::= { g104EventObjects16 2 }

g10416_bytes OBJECT-TYPE
    SYNTAX Integer32
    MAX-ACCESS accessible-for-notify
    STATUS current
    DESCRIPTION
        "Parameter 'bytes' in event G104.16"
    ::= { g104EventObjects16 3 }

g10416_foreign_host OBJECT-TYPE
    SYNTAX IpAddress
    MAX-ACCESS accessible-for-notify
    STATUS current
    DESCRIPTION
        "Parameter 'foreign_host' in event G104.16"
    ::= { g104EventObjects16 4 }

g10416_remote_port OBJECT-TYPE
    SYNTAX Integer32
    MAX-ACCESS accessible-for-notify
    STATUS current
    DESCRIPTION
        "Parameter 'remote_port' in event G104.16"
    ::= { g104EventObjects16 5 }

g104EventObjects17 OBJECT-IDENTITY
    STATUS current
    DESCRIPTION
        "Event G104.17
        An I frame has been received from TCP."
    ::= { g104EventsGroup 17 }

g10417_nr OBJECT-TYPE
    SYNTAX Integer32
    MAX-ACCESS accessible-for-notify
    STATUS current
    DESCRIPTION
        "Parameter 'nr' in event G104.17"
    ::= { g104EventObjects17 1 }

g10417_bytes OBJECT-TYPE
    SYNTAX Integer32
    MAX-ACCESS accessible-for-notify
    STATUS current
    DESCRIPTION
        "Parameter 'bytes' in event G104.17"
    ::= { g104EventObjects17 2 }

g10417_foreign_host OBJECT-TYPE
    SYNTAX IpAddress
    MAX-ACCESS accessible-for-notify
    STATUS current
    DESCRIPTION
        "Parameter 'foreign_host' in event G104.17"
    ::= { g104EventObjects17 3 }

g10417_remote_port OBJECT-TYPE
    SYNTAX Integer32
    MAX-ACCESS accessible-for-notify
    STATUS current
    DESCRIPTION
        "Parameter 'remote_port' in event G104.17"
    ::= { g104EventObjects17 4 }

g104EventObjects18 OBJECT-IDENTITY
    STATUS current
    DESCRIPTION
        "Event G104.18
        Trying to send TCP a S frame to Control Center."
    ::= { g104EventsGroup 18 }

g10418_nr OBJECT-TYPE
    SYNTAX Integer32
    MAX-ACCESS accessible-for-notify
    STATUS current
    DESCRIPTION
        "Parameter 'nr' in event G104.18"
    ::= { g104EventObjects18 1 }

g10418_cc_address OBJECT-TYPE
    SYNTAX IpAddress
    MAX-ACCESS accessible-for-notify
    STATUS current
    DESCRIPTION
        "Parameter 'cc_address' in event G104.18"
    ::= { g104EventObjects18 2 }

g10418_bytes OBJECT-TYPE
    SYNTAX Integer32
    MAX-ACCESS accessible-for-notify
    STATUS current
    DESCRIPTION
        "Parameter 'bytes' in event G104.18"
    ::= { g104EventObjects18 3 }

g104EventObjects19 OBJECT-IDENTITY
    STATUS current
    DESCRIPTION
        "Event G104.19
        Trying to send TCP an U frame to Control Center."
    ::= { g104EventsGroup 19 }

g10419_cc_address OBJECT-TYPE
    SYNTAX IpAddress
    MAX-ACCESS accessible-for-notify
    STATUS current
    DESCRIPTION
        "Parameter 'cc_address' in event G104.19"
    ::= { g104EventObjects19 1 }

g10419_bytes OBJECT-TYPE
    SYNTAX Integer32
    MAX-ACCESS accessible-for-notify
    STATUS current
    DESCRIPTION
        "Parameter 'bytes' in event G104.19"
    ::= { g104EventObjects19 2 }

g104EventObjects20 OBJECT-IDENTITY
    STATUS current
    DESCRIPTION
        "Event G104.20
        The TCP session has been closed by the Local end."
    ::= { g104EventsGroup 20 }

g10420_cause OBJECT-TYPE
    SYNTAX DisplayString
    MAX-ACCESS accessible-for-notify
    STATUS current
    DESCRIPTION
        "Parameter 'cause' in event G104.20"
    ::= { g104EventObjects20 1 }

g10420_foreign_host OBJECT-TYPE
    SYNTAX IpAddress
    MAX-ACCESS accessible-for-notify
    STATUS current
    DESCRIPTION
        "Parameter 'foreign_host' in event G104.20"
    ::= { g104EventObjects20 2 }

g10420_remote_port OBJECT-TYPE
    SYNTAX Integer32
    MAX-ACCESS accessible-for-notify
    STATUS current
    DESCRIPTION
        "Parameter 'remote_port' in event G104.20"
    ::= { g104EventObjects20 3 }


g104Notification1 NOTIFICATION-TYPE
    OBJECTS { 
              g1041_message_type, 
              g1041_bytes,
              g1041_foreign_host,
              g1041_remote_port 
            }
    STATUS current
    DESCRIPTION
        "Notification of Event G104.1

        Message: 'A TCP packet $1 has been received, $2 bytes. rem. IP: $3, Port: $4'

        Parameters list:
              $1: g1041_message_type
              $2: g1041_bytes
              $3: g1041_foreign_host
              $4: g1041_remote_port

        A TCP Packet has been received."
    ::= { g104NotificationsPrefix 1 }

g104Notification2 NOTIFICATION-TYPE
    OBJECTS { 
              g1042_foreign_host, 
              g1042_remote_port 
            }
    STATUS current
    DESCRIPTION
        "Notification of Event G104.2

        Message: 'The TCP session has been closed. rem. IP: $1, Port: $2'

        Parameters list:
              $1: g1042_foreign_host
              $2: g1042_remote_port

        The TCP session has been closed."
    ::= { g104NotificationsPrefix 2 }

g104Notification3 NOTIFICATION-TYPE
    OBJECTS { 
              g1043_foreign_host, 
              g1043_remote_port 
            }
    STATUS current
    DESCRIPTION
        "Notification of Event G104.3

        Message: 'The TCP session has been closed by the Remote end. rem. IP: $1, Port: $2'

        Parameters list:
              $1: g1043_foreign_host
              $2: g1043_remote_port

        The TCP session has been closed by the Remote end."
    ::= { g104NotificationsPrefix 3 }

g104Notification4 NOTIFICATION-TYPE
    OBJECTS { 
              g1044_remote_ip, 
              g1044_remote_port 
            }
    STATUS current
    DESCRIPTION
        "Notification of Event G104.4

        Message: 'The TCP session has been opened by the Remote end. Remote IP:$1 , Port: $2'

        Parameters list:
              $1: g1044_remote_ip
              $2: g1044_remote_port

        The TCP session has been opened by the Remote end."
    ::= { g104NotificationsPrefix 4 }

g104Notification5 NOTIFICATION-TYPE
    OBJECTS { 
              g1045_cc_address 
            }
    STATUS current
    DESCRIPTION
        "Notification of Event G104.5

        Message: 'Packet lost due TCP Tx overrun error. C.C. address $1'

        Parameters list:
              $1: g1045_cc_address

        A packet was lost, due TCP Tx overrun error."
    ::= { g104NotificationsPrefix 5 }

g104Notification6 NOTIFICATION-TYPE
    OBJECTS { 
              g1046_cc_address 
            }
    STATUS current
    DESCRIPTION
        "Notification of Event G104.6

        Message: 'Packet lost due TCP session is closes. C.C IP address $1'

        Parameters list:
              $1: g1046_cc_address

        A packet was lost, due TCP is closed."
    ::= { g104NotificationsPrefix 6 }

g104Notification7 NOTIFICATION-TYPE
    OBJECTS { 
              g1047_event, 
              g1047_ip,
              g1047_port 
            }
    STATUS current
    DESCRIPTION
        "Notification of Event G104.7

        Message: 'The TCP event: $1 . Rem. IP: $2, rem. Port: $3'

        Parameters list:
              $1: g1047_event
              $2: g1047_ip
              $3: g1047_port

        TCP generic event was occurred."
    ::= { g104NotificationsPrefix 7 }

g104Notification8 NOTIFICATION-TYPE
    OBJECTS { 
              g1048_event, 
              g1048_ip,
              g1048_port 
            }
    STATUS current
    DESCRIPTION
        "Notification of Event G104.8

        Message: 'TCP inout session rejet: $1 . Rem. IP: $2, rem. Port: $3'

        Parameters list:
              $1: g1048_event
              $2: g1048_ip
              $3: g1048_port

        An input TCP session has been rejet."
    ::= { g104NotificationsPrefix 8 }

g104Notification9 NOTIFICATION-TYPE
    OBJECTS { 
              g1049_ns, 
              g1049_nr,
              g1049_cc_address,
              g1049_bytes 
            }
    STATUS current
    DESCRIPTION
        "Notification of Event G104.9

        Message: 'Trying to send TCP an I frame(Ns:$1/Nr:$2) to Control Center $3, $4 bytes'

        Parameters list:
              $1: g1049_ns
              $2: g1049_nr
              $3: g1049_cc_address
              $4: g1049_bytes

        Trying to send TCP an I frame to Control Center."
    ::= { g104NotificationsPrefix 9 }

g104Notification10 NOTIFICATION-TYPE
    OBJECTS { 
              g10410_ip_address, 
              g10410_lenght,
              g10410_hex_data 
            }
    STATUS current
    DESCRIPTION
        "Notification of Event G104.10

        Message: 'Data transmitted to TCP session(addr:$1,$2 bytes):$3'

        Parameters list:
              $1: g10410_ip_address
              $2: g10410_lenght
              $3: g10410_hex_data

        Detailed Data send to TCP session."
    ::= { g104NotificationsPrefix 10 }

g104Notification11 NOTIFICATION-TYPE
    OBJECTS { 
              g10411_ip_address, 
              g10411_lenght,
              g10411_hex_data 
            }
    STATUS current
    DESCRIPTION
        "Notification of Event G104.11

        Message: 'Data recived from TCP session(addr:$1,$2 bytes):$3'

        Parameters list:
              $1: g10411_ip_address
              $2: g10411_lenght
              $3: g10411_hex_data

        Detailed Data received from TCP session."
    ::= { g104NotificationsPrefix 11 }

g104Notification12 NOTIFICATION-TYPE
    OBJECTS { 
              g10412_agent, 
              g10412_channel 
            }
    STATUS current
    DESCRIPTION
        "Notification of Event G104.12

        Message: 'Agent IEC-104 $1 START on channel $2'

        Parameters list:
              $1: g10412_agent
              $2: g10412_channel

        Agent IEC-104 protocol START on specified channel."
    ::= { g104NotificationsPrefix 12 }

g104Notification13 NOTIFICATION-TYPE
    OBJECTS { 
              g10413_agent, 
              g10413_channel 
            }
    STATUS current
    DESCRIPTION
        "Notification of Event G104.13

        Message: 'Agent IEC-104 $1 STOPPED on channel $2'

        Parameters list:
              $1: g10413_agent
              $2: g10413_channel

        Agent IEC-104 protocol STOPPED on specified channel."
    ::= { g104NotificationsPrefix 13 }

g104Notification14 NOTIFICATION-TYPE
    OBJECTS { 
              g10414_agent 
            }
    STATUS current
    DESCRIPTION
        "Notification of Event G104.14

        Message: 'Agent IEC-104 $1 is running'

        Parameters list:
              $1: g10414_agent

        Agent IEC-104 start running."
    ::= { g104NotificationsPrefix 14 }

g104Notification15 NOTIFICATION-TYPE
    OBJECTS { 
              g10415_agent 
            }
    STATUS current
    DESCRIPTION
        "Notification of Event G104.15

        Message: 'Agent IEC-104 $1 is not running'

        Parameters list:
              $1: g10415_agent

        Agent IEC-104 stop."
    ::= { g104NotificationsPrefix 15 }

g104Notification16 NOTIFICATION-TYPE
    OBJECTS { 
              g10416_ns, 
              g10416_nr,
              g10416_bytes,
              g10416_foreign_host,
              g10416_remote_port 
            }
    STATUS current
    DESCRIPTION
        "Notification of Event G104.16

        Message: 'A TCP packet with I frame(Ns:$1/Nr:$2) has been received, $3 bytes. rem. IP: $4, Port: $5'

        Parameters list:
              $1: g10416_ns
              $2: g10416_nr
              $3: g10416_bytes
              $4: g10416_foreign_host
              $5: g10416_remote_port

        An I frame has been received from TCP."
    ::= { g104NotificationsPrefix 16 }

g104Notification17 NOTIFICATION-TYPE
    OBJECTS { 
              g10417_nr, 
              g10417_bytes,
              g10417_foreign_host,
              g10417_remote_port 
            }
    STATUS current
    DESCRIPTION
        "Notification of Event G104.17

        Message: 'A TCP packet with I frame(Nr:$1)has been received, $2 bytes. rem. IP: $3, Port: $4'

        Parameters list:
              $1: g10417_nr
              $2: g10417_bytes
              $3: g10417_foreign_host
              $4: g10417_remote_port

        An I frame has been received from TCP."
    ::= { g104NotificationsPrefix 17 }

g104Notification18 NOTIFICATION-TYPE
    OBJECTS { 
              g10418_nr, 
              g10418_cc_address,
              g10418_bytes 
            }
    STATUS current
    DESCRIPTION
        "Notification of Event G104.18

        Message: 'Trying to send TCP a S frame(Nr:$1) to Control Center $2, $3 bytes'

        Parameters list:
              $1: g10418_nr
              $2: g10418_cc_address
              $3: g10418_bytes

        Trying to send TCP a S frame to Control Center."
    ::= { g104NotificationsPrefix 18 }

g104Notification19 NOTIFICATION-TYPE
    OBJECTS { 
              g10419_cc_address, 
              g10419_bytes 
            }
    STATUS current
    DESCRIPTION
        "Notification of Event G104.19

        Message: 'Trying to send TCP an U frame to Control Center $1, $2 bytes'

        Parameters list:
              $1: g10419_cc_address
              $2: g10419_bytes

        Trying to send TCP an U frame to Control Center."
    ::= { g104NotificationsPrefix 19 }

g104Notification20 NOTIFICATION-TYPE
    OBJECTS { 
              g10420_cause, 
              g10420_foreign_host,
              g10420_remote_port 
            }
    STATUS current
    DESCRIPTION
        "Notification of Event G104.20

        Message: 'The TCP session has been closed by the Local end. cause[$1], rem. IP: $2, Port: $3'

        Parameters list:
              $1: g10420_cause
              $2: g10420_foreign_host
              $3: g10420_remote_port

        The TCP session has been closed by the Local end."
    ::= { g104NotificationsPrefix 20 }


END
