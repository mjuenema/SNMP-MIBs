-- file automatically created


TELDAT-TRAP-BR-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


brTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BR event subsystem."
    REVISION "201401200930Z"
    DESCRIPTION "Initial implementation"
        ::= { telEventTraps 74 }


brEventsGroup	OBJECT IDENTIFIER	::= { brTrapsMIB 1 }

brNotifications	OBJECT IDENTIFIER	::= { brTrapsMIB 2 }
brNotificationsPrefix	OBJECT IDENTIFIER	::= { brNotifications 0 }

brEventObjects1 OBJECT-IDENTITY
    STATUS current
    DESCRIPTION
        "Event BR.1
        A MAC frame has been received by the hardware, but is being dropped
        because the port it was received on is in the 'blocking' or 'listening'
        state. Frames are only processed when the port is in the 'learning' or
        'forwarding' state."
    ::= { brEventsGroup 1 }

br1_source_mac OBJECT-TYPE
    SYNTAX DisplayString
    MAX-ACCESS accessible-for-notify
    STATUS current
    DESCRIPTION
        "Parameter 'source_mac' in event BR.1"
    ::= { brEventObjects1 1 }

br1_dest_mac OBJECT-TYPE
    SYNTAX DisplayString
    MAX-ACCESS accessible-for-notify
    STATUS current
    DESCRIPTION
        "Parameter 'dest_mac' in event BR.1"
    ::= { brEventObjects1 2 }

br1_interface OBJECT-TYPE
    SYNTAX DisplayString
    MAX-ACCESS accessible-for-notify
    STATUS current
    DESCRIPTION
        "Parameter 'interface' in event BR.1"
    ::= { brEventObjects1 3 }

brEventObjects2 OBJECT-IDENTITY
    STATUS current
    DESCRIPTION
        "Event BR.2
        A MAC frame has been received whose destination address is known to be
        on the same side of the bridge as the packet came from. It is dropped
        by the filtering logic since it does not need to be bridged. Note that
        this event is not counted by ELS for performance reasons. A counter
        is kept in ASRT, it is the 'Dropped, dest addr filtering' entry in
        the ASRT>LIST SOURCE-ROUTE COUNTERS and ASRT>LIST TRANSPARENT COUNTERS
        commands."
    ::= { brEventsGroup 2 }

br2_source_mac OBJECT-TYPE
    SYNTAX DisplayString
    MAX-ACCESS accessible-for-notify
    STATUS current
    DESCRIPTION
        "Parameter 'source_mac' in event BR.2"
    ::= { brEventObjects2 1 }

br2_dest_mac OBJECT-TYPE
    SYNTAX DisplayString
    MAX-ACCESS accessible-for-notify
    STATUS current
    DESCRIPTION
        "Parameter 'dest_mac' in event BR.2"
    ::= { brEventObjects2 2 }

br2_interface OBJECT-TYPE
    SYNTAX DisplayString
    MAX-ACCESS accessible-for-notify
    STATUS current
    DESCRIPTION
        "Parameter 'interface' in event BR.2"
    ::= { brEventObjects2 3 }

brEventObjects3 OBJECT-IDENTITY
    STATUS current
    DESCRIPTION
        "Event BR.3
        A frame has been received over a WAN interface in the Ethernet bridge
        encapsulation, but the IPX protocol (in 802.3 encapsulation) is routed
        by this node."
    ::= { brEventsGroup 3 }

br3_source_mac OBJECT-TYPE
    SYNTAX DisplayString
    MAX-ACCESS accessible-for-notify
    STATUS current
    DESCRIPTION
        "Parameter 'source_mac' in event BR.3"
    ::= { brEventObjects3 1 }

br3_dest_mac OBJECT-TYPE
    SYNTAX DisplayString
    MAX-ACCESS accessible-for-notify
    STATUS current
    DESCRIPTION
        "Parameter 'dest_mac' in event BR.3"
    ::= { brEventObjects3 2 }

br3_interface OBJECT-TYPE
    SYNTAX DisplayString
    MAX-ACCESS accessible-for-notify
    STATUS current
    DESCRIPTION
        "Parameter 'interface' in event BR.3"
    ::= { brEventObjects3 3 }

brEventObjects4 OBJECT-IDENTITY
    STATUS current
    DESCRIPTION
        "Event BR.4
        A frame has been received for the IPX protocol (in 802.3 encapsulation),
        but the IPX protocol is being administratively filtered by the bridge.
        The frame will be dropped."
    ::= { brEventsGroup 4 }

br4_source_mac OBJECT-TYPE
    SYNTAX DisplayString
    MAX-ACCESS accessible-for-notify
    STATUS current
    DESCRIPTION
        "Parameter 'source_mac' in event BR.4"
    ::= { brEventObjects4 1 }

br4_dest_mac OBJECT-TYPE
    SYNTAX DisplayString
    MAX-ACCESS accessible-for-notify
    STATUS current
    DESCRIPTION
        "Parameter 'dest_mac' in event BR.4"
    ::= { brEventObjects4 2 }

br4_interface OBJECT-TYPE
    SYNTAX DisplayString
    MAX-ACCESS accessible-for-notify
    STATUS current
    DESCRIPTION
        "Parameter 'interface' in event BR.4"
    ::= { brEventObjects4 3 }

brEventObjects5 OBJECT-IDENTITY
    STATUS current
    DESCRIPTION
        "Event BR.5
        A frame has been received for the specified IEEE 802 Subnetwork Access
        Protocol (SNAP) Protocol Identifier (PID), but this PID is being
        administratively filtered by the bridge. The frame will be dropped."
    ::= { brEventsGroup 5 }

br5_source_mac OBJECT-TYPE
    SYNTAX DisplayString
    MAX-ACCESS accessible-for-notify
    STATUS current
    DESCRIPTION
        "Parameter 'source_mac' in event BR.5"
    ::= { brEventObjects5 1 }

br5_dest_mac OBJECT-TYPE
    SYNTAX DisplayString
    MAX-ACCESS accessible-for-notify
    STATUS current
    DESCRIPTION
        "Parameter 'dest_mac' in event BR.5"
    ::= { brEventObjects5 2 }

br5_protocol_identifier OBJECT-TYPE
    SYNTAX Integer32
    MAX-ACCESS accessible-for-notify
    STATUS current
    DESCRIPTION
        "Parameter 'protocol_identifier' in event BR.5"
    ::= { brEventObjects5 3 }

br5_interface OBJECT-TYPE
    SYNTAX DisplayString
    MAX-ACCESS accessible-for-notify
    STATUS current
    DESCRIPTION
        "Parameter 'interface' in event BR.5"
    ::= { brEventObjects5 4 }

brEventObjects6 OBJECT-IDENTITY
    STATUS current
    DESCRIPTION
        "Event BR.6
        A frame has been received for the IEEE 802 Subnetwork Access Protocol
        (SNAP) Protocol Identifier (PID) which corresponds with an enabled
        protocol, but the destination MAC address is not registered
        in the bridge. The frame will be dropped."
    ::= { brEventsGroup 6 }

br6_source_mac OBJECT-TYPE
    SYNTAX DisplayString
    MAX-ACCESS accessible-for-notify
    STATUS current
    DESCRIPTION
        "Parameter 'source_mac' in event BR.6"
    ::= { brEventObjects6 1 }

br6_dest_mac OBJECT-TYPE
    SYNTAX DisplayString
    MAX-ACCESS accessible-for-notify
    STATUS current
    DESCRIPTION
        "Parameter 'dest_mac' in event BR.6"
    ::= { brEventObjects6 2 }

br6_protocol_identifier OBJECT-TYPE
    SYNTAX Integer32
    MAX-ACCESS accessible-for-notify
    STATUS current
    DESCRIPTION
        "Parameter 'protocol_identifier' in event BR.6"
    ::= { brEventObjects6 3 }

br6_interface OBJECT-TYPE
    SYNTAX DisplayString
    MAX-ACCESS accessible-for-notify
    STATUS current
    DESCRIPTION
        "Parameter 'interface' in event BR.6"
    ::= { brEventObjects6 4 }

brEventObjects7 OBJECT-IDENTITY
    STATUS current
    DESCRIPTION
        "Event BR.7
        A multicast frame has been received for the IEEE 802 Subnetwork Access
        Protocol (SNAP) Protocol Identifier (PID) which corresponds with
        an endnode protocol. The frame will be both bridged and
        locally processed by the endnode protocol."
    ::= { brEventsGroup 7 }

br7_source_mac OBJECT-TYPE
    SYNTAX DisplayString
    MAX-ACCESS accessible-for-notify
    STATUS current
    DESCRIPTION
        "Parameter 'source_mac' in event BR.7"
    ::= { brEventObjects7 1 }

br7_dest_mac OBJECT-TYPE
    SYNTAX DisplayString
    MAX-ACCESS accessible-for-notify
    STATUS current
    DESCRIPTION
        "Parameter 'dest_mac' in event BR.7"
    ::= { brEventObjects7 2 }

br7_protocol_identifier OBJECT-TYPE
    SYNTAX Integer32
    MAX-ACCESS accessible-for-notify
    STATUS current
    DESCRIPTION
        "Parameter 'protocol_identifier' in event BR.7"
    ::= { brEventObjects7 3 }

br7_interface OBJECT-TYPE
    SYNTAX DisplayString
    MAX-ACCESS accessible-for-notify
    STATUS current
    DESCRIPTION
        "Parameter 'interface' in event BR.7"
    ::= { brEventObjects7 4 }

brEventObjects8 OBJECT-IDENTITY
    STATUS current
    DESCRIPTION
        "Event BR.8
        An IEEE 802.2 frame has been received over a WAN interface in a bridge
        encapsulation, but its IEEE 802 Subnetwork Access Protocol (SNAP)
        Protocol Identifier (PID) is one that is being routed by this node.
        The frame will be dropped."
    ::= { brEventsGroup 8 }

br8_source_mac OBJECT-TYPE
    SYNTAX DisplayString
    MAX-ACCESS accessible-for-notify
    STATUS current
    DESCRIPTION
        "Parameter 'source_mac' in event BR.8"
    ::= { brEventObjects8 1 }

br8_dest_mac OBJECT-TYPE
    SYNTAX DisplayString
    MAX-ACCESS accessible-for-notify
    STATUS current
    DESCRIPTION
        "Parameter 'dest_mac' in event BR.8"
    ::= { brEventObjects8 2 }

br8_protocol_identifier OBJECT-TYPE
    SYNTAX Integer32
    MAX-ACCESS accessible-for-notify
    STATUS current
    DESCRIPTION
        "Parameter 'protocol_identifier' in event BR.8"
    ::= { brEventObjects8 3 }

br8_interface OBJECT-TYPE
    SYNTAX DisplayString
    MAX-ACCESS accessible-for-notify
    STATUS current
    DESCRIPTION
        "Parameter 'interface' in event BR.8"
    ::= { brEventObjects8 4 }

brEventObjects9 OBJECT-IDENTITY
    STATUS current
    DESCRIPTION
        "Event BR.9
        An IEEE 802.1D Bridge Protocol Data Unit (BPDU) was received at
        the wrong destination address. It is supposed to be addressed to
        a particular multicast address. The BPDU will be dropped."
    ::= { brEventsGroup 9 }

br9_source_mac OBJECT-TYPE
    SYNTAX DisplayString
    MAX-ACCESS accessible-for-notify
    STATUS current
    DESCRIPTION
        "Parameter 'source_mac' in event BR.9"
    ::= { brEventObjects9 1 }

br9_dest_mac OBJECT-TYPE
    SYNTAX DisplayString
    MAX-ACCESS accessible-for-notify
    STATUS current
    DESCRIPTION
        "Parameter 'dest_mac' in event BR.9"
    ::= { brEventObjects9 2 }

br9_interface OBJECT-TYPE
    SYNTAX DisplayString
    MAX-ACCESS accessible-for-notify
    STATUS current
    DESCRIPTION
        "Parameter 'interface' in event BR.9"
    ::= { brEventObjects9 3 }

brEventObjects10 OBJECT-IDENTITY
    STATUS current
    DESCRIPTION
        "Event BR.10
        A frame has been received for the specified IEEE 802.2 Destination
        Service Access Point (DSAP), but this DSAP is being administratively
        filtered by the bridge. The frame will be dropped."
    ::= { brEventsGroup 10 }

br10_source_mac OBJECT-TYPE
    SYNTAX DisplayString
    MAX-ACCESS accessible-for-notify
    STATUS current
    DESCRIPTION
        "Parameter 'source_mac' in event BR.10"
    ::= { brEventObjects10 1 }

br10_dest_mac OBJECT-TYPE
    SYNTAX DisplayString
    MAX-ACCESS accessible-for-notify
    STATUS current
    DESCRIPTION
        "Parameter 'dest_mac' in event BR.10"
    ::= { brEventObjects10 2 }

br10_destination_service_access_point OBJECT-TYPE
    SYNTAX Integer32
    MAX-ACCESS accessible-for-notify
    STATUS current
    DESCRIPTION
        "Parameter 'destination_service_access_point' in event BR.10"
    ::= { brEventObjects10 3 }

br10_interface OBJECT-TYPE
    SYNTAX DisplayString
    MAX-ACCESS accessible-for-notify
    STATUS current
    DESCRIPTION
        "Parameter 'interface' in event BR.10"
    ::= { brEventObjects10 4 }

brEventObjects11 OBJECT-IDENTITY
    STATUS current
    DESCRIPTION
        "Event BR.11
        A frame has been received for the IEEE 802.2 Destination Service Access
        Point (DSAP) which corresponds with an enabled protocol, but
        the destination MAC address is not registered in the bridge.
        The frame will be dropped."
    ::= { brEventsGroup 11 }

br11_source_mac OBJECT-TYPE
    SYNTAX DisplayString
    MAX-ACCESS accessible-for-notify
    STATUS current
    DESCRIPTION
        "Parameter 'source_mac' in event BR.11"
    ::= { brEventObjects11 1 }

br11_dest_mac OBJECT-TYPE
    SYNTAX DisplayString
    MAX-ACCESS accessible-for-notify
    STATUS current
    DESCRIPTION
        "Parameter 'dest_mac' in event BR.11"
    ::= { brEventObjects11 2 }

br11_destination_service_access_point OBJECT-TYPE
    SYNTAX Integer32
    MAX-ACCESS accessible-for-notify
    STATUS current
    DESCRIPTION
        "Parameter 'destination_service_access_point' in event BR.11"
    ::= { brEventObjects11 3 }

br11_interface OBJECT-TYPE
    SYNTAX DisplayString
    MAX-ACCESS accessible-for-notify
    STATUS current
    DESCRIPTION
        "Parameter 'interface' in event BR.11"
    ::= { brEventObjects11 4 }

brEventObjects12 OBJECT-IDENTITY
    STATUS current
    DESCRIPTION
        "Event BR.12
        A multicast frame has been received for the IEEE 802.2 Destination
        Service Access Point (DSAP) which corresponds with an endnode protocol.
        The frame will be both bridged and locally processed by
        the endnode protocol."
    ::= { brEventsGroup 12 }

br12_source_mac OBJECT-TYPE
    SYNTAX DisplayString
    MAX-ACCESS accessible-for-notify
    STATUS current
    DESCRIPTION
        "Parameter 'source_mac' in event BR.12"
    ::= { brEventObjects12 1 }

br12_dest_mac OBJECT-TYPE
    SYNTAX DisplayString
    MAX-ACCESS accessible-for-notify
    STATUS current
    DESCRIPTION
        "Parameter 'dest_mac' in event BR.12"
    ::= { brEventObjects12 2 }

br12_destination_service_access_point OBJECT-TYPE
    SYNTAX Integer32
    MAX-ACCESS accessible-for-notify
    STATUS current
    DESCRIPTION
        "Parameter 'destination_service_access_point' in event BR.12"
    ::= { brEventObjects12 3 }

br12_interface OBJECT-TYPE
    SYNTAX DisplayString
    MAX-ACCESS accessible-for-notify
    STATUS current
    DESCRIPTION
        "Parameter 'interface' in event BR.12"
    ::= { brEventObjects12 4 }

brEventObjects13 OBJECT-IDENTITY
    STATUS current
    DESCRIPTION
        "Event BR.13
        An IEEE 802.2 frame has been received over a WAN interface in a bridge
        encapsulation, but its IEEE 802.2 Destination Service Access Point
        (DSAP) is one that is being routed by this node. The frame will be
        dropped."
    ::= { brEventsGroup 13 }

br13_source_mac OBJECT-TYPE
    SYNTAX DisplayString
    MAX-ACCESS accessible-for-notify
    STATUS current
    DESCRIPTION
        "Parameter 'source_mac' in event BR.13"
    ::= { brEventObjects13 1 }

br13_dest_mac OBJECT-TYPE
    SYNTAX DisplayString
    MAX-ACCESS accessible-for-notify
    STATUS current
    DESCRIPTION
        "Parameter 'dest_mac' in event BR.13"
    ::= { brEventObjects13 2 }

br13_destination_service_access_point OBJECT-TYPE
    SYNTAX Integer32
    MAX-ACCESS accessible-for-notify
    STATUS current
    DESCRIPTION
        "Parameter 'destination_service_access_point' in event BR.13"
    ::= { brEventObjects13 3 }

br13_interface OBJECT-TYPE
    SYNTAX DisplayString
    MAX-ACCESS accessible-for-notify
    STATUS current
    DESCRIPTION
        "Parameter 'interface' in event BR.13"
    ::= { brEventObjects13 4 }

brEventObjects14 OBJECT-IDENTITY
    STATUS current
    DESCRIPTION
        "Event BR.14
        A frame has been received for the specified Ethernet type, but this type
        is being administratively filtered by the bridge. The frame will be
        dropped."
    ::= { brEventsGroup 14 }

br14_source_mac OBJECT-TYPE
    SYNTAX DisplayString
    MAX-ACCESS accessible-for-notify
    STATUS current
    DESCRIPTION
        "Parameter 'source_mac' in event BR.14"
    ::= { brEventObjects14 1 }

br14_dest_mac OBJECT-TYPE
    SYNTAX DisplayString
    MAX-ACCESS accessible-for-notify
    STATUS current
    DESCRIPTION
        "Parameter 'dest_mac' in event BR.14"
    ::= { brEventObjects14 2 }

br14_Ethernet_type OBJECT-TYPE
    SYNTAX Integer32
    MAX-ACCESS accessible-for-notify
    STATUS current
    DESCRIPTION
        "Parameter 'Ethernet_type' in event BR.14"
    ::= { brEventObjects14 3 }

br14_interface OBJECT-TYPE
    SYNTAX DisplayString
    MAX-ACCESS accessible-for-notify
    STATUS current
    DESCRIPTION
        "Parameter 'interface' in event BR.14"
    ::= { brEventObjects14 4 }

brEventObjects15 OBJECT-IDENTITY
    STATUS current
    DESCRIPTION
        "Event BR.15
        A frame has been received for the Ethernet type which corresponds with
        an enabled protocol, but the destination MAC address is not registered
        in the bridge. The frame will be dropped."
    ::= { brEventsGroup 15 }

br15_source_mac OBJECT-TYPE
    SYNTAX DisplayString
    MAX-ACCESS accessible-for-notify
    STATUS current
    DESCRIPTION
        "Parameter 'source_mac' in event BR.15"
    ::= { brEventObjects15 1 }

br15_dest_mac OBJECT-TYPE
    SYNTAX DisplayString
    MAX-ACCESS accessible-for-notify
    STATUS current
    DESCRIPTION
        "Parameter 'dest_mac' in event BR.15"
    ::= { brEventObjects15 2 }

br15_Ethernet_type OBJECT-TYPE
    SYNTAX Integer32
    MAX-ACCESS accessible-for-notify
    STATUS current
    DESCRIPTION
        "Parameter 'Ethernet_type' in event BR.15"
    ::= { brEventObjects15 3 }

br15_interface OBJECT-TYPE
    SYNTAX DisplayString
    MAX-ACCESS accessible-for-notify
    STATUS current
    DESCRIPTION
        "Parameter 'interface' in event BR.15"
    ::= { brEventObjects15 4 }

brEventObjects16 OBJECT-IDENTITY
    STATUS current
    DESCRIPTION
        "Event BR.16
        A multicast frame has been received for the Ethernet type which
        corresponds with an endnode protocol. The frame will be both bridged
        and locally processed by the endnode protocol."
    ::= { brEventsGroup 16 }

br16_source_mac OBJECT-TYPE
    SYNTAX DisplayString
    MAX-ACCESS accessible-for-notify
    STATUS current
    DESCRIPTION
        "Parameter 'source_mac' in event BR.16"
    ::= { brEventObjects16 1 }

br16_dest_mac OBJECT-TYPE
    SYNTAX DisplayString
    MAX-ACCESS accessible-for-notify
    STATUS current
    DESCRIPTION
        "Parameter 'dest_mac' in event BR.16"
    ::= { brEventObjects16 2 }

br16_Ethernet_type OBJECT-TYPE
    SYNTAX Integer32
    MAX-ACCESS accessible-for-notify
    STATUS current
    DESCRIPTION
        "Parameter 'Ethernet_type' in event BR.16"
    ::= { brEventObjects16 3 }

br16_interface OBJECT-TYPE
    SYNTAX DisplayString
    MAX-ACCESS accessible-for-notify
    STATUS current
    DESCRIPTION
        "Parameter 'interface' in event BR.16"
    ::= { brEventObjects16 4 }

brEventObjects17 OBJECT-IDENTITY
    STATUS current
    DESCRIPTION
        "Event BR.17
        An Ethernet frame has been received over a WAN interface in the Ethernet
        bridge encapsulation, but its Ethernet type is one that is being routed
        by this node. The frame will be dropped."
    ::= { brEventsGroup 17 }

br17_source_mac OBJECT-TYPE
    SYNTAX DisplayString
    MAX-ACCESS accessible-for-notify
    STATUS current
    DESCRIPTION
        "Parameter 'source_mac' in event BR.17"
    ::= { brEventObjects17 1 }

br17_dest_mac OBJECT-TYPE
    SYNTAX DisplayString
    MAX-ACCESS accessible-for-notify
    STATUS current
    DESCRIPTION
        "Parameter 'dest_mac' in event BR.17"
    ::= { brEventObjects17 2 }

br17_Ethernet_type OBJECT-TYPE
    SYNTAX Integer32
    MAX-ACCESS accessible-for-notify
    STATUS current
    DESCRIPTION
        "Parameter 'Ethernet_type' in event BR.17"
    ::= { brEventObjects17 3 }

br17_interface OBJECT-TYPE
    SYNTAX DisplayString
    MAX-ACCESS accessible-for-notify
    STATUS current
    DESCRIPTION
        "Parameter 'interface' in event BR.17"
    ::= { brEventObjects17 4 }

brEventObjects18 OBJECT-IDENTITY
    STATUS current
    DESCRIPTION
        "Event BR.18
        A source-routed frame has been received for the specified IEEE 802.2
        Destination Service Access Point (DSAP), but this DSAP is being
        administratively filtered by the bridge. The frame will be dropped."
    ::= { brEventsGroup 18 }

br18_source_mac OBJECT-TYPE
    SYNTAX DisplayString
    MAX-ACCESS accessible-for-notify
    STATUS current
    DESCRIPTION
        "Parameter 'source_mac' in event BR.18"
    ::= { brEventObjects18 1 }

br18_dest_mac OBJECT-TYPE
    SYNTAX DisplayString
    MAX-ACCESS accessible-for-notify
    STATUS current
    DESCRIPTION
        "Parameter 'dest_mac' in event BR.18"
    ::= { brEventObjects18 2 }

br18_destination_service_access_point OBJECT-TYPE
    SYNTAX Integer32
    MAX-ACCESS accessible-for-notify
    STATUS current
    DESCRIPTION
        "Parameter 'destination_service_access_point' in event BR.18"
    ::= { brEventObjects18 3 }

br18_interface OBJECT-TYPE
    SYNTAX DisplayString
    MAX-ACCESS accessible-for-notify
    STATUS current
    DESCRIPTION
        "Parameter 'interface' in event BR.18"
    ::= { brEventObjects18 4 }

brEventObjects19 OBJECT-IDENTITY
    STATUS current
    DESCRIPTION
        "Event BR.19
        A source-routed frame has been received for the IEEE 802.2 Destination
        Service Access Point (DSAP) which corresponds with an enabled protocol,
        but the destination MAC address is not registered in the bridge.
        The frame will be dropped."
    ::= { brEventsGroup 19 }

br19_source_mac OBJECT-TYPE
    SYNTAX DisplayString
    MAX-ACCESS accessible-for-notify
    STATUS current
    DESCRIPTION
        "Parameter 'source_mac' in event BR.19"
    ::= { brEventObjects19 1 }

br19_dest_mac OBJECT-TYPE
    SYNTAX DisplayString
    MAX-ACCESS accessible-for-notify
    STATUS current
    DESCRIPTION
        "Parameter 'dest_mac' in event BR.19"
    ::= { brEventObjects19 2 }

br19_destination_service_access_point OBJECT-TYPE
    SYNTAX Integer32
    MAX-ACCESS accessible-for-notify
    STATUS current
    DESCRIPTION
        "Parameter 'destination_service_access_point' in event BR.19"
    ::= { brEventObjects19 3 }

br19_interface OBJECT-TYPE
    SYNTAX DisplayString
    MAX-ACCESS accessible-for-notify
    STATUS current
    DESCRIPTION
        "Parameter 'interface' in event BR.19"
    ::= { brEventObjects19 4 }

brEventObjects20 OBJECT-IDENTITY
    STATUS current
    DESCRIPTION
        "Event BR.20
        A multicast source-routed frame has been received for the IEEE 802.2
        Destination Service Access Point (DSAP) which corresponds with
        an endnode protocol. The frame will be both bridged and
        locally processed by the endnode protocol."
    ::= { brEventsGroup 20 }

br20_source_mac OBJECT-TYPE
    SYNTAX DisplayString
    MAX-ACCESS accessible-for-notify
    STATUS current
    DESCRIPTION
        "Parameter 'source_mac' in event BR.20"
    ::= { brEventObjects20 1 }

br20_dest_mac OBJECT-TYPE
    SYNTAX DisplayString
    MAX-ACCESS accessible-for-notify
    STATUS current
    DESCRIPTION
        "Parameter 'dest_mac' in event BR.20"
    ::= { brEventObjects20 2 }

br20_destination_service_access_point OBJECT-TYPE
    SYNTAX Integer32
    MAX-ACCESS accessible-for-notify
    STATUS current
    DESCRIPTION
        "Parameter 'destination_service_access_point' in event BR.20"
    ::= { brEventObjects20 3 }

br20_interface OBJECT-TYPE
    SYNTAX DisplayString
    MAX-ACCESS accessible-for-notify
    STATUS current
    DESCRIPTION
        "Parameter 'interface' in event BR.20"
    ::= { brEventObjects20 4 }

brEventObjects21 OBJECT-IDENTITY
    STATUS current
    DESCRIPTION
        "Event BR.21
        A source-routed frame has been received for the specified IEEE 802
        Subnetwork Access Protocol (SNAP) Protocol Identifier (PID), but
        this PID is being administratively filtered by the bridge. The frame
        will be dropped."
    ::= { brEventsGroup 21 }

br21_source_mac OBJECT-TYPE
    SYNTAX DisplayString
    MAX-ACCESS accessible-for-notify
    STATUS current
    DESCRIPTION
        "Parameter 'source_mac' in event BR.21"
    ::= { brEventObjects21 1 }

br21_dest_mac OBJECT-TYPE
    SYNTAX DisplayString
    MAX-ACCESS accessible-for-notify
    STATUS current
    DESCRIPTION
        "Parameter 'dest_mac' in event BR.21"
    ::= { brEventObjects21 2 }

br21_protocol_identifier OBJECT-TYPE
    SYNTAX Integer32
    MAX-ACCESS accessible-for-notify
    STATUS current
    DESCRIPTION
        "Parameter 'protocol_identifier' in event BR.21"
    ::= { brEventObjects21 3 }

br21_interface OBJECT-TYPE
    SYNTAX DisplayString
    MAX-ACCESS accessible-for-notify
    STATUS current
    DESCRIPTION
        "Parameter 'interface' in event BR.21"
    ::= { brEventObjects21 4 }

brEventObjects22 OBJECT-IDENTITY
    STATUS current
    DESCRIPTION
        "Event BR.22
        A source-routed frame has been received for the IEEE 802 Subnetwork
        Access Protocol (SNAP) Protocol Identifier (PID) which corresponds with
        an enabled protocol, but the destination MAC address is not registered
        in the bridge. The frame will be dropped."
    ::= { brEventsGroup 22 }

br22_source_mac OBJECT-TYPE
    SYNTAX DisplayString
    MAX-ACCESS accessible-for-notify
    STATUS current
    DESCRIPTION
        "Parameter 'source_mac' in event BR.22"
    ::= { brEventObjects22 1 }

br22_dest_mac OBJECT-TYPE
    SYNTAX DisplayString
    MAX-ACCESS accessible-for-notify
    STATUS current
    DESCRIPTION
        "Parameter 'dest_mac' in event BR.22"
    ::= { brEventObjects22 2 }

br22_protocol_identifier OBJECT-TYPE
    SYNTAX Integer32
    MAX-ACCESS accessible-for-notify
    STATUS current
    DESCRIPTION
        "Parameter 'protocol_identifier' in event BR.22"
    ::= { brEventObjects22 3 }

br22_interface OBJECT-TYPE
    SYNTAX DisplayString
    MAX-ACCESS accessible-for-notify
    STATUS current
    DESCRIPTION
        "Parameter 'interface' in event BR.22"
    ::= { brEventObjects22 4 }

brEventObjects23 OBJECT-IDENTITY
    STATUS current
    DESCRIPTION
        "Event BR.23
        SA source-routed multicast frame has been received for the IEEE 802
        Subnetwork Access Protocol (SNAP) Protocol Identifier (PID) which
        corresponds with an endnode protocol. The frame will be both bridged
        and locally processed by the endnode protocol."
    ::= { brEventsGroup 23 }

br23_source_mac OBJECT-TYPE
    SYNTAX DisplayString
    MAX-ACCESS accessible-for-notify
    STATUS current
    DESCRIPTION
        "Parameter 'source_mac' in event BR.23"
    ::= { brEventObjects23 1 }

br23_dest_mac OBJECT-TYPE
    SYNTAX DisplayString
    MAX-ACCESS accessible-for-notify
    STATUS current
    DESCRIPTION
        "Parameter 'dest_mac' in event BR.23"
    ::= { brEventObjects23 2 }

br23_protocol_identifier OBJECT-TYPE
    SYNTAX Integer32
    MAX-ACCESS accessible-for-notify
    STATUS current
    DESCRIPTION
        "Parameter 'protocol_identifier' in event BR.23"
    ::= { brEventObjects23 3 }

br23_interface OBJECT-TYPE
    SYNTAX DisplayString
    MAX-ACCESS accessible-for-notify
    STATUS current
    DESCRIPTION
        "Parameter 'interface' in event BR.23"
    ::= { brEventObjects23 4 }

brEventObjects24 OBJECT-IDENTITY
    STATUS current
    DESCRIPTION
        "Event BR.24
        A vlan frame has been received whose virtual lan id is not supported.
        Frame is dropped."
    ::= { brEventsGroup 24 }

br24_vlan_id OBJECT-TYPE
    SYNTAX Integer32
    MAX-ACCESS accessible-for-notify
    STATUS current
    DESCRIPTION
        "Parameter 'vlan_id' in event BR.24"
    ::= { brEventObjects24 1 }

br24_interface OBJECT-TYPE
    SYNTAX DisplayString
    MAX-ACCESS accessible-for-notify
    STATUS current
    DESCRIPTION
        "Parameter 'interface' in event BR.24"
    ::= { brEventObjects24 2 }

brEventObjects26 OBJECT-IDENTITY
    STATUS current
    DESCRIPTION
        "Event BR.26
        A source-routed MAC frame has been received by the hardware, but
        is being dropped because the destination MAC address is being
        administratively filtered by the bridge. The frame will be dropped."
    ::= { brEventsGroup 26 }

br26_source_mac OBJECT-TYPE
    SYNTAX DisplayString
    MAX-ACCESS accessible-for-notify
    STATUS current
    DESCRIPTION
        "Parameter 'source_mac' in event BR.26"
    ::= { brEventObjects26 1 }

br26_dest_mac OBJECT-TYPE
    SYNTAX DisplayString
    MAX-ACCESS accessible-for-notify
    STATUS current
    DESCRIPTION
        "Parameter 'dest_mac' in event BR.26"
    ::= { brEventObjects26 2 }

br26_interface OBJECT-TYPE
    SYNTAX DisplayString
    MAX-ACCESS accessible-for-notify
    STATUS current
    DESCRIPTION
        "Parameter 'interface' in event BR.26"
    ::= { brEventObjects26 3 }

brEventObjects27 OBJECT-IDENTITY
    STATUS current
    DESCRIPTION
        "Event BR.27
        A source-routed MAC frame has been received by the hardware, but
        is being dropped because the source MAC address is being
        administratively filtered by the bridge. The frame will be dropped."
    ::= { brEventsGroup 27 }

br27_source_mac OBJECT-TYPE
    SYNTAX DisplayString
    MAX-ACCESS accessible-for-notify
    STATUS current
    DESCRIPTION
        "Parameter 'source_mac' in event BR.27"
    ::= { brEventObjects27 1 }

br27_dest_mac OBJECT-TYPE
    SYNTAX DisplayString
    MAX-ACCESS accessible-for-notify
    STATUS current
    DESCRIPTION
        "Parameter 'dest_mac' in event BR.27"
    ::= { brEventObjects27 2 }

br27_interface OBJECT-TYPE
    SYNTAX DisplayString
    MAX-ACCESS accessible-for-notify
    STATUS current
    DESCRIPTION
        "Parameter 'interface' in event BR.27"
    ::= { brEventObjects27 3 }

brEventObjects28 OBJECT-IDENTITY
    STATUS current
    DESCRIPTION
        "Event BR.28
        A multicast frame has been received for an endnode protocol that is
        both bridged and locally processed. There was no buffer to make
        two copies of the frame for both types of processing, so it will not be
        bridged, only locally processed."
    ::= { brEventsGroup 28 }

br28_source_mac OBJECT-TYPE
    SYNTAX DisplayString
    MAX-ACCESS accessible-for-notify
    STATUS current
    DESCRIPTION
        "Parameter 'source_mac' in event BR.28"
    ::= { brEventObjects28 1 }

br28_dest_mac OBJECT-TYPE
    SYNTAX DisplayString
    MAX-ACCESS accessible-for-notify
    STATUS current
    DESCRIPTION
        "Parameter 'dest_mac' in event BR.28"
    ::= { brEventObjects28 2 }

br28_interface OBJECT-TYPE
    SYNTAX DisplayString
    MAX-ACCESS accessible-for-notify
    STATUS current
    DESCRIPTION
        "Parameter 'interface' in event BR.28"
    ::= { brEventObjects28 3 }

brEventObjects29 OBJECT-IDENTITY
    STATUS current
    DESCRIPTION
        "Event BR.29
        A NETBIOS packet has matched the criteria specified in a NETBIOS Filter
        configuration record. The packet is dropped."
    ::= { brEventsGroup 29 }

br29_source_mac OBJECT-TYPE
    SYNTAX DisplayString
    MAX-ACCESS accessible-for-notify
    STATUS current
    DESCRIPTION
        "Parameter 'source_mac' in event BR.29"
    ::= { brEventObjects29 1 }

br29_dest_mac OBJECT-TYPE
    SYNTAX DisplayString
    MAX-ACCESS accessible-for-notify
    STATUS current
    DESCRIPTION
        "Parameter 'dest_mac' in event BR.29"
    ::= { brEventObjects29 2 }

br29_port OBJECT-TYPE
    SYNTAX Integer32
    MAX-ACCESS accessible-for-notify
    STATUS current
    DESCRIPTION
        "Parameter 'port' in event BR.29"
    ::= { brEventObjects29 3 }

br29_interface OBJECT-TYPE
    SYNTAX DisplayString
    MAX-ACCESS accessible-for-notify
    STATUS current
    DESCRIPTION
        "Parameter 'interface' in event BR.29"
    ::= { brEventObjects29 4 }

brEventObjects30 OBJECT-IDENTITY
    STATUS current
    DESCRIPTION
        "Event BR.30
        The MAC address of a BVI interface has been updated"
    ::= { brEventsGroup 30 }

br30_interface OBJECT-TYPE
    SYNTAX DisplayString
    MAX-ACCESS accessible-for-notify
    STATUS current
    DESCRIPTION
        "Parameter 'interface' in event BR.30"
    ::= { brEventObjects30 1 }

br30_new_mac OBJECT-TYPE
    SYNTAX DisplayString
    MAX-ACCESS accessible-for-notify
    STATUS current
    DESCRIPTION
        "Parameter 'new_mac' in event BR.30"
    ::= { brEventObjects30 2 }

brEventObjects31 OBJECT-IDENTITY
    STATUS current
    DESCRIPTION
        "Event BR.31
        A frame is going to be output to the bridge through a BVI interface."
    ::= { brEventsGroup 31 }

br31_interface OBJECT-TYPE
    SYNTAX DisplayString
    MAX-ACCESS accessible-for-notify
    STATUS current
    DESCRIPTION
        "Parameter 'interface' in event BR.31"
    ::= { brEventObjects31 1 }

br31_source_mac OBJECT-TYPE
    SYNTAX DisplayString
    MAX-ACCESS accessible-for-notify
    STATUS current
    DESCRIPTION
        "Parameter 'source_mac' in event BR.31"
    ::= { brEventObjects31 2 }

br31_dest_mac OBJECT-TYPE
    SYNTAX DisplayString
    MAX-ACCESS accessible-for-notify
    STATUS current
    DESCRIPTION
        "Parameter 'dest_mac' in event BR.31"
    ::= { brEventObjects31 3 }

br31_protocol OBJECT-TYPE
    SYNTAX Integer32
    MAX-ACCESS accessible-for-notify
    STATUS current
    DESCRIPTION
        "Parameter 'protocol' in event BR.31"
    ::= { brEventObjects31 4 }

brEventObjects32 OBJECT-IDENTITY
    STATUS current
    DESCRIPTION
        "Event BR.32
        A frame has been received in a BVI interface."
    ::= { brEventsGroup 32 }

br32_interface OBJECT-TYPE
    SYNTAX DisplayString
    MAX-ACCESS accessible-for-notify
    STATUS current
    DESCRIPTION
        "Parameter 'interface' in event BR.32"
    ::= { brEventObjects32 1 }

br32_source_mac OBJECT-TYPE
    SYNTAX DisplayString
    MAX-ACCESS accessible-for-notify
    STATUS current
    DESCRIPTION
        "Parameter 'source_mac' in event BR.32"
    ::= { brEventObjects32 2 }

br32_dest_mac OBJECT-TYPE
    SYNTAX DisplayString
    MAX-ACCESS accessible-for-notify
    STATUS current
    DESCRIPTION
        "Parameter 'dest_mac' in event BR.32"
    ::= { brEventObjects32 3 }

br32_protocol OBJECT-TYPE
    SYNTAX Integer32
    MAX-ACCESS accessible-for-notify
    STATUS current
    DESCRIPTION
        "Parameter 'protocol' in event BR.32"
    ::= { brEventObjects32 4 }

brEventObjects33 OBJECT-IDENTITY
    STATUS current
    DESCRIPTION
        "Event BR.33
        A frame is droped because BVI interface is down"
    ::= { brEventsGroup 33 }

br33_interface OBJECT-TYPE
    SYNTAX DisplayString
    MAX-ACCESS accessible-for-notify
    STATUS current
    DESCRIPTION
        "Parameter 'interface' in event BR.33"
    ::= { brEventObjects33 1 }

brEventObjects34 OBJECT-IDENTITY
    STATUS current
    DESCRIPTION
        "Event BR.34
        A frame is dropped because destination IP has no registered MAC address."
    ::= { brEventsGroup 34 }

br34_interface OBJECT-TYPE
    SYNTAX DisplayString
    MAX-ACCESS accessible-for-notify
    STATUS current
    DESCRIPTION
        "Parameter 'interface' in event BR.34"
    ::= { brEventObjects34 1 }

br34_source_mac OBJECT-TYPE
    SYNTAX DisplayString
    MAX-ACCESS accessible-for-notify
    STATUS current
    DESCRIPTION
        "Parameter 'source_mac' in event BR.34"
    ::= { brEventObjects34 2 }

br34_dest_IP_address OBJECT-TYPE
    SYNTAX IpAddress
    MAX-ACCESS accessible-for-notify
    STATUS current
    DESCRIPTION
        "Parameter 'dest_IP_address' in event BR.34"
    ::= { brEventObjects34 3 }

brEventObjects35 OBJECT-IDENTITY
    STATUS current
    DESCRIPTION
        "Event BR.35
        A frame is droped because BVI interface has no protocol handler"
    ::= { brEventsGroup 35 }

br35_interface OBJECT-TYPE
    SYNTAX DisplayString
    MAX-ACCESS accessible-for-notify
    STATUS current
    DESCRIPTION
        "Parameter 'interface' in event BR.35"
    ::= { brEventObjects35 1 }

br35_protocol OBJECT-TYPE
    SYNTAX Integer32
    MAX-ACCESS accessible-for-notify
    STATUS current
    DESCRIPTION
        "Parameter 'protocol' in event BR.35"
    ::= { brEventObjects35 2 }

brEventObjects36 OBJECT-IDENTITY
    STATUS current
    DESCRIPTION
        "Event BR.36
        A frame has been received for the specified IEEE 802 Subnetwork Access
        Protocol (SNAP) Protocol Identifier (PID), but this PID has no
        forwarder or endnode support. The frame will be dropped."
    ::= { brEventsGroup 36 }

br36_source_mac OBJECT-TYPE
    SYNTAX DisplayString
    MAX-ACCESS accessible-for-notify
    STATUS current
    DESCRIPTION
        "Parameter 'source_mac' in event BR.36"
    ::= { brEventObjects36 1 }

br36_dest_mac OBJECT-TYPE
    SYNTAX DisplayString
    MAX-ACCESS accessible-for-notify
    STATUS current
    DESCRIPTION
        "Parameter 'dest_mac' in event BR.36"
    ::= { brEventObjects36 2 }

br36_protocol_identifier OBJECT-TYPE
    SYNTAX Integer32
    MAX-ACCESS accessible-for-notify
    STATUS current
    DESCRIPTION
        "Parameter 'protocol_identifier' in event BR.36"
    ::= { brEventObjects36 3 }

br36_interface OBJECT-TYPE
    SYNTAX DisplayString
    MAX-ACCESS accessible-for-notify
    STATUS current
    DESCRIPTION
        "Parameter 'interface' in event BR.36"
    ::= { brEventObjects36 4 }

brEventObjects37 OBJECT-IDENTITY
    STATUS current
    DESCRIPTION
        "Event BR.37
        A frame has been received for the specified IEEE 802 Subnetwork Access
        Protocol (SNAP) Protocol Identifier (PID), but this PID has no
        enabled bridging nor routing. The frame will be dropped."
    ::= { brEventsGroup 37 }

br37_source_mac OBJECT-TYPE
    SYNTAX DisplayString
    MAX-ACCESS accessible-for-notify
    STATUS current
    DESCRIPTION
        "Parameter 'source_mac' in event BR.37"
    ::= { brEventObjects37 1 }

br37_dest_mac OBJECT-TYPE
    SYNTAX DisplayString
    MAX-ACCESS accessible-for-notify
    STATUS current
    DESCRIPTION
        "Parameter 'dest_mac' in event BR.37"
    ::= { brEventObjects37 2 }

br37_protocol_identifier OBJECT-TYPE
    SYNTAX Integer32
    MAX-ACCESS accessible-for-notify
    STATUS current
    DESCRIPTION
        "Parameter 'protocol_identifier' in event BR.37"
    ::= { brEventObjects37 3 }

br37_interface OBJECT-TYPE
    SYNTAX DisplayString
    MAX-ACCESS accessible-for-notify
    STATUS current
    DESCRIPTION
        "Parameter 'interface' in event BR.37"
    ::= { brEventObjects37 4 }

brEventObjects38 OBJECT-IDENTITY
    STATUS current
    DESCRIPTION
        "Event BR.38
        A frame has been received for the specified IEEE 802.2 Destination
        Service Access Point (DSAP), but this DSAP has no forwarder or
        endnode support. The frame will be dropped."
    ::= { brEventsGroup 38 }

br38_source_mac OBJECT-TYPE
    SYNTAX DisplayString
    MAX-ACCESS accessible-for-notify
    STATUS current
    DESCRIPTION
        "Parameter 'source_mac' in event BR.38"
    ::= { brEventObjects38 1 }

br38_dest_mac OBJECT-TYPE
    SYNTAX DisplayString
    MAX-ACCESS accessible-for-notify
    STATUS current
    DESCRIPTION
        "Parameter 'dest_mac' in event BR.38"
    ::= { brEventObjects38 2 }

br38_destination_service_access_point OBJECT-TYPE
    SYNTAX Integer32
    MAX-ACCESS accessible-for-notify
    STATUS current
    DESCRIPTION
        "Parameter 'destination_service_access_point' in event BR.38"
    ::= { brEventObjects38 3 }

br38_interface OBJECT-TYPE
    SYNTAX DisplayString
    MAX-ACCESS accessible-for-notify
    STATUS current
    DESCRIPTION
        "Parameter 'interface' in event BR.38"
    ::= { brEventObjects38 4 }

brEventObjects39 OBJECT-IDENTITY
    STATUS current
    DESCRIPTION
        "Event BR.39
        A frame has been received for the specified IEEE 802.2 Destination
        Service Access Point (DSAP), but this DSAP has no enabled
        bridging nor routing. The frame will be dropped."
    ::= { brEventsGroup 39 }

br39_source_mac OBJECT-TYPE
    SYNTAX DisplayString
    MAX-ACCESS accessible-for-notify
    STATUS current
    DESCRIPTION
        "Parameter 'source_mac' in event BR.39"
    ::= { brEventObjects39 1 }

br39_dest_mac OBJECT-TYPE
    SYNTAX DisplayString
    MAX-ACCESS accessible-for-notify
    STATUS current
    DESCRIPTION
        "Parameter 'dest_mac' in event BR.39"
    ::= { brEventObjects39 2 }

br39_destination_service_access_point OBJECT-TYPE
    SYNTAX Integer32
    MAX-ACCESS accessible-for-notify
    STATUS current
    DESCRIPTION
        "Parameter 'destination_service_access_point' in event BR.39"
    ::= { brEventObjects39 3 }

br39_interface OBJECT-TYPE
    SYNTAX DisplayString
    MAX-ACCESS accessible-for-notify
    STATUS current
    DESCRIPTION
        "Parameter 'interface' in event BR.39"
    ::= { brEventObjects39 4 }

brEventObjects40 OBJECT-IDENTITY
    STATUS current
    DESCRIPTION
        "Event BR.40
        A frame has been received for the specified Ethernet type, but this type
        has no forwarder or endnode support. The frame will be
        dropped."
    ::= { brEventsGroup 40 }

br40_source_mac OBJECT-TYPE
    SYNTAX DisplayString
    MAX-ACCESS accessible-for-notify
    STATUS current
    DESCRIPTION
        "Parameter 'source_mac' in event BR.40"
    ::= { brEventObjects40 1 }

br40_dest_mac OBJECT-TYPE
    SYNTAX DisplayString
    MAX-ACCESS accessible-for-notify
    STATUS current
    DESCRIPTION
        "Parameter 'dest_mac' in event BR.40"
    ::= { brEventObjects40 2 }

br40_Ethernet_type OBJECT-TYPE
    SYNTAX Integer32
    MAX-ACCESS accessible-for-notify
    STATUS current
    DESCRIPTION
        "Parameter 'Ethernet_type' in event BR.40"
    ::= { brEventObjects40 3 }

br40_interface OBJECT-TYPE
    SYNTAX DisplayString
    MAX-ACCESS accessible-for-notify
    STATUS current
    DESCRIPTION
        "Parameter 'interface' in event BR.40"
    ::= { brEventObjects40 4 }

brEventObjects41 OBJECT-IDENTITY
    STATUS current
    DESCRIPTION
        "Event BR.41
        A frame has been received for the specified Ethernet type, but this type
        has no enabled bridging nor routing. The frame will be
        dropped."
    ::= { brEventsGroup 41 }

br41_source_mac OBJECT-TYPE
    SYNTAX DisplayString
    MAX-ACCESS accessible-for-notify
    STATUS current
    DESCRIPTION
        "Parameter 'source_mac' in event BR.41"
    ::= { brEventObjects41 1 }

br41_dest_mac OBJECT-TYPE
    SYNTAX DisplayString
    MAX-ACCESS accessible-for-notify
    STATUS current
    DESCRIPTION
        "Parameter 'dest_mac' in event BR.41"
    ::= { brEventObjects41 2 }

br41_Ethernet_type OBJECT-TYPE
    SYNTAX Integer32
    MAX-ACCESS accessible-for-notify
    STATUS current
    DESCRIPTION
        "Parameter 'Ethernet_type' in event BR.41"
    ::= { brEventObjects41 3 }

br41_interface OBJECT-TYPE
    SYNTAX DisplayString
    MAX-ACCESS accessible-for-notify
    STATUS current
    DESCRIPTION
        "Parameter 'interface' in event BR.41"
    ::= { brEventObjects41 4 }

brEventObjects42 OBJECT-IDENTITY
    STATUS current
    DESCRIPTION
        "Event BR.42
        A source-routed frame has been received for the specified IEEE 802.2
        Destination Service Access Point (DSAP), but this DSAP has no enabled
        bridging nor routing. The frame will be dropped."
    ::= { brEventsGroup 42 }

br42_source_mac OBJECT-TYPE
    SYNTAX DisplayString
    MAX-ACCESS accessible-for-notify
    STATUS current
    DESCRIPTION
        "Parameter 'source_mac' in event BR.42"
    ::= { brEventObjects42 1 }

br42_dest_mac OBJECT-TYPE
    SYNTAX DisplayString
    MAX-ACCESS accessible-for-notify
    STATUS current
    DESCRIPTION
        "Parameter 'dest_mac' in event BR.42"
    ::= { brEventObjects42 2 }

br42_destination_service_access_point OBJECT-TYPE
    SYNTAX Integer32
    MAX-ACCESS accessible-for-notify
    STATUS current
    DESCRIPTION
        "Parameter 'destination_service_access_point' in event BR.42"
    ::= { brEventObjects42 3 }

br42_interface OBJECT-TYPE
    SYNTAX DisplayString
    MAX-ACCESS accessible-for-notify
    STATUS current
    DESCRIPTION
        "Parameter 'interface' in event BR.42"
    ::= { brEventObjects42 4 }

brEventObjects43 OBJECT-IDENTITY
    STATUS current
    DESCRIPTION
        "Event BR.43
        A source-routed frame has been received for the specified IEEE 802
        Subnetwork Access Protocol (SNAP) Protocol Identifier (PID), but
        this PID has no enabled bridging nor routing. The frame
        will be dropped."
    ::= { brEventsGroup 43 }

br43_source_mac OBJECT-TYPE
    SYNTAX DisplayString
    MAX-ACCESS accessible-for-notify
    STATUS current
    DESCRIPTION
        "Parameter 'source_mac' in event BR.43"
    ::= { brEventObjects43 1 }

br43_dest_mac OBJECT-TYPE
    SYNTAX DisplayString
    MAX-ACCESS accessible-for-notify
    STATUS current
    DESCRIPTION
        "Parameter 'dest_mac' in event BR.43"
    ::= { brEventObjects43 2 }

br43_protocol_identifier OBJECT-TYPE
    SYNTAX Integer32
    MAX-ACCESS accessible-for-notify
    STATUS current
    DESCRIPTION
        "Parameter 'protocol_identifier' in event BR.43"
    ::= { brEventObjects43 3 }

br43_interface OBJECT-TYPE
    SYNTAX DisplayString
    MAX-ACCESS accessible-for-notify
    STATUS current
    DESCRIPTION
        "Parameter 'interface' in event BR.43"
    ::= { brEventObjects43 4 }

brEventObjects44 OBJECT-IDENTITY
    STATUS current
    DESCRIPTION
        "Event BR.44
        A frame has been received with vlan identifier FFF. This
        frame will be dropped."
    ::= { brEventsGroup 44 }

br44_source_mac OBJECT-TYPE
    SYNTAX DisplayString
    MAX-ACCESS accessible-for-notify
    STATUS current
    DESCRIPTION
        "Parameter 'source_mac' in event BR.44"
    ::= { brEventObjects44 1 }

br44_dest_mac OBJECT-TYPE
    SYNTAX DisplayString
    MAX-ACCESS accessible-for-notify
    STATUS current
    DESCRIPTION
        "Parameter 'dest_mac' in event BR.44"
    ::= { brEventObjects44 2 }

br44_interface OBJECT-TYPE
    SYNTAX DisplayString
    MAX-ACCESS accessible-for-notify
    STATUS current
    DESCRIPTION
        "Parameter 'interface' in event BR.44"
    ::= { brEventObjects44 3 }

brEventObjects45 OBJECT-IDENTITY
    STATUS current
    DESCRIPTION
        "Event BR.45
        A frame has been received with no vlan tag and port
        is configured to accept only tagged frames. This frame will be dropped."
    ::= { brEventsGroup 45 }

br45_source_mac OBJECT-TYPE
    SYNTAX DisplayString
    MAX-ACCESS accessible-for-notify
    STATUS current
    DESCRIPTION
        "Parameter 'source_mac' in event BR.45"
    ::= { brEventObjects45 1 }

br45_dest_mac OBJECT-TYPE
    SYNTAX DisplayString
    MAX-ACCESS accessible-for-notify
    STATUS current
    DESCRIPTION
        "Parameter 'dest_mac' in event BR.45"
    ::= { brEventObjects45 2 }

br45_interface OBJECT-TYPE
    SYNTAX DisplayString
    MAX-ACCESS accessible-for-notify
    STATUS current
    DESCRIPTION
        "Parameter 'interface' in event BR.45"
    ::= { brEventObjects45 3 }

brEventObjects46 OBJECT-IDENTITY
    STATUS current
    DESCRIPTION
        "Event BR.46
        A frame has been received, but its VLAN ID is not ingress enabled in the
        the port bridge. The frame will be dropped."
    ::= { brEventsGroup 46 }

br46_source_mac OBJECT-TYPE
    SYNTAX DisplayString
    MAX-ACCESS accessible-for-notify
    STATUS current
    DESCRIPTION
        "Parameter 'source_mac' in event BR.46"
    ::= { brEventObjects46 1 }

br46_dest_mac OBJECT-TYPE
    SYNTAX DisplayString
    MAX-ACCESS accessible-for-notify
    STATUS current
    DESCRIPTION
        "Parameter 'dest_mac' in event BR.46"
    ::= { brEventObjects46 2 }

br46_vlan_id OBJECT-TYPE
    SYNTAX Integer32
    MAX-ACCESS accessible-for-notify
    STATUS current
    DESCRIPTION
        "Parameter 'vlan_id' in event BR.46"
    ::= { brEventObjects46 3 }

br46_interface OBJECT-TYPE
    SYNTAX DisplayString
    MAX-ACCESS accessible-for-notify
    STATUS current
    DESCRIPTION
        "Parameter 'interface' in event BR.46"
    ::= { brEventObjects46 4 }

brEventObjects47 OBJECT-IDENTITY
    STATUS current
    DESCRIPTION
        "Event BR.47
        A frame has been received, but its VLAN ID is not egress enabled in the
        the port bridge. The frame will be dropped."
    ::= { brEventsGroup 47 }

br47_source_mac OBJECT-TYPE
    SYNTAX DisplayString
    MAX-ACCESS accessible-for-notify
    STATUS current
    DESCRIPTION
        "Parameter 'source_mac' in event BR.47"
    ::= { brEventObjects47 1 }

br47_dest_mac OBJECT-TYPE
    SYNTAX DisplayString
    MAX-ACCESS accessible-for-notify
    STATUS current
    DESCRIPTION
        "Parameter 'dest_mac' in event BR.47"
    ::= { brEventObjects47 2 }

br47_vlan_id OBJECT-TYPE
    SYNTAX Integer32
    MAX-ACCESS accessible-for-notify
    STATUS current
    DESCRIPTION
        "Parameter 'vlan_id' in event BR.47"
    ::= { brEventObjects47 3 }

br47_interface OBJECT-TYPE
    SYNTAX DisplayString
    MAX-ACCESS accessible-for-notify
    STATUS current
    DESCRIPTION
        "Parameter 'interface' in event BR.47"
    ::= { brEventObjects47 4 }

brEventObjects48 OBJECT-IDENTITY
    STATUS current
    DESCRIPTION
        "Event BR.48
        A frame has been received, but its VLAN ID is not active in the
        this port bridge. The frame will be dropped."
    ::= { brEventsGroup 48 }

br48_source_mac OBJECT-TYPE
    SYNTAX DisplayString
    MAX-ACCESS accessible-for-notify
    STATUS current
    DESCRIPTION
        "Parameter 'source_mac' in event BR.48"
    ::= { brEventObjects48 1 }

br48_dest_mac OBJECT-TYPE
    SYNTAX DisplayString
    MAX-ACCESS accessible-for-notify
    STATUS current
    DESCRIPTION
        "Parameter 'dest_mac' in event BR.48"
    ::= { brEventObjects48 2 }

br48_vlan_id OBJECT-TYPE
    SYNTAX Integer32
    MAX-ACCESS accessible-for-notify
    STATUS current
    DESCRIPTION
        "Parameter 'vlan_id' in event BR.48"
    ::= { brEventObjects48 3 }

br48_interface OBJECT-TYPE
    SYNTAX DisplayString
    MAX-ACCESS accessible-for-notify
    STATUS current
    DESCRIPTION
        "Parameter 'interface' in event BR.48"
    ::= { brEventObjects48 4 }


brNotification1 NOTIFICATION-TYPE
    OBJECTS { 
              br1_source_mac, 
              br1_dest_mac,
              br1_interface 
            }
    STATUS current
    DESCRIPTION
        "Notification of Event BR.1

        Message: 'Frame from $1 to $2 dropped, received on blocked or listening port, interface $3'

        Parameters list:
              $1: br1_source_mac
              $2: br1_dest_mac
              $3: br1_interface

        A MAC frame has been received by the hardware, but is being dropped
        because the port it was received on is in the 'blocking' or 'listening'
        state. Frames are only processed when the port is in the 'learning' or
        'forwarding' state."
    ::= { brNotificationsPrefix 1 }

brNotification2 NOTIFICATION-TYPE
    OBJECTS { 
              br2_source_mac, 
              br2_dest_mac,
              br2_interface 
            }
    STATUS current
    DESCRIPTION
        "Notification of Event BR.2

        Message: 'Frame from $1 to $2 dropped, destination on same LAN, interface $3'

        Parameters list:
              $1: br2_source_mac
              $2: br2_dest_mac
              $3: br2_interface

        A MAC frame has been received whose destination address is known to be
        on the same side of the bridge as the packet came from. It is dropped
        by the filtering logic since it does not need to be bridged. Note that
        this event is not counted by ELS for performance reasons. A counter
        is kept in ASRT, it is the 'Dropped, dest addr filtering' entry in
        the ASRT>LIST SOURCE-ROUTE COUNTERS and ASRT>LIST TRANSPARENT COUNTERS
        commands."
    ::= { brNotificationsPrefix 2 }

brNotification3 NOTIFICATION-TYPE
    OBJECTS { 
              br3_source_mac, 
              br3_dest_mac,
              br3_interface 
            }
    STATUS current
    DESCRIPTION
        "Notification of Event BR.3

        Message: 'Frame from $1 a $2, WAN bridge encapsulation for routed protocol IPX (802.3), dropped, interface $3'

        Parameters list:
              $1: br3_source_mac
              $2: br3_dest_mac
              $3: br3_interface

        A frame has been received over a WAN interface in the Ethernet bridge
        encapsulation, but the IPX protocol (in 802.3 encapsulation) is routed
        by this node."
    ::= { brNotificationsPrefix 3 }

brNotification4 NOTIFICATION-TYPE
    OBJECTS { 
              br4_source_mac, 
              br4_dest_mac,
              br4_interface 
            }
    STATUS current
    DESCRIPTION
        "Notification of Event BR.4

        Message: 'Frame from $1 to $2, protocol IPX (802.3) filtered, dropped, interface $3'

        Parameters list:
              $1: br4_source_mac
              $2: br4_dest_mac
              $3: br4_interface

        A frame has been received for the IPX protocol (in 802.3 encapsulation),
        but the IPX protocol is being administratively filtered by the bridge.
        The frame will be dropped."
    ::= { brNotificationsPrefix 4 }

brNotification5 NOTIFICATION-TYPE
    OBJECTS { 
              br5_source_mac, 
              br5_dest_mac,
              br5_protocol_identifier,
              br5_protocol_identifier,
              br5_protocol_identifier,
              br5_protocol_identifier,
              br5_protocol_identifier,
              br5_interface 
            }
    STATUS current
    DESCRIPTION
        "Notification of Event BR.5

        Message: 'Frame from $1 to $2, IEEE 802 SNAP Protocol Identifier $3-$4-$5-$6-$7 filtered, dropped, interface $8'

        Parameters list:
              $1: br5_source_mac
              $2: br5_dest_mac
              $3: br5_protocol_identifier
              $4: br5_protocol_identifier
              $5: br5_protocol_identifier
              $6: br5_protocol_identifier
              $7: br5_protocol_identifier
              $8: br5_interface

        A frame has been received for the specified IEEE 802 Subnetwork Access
        Protocol (SNAP) Protocol Identifier (PID), but this PID is being
        administratively filtered by the bridge. The frame will be dropped."
    ::= { brNotificationsPrefix 5 }

brNotification6 NOTIFICATION-TYPE
    OBJECTS { 
              br6_source_mac, 
              br6_dest_mac,
              br6_protocol_identifier,
              br6_protocol_identifier,
              br6_protocol_identifier,
              br6_protocol_identifier,
              br6_protocol_identifier,
              br6_interface 
            }
    STATUS current
    DESCRIPTION
        "Notification of Event BR.6

        Message: 'Frame from $1 to unregistered destination MAC address $2, IEEE 802 SNAP Protocol Identifier $3-$4-$5-$6-$7, dropped, interface $8'

        Parameters list:
              $1: br6_source_mac
              $2: br6_dest_mac
              $3: br6_protocol_identifier
              $4: br6_protocol_identifier
              $5: br6_protocol_identifier
              $6: br6_protocol_identifier
              $7: br6_protocol_identifier
              $8: br6_interface

        A frame has been received for the IEEE 802 Subnetwork Access Protocol
        (SNAP) Protocol Identifier (PID) which corresponds with an enabled
        protocol, but the destination MAC address is not registered
        in the bridge. The frame will be dropped."
    ::= { brNotificationsPrefix 6 }

brNotification7 NOTIFICATION-TYPE
    OBJECTS { 
              br7_source_mac, 
              br7_dest_mac,
              br7_protocol_identifier,
              br7_protocol_identifier,
              br7_protocol_identifier,
              br7_protocol_identifier,
              br7_protocol_identifier,
              br7_interface 
            }
    STATUS current
    DESCRIPTION
        "Notification of Event BR.7

        Message: 'Frame from $1 to $2, IEEE 802 SNAP Protocol Identifier $3-$4-$5-$6-$7 for endnode protocol, interface $8'

        Parameters list:
              $1: br7_source_mac
              $2: br7_dest_mac
              $3: br7_protocol_identifier
              $4: br7_protocol_identifier
              $5: br7_protocol_identifier
              $6: br7_protocol_identifier
              $7: br7_protocol_identifier
              $8: br7_interface

        A multicast frame has been received for the IEEE 802 Subnetwork Access
        Protocol (SNAP) Protocol Identifier (PID) which corresponds with
        an endnode protocol. The frame will be both bridged and
        locally processed by the endnode protocol."
    ::= { brNotificationsPrefix 7 }

brNotification8 NOTIFICATION-TYPE
    OBJECTS { 
              br8_source_mac, 
              br8_dest_mac,
              br8_protocol_identifier,
              br8_protocol_identifier,
              br8_protocol_identifier,
              br8_protocol_identifier,
              br8_protocol_identifier,
              br8_interface 
            }
    STATUS current
    DESCRIPTION
        "Notification of Event BR.8

        Message: 'Frame from $1 to $2, WAN bridge encapsulation for routed IEEE 802 SNAP Protocol Identifier $3-$4-$5-$6-$7, dropped, interface $8'

        Parameters list:
              $1: br8_source_mac
              $2: br8_dest_mac
              $3: br8_protocol_identifier
              $4: br8_protocol_identifier
              $5: br8_protocol_identifier
              $6: br8_protocol_identifier
              $7: br8_protocol_identifier
              $8: br8_interface

        An IEEE 802.2 frame has been received over a WAN interface in a bridge
        encapsulation, but its IEEE 802 Subnetwork Access Protocol (SNAP)
        Protocol Identifier (PID) is one that is being routed by this node.
        The frame will be dropped."
    ::= { brNotificationsPrefix 8 }

brNotification9 NOTIFICATION-TYPE
    OBJECTS { 
              br9_source_mac, 
              br9_dest_mac,
              br9_interface 
            }
    STATUS current
    DESCRIPTION
        "Notification of Event BR.9

        Message: 'IEEE 802.1D BPDU $1 to $2, wrong destination, dropped, interface $3'

        Parameters list:
              $1: br9_source_mac
              $2: br9_dest_mac
              $3: br9_interface

        An IEEE 802.1D Bridge Protocol Data Unit (BPDU) was received at
        the wrong destination address. It is supposed to be addressed to
        a particular multicast address. The BPDU will be dropped."
    ::= { brNotificationsPrefix 9 }

brNotification10 NOTIFICATION-TYPE
    OBJECTS { 
              br10_source_mac, 
              br10_dest_mac,
              br10_destination_service_access_point,
              br10_interface 
            }
    STATUS current
    DESCRIPTION
        "Notification of Event BR.10

        Message: 'Frame from $1 to $2, IEEE 802.2 DSAP $3 filtered, dropped, interface $4'

        Parameters list:
              $1: br10_source_mac
              $2: br10_dest_mac
              $3: br10_destination_service_access_point
              $4: br10_interface

        A frame has been received for the specified IEEE 802.2 Destination
        Service Access Point (DSAP), but this DSAP is being administratively
        filtered by the bridge. The frame will be dropped."
    ::= { brNotificationsPrefix 10 }

brNotification11 NOTIFICATION-TYPE
    OBJECTS { 
              br11_source_mac, 
              br11_dest_mac,
              br11_destination_service_access_point,
              br11_interface 
            }
    STATUS current
    DESCRIPTION
        "Notification of Event BR.11

        Message: 'Frame from $1 to unregistered destination MAC address $2, IEEE 802.2 DSAP $3, dropped, interface $4'

        Parameters list:
              $1: br11_source_mac
              $2: br11_dest_mac
              $3: br11_destination_service_access_point
              $4: br11_interface

        A frame has been received for the IEEE 802.2 Destination Service Access
        Point (DSAP) which corresponds with an enabled protocol, but
        the destination MAC address is not registered in the bridge.
        The frame will be dropped."
    ::= { brNotificationsPrefix 11 }

brNotification12 NOTIFICATION-TYPE
    OBJECTS { 
              br12_source_mac, 
              br12_dest_mac,
              br12_destination_service_access_point,
              br12_interface 
            }
    STATUS current
    DESCRIPTION
        "Notification of Event BR.12

        Message: 'Frame from $1 to $2, IEEE 802.2 DSAP $3 for endnode protocol, interface $4'

        Parameters list:
              $1: br12_source_mac
              $2: br12_dest_mac
              $3: br12_destination_service_access_point
              $4: br12_interface

        A multicast frame has been received for the IEEE 802.2 Destination
        Service Access Point (DSAP) which corresponds with an endnode protocol.
        The frame will be both bridged and locally processed by
        the endnode protocol."
    ::= { brNotificationsPrefix 12 }

brNotification13 NOTIFICATION-TYPE
    OBJECTS { 
              br13_source_mac, 
              br13_dest_mac,
              br13_destination_service_access_point,
              br13_interface 
            }
    STATUS current
    DESCRIPTION
        "Notification of Event BR.13

        Message: 'Frame from $1 to $2, WAN bridge encapsulation for routed IEEE 802.2 DSAP $3, dropped, interface $4'

        Parameters list:
              $1: br13_source_mac
              $2: br13_dest_mac
              $3: br13_destination_service_access_point
              $4: br13_interface

        An IEEE 802.2 frame has been received over a WAN interface in a bridge
        encapsulation, but its IEEE 802.2 Destination Service Access Point
        (DSAP) is one that is being routed by this node. The frame will be
        dropped."
    ::= { brNotificationsPrefix 13 }

brNotification14 NOTIFICATION-TYPE
    OBJECTS { 
              br14_source_mac, 
              br14_dest_mac,
              br14_Ethernet_type,
              br14_interface 
            }
    STATUS current
    DESCRIPTION
        "Notification of Event BR.14

        Message: 'Frame from $1 to $2, Ethernet type $3 filtered, dropped, interface $4'

        Parameters list:
              $1: br14_source_mac
              $2: br14_dest_mac
              $3: br14_Ethernet_type
              $4: br14_interface

        A frame has been received for the specified Ethernet type, but this type
        is being administratively filtered by the bridge. The frame will be
        dropped."
    ::= { brNotificationsPrefix 14 }

brNotification15 NOTIFICATION-TYPE
    OBJECTS { 
              br15_source_mac, 
              br15_dest_mac,
              br15_Ethernet_type,
              br15_interface 
            }
    STATUS current
    DESCRIPTION
        "Notification of Event BR.15

        Message: 'Frame from $1 to unregistered destination MAC address $2, Ethernet type $3, dropped, interface $4'

        Parameters list:
              $1: br15_source_mac
              $2: br15_dest_mac
              $3: br15_Ethernet_type
              $4: br15_interface

        A frame has been received for the Ethernet type which corresponds with
        an enabled protocol, but the destination MAC address is not registered
        in the bridge. The frame will be dropped."
    ::= { brNotificationsPrefix 15 }

brNotification16 NOTIFICATION-TYPE
    OBJECTS { 
              br16_source_mac, 
              br16_dest_mac,
              br16_Ethernet_type,
              br16_interface 
            }
    STATUS current
    DESCRIPTION
        "Notification of Event BR.16

        Message: 'Frame from $1 to $2, Ethernet type $3 for endnode protocol, interface $4'

        Parameters list:
              $1: br16_source_mac
              $2: br16_dest_mac
              $3: br16_Ethernet_type
              $4: br16_interface

        A multicast frame has been received for the Ethernet type which
        corresponds with an endnode protocol. The frame will be both bridged
        and locally processed by the endnode protocol."
    ::= { brNotificationsPrefix 16 }

brNotification17 NOTIFICATION-TYPE
    OBJECTS { 
              br17_source_mac, 
              br17_dest_mac,
              br17_Ethernet_type,
              br17_interface 
            }
    STATUS current
    DESCRIPTION
        "Notification of Event BR.17

        Message: 'Frame from $1 to $2, WAN bridge encapsulation for routed Ethernet type $3, dropped, interface $4'

        Parameters list:
              $1: br17_source_mac
              $2: br17_dest_mac
              $3: br17_Ethernet_type
              $4: br17_interface

        An Ethernet frame has been received over a WAN interface in the Ethernet
        bridge encapsulation, but its Ethernet type is one that is being routed
        by this node. The frame will be dropped."
    ::= { brNotificationsPrefix 17 }

brNotification18 NOTIFICATION-TYPE
    OBJECTS { 
              br18_source_mac, 
              br18_dest_mac,
              br18_destination_service_access_point,
              br18_interface 
            }
    STATUS current
    DESCRIPTION
        "Notification of Event BR.18

        Message: 'Source-routed frame from $1 to $2, IEEE 802.2 DSAP $3 filtered, dropped, interface $4'

        Parameters list:
              $1: br18_source_mac
              $2: br18_dest_mac
              $3: br18_destination_service_access_point
              $4: br18_interface

        A source-routed frame has been received for the specified IEEE 802.2
        Destination Service Access Point (DSAP), but this DSAP is being
        administratively filtered by the bridge. The frame will be dropped."
    ::= { brNotificationsPrefix 18 }

brNotification19 NOTIFICATION-TYPE
    OBJECTS { 
              br19_source_mac, 
              br19_dest_mac,
              br19_destination_service_access_point,
              br19_interface 
            }
    STATUS current
    DESCRIPTION
        "Notification of Event BR.19

        Message: 'Source-routed frame from $1 to unregistered destination MAC address $2, IEEE 802.2 DSAP $3, dropped, interface $4'

        Parameters list:
              $1: br19_source_mac
              $2: br19_dest_mac
              $3: br19_destination_service_access_point
              $4: br19_interface

        A source-routed frame has been received for the IEEE 802.2 Destination
        Service Access Point (DSAP) which corresponds with an enabled protocol,
        but the destination MAC address is not registered in the bridge.
        The frame will be dropped."
    ::= { brNotificationsPrefix 19 }

brNotification20 NOTIFICATION-TYPE
    OBJECTS { 
              br20_source_mac, 
              br20_dest_mac,
              br20_destination_service_access_point,
              br20_interface 
            }
    STATUS current
    DESCRIPTION
        "Notification of Event BR.20

        Message: 'Source-routed frame from $1 to $2, IEEE 802.2 DSAP $3 for endnode protocol, interface $4'

        Parameters list:
              $1: br20_source_mac
              $2: br20_dest_mac
              $3: br20_destination_service_access_point
              $4: br20_interface

        A multicast source-routed frame has been received for the IEEE 802.2
        Destination Service Access Point (DSAP) which corresponds with
        an endnode protocol. The frame will be both bridged and
        locally processed by the endnode protocol."
    ::= { brNotificationsPrefix 20 }

brNotification21 NOTIFICATION-TYPE
    OBJECTS { 
              br21_source_mac, 
              br21_dest_mac,
              br21_protocol_identifier,
              br21_protocol_identifier,
              br21_protocol_identifier,
              br21_protocol_identifier,
              br21_protocol_identifier,
              br21_interface 
            }
    STATUS current
    DESCRIPTION
        "Notification of Event BR.21

        Message: 'Source-routed frame from $1 to $2, IEEE 802 SNAP Protocol Identifier $3-$4-$5-$6-$7 filtered, dropped, interface $8'

        Parameters list:
              $1: br21_source_mac
              $2: br21_dest_mac
              $3: br21_protocol_identifier
              $4: br21_protocol_identifier
              $5: br21_protocol_identifier
              $6: br21_protocol_identifier
              $7: br21_protocol_identifier
              $8: br21_interface

        A source-routed frame has been received for the specified IEEE 802
        Subnetwork Access Protocol (SNAP) Protocol Identifier (PID), but
        this PID is being administratively filtered by the bridge. The frame
        will be dropped."
    ::= { brNotificationsPrefix 21 }

brNotification22 NOTIFICATION-TYPE
    OBJECTS { 
              br22_source_mac, 
              br22_dest_mac,
              br22_protocol_identifier,
              br22_protocol_identifier,
              br22_protocol_identifier,
              br22_protocol_identifier,
              br22_protocol_identifier,
              br22_interface 
            }
    STATUS current
    DESCRIPTION
        "Notification of Event BR.22

        Message: 'Source-routed frame from $1 to unregistered destination MAC address $2, IEEE 802 SNAP Protocol Identifier $3-$4-$5-$6-$7, dropped, interface $8'

        Parameters list:
              $1: br22_source_mac
              $2: br22_dest_mac
              $3: br22_protocol_identifier
              $4: br22_protocol_identifier
              $5: br22_protocol_identifier
              $6: br22_protocol_identifier
              $7: br22_protocol_identifier
              $8: br22_interface

        A source-routed frame has been received for the IEEE 802 Subnetwork
        Access Protocol (SNAP) Protocol Identifier (PID) which corresponds with
        an enabled protocol, but the destination MAC address is not registered
        in the bridge. The frame will be dropped."
    ::= { brNotificationsPrefix 22 }

brNotification23 NOTIFICATION-TYPE
    OBJECTS { 
              br23_source_mac, 
              br23_dest_mac,
              br23_protocol_identifier,
              br23_protocol_identifier,
              br23_protocol_identifier,
              br23_protocol_identifier,
              br23_protocol_identifier,
              br23_interface 
            }
    STATUS current
    DESCRIPTION
        "Notification of Event BR.23

        Message: 'Source-routed frame from $1 to $2 IEEE 802 SNAP Protocol Identifier $3-$4-$5-$6-$7 for endnode protocol, interface $8'

        Parameters list:
              $1: br23_source_mac
              $2: br23_dest_mac
              $3: br23_protocol_identifier
              $4: br23_protocol_identifier
              $5: br23_protocol_identifier
              $6: br23_protocol_identifier
              $7: br23_protocol_identifier
              $8: br23_interface

        SA source-routed multicast frame has been received for the IEEE 802
        Subnetwork Access Protocol (SNAP) Protocol Identifier (PID) which
        corresponds with an endnode protocol. The frame will be both bridged
        and locally processed by the endnode protocol."
    ::= { brNotificationsPrefix 23 }

brNotification24 NOTIFICATION-TYPE
    OBJECTS { 
              br24_vlan_id, 
              br24_interface 
            }
    STATUS current
    DESCRIPTION
        "Notification of Event BR.24

        Message: 'VLAN vid $1 not supported. Frame discarded, interface $2'

        Parameters list:
              $1: br24_vlan_id
              $2: br24_interface

        A vlan frame has been received whose virtual lan id is not supported.
        Frame is dropped."
    ::= { brNotificationsPrefix 24 }

brNotification25 NOTIFICATION-TYPE
    STATUS current
    DESCRIPTION
        "Notification of Event BR.25

        Message: '---'

        Reserved for possible future use."
    ::= { brNotificationsPrefix 25 }

brNotification26 NOTIFICATION-TYPE
    OBJECTS { 
              br26_source_mac, 
              br26_dest_mac,
              br26_interface 
            }
    STATUS current
    DESCRIPTION
        "Notification of Event BR.26

        Message: 'Frame from $1 to $2 dropped, destination address filtered, interface $3'

        Parameters list:
              $1: br26_source_mac
              $2: br26_dest_mac
              $3: br26_interface

        A source-routed MAC frame has been received by the hardware, but
        is being dropped because the destination MAC address is being
        administratively filtered by the bridge. The frame will be dropped."
    ::= { brNotificationsPrefix 26 }

brNotification27 NOTIFICATION-TYPE
    OBJECTS { 
              br27_source_mac, 
              br27_dest_mac,
              br27_interface 
            }
    STATUS current
    DESCRIPTION
        "Notification of Event BR.27

        Message: 'Frame from $1 to $2 dropped, source address filtered, interface $3'

        Parameters list:
              $1: br27_source_mac
              $2: br27_dest_mac
              $3: br27_interface

        A source-routed MAC frame has been received by the hardware, but
        is being dropped because the source MAC address is being
        administratively filtered by the bridge. The frame will be dropped."
    ::= { brNotificationsPrefix 27 }

brNotification28 NOTIFICATION-TYPE
    OBJECTS { 
              br28_source_mac, 
              br28_dest_mac,
              br28_interface 
            }
    STATUS current
    DESCRIPTION
        "Notification of Event BR.28

        Message: 'No buffer to copy packet for endnode bridge and process, from $1 to $2, interface $3 not bridged'

        Parameters list:
              $1: br28_source_mac
              $2: br28_dest_mac
              $3: br28_interface

        A multicast frame has been received for an endnode protocol that is
        both bridged and locally processed. There was no buffer to make
        two copies of the frame for both types of processing, so it will not be
        bridged, only locally processed."
    ::= { brNotificationsPrefix 28 }

brNotification29 NOTIFICATION-TYPE
    OBJECTS { 
              br29_source_mac, 
              br29_dest_mac,
              br29_port,
              br29_interface 
            }
    STATUS current
    DESCRIPTION
        "Notification of Event BR.29

        Message: 'NETBIOS Input Packet Filtered - $1->$2, port $3, interface $4'

        Parameters list:
              $1: br29_source_mac
              $2: br29_dest_mac
              $3: br29_port
              $4: br29_interface

        A NETBIOS packet has matched the criteria specified in a NETBIOS Filter
        configuration record. The packet is dropped."
    ::= { brNotificationsPrefix 29 }

brNotification30 NOTIFICATION-TYPE
    OBJECTS { 
              br30_interface, 
              br30_new_mac 
            }
    STATUS current
    DESCRIPTION
        "Notification of Event BR.30

        Message: 'Updated MAC address for interface $1: $2'

        Parameters list:
              $1: br30_interface
              $2: br30_new_mac

        The MAC address of a BVI interface has been updated"
    ::= { brNotificationsPrefix 30 }

brNotification31 NOTIFICATION-TYPE
    OBJECTS { 
              br31_interface, 
              br31_source_mac,
              br31_dest_mac,
              br31_protocol 
            }
    STATUS current
    DESCRIPTION
        "Notification of Event BR.31

        Message: 'Interface $1 sends a frame from $2 to $3, protocol $4'

        Parameters list:
              $1: br31_interface
              $2: br31_source_mac
              $3: br31_dest_mac
              $4: br31_protocol

        A frame is going to be output to the bridge through a BVI interface."
    ::= { brNotificationsPrefix 31 }

brNotification32 NOTIFICATION-TYPE
    OBJECTS { 
              br32_interface, 
              br32_source_mac,
              br32_dest_mac,
              br32_protocol 
            }
    STATUS current
    DESCRIPTION
        "Notification of Event BR.32

        Message: 'Interface $1 has received a frame from $2 to $3, protocol $4'

        Parameters list:
              $1: br32_interface
              $2: br32_source_mac
              $3: br32_dest_mac
              $4: br32_protocol

        A frame has been received in a BVI interface."
    ::= { brNotificationsPrefix 32 }

brNotification33 NOTIFICATION-TYPE
    OBJECTS { 
              br33_interface 
            }
    STATUS current
    DESCRIPTION
        "Notification of Event BR.33

        Message: 'Interface $1 drops frame because interface is down'

        Parameters list:
              $1: br33_interface

        A frame is droped because BVI interface is down"
    ::= { brNotificationsPrefix 33 }

brNotification34 NOTIFICATION-TYPE
    OBJECTS { 
              br34_interface, 
              br34_source_mac,
              br34_dest_IP_address 
            }
    STATUS current
    DESCRIPTION
        "Notification of Event BR.34

        Message: 'Interface $1 sends a frame from $2 to $3, protocol IP'

        Parameters list:
              $1: br34_interface
              $2: br34_source_mac
              $3: br34_dest_IP_address

        A frame is dropped because destination IP has no registered MAC address."
    ::= { brNotificationsPrefix 34 }

brNotification35 NOTIFICATION-TYPE
    OBJECTS { 
              br35_interface, 
              br35_protocol 
            }
    STATUS current
    DESCRIPTION
        "Notification of Event BR.35

        Message: 'Interface $1 drops frame because protocol $2 is unhandled'

        Parameters list:
              $1: br35_interface
              $2: br35_protocol

        A frame is droped because BVI interface has no protocol handler"
    ::= { brNotificationsPrefix 35 }

brNotification36 NOTIFICATION-TYPE
    OBJECTS { 
              br36_source_mac, 
              br36_dest_mac,
              br36_protocol_identifier,
              br36_protocol_identifier,
              br36_protocol_identifier,
              br36_protocol_identifier,
              br36_protocol_identifier,
              br36_interface 
            }
    STATUS current
    DESCRIPTION
        "Notification of Event BR.36

        Message: 'Frame from $1 to $2, IEEE 802 SNAP Protocol Identifier $3-$4-$5-$6-$7 not handled, dropped, interface $8'

        Parameters list:
              $1: br36_source_mac
              $2: br36_dest_mac
              $3: br36_protocol_identifier
              $4: br36_protocol_identifier
              $5: br36_protocol_identifier
              $6: br36_protocol_identifier
              $7: br36_protocol_identifier
              $8: br36_interface

        A frame has been received for the specified IEEE 802 Subnetwork Access
        Protocol (SNAP) Protocol Identifier (PID), but this PID has no
        forwarder or endnode support. The frame will be dropped."
    ::= { brNotificationsPrefix 36 }

brNotification37 NOTIFICATION-TYPE
    OBJECTS { 
              br37_source_mac, 
              br37_dest_mac,
              br37_protocol_identifier,
              br37_protocol_identifier,
              br37_protocol_identifier,
              br37_protocol_identifier,
              br37_protocol_identifier,
              br37_interface 
            }
    STATUS current
    DESCRIPTION
        "Notification of Event BR.37

        Message: 'Frame from $1 to $2, IEEE 802 SNAP Protocol Identifier $3-$4-$5-$6-$7 dropped, interface $8'

        Parameters list:
              $1: br37_source_mac
              $2: br37_dest_mac
              $3: br37_protocol_identifier
              $4: br37_protocol_identifier
              $5: br37_protocol_identifier
              $6: br37_protocol_identifier
              $7: br37_protocol_identifier
              $8: br37_interface

        A frame has been received for the specified IEEE 802 Subnetwork Access
        Protocol (SNAP) Protocol Identifier (PID), but this PID has no
        enabled bridging nor routing. The frame will be dropped."
    ::= { brNotificationsPrefix 37 }

brNotification38 NOTIFICATION-TYPE
    OBJECTS { 
              br38_source_mac, 
              br38_dest_mac,
              br38_destination_service_access_point,
              br38_interface 
            }
    STATUS current
    DESCRIPTION
        "Notification of Event BR.38

        Message: 'Frame from $1 to $2, IEEE 802.2 DSAP $3 not handled, dropped, interface $4'

        Parameters list:
              $1: br38_source_mac
              $2: br38_dest_mac
              $3: br38_destination_service_access_point
              $4: br38_interface

        A frame has been received for the specified IEEE 802.2 Destination
        Service Access Point (DSAP), but this DSAP has no forwarder or
        endnode support. The frame will be dropped."
    ::= { brNotificationsPrefix 38 }

brNotification39 NOTIFICATION-TYPE
    OBJECTS { 
              br39_source_mac, 
              br39_dest_mac,
              br39_destination_service_access_point,
              br39_interface 
            }
    STATUS current
    DESCRIPTION
        "Notification of Event BR.39

        Message: 'Frame from $1 to $2, IEEE 802.2 DSAP $3, dropped, interface $4'

        Parameters list:
              $1: br39_source_mac
              $2: br39_dest_mac
              $3: br39_destination_service_access_point
              $4: br39_interface

        A frame has been received for the specified IEEE 802.2 Destination
        Service Access Point (DSAP), but this DSAP has no enabled
        bridging nor routing. The frame will be dropped."
    ::= { brNotificationsPrefix 39 }

brNotification40 NOTIFICATION-TYPE
    OBJECTS { 
              br40_source_mac, 
              br40_dest_mac,
              br40_Ethernet_type,
              br40_interface 
            }
    STATUS current
    DESCRIPTION
        "Notification of Event BR.40

        Message: 'Frame from $1 to $2, Ethernet type $3 not handled, dropped, interface $4'

        Parameters list:
              $1: br40_source_mac
              $2: br40_dest_mac
              $3: br40_Ethernet_type
              $4: br40_interface

        A frame has been received for the specified Ethernet type, but this type
        has no forwarder or endnode support. The frame will be
        dropped."
    ::= { brNotificationsPrefix 40 }

brNotification41 NOTIFICATION-TYPE
    OBJECTS { 
              br41_source_mac, 
              br41_dest_mac,
              br41_Ethernet_type,
              br41_interface 
            }
    STATUS current
    DESCRIPTION
        "Notification of Event BR.41

        Message: 'Frame from $1 to $2, Ethernet type $3 dropped, interface $4'

        Parameters list:
              $1: br41_source_mac
              $2: br41_dest_mac
              $3: br41_Ethernet_type
              $4: br41_interface

        A frame has been received for the specified Ethernet type, but this type
        has no enabled bridging nor routing. The frame will be
        dropped."
    ::= { brNotificationsPrefix 41 }

brNotification42 NOTIFICATION-TYPE
    OBJECTS { 
              br42_source_mac, 
              br42_dest_mac,
              br42_destination_service_access_point,
              br42_interface 
            }
    STATUS current
    DESCRIPTION
        "Notification of Event BR.42

        Message: 'Source-routed frame from $1 to $2, IEEE 802.2 DSAP $3 dropped, interface $4'

        Parameters list:
              $1: br42_source_mac
              $2: br42_dest_mac
              $3: br42_destination_service_access_point
              $4: br42_interface

        A source-routed frame has been received for the specified IEEE 802.2
        Destination Service Access Point (DSAP), but this DSAP has no enabled
        bridging nor routing. The frame will be dropped."
    ::= { brNotificationsPrefix 42 }

brNotification43 NOTIFICATION-TYPE
    OBJECTS { 
              br43_source_mac, 
              br43_dest_mac,
              br43_protocol_identifier,
              br43_protocol_identifier,
              br43_protocol_identifier,
              br43_protocol_identifier,
              br43_protocol_identifier,
              br43_interface 
            }
    STATUS current
    DESCRIPTION
        "Notification of Event BR.43

        Message: 'Source-routed frame from $1 to $2, IEEE 802 SNAP Protocol Identifier $3-$4-$5-$6-$7 dropped, interface $8'

        Parameters list:
              $1: br43_source_mac
              $2: br43_dest_mac
              $3: br43_protocol_identifier
              $4: br43_protocol_identifier
              $5: br43_protocol_identifier
              $6: br43_protocol_identifier
              $7: br43_protocol_identifier
              $8: br43_interface

        A source-routed frame has been received for the specified IEEE 802
        Subnetwork Access Protocol (SNAP) Protocol Identifier (PID), but
        this PID has no enabled bridging nor routing. The frame
        will be dropped."
    ::= { brNotificationsPrefix 43 }

brNotification44 NOTIFICATION-TYPE
    OBJECTS { 
              br44_source_mac, 
              br44_dest_mac,
              br44_interface 
            }
    STATUS current
    DESCRIPTION
        "Notification of Event BR.44

        Message: 'Frame from $1 to $2, with VID FFF dropped, interface $3'

        Parameters list:
              $1: br44_source_mac
              $2: br44_dest_mac
              $3: br44_interface

        A frame has been received with vlan identifier FFF. This
        frame will be dropped."
    ::= { brNotificationsPrefix 44 }

brNotification45 NOTIFICATION-TYPE
    OBJECTS { 
              br45_source_mac, 
              br45_dest_mac,
              br45_interface 
            }
    STATUS current
    DESCRIPTION
        "Notification of Event BR.45

        Message: 'Frame without vlan tag from $1 to $2, dropped, interface $3'

        Parameters list:
              $1: br45_source_mac
              $2: br45_dest_mac
              $3: br45_interface

        A frame has been received with no vlan tag and port
        is configured to accept only tagged frames. This frame will be dropped."
    ::= { brNotificationsPrefix 45 }

brNotification46 NOTIFICATION-TYPE
    OBJECTS { 
              br46_source_mac, 
              br46_dest_mac,
              br46_vlan_id,
              br46_interface 
            }
    STATUS current
    DESCRIPTION
        "Notification of Event BR.46

        Message: 'Frame dropped from $1 to $2, vlan ID $3, ingress not enabled on interface $4'

        Parameters list:
              $1: br46_source_mac
              $2: br46_dest_mac
              $3: br46_vlan_id
              $4: br46_interface

        A frame has been received, but its VLAN ID is not ingress enabled in the
        the port bridge. The frame will be dropped."
    ::= { brNotificationsPrefix 46 }

brNotification47 NOTIFICATION-TYPE
    OBJECTS { 
              br47_source_mac, 
              br47_dest_mac,
              br47_vlan_id,
              br47_interface 
            }
    STATUS current
    DESCRIPTION
        "Notification of Event BR.47

        Message: 'Frame dropped from $1 to $2, vlan ID $3 egress not enabled on interface $4'

        Parameters list:
              $1: br47_source_mac
              $2: br47_dest_mac
              $3: br47_vlan_id
              $4: br47_interface

        A frame has been received, but its VLAN ID is not egress enabled in the
        the port bridge. The frame will be dropped."
    ::= { brNotificationsPrefix 47 }

brNotification48 NOTIFICATION-TYPE
    OBJECTS { 
              br48_source_mac, 
              br48_dest_mac,
              br48_vlan_id,
              br48_interface 
            }
    STATUS current
    DESCRIPTION
        "Notification of Event BR.48

        Message: 'Frame dropped from $1 to $2, vlan ID $3 egress filt, not active on interface $4'

        Parameters list:
              $1: br48_source_mac
              $2: br48_dest_mac
              $3: br48_vlan_id
              $4: br48_interface

        A frame has been received, but its VLAN ID is not active in the
        this port bridge. The frame will be dropped."
    ::= { brNotificationsPrefix 48 }


END
