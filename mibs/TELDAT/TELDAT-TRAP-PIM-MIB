-- file automatically created


TELDAT-TRAP-PIM-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


pimTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the PIM event subsystem."
    REVISION "201401200930Z"
    DESCRIPTION "Initial implementation"
        ::= { telEventTraps 238 }


pimEventsGroup	OBJECT IDENTIFIER	::= { pimTrapsMIB 1 }

pimNotifications	OBJECT IDENTIFIER	::= { pimTrapsMIB 2 }
pimNotificationsPrefix	OBJECT IDENTIFIER	::= { pimNotifications 0 }

pimEventObjects1 OBJECT-IDENTITY
    STATUS current
    DESCRIPTION
        "Event PIM.1
        Event related to protocol at virtual interface"
    ::= { pimEventsGroup 1 }

pim1_ifc_name OBJECT-TYPE
    SYNTAX DisplayString
    MAX-ACCESS accessible-for-notify
    STATUS current
    DESCRIPTION
        "Parameter 'ifc_name' in event PIM.1"
    ::= { pimEventObjects1 1 }

pim1_message OBJECT-TYPE
    SYNTAX DisplayString
    MAX-ACCESS accessible-for-notify
    STATUS current
    DESCRIPTION
        "Parameter 'message' in event PIM.1"
    ::= { pimEventObjects1 2 }

pimEventObjects2 OBJECT-IDENTITY
    STATUS current
    DESCRIPTION
        "Event PIM.2
        An errored packet was received from specified address on specified interface"
    ::= { pimEventsGroup 2 }

pim2_source-address OBJECT-TYPE
    SYNTAX IpAddress
    MAX-ACCESS accessible-for-notify
    STATUS current
    DESCRIPTION
        "Parameter 'source-address' in event PIM.2"
    ::= { pimEventObjects2 1 }

pim2_interface OBJECT-TYPE
    SYNTAX DisplayString
    MAX-ACCESS accessible-for-notify
    STATUS current
    DESCRIPTION
        "Parameter 'interface' in event PIM.2"
    ::= { pimEventObjects2 2 }

pimEventObjects3 OBJECT-IDENTITY
    STATUS current
    DESCRIPTION
        "Event PIM.3
        Description of previous event."
    ::= { pimEventsGroup 3 }

pim3_description OBJECT-TYPE
    SYNTAX DisplayString
    MAX-ACCESS accessible-for-notify
    STATUS current
    DESCRIPTION
        "Parameter 'description' in event PIM.3"
    ::= { pimEventObjects3 1 }

pimEventObjects4 OBJECT-IDENTITY
    STATUS current
    DESCRIPTION
        "Event PIM.4
        Ignore a received packet that is of an unknown PIM type"
    ::= { pimEventsGroup 4 }

pim4_message_type OBJECT-TYPE
    SYNTAX Integer32
    MAX-ACCESS accessible-for-notify
    STATUS current
    DESCRIPTION
        "Parameter 'message_type' in event PIM.4"
    ::= { pimEventObjects4 1 }

pim4_source-address OBJECT-TYPE
    SYNTAX IpAddress
    MAX-ACCESS accessible-for-notify
    STATUS current
    DESCRIPTION
        "Parameter 'source-address' in event PIM.4"
    ::= { pimEventObjects4 2 }

pim4_destination-address OBJECT-TYPE
    SYNTAX IpAddress
    MAX-ACCESS accessible-for-notify
    STATUS current
    DESCRIPTION
        "Parameter 'destination-address' in event PIM.4"
    ::= { pimEventObjects4 3 }

pimEventObjects5 OBJECT-IDENTITY
    STATUS current
    DESCRIPTION
        "Event PIM.5
        Received PIM %s from non-directly connected or not PIM router. Ignore it."
    ::= { pimEventsGroup 5 }

pim5_message OBJECT-TYPE
    SYNTAX DisplayString
    MAX-ACCESS accessible-for-notify
    STATUS current
    DESCRIPTION
        "Parameter 'message' in event PIM.5"
    ::= { pimEventObjects5 1 }

pim5_non-neighbour-address OBJECT-TYPE
    SYNTAX IpAddress
    MAX-ACCESS accessible-for-notify
    STATUS current
    DESCRIPTION
        "Parameter 'non-neighbour-address' in event PIM.5"
    ::= { pimEventObjects5 2 }

pimEventObjects6 OBJECT-IDENTITY
    STATUS current
    DESCRIPTION
        "Event PIM.6
        Event in Reverse Path Forwarding towards a source or RP"
    ::= { pimEventsGroup 6 }

pim6_rp-src OBJECT-TYPE
    SYNTAX DisplayString
    MAX-ACCESS accessible-for-notify
    STATUS current
    DESCRIPTION
        "Parameter 'rp-src' in event PIM.6"
    ::= { pimEventObjects6 1 }

pim6_address OBJECT-TYPE
    SYNTAX IpAddress
    MAX-ACCESS accessible-for-notify
    STATUS current
    DESCRIPTION
        "Parameter 'address' in event PIM.6"
    ::= { pimEventObjects6 2 }

pim6_message OBJECT-TYPE
    SYNTAX DisplayString
    MAX-ACCESS accessible-for-notify
    STATUS current
    DESCRIPTION
        "Parameter 'message' in event PIM.6"
    ::= { pimEventObjects6 3 }

pimEventObjects7 OBJECT-IDENTITY
    STATUS current
    DESCRIPTION
        "Event PIM.7
        Description of previous event."
    ::= { pimEventsGroup 7 }

pim7_description OBJECT-TYPE
    SYNTAX DisplayString
    MAX-ACCESS accessible-for-notify
    STATUS current
    DESCRIPTION
        "Parameter 'description' in event PIM.7"
    ::= { pimEventObjects7 1 }

pimEventObjects10 OBJECT-IDENTITY
    STATUS current
    DESCRIPTION
        "Event PIM.10
        Not enough bytes in the message as advertised"
    ::= { pimEventsGroup 10 }

pim10_source_address OBJECT-TYPE
    SYNTAX IpAddress
    MAX-ACCESS accessible-for-notify
    STATUS current
    DESCRIPTION
        "Parameter 'source_address' in event PIM.10"
    ::= { pimEventObjects10 1 }

pimEventObjects11 OBJECT-IDENTITY
    STATUS current
    DESCRIPTION
        "Event PIM.11
        Invalid option length in PIM HELLO message"
    ::= { pimEventsGroup 11 }

pim11_source_address OBJECT-TYPE
    SYNTAX DisplayString
    MAX-ACCESS accessible-for-notify
    STATUS current
    DESCRIPTION
        "Parameter 'source_address' in event PIM.11"
    ::= { pimEventObjects11 1 }

pim11_option OBJECT-TYPE
    SYNTAX IpAddress
    MAX-ACCESS accessible-for-notify
    STATUS current
    DESCRIPTION
        "Parameter 'option' in event PIM.11"
    ::= { pimEventObjects11 2 }

pim11_option_length OBJECT-TYPE
    SYNTAX Integer32
    MAX-ACCESS accessible-for-notify
    STATUS current
    DESCRIPTION
        "Parameter 'option_length' in event PIM.11"
    ::= { pimEventObjects11 3 }

pimEventObjects12 OBJECT-IDENTITY
    STATUS current
    DESCRIPTION
        "Event PIM.12
        Ignore any unknown HELLO options"
    ::= { pimEventsGroup 12 }

pim12_option_type OBJECT-TYPE
    SYNTAX Integer32
    MAX-ACCESS accessible-for-notify
    STATUS current
    DESCRIPTION
        "Parameter 'option_type' in event PIM.12"
    ::= { pimEventObjects12 1 }

pim12_source_address OBJECT-TYPE
    SYNTAX IpAddress
    MAX-ACCESS accessible-for-notify
    STATUS current
    DESCRIPTION
        "Parameter 'source_address' in event PIM.12"
    ::= { pimEventObjects12 2 }

pimEventObjects13 OBJECT-IDENTITY
    STATUS current
    DESCRIPTION
        "Event PIM.13
        Ignore a PIM HELLO message from non-neighbour router"
    ::= { pimEventsGroup 13 }

pim13_source_address OBJECT-TYPE
    SYNTAX IpAddress
    MAX-ACCESS accessible-for-notify
    STATUS current
    DESCRIPTION
        "Parameter 'source_address' in event PIM.13"
    ::= { pimEventObjects13 1 }

pimEventObjects14 OBJECT-IDENTITY
    STATUS current
    DESCRIPTION
        "Event PIM.14
        Deny a PIM HELLO message by neighbour filter access-list"
    ::= { pimEventsGroup 14 }

pim14_source_address OBJECT-TYPE
    SYNTAX IpAddress
    MAX-ACCESS accessible-for-notify
    STATUS current
    DESCRIPTION
        "Parameter 'source_address' in event PIM.14"
    ::= { pimEventObjects14 1 }

pim14_access-list-number OBJECT-TYPE
    SYNTAX Integer32
    MAX-ACCESS accessible-for-notify
    STATUS current
    DESCRIPTION
        "Parameter 'access-list-number' in event PIM.14"
    ::= { pimEventObjects14 2 }

pimEventObjects15 OBJECT-IDENTITY
    STATUS current
    DESCRIPTION
        "Event PIM.15
        Received PIM HELLO with holdtime and DR priority at an interface"
    ::= { pimEventsGroup 15 }

pim15_source-address OBJECT-TYPE
    SYNTAX IpAddress
    MAX-ACCESS accessible-for-notify
    STATUS current
    DESCRIPTION
        "Parameter 'source-address' in event PIM.15"
    ::= { pimEventObjects15 1 }

pim15_holdtime OBJECT-TYPE
    SYNTAX Integer32
    MAX-ACCESS accessible-for-notify
    STATUS current
    DESCRIPTION
        "Parameter 'holdtime' in event PIM.15"
    ::= { pimEventObjects15 2 }

pim15_DR-priority OBJECT-TYPE
    SYNTAX DisplayString
    MAX-ACCESS accessible-for-notify
    STATUS current
    DESCRIPTION
        "Parameter 'DR-priority' in event PIM.15"
    ::= { pimEventObjects15 3 }

pim15_incomingifc OBJECT-TYPE
    SYNTAX DisplayString
    MAX-ACCESS accessible-for-notify
    STATUS current
    DESCRIPTION
        "Parameter 'incomingifc' in event PIM.15"
    ::= { pimEventObjects15 4 }

pimEventObjects16 OBJECT-IDENTITY
    STATUS current
    DESCRIPTION
        "Event PIM.16
        Relevant action related to a neighbour"
    ::= { pimEventsGroup 16 }

pim16_nbr-addr OBJECT-TYPE
    SYNTAX IpAddress
    MAX-ACCESS accessible-for-notify
    STATUS current
    DESCRIPTION
        "Parameter 'nbr-addr' in event PIM.16"
    ::= { pimEventObjects16 1 }

pim16_interface OBJECT-TYPE
    SYNTAX DisplayString
    MAX-ACCESS accessible-for-notify
    STATUS current
    DESCRIPTION
        "Parameter 'interface' in event PIM.16"
    ::= { pimEventObjects16 2 }

pim16_message OBJECT-TYPE
    SYNTAX DisplayString
    MAX-ACCESS accessible-for-notify
    STATUS current
    DESCRIPTION
        "Parameter 'message' in event PIM.16"
    ::= { pimEventObjects16 3 }

pimEventObjects17 OBJECT-IDENTITY
    STATUS current
    DESCRIPTION
        "Event PIM.17
        Sending PIM HELLO to all PIM routers group through an interface"
    ::= { pimEventsGroup 17 }

pim17_source-address OBJECT-TYPE
    SYNTAX IpAddress
    MAX-ACCESS accessible-for-notify
    STATUS current
    DESCRIPTION
        "Parameter 'source-address' in event PIM.17"
    ::= { pimEventObjects17 1 }

pim17_holdtime OBJECT-TYPE
    SYNTAX Integer32
    MAX-ACCESS accessible-for-notify
    STATUS current
    DESCRIPTION
        "Parameter 'holdtime' in event PIM.17"
    ::= { pimEventObjects17 2 }

pim17_outgoingifc OBJECT-TYPE
    SYNTAX DisplayString
    MAX-ACCESS accessible-for-notify
    STATUS current
    DESCRIPTION
        "Parameter 'outgoingifc' in event PIM.17"
    ::= { pimEventObjects17 3 }

pimEventObjects18 OBJECT-IDENTITY
    STATUS current
    DESCRIPTION
        "Event PIM.18
        DR election results in being the new DR"
    ::= { pimEventsGroup 18 }

pim18_interface OBJECT-TYPE
    SYNTAX DisplayString
    MAX-ACCESS accessible-for-notify
    STATUS current
    DESCRIPTION
        "Parameter 'interface' in event PIM.18"
    ::= { pimEventObjects18 1 }

pim18_address OBJECT-TYPE
    SYNTAX IpAddress
    MAX-ACCESS accessible-for-notify
    STATUS current
    DESCRIPTION
        "Parameter 'address' in event PIM.18"
    ::= { pimEventObjects18 2 }

pimEventObjects19 OBJECT-IDENTITY
    STATUS current
    DESCRIPTION
        "Event PIM.19
        DR election results in another router being the new DR"
    ::= { pimEventsGroup 19 }

pim19_interface OBJECT-TYPE
    SYNTAX DisplayString
    MAX-ACCESS accessible-for-notify
    STATUS current
    DESCRIPTION
        "Parameter 'interface' in event PIM.19"
    ::= { pimEventObjects19 1 }

pim19_address OBJECT-TYPE
    SYNTAX IpAddress
    MAX-ACCESS accessible-for-notify
    STATUS current
    DESCRIPTION
        "Parameter 'address' in event PIM.19"
    ::= { pimEventObjects19 2 }

pimEventObjects21 OBJECT-IDENTITY
    STATUS current
    DESCRIPTION
        "Event PIM.21
        Error receiving PIM REGISTER"
    ::= { pimEventsGroup 21 }

pim21_source_address OBJECT-TYPE
    SYNTAX IpAddress
    MAX-ACCESS accessible-for-notify
    STATUS current
    DESCRIPTION
        "Parameter 'source_address' in event PIM.21"
    ::= { pimEventObjects21 1 }

pim21_error_message OBJECT-TYPE
    SYNTAX DisplayString
    MAX-ACCESS accessible-for-notify
    STATUS current
    DESCRIPTION
        "Parameter 'error_message' in event PIM.21"
    ::= { pimEventObjects21 2 }

pimEventObjects22 OBJECT-IDENTITY
    STATUS current
    DESCRIPTION
        "Event PIM.22
        Received PIM REGISTER from source, with encapsulated packet."
    ::= { pimEventsGroup 22 }

pim22_source-address OBJECT-TYPE
    SYNTAX IpAddress
    MAX-ACCESS accessible-for-notify
    STATUS current
    DESCRIPTION
        "Parameter 'source-address' in event PIM.22"
    ::= { pimEventObjects22 1 }

pim22_inner-src OBJECT-TYPE
    SYNTAX IpAddress
    MAX-ACCESS accessible-for-notify
    STATUS current
    DESCRIPTION
        "Parameter 'inner-src' in event PIM.22"
    ::= { pimEventObjects22 2 }

pim22_inner-grp OBJECT-TYPE
    SYNTAX IpAddress
    MAX-ACCESS accessible-for-notify
    STATUS current
    DESCRIPTION
        "Parameter 'inner-grp' in event PIM.22"
    ::= { pimEventObjects22 3 }

pimEventObjects23 OBJECT-IDENTITY
    STATUS current
    DESCRIPTION
        "Event PIM.23
        Received PIM NULL-REGISTER from source, with dummy IP packet."
    ::= { pimEventsGroup 23 }

pim23_source-address OBJECT-TYPE
    SYNTAX IpAddress
    MAX-ACCESS accessible-for-notify
    STATUS current
    DESCRIPTION
        "Parameter 'source-address' in event PIM.23"
    ::= { pimEventObjects23 1 }

pim23_inner-src OBJECT-TYPE
    SYNTAX IpAddress
    MAX-ACCESS accessible-for-notify
    STATUS current
    DESCRIPTION
        "Parameter 'inner-src' in event PIM.23"
    ::= { pimEventObjects23 2 }

pim23_inner-grp OBJECT-TYPE
    SYNTAX IpAddress
    MAX-ACCESS accessible-for-notify
    STATUS current
    DESCRIPTION
        "Parameter 'inner-grp' in event PIM.23"
    ::= { pimEventObjects23 3 }

pimEventObjects24 OBJECT-IDENTITY
    STATUS current
    DESCRIPTION
        "Event PIM.24
        Received a PIM REGISTER STOP from Rendevouz-Point"
    ::= { pimEventsGroup 24 }

pim24_rp_address OBJECT-TYPE
    SYNTAX IpAddress
    MAX-ACCESS accessible-for-notify
    STATUS current
    DESCRIPTION
        "Parameter 'rp_address' in event PIM.24"
    ::= { pimEventObjects24 1 }

pim24_destination_address OBJECT-TYPE
    SYNTAX IpAddress
    MAX-ACCESS accessible-for-notify
    STATUS current
    DESCRIPTION
        "Parameter 'destination_address' in event PIM.24"
    ::= { pimEventObjects24 2 }

pim24_source_address OBJECT-TYPE
    SYNTAX IpAddress
    MAX-ACCESS accessible-for-notify
    STATUS current
    DESCRIPTION
        "Parameter 'source_address' in event PIM.24"
    ::= { pimEventObjects24 3 }

pim24_group_address OBJECT-TYPE
    SYNTAX IpAddress
    MAX-ACCESS accessible-for-notify
    STATUS current
    DESCRIPTION
        "Parameter 'group_address' in event PIM.24"
    ::= { pimEventObjects24 4 }

pimEventObjects25 OBJECT-IDENTITY
    STATUS current
    DESCRIPTION
        "Event PIM.25
        Sending PIM REGISTER STOP message from Rendezvous-Point (RP) to Designated Router (DR)"
    ::= { pimEventsGroup 25 }

pim25_source-address OBJECT-TYPE
    SYNTAX IpAddress
    MAX-ACCESS accessible-for-notify
    STATUS current
    DESCRIPTION
        "Parameter 'source-address' in event PIM.25"
    ::= { pimEventObjects25 1 }

pim25_destination-address OBJECT-TYPE
    SYNTAX IpAddress
    MAX-ACCESS accessible-for-notify
    STATUS current
    DESCRIPTION
        "Parameter 'destination-address' in event PIM.25"
    ::= { pimEventObjects25 2 }

pim25_source_address OBJECT-TYPE
    SYNTAX IpAddress
    MAX-ACCESS accessible-for-notify
    STATUS current
    DESCRIPTION
        "Parameter 'source_address' in event PIM.25"
    ::= { pimEventObjects25 3 }

pim25_group_address OBJECT-TYPE
    SYNTAX IpAddress
    MAX-ACCESS accessible-for-notify
    STATUS current
    DESCRIPTION
        "Parameter 'group_address' in event PIM.25"
    ::= { pimEventObjects25 4 }

pimEventObjects26 OBJECT-IDENTITY
    STATUS current
    DESCRIPTION
        "Event PIM.26
        Sending PIM REGISTER message for a state from Designated Router (DR) to Rendezvous-Point (RP)"
    ::= { pimEventsGroup 26 }

pim26_source-address OBJECT-TYPE
    SYNTAX IpAddress
    MAX-ACCESS accessible-for-notify
    STATUS current
    DESCRIPTION
        "Parameter 'source-address' in event PIM.26"
    ::= { pimEventObjects26 1 }

pim26_group-address OBJECT-TYPE
    SYNTAX IpAddress
    MAX-ACCESS accessible-for-notify
    STATUS current
    DESCRIPTION
        "Parameter 'group-address' in event PIM.26"
    ::= { pimEventObjects26 2 }

pimEventObjects27 OBJECT-IDENTITY
    STATUS current
    DESCRIPTION
        "Event PIM.27
        Sending PIM NULL REGISTER message for a state from Designated Router (DR) to Rendezvous-Point (RP)"
    ::= { pimEventsGroup 27 }

pim27_source-address OBJECT-TYPE
    SYNTAX IpAddress
    MAX-ACCESS accessible-for-notify
    STATUS current
    DESCRIPTION
        "Parameter 'source-address' in event PIM.27"
    ::= { pimEventObjects27 1 }

pim27_group-address OBJECT-TYPE
    SYNTAX IpAddress
    MAX-ACCESS accessible-for-notify
    STATUS current
    DESCRIPTION
        "Parameter 'group-address' in event PIM.27"
    ::= { pimEventObjects27 2 }

pimEventObjects28 OBJECT-IDENTITY
    STATUS current
    DESCRIPTION
        "Event PIM.28
        Action related to Register-Stop timer"
    ::= { pimEventsGroup 28 }

pim28_srcaddr OBJECT-TYPE
    SYNTAX IpAddress
    MAX-ACCESS accessible-for-notify
    STATUS current
    DESCRIPTION
        "Parameter 'srcaddr' in event PIM.28"
    ::= { pimEventObjects28 1 }

pim28_grpaddr OBJECT-TYPE
    SYNTAX IpAddress
    MAX-ACCESS accessible-for-notify
    STATUS current
    DESCRIPTION
        "Parameter 'grpaddr' in event PIM.28"
    ::= { pimEventObjects28 2 }

pim28_message OBJECT-TYPE
    SYNTAX DisplayString
    MAX-ACCESS accessible-for-notify
    STATUS current
    DESCRIPTION
        "Parameter 'message' in event PIM.28"
    ::= { pimEventObjects28 3 }

pimEventObjects29 OBJECT-IDENTITY
    STATUS current
    DESCRIPTION
        "Event PIM.29
        Add PIM JOIN/PRUNE entry to JP message"
    ::= { pimEventsGroup 29 }

pim29_join-prune OBJECT-TYPE
    SYNTAX DisplayString
    MAX-ACCESS accessible-for-notify
    STATUS current
    DESCRIPTION
        "Parameter 'join-prune' in event PIM.29"
    ::= { pimEventObjects29 1 }

pim29_state OBJECT-TYPE
    SYNTAX DisplayString
    MAX-ACCESS accessible-for-notify
    STATUS current
    DESCRIPTION
        "Parameter 'state' in event PIM.29"
    ::= { pimEventObjects29 2 }

pim29_dest-address OBJECT-TYPE
    SYNTAX IpAddress
    MAX-ACCESS accessible-for-notify
    STATUS current
    DESCRIPTION
        "Parameter 'dest-address' in event PIM.29"
    ::= { pimEventObjects29 3 }

pimEventObjects30 OBJECT-IDENTITY
    STATUS current
    DESCRIPTION
        "Event PIM.30
        Sending PIM JOIN/PRUNE message to all PIM routers group"
    ::= { pimEventsGroup 30 }

pim30_source-address OBJECT-TYPE
    SYNTAX DisplayString
    MAX-ACCESS accessible-for-notify
    STATUS current
    DESCRIPTION
        "Parameter 'source-address' in event PIM.30"
    ::= { pimEventObjects30 1 }

pim30_destination-address OBJECT-TYPE
    SYNTAX DisplayString
    MAX-ACCESS accessible-for-notify
    STATUS current
    DESCRIPTION
        "Parameter 'destination-address' in event PIM.30"
    ::= { pimEventObjects30 2 }

pim30_out-interface OBJECT-TYPE
    SYNTAX DisplayString
    MAX-ACCESS accessible-for-notify
    STATUS current
    DESCRIPTION
        "Parameter 'out-interface' in event PIM.30"
    ::= { pimEventObjects30 3 }

pimEventObjects31 OBJECT-IDENTITY
    STATUS current
    DESCRIPTION
        "Event PIM.31
        Error seeing/receiving PIM JOIN/PRUNE"
    ::= { pimEventsGroup 31 }

pim31_type OBJECT-TYPE
    SYNTAX DisplayString
    MAX-ACCESS accessible-for-notify
    STATUS current
    DESCRIPTION
        "Parameter 'type' in event PIM.31"
    ::= { pimEventObjects31 1 }

pim31_error_message OBJECT-TYPE
    SYNTAX DisplayString
    MAX-ACCESS accessible-for-notify
    STATUS current
    DESCRIPTION
        "Parameter 'error_message' in event PIM.31"
    ::= { pimEventObjects31 2 }

pimEventObjects32 OBJECT-IDENTITY
    STATUS current
    DESCRIPTION
        "Event PIM.32
        Received PIM JOIN/PRUNE message"
    ::= { pimEventsGroup 32 }

pim32_source-address OBJECT-TYPE
    SYNTAX IpAddress
    MAX-ACCESS accessible-for-notify
    STATUS current
    DESCRIPTION
        "Parameter 'source-address' in event PIM.32"
    ::= { pimEventObjects32 1 }

pim32_destination-address OBJECT-TYPE
    SYNTAX IpAddress
    MAX-ACCESS accessible-for-notify
    STATUS current
    DESCRIPTION
        "Parameter 'destination-address' in event PIM.32"
    ::= { pimEventObjects32 2 }

pim32_incoming-interface OBJECT-TYPE
    SYNTAX DisplayString
    MAX-ACCESS accessible-for-notify
    STATUS current
    DESCRIPTION
        "Parameter 'incoming-interface' in event PIM.32"
    ::= { pimEventObjects32 3 }

pimEventObjects33 OBJECT-IDENTITY
    STATUS current
    DESCRIPTION
        "Event PIM.33
        Received PIM JOIN"
    ::= { pimEventsGroup 33 }

pim33_state OBJECT-TYPE
    SYNTAX DisplayString
    MAX-ACCESS accessible-for-notify
    STATUS current
    DESCRIPTION
        "Parameter 'state' in event PIM.33"
    ::= { pimEventObjects33 1 }

pimEventObjects34 OBJECT-IDENTITY
    STATUS current
    DESCRIPTION
        "Event PIM.34
        Received PIM PRUNE"
    ::= { pimEventsGroup 34 }

pim34_state OBJECT-TYPE
    SYNTAX DisplayString
    MAX-ACCESS accessible-for-notify
    STATUS current
    DESCRIPTION
        "Parameter 'state' in event PIM.34"
    ::= { pimEventObjects34 1 }

pimEventObjects35 OBJECT-IDENTITY
    STATUS current
    DESCRIPTION
        "Event PIM.35
        See a JOIN/PRUNE message not addressed to me."
    ::= { pimEventsGroup 35 }

pim35_source-address OBJECT-TYPE
    SYNTAX IpAddress
    MAX-ACCESS accessible-for-notify
    STATUS current
    DESCRIPTION
        "Parameter 'source-address' in event PIM.35"
    ::= { pimEventObjects35 1 }

pim35_destination-address OBJECT-TYPE
    SYNTAX IpAddress
    MAX-ACCESS accessible-for-notify
    STATUS current
    DESCRIPTION
        "Parameter 'destination-address' in event PIM.35"
    ::= { pimEventObjects35 2 }

pim35_incoming-interface OBJECT-TYPE
    SYNTAX DisplayString
    MAX-ACCESS accessible-for-notify
    STATUS current
    DESCRIPTION
        "Parameter 'incoming-interface' in event PIM.35"
    ::= { pimEventObjects35 3 }

pimEventObjects36 OBJECT-IDENTITY
    STATUS current
    DESCRIPTION
        "Event PIM.36
        See PIM JOIN"
    ::= { pimEventsGroup 36 }

pim36_state OBJECT-TYPE
    SYNTAX DisplayString
    MAX-ACCESS accessible-for-notify
    STATUS current
    DESCRIPTION
        "Parameter 'state' in event PIM.36"
    ::= { pimEventObjects36 1 }

pimEventObjects37 OBJECT-IDENTITY
    STATUS current
    DESCRIPTION
        "Event PIM.37
        See PIM PRUNE"
    ::= { pimEventsGroup 37 }

pim37_state OBJECT-TYPE
    SYNTAX DisplayString
    MAX-ACCESS accessible-for-notify
    STATUS current
    DESCRIPTION
        "Parameter 'state' in event PIM.37"
    ::= { pimEventObjects37 1 }

pimEventObjects38 OBJECT-IDENTITY
    STATUS current
    DESCRIPTION
        "Event PIM.38
        RPTJoinDesired/JoinDesired/PruneDesired changes"
    ::= { pimEventsGroup 38 }

pim38_state OBJECT-TYPE
    SYNTAX DisplayString
    MAX-ACCESS accessible-for-notify
    STATUS current
    DESCRIPTION
        "Parameter 'state' in event PIM.38"
    ::= { pimEventObjects38 1 }

pim38_info OBJECT-TYPE
    SYNTAX DisplayString
    MAX-ACCESS accessible-for-notify
    STATUS current
    DESCRIPTION
        "Parameter 'info' in event PIM.38"
    ::= { pimEventObjects38 2 }

pim38_prev-val OBJECT-TYPE
    SYNTAX DisplayString
    MAX-ACCESS accessible-for-notify
    STATUS current
    DESCRIPTION
        "Parameter 'prev-val' in event PIM.38"
    ::= { pimEventObjects38 3 }

pim38_new-val OBJECT-TYPE
    SYNTAX DisplayString
    MAX-ACCESS accessible-for-notify
    STATUS current
    DESCRIPTION
        "Parameter 'new-val' in event PIM.38"
    ::= { pimEventObjects38 4 }

pimEventObjects39 OBJECT-IDENTITY
    STATUS current
    DESCRIPTION
        "Event PIM.39
        Action related to Override Timer"
    ::= { pimEventsGroup 39 }

pim39_srcaddr OBJECT-TYPE
    SYNTAX IpAddress
    MAX-ACCESS accessible-for-notify
    STATUS current
    DESCRIPTION
        "Parameter 'srcaddr' in event PIM.39"
    ::= { pimEventObjects39 1 }

pim39_grpaddr OBJECT-TYPE
    SYNTAX IpAddress
    MAX-ACCESS accessible-for-notify
    STATUS current
    DESCRIPTION
        "Parameter 'grpaddr' in event PIM.39"
    ::= { pimEventObjects39 2 }

pim39_message OBJECT-TYPE
    SYNTAX DisplayString
    MAX-ACCESS accessible-for-notify
    STATUS current
    DESCRIPTION
        "Parameter 'message' in event PIM.39"
    ::= { pimEventObjects39 3 }

pimEventObjects40 OBJECT-IDENTITY
    STATUS current
    DESCRIPTION
        "Event PIM.40
        Action related to JOIN/PRUNE Timer"
    ::= { pimEventsGroup 40 }

pim40_state OBJECT-TYPE
    SYNTAX DisplayString
    MAX-ACCESS accessible-for-notify
    STATUS current
    DESCRIPTION
        "Parameter 'state' in event PIM.40"
    ::= { pimEventObjects40 1 }

pim40_message OBJECT-TYPE
    SYNTAX DisplayString
    MAX-ACCESS accessible-for-notify
    STATUS current
    DESCRIPTION
        "Parameter 'message' in event PIM.40"
    ::= { pimEventObjects40 2 }

pimEventObjects41 OBJECT-IDENTITY
    STATUS current
    DESCRIPTION
        "Event PIM.41
        Received PIM ASSERT/ASSERT_CANCEL(*,G)"
    ::= { pimEventsGroup 41 }

pim41_assert_type OBJECT-TYPE
    SYNTAX DisplayString
    MAX-ACCESS accessible-for-notify
    STATUS current
    DESCRIPTION
        "Parameter 'assert_type' in event PIM.41"
    ::= { pimEventObjects41 1 }

pim41_group-address OBJECT-TYPE
    SYNTAX IpAddress
    MAX-ACCESS accessible-for-notify
    STATUS current
    DESCRIPTION
        "Parameter 'group-address' in event PIM.41"
    ::= { pimEventObjects41 2 }

pim41_nbr-address OBJECT-TYPE
    SYNTAX IpAddress
    MAX-ACCESS accessible-for-notify
    STATUS current
    DESCRIPTION
        "Parameter 'nbr-address' in event PIM.41"
    ::= { pimEventObjects41 3 }

pimEventObjects42 OBJECT-IDENTITY
    STATUS current
    DESCRIPTION
        "Event PIM.42
        Received PIM ASSERT/ASSERT_CANCEL(S,G)"
    ::= { pimEventsGroup 42 }

pim42_assert_type OBJECT-TYPE
    SYNTAX DisplayString
    MAX-ACCESS accessible-for-notify
    STATUS current
    DESCRIPTION
        "Parameter 'assert_type' in event PIM.42"
    ::= { pimEventObjects42 1 }

pim42_source-address OBJECT-TYPE
    SYNTAX IpAddress
    MAX-ACCESS accessible-for-notify
    STATUS current
    DESCRIPTION
        "Parameter 'source-address' in event PIM.42"
    ::= { pimEventObjects42 2 }

pim42_group-address OBJECT-TYPE
    SYNTAX IpAddress
    MAX-ACCESS accessible-for-notify
    STATUS current
    DESCRIPTION
        "Parameter 'group-address' in event PIM.42"
    ::= { pimEventObjects42 3 }

pim42_nbr-address OBJECT-TYPE
    SYNTAX IpAddress
    MAX-ACCESS accessible-for-notify
    STATUS current
    DESCRIPTION
        "Parameter 'nbr-address' in event PIM.42"
    ::= { pimEventObjects42 4 }

pimEventObjects43 OBJECT-IDENTITY
    STATUS current
    DESCRIPTION
        "Event PIM.43
        Sending PIM ASSERT/ASSERT_CANCEL(*,G) to all PIM routers group"
    ::= { pimEventsGroup 43 }

pim43_assert_type OBJECT-TYPE
    SYNTAX DisplayString
    MAX-ACCESS accessible-for-notify
    STATUS current
    DESCRIPTION
        "Parameter 'assert_type' in event PIM.43"
    ::= { pimEventObjects43 1 }

pim43_group-address OBJECT-TYPE
    SYNTAX IpAddress
    MAX-ACCESS accessible-for-notify
    STATUS current
    DESCRIPTION
        "Parameter 'group-address' in event PIM.43"
    ::= { pimEventObjects43 2 }

pim43_out-interface OBJECT-TYPE
    SYNTAX DisplayString
    MAX-ACCESS accessible-for-notify
    STATUS current
    DESCRIPTION
        "Parameter 'out-interface' in event PIM.43"
    ::= { pimEventObjects43 3 }

pimEventObjects44 OBJECT-IDENTITY
    STATUS current
    DESCRIPTION
        "Event PIM.44
        Sending PIM ASSERT/ASSERT_CANCEL(S,G) to all PIM routers group"
    ::= { pimEventsGroup 44 }

pim44_assert_type OBJECT-TYPE
    SYNTAX DisplayString
    MAX-ACCESS accessible-for-notify
    STATUS current
    DESCRIPTION
        "Parameter 'assert_type' in event PIM.44"
    ::= { pimEventObjects44 1 }

pim44_source-address OBJECT-TYPE
    SYNTAX IpAddress
    MAX-ACCESS accessible-for-notify
    STATUS current
    DESCRIPTION
        "Parameter 'source-address' in event PIM.44"
    ::= { pimEventObjects44 2 }

pim44_group-address OBJECT-TYPE
    SYNTAX IpAddress
    MAX-ACCESS accessible-for-notify
    STATUS current
    DESCRIPTION
        "Parameter 'group-address' in event PIM.44"
    ::= { pimEventObjects44 3 }

pim44_out-interface OBJECT-TYPE
    SYNTAX DisplayString
    MAX-ACCESS accessible-for-notify
    STATUS current
    DESCRIPTION
        "Parameter 'out-interface' in event PIM.44"
    ::= { pimEventObjects44 4 }

pimEventObjects45 OBJECT-IDENTITY
    STATUS current
    DESCRIPTION
        "Event PIM.45
        Action related to Assert timer"
    ::= { pimEventsGroup 45 }

pim45_srcaddr OBJECT-TYPE
    SYNTAX DisplayString
    MAX-ACCESS accessible-for-notify
    STATUS current
    DESCRIPTION
        "Parameter 'srcaddr' in event PIM.45"
    ::= { pimEventObjects45 1 }

pim45_grpaddr OBJECT-TYPE
    SYNTAX IpAddress
    MAX-ACCESS accessible-for-notify
    STATUS current
    DESCRIPTION
        "Parameter 'grpaddr' in event PIM.45"
    ::= { pimEventObjects45 2 }

pim45_interface OBJECT-TYPE
    SYNTAX DisplayString
    MAX-ACCESS accessible-for-notify
    STATUS current
    DESCRIPTION
        "Parameter 'interface' in event PIM.45"
    ::= { pimEventObjects45 3 }

pim45_message OBJECT-TYPE
    SYNTAX DisplayString
    MAX-ACCESS accessible-for-notify
    STATUS current
    DESCRIPTION
        "Parameter 'message' in event PIM.45"
    ::= { pimEventObjects45 4 }

pimEventObjects46 OBJECT-IDENTITY
    STATUS current
    DESCRIPTION
        "Event PIM.46
        Assert state event for an interface in a MRT entry"
    ::= { pimEventsGroup 46 }

pim46_srcaddr OBJECT-TYPE
    SYNTAX DisplayString
    MAX-ACCESS accessible-for-notify
    STATUS current
    DESCRIPTION
        "Parameter 'srcaddr' in event PIM.46"
    ::= { pimEventObjects46 1 }

pim46_grpaddr OBJECT-TYPE
    SYNTAX IpAddress
    MAX-ACCESS accessible-for-notify
    STATUS current
    DESCRIPTION
        "Parameter 'grpaddr' in event PIM.46"
    ::= { pimEventObjects46 2 }

pim46_interface OBJECT-TYPE
    SYNTAX DisplayString
    MAX-ACCESS accessible-for-notify
    STATUS current
    DESCRIPTION
        "Parameter 'interface' in event PIM.46"
    ::= { pimEventObjects46 3 }

pim46_state_event OBJECT-TYPE
    SYNTAX DisplayString
    MAX-ACCESS accessible-for-notify
    STATUS current
    DESCRIPTION
        "Parameter 'state_event' in event PIM.46"
    ::= { pimEventObjects46 4 }

pimEventObjects47 OBJECT-IDENTITY
    STATUS current
    DESCRIPTION
        "Event PIM.47
        Change in KAT for a (S,G) state"
    ::= { pimEventsGroup 47 }

pim47_srcaddr OBJECT-TYPE
    SYNTAX IpAddress
    MAX-ACCESS accessible-for-notify
    STATUS current
    DESCRIPTION
        "Parameter 'srcaddr' in event PIM.47"
    ::= { pimEventObjects47 1 }

pim47_grpaddr OBJECT-TYPE
    SYNTAX IpAddress
    MAX-ACCESS accessible-for-notify
    STATUS current
    DESCRIPTION
        "Parameter 'grpaddr' in event PIM.47"
    ::= { pimEventObjects47 2 }

pim47_message OBJECT-TYPE
    SYNTAX DisplayString
    MAX-ACCESS accessible-for-notify
    STATUS current
    DESCRIPTION
        "Parameter 'message' in event PIM.47"
    ::= { pimEventObjects47 3 }

pimEventObjects48 OBJECT-IDENTITY
    STATUS current
    DESCRIPTION
        "Event PIM.48
        Change in SPT bit for a (S,G) state"
    ::= { pimEventsGroup 48 }

pim48_srcaddr OBJECT-TYPE
    SYNTAX IpAddress
    MAX-ACCESS accessible-for-notify
    STATUS current
    DESCRIPTION
        "Parameter 'srcaddr' in event PIM.48"
    ::= { pimEventObjects48 1 }

pim48_grpaddr OBJECT-TYPE
    SYNTAX IpAddress
    MAX-ACCESS accessible-for-notify
    STATUS current
    DESCRIPTION
        "Parameter 'grpaddr' in event PIM.48"
    ::= { pimEventObjects48 2 }

pim48_message OBJECT-TYPE
    SYNTAX DisplayString
    MAX-ACCESS accessible-for-notify
    STATUS current
    DESCRIPTION
        "Parameter 'message' in event PIM.48"
    ::= { pimEventObjects48 3 }

pimEventObjects50 OBJECT-IDENTITY
    STATUS current
    DESCRIPTION
        "Event PIM.50
        Error while adding or deleting include or exclude on an
        interface"
    ::= { pimEventsGroup 50 }

pim50_add_del OBJECT-TYPE
    SYNTAX DisplayString
    MAX-ACCESS accessible-for-notify
    STATUS current
    DESCRIPTION
        "Parameter 'add_del' in event PIM.50"
    ::= { pimEventObjects50 1 }

pim50_inc_exc OBJECT-TYPE
    SYNTAX DisplayString
    MAX-ACCESS accessible-for-notify
    STATUS current
    DESCRIPTION
        "Parameter 'inc_exc' in event PIM.50"
    ::= { pimEventObjects50 2 }

pim50_state OBJECT-TYPE
    SYNTAX DisplayString
    MAX-ACCESS accessible-for-notify
    STATUS current
    DESCRIPTION
        "Parameter 'state' in event PIM.50"
    ::= { pimEventObjects50 3 }

pim50_ifc OBJECT-TYPE
    SYNTAX DisplayString
    MAX-ACCESS accessible-for-notify
    STATUS current
    DESCRIPTION
        "Parameter 'ifc' in event PIM.50"
    ::= { pimEventObjects50 4 }

pim50_message OBJECT-TYPE
    SYNTAX DisplayString
    MAX-ACCESS accessible-for-notify
    STATUS current
    DESCRIPTION
        "Parameter 'message' in event PIM.50"
    ::= { pimEventObjects50 5 }

pimEventObjects51 OBJECT-IDENTITY
    STATUS current
    DESCRIPTION
        "Event PIM.51
        Add or delete an IGMP include (S,G) leaf"
    ::= { pimEventsGroup 51 }

pim51_add_delete OBJECT-TYPE
    SYNTAX DisplayString
    MAX-ACCESS accessible-for-notify
    STATUS current
    DESCRIPTION
        "Parameter 'add_delete' in event PIM.51"
    ::= { pimEventObjects51 1 }

pim51_interface OBJECT-TYPE
    SYNTAX DisplayString
    MAX-ACCESS accessible-for-notify
    STATUS current
    DESCRIPTION
        "Parameter 'interface' in event PIM.51"
    ::= { pimEventObjects51 2 }

pim51_group_address OBJECT-TYPE
    SYNTAX IpAddress
    MAX-ACCESS accessible-for-notify
    STATUS current
    DESCRIPTION
        "Parameter 'group_address' in event PIM.51"
    ::= { pimEventObjects51 3 }

pim51_source_address OBJECT-TYPE
    SYNTAX IpAddress
    MAX-ACCESS accessible-for-notify
    STATUS current
    DESCRIPTION
        "Parameter 'source_address' in event PIM.51"
    ::= { pimEventObjects51 4 }

pimEventObjects52 OBJECT-IDENTITY
    STATUS current
    DESCRIPTION
        "Event PIM.52
        Add or delete an IGMP exclude (S,G) leaf"
    ::= { pimEventsGroup 52 }

pim52_add_delete OBJECT-TYPE
    SYNTAX DisplayString
    MAX-ACCESS accessible-for-notify
    STATUS current
    DESCRIPTION
        "Parameter 'add_delete' in event PIM.52"
    ::= { pimEventObjects52 1 }

pim52_interface OBJECT-TYPE
    SYNTAX DisplayString
    MAX-ACCESS accessible-for-notify
    STATUS current
    DESCRIPTION
        "Parameter 'interface' in event PIM.52"
    ::= { pimEventObjects52 2 }

pim52_group_address OBJECT-TYPE
    SYNTAX IpAddress
    MAX-ACCESS accessible-for-notify
    STATUS current
    DESCRIPTION
        "Parameter 'group_address' in event PIM.52"
    ::= { pimEventObjects52 3 }

pim52_source_address OBJECT-TYPE
    SYNTAX IpAddress
    MAX-ACCESS accessible-for-notify
    STATUS current
    DESCRIPTION
        "Parameter 'source_address' in event PIM.52"
    ::= { pimEventObjects52 4 }

pimEventObjects53 OBJECT-IDENTITY
    STATUS current
    DESCRIPTION
        "Event PIM.53
        Add or delete an IGMP include (*,G) leaf"
    ::= { pimEventsGroup 53 }

pim53_add_delete OBJECT-TYPE
    SYNTAX DisplayString
    MAX-ACCESS accessible-for-notify
    STATUS current
    DESCRIPTION
        "Parameter 'add_delete' in event PIM.53"
    ::= { pimEventObjects53 1 }

pim53_interface OBJECT-TYPE
    SYNTAX DisplayString
    MAX-ACCESS accessible-for-notify
    STATUS current
    DESCRIPTION
        "Parameter 'interface' in event PIM.53"
    ::= { pimEventObjects53 2 }

pim53_group_address OBJECT-TYPE
    SYNTAX IpAddress
    MAX-ACCESS accessible-for-notify
    STATUS current
    DESCRIPTION
        "Parameter 'group_address' in event PIM.53"
    ::= { pimEventObjects53 3 }

pimEventObjects54 OBJECT-IDENTITY
    STATUS current
    DESCRIPTION
        "Event PIM.54
        Error sending a PIM multicast message"
    ::= { pimEventsGroup 54 }

pim54_source_address OBJECT-TYPE
    SYNTAX IpAddress
    MAX-ACCESS accessible-for-notify
    STATUS current
    DESCRIPTION
        "Parameter 'source_address' in event PIM.54"
    ::= { pimEventObjects54 1 }

pim54_destination_address OBJECT-TYPE
    SYNTAX IpAddress
    MAX-ACCESS accessible-for-notify
    STATUS current
    DESCRIPTION
        "Parameter 'destination_address' in event PIM.54"
    ::= { pimEventObjects54 2 }

pimEventObjects55 OBJECT-IDENTITY
    STATUS current
    DESCRIPTION
        "Event PIM.55
        Sending a PIM unicast message"
    ::= { pimEventsGroup 55 }

pim55_source_address OBJECT-TYPE
    SYNTAX IpAddress
    MAX-ACCESS accessible-for-notify
    STATUS current
    DESCRIPTION
        "Parameter 'source_address' in event PIM.55"
    ::= { pimEventObjects55 1 }

pim55_destination_address OBJECT-TYPE
    SYNTAX IpAddress
    MAX-ACCESS accessible-for-notify
    STATUS current
    DESCRIPTION
        "Parameter 'destination_address' in event PIM.55"
    ::= { pimEventObjects55 2 }

pim55_outgoing_interface OBJECT-TYPE
    SYNTAX DisplayString
    MAX-ACCESS accessible-for-notify
    STATUS current
    DESCRIPTION
        "Parameter 'outgoing_interface' in event PIM.55"
    ::= { pimEventObjects55 3 }

pimEventObjects56 OBJECT-IDENTITY
    STATUS current
    DESCRIPTION
        "Event PIM.56
        Sending a PIM multicast message"
    ::= { pimEventsGroup 56 }

pim56_source_address OBJECT-TYPE
    SYNTAX IpAddress
    MAX-ACCESS accessible-for-notify
    STATUS current
    DESCRIPTION
        "Parameter 'source_address' in event PIM.56"
    ::= { pimEventObjects56 1 }

pim56_destination_address OBJECT-TYPE
    SYNTAX IpAddress
    MAX-ACCESS accessible-for-notify
    STATUS current
    DESCRIPTION
        "Parameter 'destination_address' in event PIM.56"
    ::= { pimEventObjects56 2 }

pim56_outgoing_interface OBJECT-TYPE
    SYNTAX DisplayString
    MAX-ACCESS accessible-for-notify
    STATUS current
    DESCRIPTION
        "Parameter 'outgoing_interface' in event PIM.56"
    ::= { pimEventObjects56 3 }

pimEventObjects58 OBJECT-IDENTITY
    STATUS current
    DESCRIPTION
        "Event PIM.58
        An entry was added or updated in Multicast Forwarding Cache"
    ::= { pimEventsGroup 58 }

pim58_source_address OBJECT-TYPE
    SYNTAX IpAddress
    MAX-ACCESS accessible-for-notify
    STATUS current
    DESCRIPTION
        "Parameter 'source_address' in event PIM.58"
    ::= { pimEventObjects58 1 }

pim58_group_address OBJECT-TYPE
    SYNTAX IpAddress
    MAX-ACCESS accessible-for-notify
    STATUS current
    DESCRIPTION
        "Parameter 'group_address' in event PIM.58"
    ::= { pimEventObjects58 2 }

pim58_incoming-interface OBJECT-TYPE
    SYNTAX DisplayString
    MAX-ACCESS accessible-for-notify
    STATUS current
    DESCRIPTION
        "Parameter 'incoming-interface' in event PIM.58"
    ::= { pimEventObjects58 3 }

pimEventObjects59 OBJECT-IDENTITY
    STATUS current
    DESCRIPTION
        "Event PIM.59
        A MFC entry was not found while trying to remove it."
    ::= { pimEventsGroup 59 }

pim59_source_address OBJECT-TYPE
    SYNTAX IpAddress
    MAX-ACCESS accessible-for-notify
    STATUS current
    DESCRIPTION
        "Parameter 'source_address' in event PIM.59"
    ::= { pimEventObjects59 1 }

pim59_group_address OBJECT-TYPE
    SYNTAX IpAddress
    MAX-ACCESS accessible-for-notify
    STATUS current
    DESCRIPTION
        "Parameter 'group_address' in event PIM.59"
    ::= { pimEventObjects59 2 }

pimEventObjects60 OBJECT-IDENTITY
    STATUS current
    DESCRIPTION
        "Event PIM.60
        Delete a Multicast Forwarding Cache entry"
    ::= { pimEventsGroup 60 }

pim60_source_address OBJECT-TYPE
    SYNTAX IpAddress
    MAX-ACCESS accessible-for-notify
    STATUS current
    DESCRIPTION
        "Parameter 'source_address' in event PIM.60"
    ::= { pimEventObjects60 1 }

pim60_group_address OBJECT-TYPE
    SYNTAX IpAddress
    MAX-ACCESS accessible-for-notify
    STATUS current
    DESCRIPTION
        "Parameter 'group_address' in event PIM.60"
    ::= { pimEventObjects60 2 }

pimEventObjects61 OBJECT-IDENTITY
    STATUS current
    DESCRIPTION
        "Event PIM.61
        An entry is missing on Multicast Forwarding Cache"
    ::= { pimEventsGroup 61 }

pim61_source-address OBJECT-TYPE
    SYNTAX IpAddress
    MAX-ACCESS accessible-for-notify
    STATUS current
    DESCRIPTION
        "Parameter 'source-address' in event PIM.61"
    ::= { pimEventObjects61 1 }

pim61_group-address OBJECT-TYPE
    SYNTAX IpAddress
    MAX-ACCESS accessible-for-notify
    STATUS current
    DESCRIPTION
        "Parameter 'group-address' in event PIM.61"
    ::= { pimEventObjects61 2 }

pim61_incoming-interface OBJECT-TYPE
    SYNTAX DisplayString
    MAX-ACCESS accessible-for-notify
    STATUS current
    DESCRIPTION
        "Parameter 'incoming-interface' in event PIM.61"
    ::= { pimEventObjects61 3 }

pimEventObjects62 OBJECT-IDENTITY
    STATUS current
    DESCRIPTION
        "Event PIM.62
        Create/delete a source entry in Multicas Routing Table"
    ::= { pimEventsGroup 62 }

pim62_action OBJECT-TYPE
    SYNTAX DisplayString
    MAX-ACCESS accessible-for-notify
    STATUS current
    DESCRIPTION
        "Parameter 'action' in event PIM.62"
    ::= { pimEventObjects62 1 }

pim62_source_address OBJECT-TYPE
    SYNTAX IpAddress
    MAX-ACCESS accessible-for-notify
    STATUS current
    DESCRIPTION
        "Parameter 'source_address' in event PIM.62"
    ::= { pimEventObjects62 2 }

pimEventObjects63 OBJECT-IDENTITY
    STATUS current
    DESCRIPTION
        "Event PIM.63
        Create/delete/update a group entry in Multicast Routing Table"
    ::= { pimEventsGroup 63 }

pim63_action OBJECT-TYPE
    SYNTAX DisplayString
    MAX-ACCESS accessible-for-notify
    STATUS current
    DESCRIPTION
        "Parameter 'action' in event PIM.63"
    ::= { pimEventObjects63 1 }

pim63_group_address OBJECT-TYPE
    SYNTAX DisplayString
    MAX-ACCESS accessible-for-notify
    STATUS current
    DESCRIPTION
        "Parameter 'group_address' in event PIM.63"
    ::= { pimEventObjects63 2 }

pim63_text OBJECT-TYPE
    SYNTAX DisplayString
    MAX-ACCESS accessible-for-notify
    STATUS current
    DESCRIPTION
        "Parameter 'text' in event PIM.63"
    ::= { pimEventObjects63 3 }

pimEventObjects64 OBJECT-IDENTITY
    STATUS current
    DESCRIPTION
        "Event PIM.64
        Multicast Routing Table inconsistency for an entry"
    ::= { pimEventsGroup 64 }

pim64_source_address OBJECT-TYPE
    SYNTAX IpAddress
    MAX-ACCESS accessible-for-notify
    STATUS current
    DESCRIPTION
        "Parameter 'source_address' in event PIM.64"
    ::= { pimEventObjects64 1 }

pim64_group_address OBJECT-TYPE
    SYNTAX IpAddress
    MAX-ACCESS accessible-for-notify
    STATUS current
    DESCRIPTION
        "Parameter 'group_address' in event PIM.64"
    ::= { pimEventObjects64 2 }

pimEventObjects65 OBJECT-IDENTITY
    STATUS current
    DESCRIPTION
        "Event PIM.65
        Event related to a Multicast Routing entry"
    ::= { pimEventsGroup 65 }

pim65_pimstate OBJECT-TYPE
    SYNTAX DisplayString
    MAX-ACCESS accessible-for-notify
    STATUS current
    DESCRIPTION
        "Parameter 'pimstate' in event PIM.65"
    ::= { pimEventObjects65 1 }

pim65_message OBJECT-TYPE
    SYNTAX DisplayString
    MAX-ACCESS accessible-for-notify
    STATUS current
    DESCRIPTION
        "Parameter 'message' in event PIM.65"
    ::= { pimEventObjects65 2 }

pimEventObjects66 OBJECT-IDENTITY
    STATUS current
    DESCRIPTION
        "Event PIM.66
        Error seeing/receiving PIM C-RP-Adv"
    ::= { pimEventsGroup 66 }

pim66_type OBJECT-TYPE
    SYNTAX DisplayString
    MAX-ACCESS accessible-for-notify
    STATUS current
    DESCRIPTION
        "Parameter 'type' in event PIM.66"
    ::= { pimEventObjects66 1 }

pim66_error_message OBJECT-TYPE
    SYNTAX DisplayString
    MAX-ACCESS accessible-for-notify
    STATUS current
    DESCRIPTION
        "Parameter 'error_message' in event PIM.66"
    ::= { pimEventObjects66 2 }

pimEventObjects67 OBJECT-IDENTITY
    STATUS current
    DESCRIPTION
        "Event PIM.67
        Check for the minimum length of Bootstrap message."
    ::= { pimEventsGroup 67 }

pim67_message_size OBJECT-TYPE
    SYNTAX Integer32
    MAX-ACCESS accessible-for-notify
    STATUS current
    DESCRIPTION
        "Parameter 'message_size' in event PIM.67"
    ::= { pimEventObjects67 1 }

pim67_source_address OBJECT-TYPE
    SYNTAX IpAddress
    MAX-ACCESS accessible-for-notify
    STATUS current
    DESCRIPTION
        "Parameter 'source_address' in event PIM.67"
    ::= { pimEventObjects67 2 }

pim67_incoming-interface OBJECT-TYPE
    SYNTAX DisplayString
    MAX-ACCESS accessible-for-notify
    STATUS current
    DESCRIPTION
        "Parameter 'incoming-interface' in event PIM.67"
    ::= { pimEventObjects67 3 }

pimEventObjects68 OBJECT-IDENTITY
    STATUS current
    DESCRIPTION
        "Event PIM.68
        Check for the minimum length of candidate RP message."
    ::= { pimEventsGroup 68 }

pim68_message-size OBJECT-TYPE
    SYNTAX Integer32
    MAX-ACCESS accessible-for-notify
    STATUS current
    DESCRIPTION
        "Parameter 'message-size' in event PIM.68"
    ::= { pimEventObjects68 1 }

pim68_source-address OBJECT-TYPE
    SYNTAX IpAddress
    MAX-ACCESS accessible-for-notify
    STATUS current
    DESCRIPTION
        "Parameter 'source-address' in event PIM.68"
    ::= { pimEventObjects68 2 }

pim68_incoming-interface OBJECT-TYPE
    SYNTAX DisplayString
    MAX-ACCESS accessible-for-notify
    STATUS current
    DESCRIPTION
        "Parameter 'incoming-interface' in event PIM.68"
    ::= { pimEventObjects68 3 }

pimEventObjects69 OBJECT-IDENTITY
    STATUS current
    DESCRIPTION
        "Event PIM.69
        Cannot find the receiving incoming interface toward that DR"
    ::= { pimEventsGroup 69 }

pim69_source-address OBJECT-TYPE
    SYNTAX IpAddress
    MAX-ACCESS accessible-for-notify
    STATUS current
    DESCRIPTION
        "Parameter 'source-address' in event PIM.69"
    ::= { pimEventObjects69 1 }

pimEventObjects70 OBJECT-IDENTITY
    STATUS current
    DESCRIPTION
        "Event PIM.70
        Received PIM Bootstrap message"
    ::= { pimEventsGroup 70 }

pim70_source-address OBJECT-TYPE
    SYNTAX IpAddress
    MAX-ACCESS accessible-for-notify
    STATUS current
    DESCRIPTION
        "Parameter 'source-address' in event PIM.70"
    ::= { pimEventObjects70 1 }

pim70_candidate-bsr-address OBJECT-TYPE
    SYNTAX IpAddress
    MAX-ACCESS accessible-for-notify
    STATUS current
    DESCRIPTION
        "Parameter 'candidate-bsr-address' in event PIM.70"
    ::= { pimEventObjects70 2 }

pim70_priority OBJECT-TYPE
    SYNTAX Integer32
    MAX-ACCESS accessible-for-notify
    STATUS current
    DESCRIPTION
        "Parameter 'priority' in event PIM.70"
    ::= { pimEventObjects70 3 }

pim70_incoming-interface OBJECT-TYPE
    SYNTAX DisplayString
    MAX-ACCESS accessible-for-notify
    STATUS current
    DESCRIPTION
        "Parameter 'incoming-interface' in event PIM.70"
    ::= { pimEventObjects70 4 }

pimEventObjects71 OBJECT-IDENTITY
    STATUS current
    DESCRIPTION
        "Event PIM.71
        Received and ignored Bootstrap message"
    ::= { pimEventsGroup 71 }

pim71_incoming-interface OBJECT-TYPE
    SYNTAX DisplayString
    MAX-ACCESS accessible-for-notify
    STATUS current
    DESCRIPTION
        "Parameter 'incoming-interface' in event PIM.71"
    ::= { pimEventObjects71 1 }

pim71_reason OBJECT-TYPE
    SYNTAX DisplayString
    MAX-ACCESS accessible-for-notify
    STATUS current
    DESCRIPTION
        "Parameter 'reason' in event PIM.71"
    ::= { pimEventObjects71 2 }

pimEventObjects72 OBJECT-IDENTITY
    STATUS current
    DESCRIPTION
        "Event PIM.72
        Sending the BSR message to all PIM routers group"
    ::= { pimEventsGroup 72 }

pim72_source-address OBJECT-TYPE
    SYNTAX IpAddress
    MAX-ACCESS accessible-for-notify
    STATUS current
    DESCRIPTION
        "Parameter 'source-address' in event PIM.72"
    ::= { pimEventObjects72 1 }

pim72_destination-address OBJECT-TYPE
    SYNTAX IpAddress
    MAX-ACCESS accessible-for-notify
    STATUS current
    DESCRIPTION
        "Parameter 'destination-address' in event PIM.72"
    ::= { pimEventObjects72 2 }

pim72_outgoing-interface OBJECT-TYPE
    SYNTAX DisplayString
    MAX-ACCESS accessible-for-notify
    STATUS current
    DESCRIPTION
        "Parameter 'outgoing-interface' in event PIM.72"
    ::= { pimEventObjects72 3 }

pimEventObjects73 OBJECT-IDENTITY
    STATUS current
    DESCRIPTION
        "Event PIM.73
        BSR Border cannot sent BSR unicast message."
    ::= { pimEventsGroup 73 }

pim73_destination-address OBJECT-TYPE
    SYNTAX IpAddress
    MAX-ACCESS accessible-for-notify
    STATUS current
    DESCRIPTION
        "Parameter 'destination-address' in event PIM.73"
    ::= { pimEventObjects73 1 }

pim73_outgoing-interface OBJECT-TYPE
    SYNTAX DisplayString
    MAX-ACCESS accessible-for-notify
    STATUS current
    DESCRIPTION
        "Parameter 'outgoing-interface' in event PIM.73"
    ::= { pimEventObjects73 2 }

pimEventObjects74 OBJECT-IDENTITY
    STATUS current
    DESCRIPTION
        "Event PIM.74
        Bootstrap message is not sent because of BSR Border configuration"
    ::= { pimEventsGroup 74 }

pim74_outgoing-interface OBJECT-TYPE
    SYNTAX DisplayString
    MAX-ACCESS accessible-for-notify
    STATUS current
    DESCRIPTION
        "Parameter 'outgoing-interface' in event PIM.74"
    ::= { pimEventObjects74 1 }

pimEventObjects75 OBJECT-IDENTITY
    STATUS current
    DESCRIPTION
        "Event PIM.75
        Forwarding the BSR message to all PIM routers group"
    ::= { pimEventsGroup 75 }

pim75_source-address OBJECT-TYPE
    SYNTAX IpAddress
    MAX-ACCESS accessible-for-notify
    STATUS current
    DESCRIPTION
        "Parameter 'source-address' in event PIM.75"
    ::= { pimEventObjects75 1 }

pim75_destination-address OBJECT-TYPE
    SYNTAX IpAddress
    MAX-ACCESS accessible-for-notify
    STATUS current
    DESCRIPTION
        "Parameter 'destination-address' in event PIM.75"
    ::= { pimEventObjects75 2 }

pim75_outgoing-interface OBJECT-TYPE
    SYNTAX DisplayString
    MAX-ACCESS accessible-for-notify
    STATUS current
    DESCRIPTION
        "Parameter 'outgoing-interface' in event PIM.75"
    ::= { pimEventObjects75 3 }

pimEventObjects76 OBJECT-IDENTITY
    STATUS current
    DESCRIPTION
        "Event PIM.76
        Received C-RP message, if I am the Bootstrap router, process the advertisement"
    ::= { pimEventsGroup 76 }

pim76_source-address OBJECT-TYPE
    SYNTAX IpAddress
    MAX-ACCESS accessible-for-notify
    STATUS current
    DESCRIPTION
        "Parameter 'source-address' in event PIM.76"
    ::= { pimEventObjects76 1 }

pim76_holdtime OBJECT-TYPE
    SYNTAX Integer32
    MAX-ACCESS accessible-for-notify
    STATUS current
    DESCRIPTION
        "Parameter 'holdtime' in event PIM.76"
    ::= { pimEventObjects76 2 }

pim76_incoming-interface OBJECT-TYPE
    SYNTAX DisplayString
    MAX-ACCESS accessible-for-notify
    STATUS current
    DESCRIPTION
        "Parameter 'incoming-interface' in event PIM.76"
    ::= { pimEventObjects76 3 }

pimEventObjects77 OBJECT-IDENTITY
    STATUS current
    DESCRIPTION
        "Event PIM.77
        Sending PIM CANDIDATE RP Advertisement"
    ::= { pimEventsGroup 77 }

pim77_C-RP-address OBJECT-TYPE
    SYNTAX IpAddress
    MAX-ACCESS accessible-for-notify
    STATUS current
    DESCRIPTION
        "Parameter 'C-RP-address' in event PIM.77"
    ::= { pimEventObjects77 1 }

pim77_holdtime OBJECT-TYPE
    SYNTAX Integer32
    MAX-ACCESS accessible-for-notify
    STATUS current
    DESCRIPTION
        "Parameter 'holdtime' in event PIM.77"
    ::= { pimEventObjects77 2 }

pim77_BSR-current-address OBJECT-TYPE
    SYNTAX IpAddress
    MAX-ACCESS accessible-for-notify
    STATUS current
    DESCRIPTION
        "Parameter 'BSR-current-address' in event PIM.77"
    ::= { pimEventObjects77 3 }

pim77_out-interface OBJECT-TYPE
    SYNTAX DisplayString
    MAX-ACCESS accessible-for-notify
    STATUS current
    DESCRIPTION
        "Parameter 'out-interface' in event PIM.77"
    ::= { pimEventObjects77 4 }

pimEventObjects78 OBJECT-IDENTITY
    STATUS current
    DESCRIPTION
        "Event PIM.78
        I am the current DR on that interface, so send an RP-Set message to the new neighbour"
    ::= { pimEventsGroup 78 }

pim78_source-addres OBJECT-TYPE
    SYNTAX IpAddress
    MAX-ACCESS accessible-for-notify
    STATUS current
    DESCRIPTION
        "Parameter 'source-addres' in event PIM.78"
    ::= { pimEventObjects78 1 }

pim78_dest-address OBJECT-TYPE
    SYNTAX IpAddress
    MAX-ACCESS accessible-for-notify
    STATUS current
    DESCRIPTION
        "Parameter 'dest-address' in event PIM.78"
    ::= { pimEventObjects78 2 }

pim78_out-interface OBJECT-TYPE
    SYNTAX DisplayString
    MAX-ACCESS accessible-for-notify
    STATUS current
    DESCRIPTION
        "Parameter 'out-interface' in event PIM.78"
    ::= { pimEventObjects78 3 }

pimEventObjects79 OBJECT-IDENTITY
    STATUS current
    DESCRIPTION
        "Event PIM.79
        Set Bootstrap Timer for BSR on interface"
    ::= { pimEventsGroup 79 }

pim79_cand-bsr-addr OBJECT-TYPE
    SYNTAX IpAddress
    MAX-ACCESS accessible-for-notify
    STATUS current
    DESCRIPTION
        "Parameter 'cand-bsr-addr' in event PIM.79"
    ::= { pimEventObjects79 1 }

pim79_interface OBJECT-TYPE
    SYNTAX DisplayString
    MAX-ACCESS accessible-for-notify
    STATUS current
    DESCRIPTION
        "Parameter 'interface' in event PIM.79"
    ::= { pimEventObjects79 2 }

pim79_timer_value OBJECT-TYPE
    SYNTAX Integer32
    MAX-ACCESS accessible-for-notify
    STATUS current
    DESCRIPTION
        "Parameter 'timer_value' in event PIM.79"
    ::= { pimEventObjects79 3 }

pimEventObjects80 OBJECT-IDENTITY
    STATUS current
    DESCRIPTION
        "Event PIM.80
        Change Bootstrap state for cand-BSR/non-cand-BSR"
    ::= { pimEventsGroup 80 }

pim80_preferred-non_preferred OBJECT-TYPE
    SYNTAX DisplayString
    MAX-ACCESS accessible-for-notify
    STATUS current
    DESCRIPTION
        "Parameter 'preferred-non_preferred' in event PIM.80"
    ::= { pimEventObjects80 1 }

pim80_new-cand-bsr OBJECT-TYPE
    SYNTAX IpAddress
    MAX-ACCESS accessible-for-notify
    STATUS current
    DESCRIPTION
        "Parameter 'new-cand-bsr' in event PIM.80"
    ::= { pimEventObjects80 2 }

pim80_interface OBJECT-TYPE
    SYNTAX DisplayString
    MAX-ACCESS accessible-for-notify
    STATUS current
    DESCRIPTION
        "Parameter 'interface' in event PIM.80"
    ::= { pimEventObjects80 3 }

pim80_old_state-new_state OBJECT-TYPE
    SYNTAX DisplayString
    MAX-ACCESS accessible-for-notify
    STATUS current
    DESCRIPTION
        "Parameter 'old_state-new_state' in event PIM.80"
    ::= { pimEventObjects80 4 }

pimEventObjects81 OBJECT-IDENTITY
    STATUS current
    DESCRIPTION
        "Event PIM.81
        BSR timer has expired, new BSR election"
    ::= { pimEventsGroup 81 }

pim81_bsr-address OBJECT-TYPE
    SYNTAX IpAddress
    MAX-ACCESS accessible-for-notify
    STATUS current
    DESCRIPTION
        "Parameter 'bsr-address' in event PIM.81"
    ::= { pimEventObjects81 1 }

pimEventObjects82 OBJECT-IDENTITY
    STATUS current
    DESCRIPTION
        "Event PIM.82
        I am a candidate-BSR with a state and a BSR timer"
    ::= { pimEventsGroup 82 }

pim82_bsr-address OBJECT-TYPE
    SYNTAX IpAddress
    MAX-ACCESS accessible-for-notify
    STATUS current
    DESCRIPTION
        "Parameter 'bsr-address' in event PIM.82"
    ::= { pimEventObjects82 1 }

pim82_state OBJECT-TYPE
    SYNTAX DisplayString
    MAX-ACCESS accessible-for-notify
    STATUS current
    DESCRIPTION
        "Parameter 'state' in event PIM.82"
    ::= { pimEventObjects82 2 }

pim82_bsr-timer OBJECT-TYPE
    SYNTAX Integer32
    MAX-ACCESS accessible-for-notify
    STATUS current
    DESCRIPTION
        "Parameter 'bsr-timer' in event PIM.82"
    ::= { pimEventObjects82 3 }

pimEventObjects83 OBJECT-IDENTITY
    STATUS current
    DESCRIPTION
        "Event PIM.83
        I am not a candidate-BSR"
    ::= { pimEventsGroup 83 }

pim83_state OBJECT-TYPE
    SYNTAX DisplayString
    MAX-ACCESS accessible-for-notify
    STATUS current
    DESCRIPTION
        "Parameter 'state' in event PIM.83"
    ::= { pimEventObjects83 1 }

pimEventObjects84 OBJECT-IDENTITY
    STATUS current
    DESCRIPTION
        "Event PIM.84
        The holdtime of cand-RP-Set entry has expired and it has been deleted"
    ::= { pimEventsGroup 84 }

pim84_rp-address OBJECT-TYPE
    SYNTAX IpAddress
    MAX-ACCESS accessible-for-notify
    STATUS current
    DESCRIPTION
        "Parameter 'rp-address' in event PIM.84"
    ::= { pimEventObjects84 1 }

pim84_group-address OBJECT-TYPE
    SYNTAX IpAddress
    MAX-ACCESS accessible-for-notify
    STATUS current
    DESCRIPTION
        "Parameter 'group-address' in event PIM.84"
    ::= { pimEventObjects84 2 }

pimEventObjects85 OBJECT-IDENTITY
    STATUS current
    DESCRIPTION
        "Event PIM.85
        Send CAND-RP Advertisement after the BSR has changed"
    ::= { pimEventsGroup 85 }

pim85_cand-rp-addr OBJECT-TYPE
    SYNTAX IpAddress
    MAX-ACCESS accessible-for-notify
    STATUS current
    DESCRIPTION
        "Parameter 'cand-rp-addr' in event PIM.85"
    ::= { pimEventObjects85 1 }

pim85_cand-bsr-addr OBJECT-TYPE
    SYNTAX IpAddress
    MAX-ACCESS accessible-for-notify
    STATUS current
    DESCRIPTION
        "Parameter 'cand-bsr-addr' in event PIM.85"
    ::= { pimEventObjects85 2 }

pimEventObjects86 OBJECT-IDENTITY
    STATUS current
    DESCRIPTION
        "Event PIM.86
        The Boostrap message must be discarded"
    ::= { pimEventsGroup 86 }

pim86_source-address OBJECT-TYPE
    SYNTAX IpAddress
    MAX-ACCESS accessible-for-notify
    STATUS current
    DESCRIPTION
        "Parameter 'source-address' in event PIM.86"
    ::= { pimEventObjects86 1 }

pimEventObjects87 OBJECT-IDENTITY
    STATUS current
    DESCRIPTION
        "Event PIM.87
        Event related to a RP group entry"
    ::= { pimEventsGroup 87 }

pim87_type OBJECT-TYPE
    SYNTAX DisplayString
    MAX-ACCESS accessible-for-notify
    STATUS current
    DESCRIPTION
        "Parameter 'type' in event PIM.87"
    ::= { pimEventObjects87 1 }

pim87_rp OBJECT-TYPE
    SYNTAX DisplayString
    MAX-ACCESS accessible-for-notify
    STATUS current
    DESCRIPTION
        "Parameter 'rp' in event PIM.87"
    ::= { pimEventObjects87 2 }

pim87_prefix OBJECT-TYPE
    SYNTAX IpAddress
    MAX-ACCESS accessible-for-notify
    STATUS current
    DESCRIPTION
        "Parameter 'prefix' in event PIM.87"
    ::= { pimEventObjects87 3 }

pim87_prefixlen OBJECT-TYPE
    SYNTAX Integer32
    MAX-ACCESS accessible-for-notify
    STATUS current
    DESCRIPTION
        "Parameter 'prefixlen' in event PIM.87"
    ::= { pimEventObjects87 4 }

pim87_message OBJECT-TYPE
    SYNTAX DisplayString
    MAX-ACCESS accessible-for-notify
    STATUS current
    DESCRIPTION
        "Parameter 'message' in event PIM.87"
    ::= { pimEventObjects87 5 }

pimEventObjects89 OBJECT-IDENTITY
    STATUS current
    DESCRIPTION
        "Event PIM.89
        Error detected due to a not allowed use of a SSM group"
    ::= { pimEventsGroup 89 }

pim89_grp-address OBJECT-TYPE
    SYNTAX IpAddress
    MAX-ACCESS accessible-for-notify
    STATUS current
    DESCRIPTION
        "Parameter 'grp-address' in event PIM.89"
    ::= { pimEventObjects89 1 }

pim89_message OBJECT-TYPE
    SYNTAX DisplayString
    MAX-ACCESS accessible-for-notify
    STATUS current
    DESCRIPTION
        "Parameter 'message' in event PIM.89"
    ::= { pimEventObjects89 2 }


pimNotification1 NOTIFICATION-TYPE
    OBJECTS { 
              pim1_ifc_name, 
              pim1_message 
            }
    STATUS current
    DESCRIPTION
        "Notification of Event PIM.1

        Message: '$1 interface: $2'

        Parameters list:
              $1: pim1_ifc_name
              $2: pim1_message

        Event related to protocol at virtual interface"
    ::= { pimNotificationsPrefix 1 }

pimNotification2 NOTIFICATION-TYPE
    OBJECTS { 
              pim2_source-address, 
              pim2_interface 
            }
    STATUS current
    DESCRIPTION
        "Notification of Event PIM.2

        Message: 'Received errored packet from $1, incoming inteface $2'

        Parameters list:
              $1: pim2_source-address
              $2: pim2_interface

        An errored packet was received from specified address on specified interface"
    ::= { pimNotificationsPrefix 2 }

pimNotification3 NOTIFICATION-TYPE
    OBJECTS { 
              pim3_description 
            }
    STATUS current
    DESCRIPTION
        "Notification of Event PIM.3

        Message: '$1'

        Parameters list:
              $1: pim3_description

        Description of previous event."
    ::= { pimNotificationsPrefix 3 }

pimNotification4 NOTIFICATION-TYPE
    OBJECTS { 
              pim4_message_type, 
              pim4_source-address,
              pim4_destination-address 
            }
    STATUS current
    DESCRIPTION
        "Notification of Event PIM.4

        Message: 'Ignore unknown PIM message code $1: from $2 to $3'

        Parameters list:
              $1: pim4_message_type
              $2: pim4_source-address
              $3: pim4_destination-address

        Ignore a received packet that is of an unknown PIM type"
    ::= { pimNotificationsPrefix 4 }

pimNotification5 NOTIFICATION-TYPE
    OBJECTS { 
              pim5_message, 
              pim5_non-neighbour-address 
            }
    STATUS current
    DESCRIPTION
        "Notification of Event PIM.5

        Message: 'Ignoring PIM $1 from non-neighbour router $2'

        Parameters list:
              $1: pim5_message
              $2: pim5_non-neighbour-address

        Received PIM %s from non-directly connected or not PIM router. Ignore it."
    ::= { pimNotificationsPrefix 5 }

pimNotification6 NOTIFICATION-TYPE
    OBJECTS { 
              pim6_rp-src, 
              pim6_address,
              pim6_message 
            }
    STATUS current
    DESCRIPTION
        "Notification of Event PIM.6

        Message: 'Reverse Path Forwarding to $1 $2: $3'

        Parameters list:
              $1: pim6_rp-src
              $2: pim6_address
              $3: pim6_message

        Event in Reverse Path Forwarding towards a source or RP"
    ::= { pimNotificationsPrefix 6 }

pimNotification7 NOTIFICATION-TYPE
    OBJECTS { 
              pim7_description 
            }
    STATUS current
    DESCRIPTION
        "Notification of Event PIM.7

        Message: '$1'

        Parameters list:
              $1: pim7_description

        Description of previous event."
    ::= { pimNotificationsPrefix 7 }

pimNotification8 NOTIFICATION-TYPE
    STATUS current
    DESCRIPTION
        "Notification of Event PIM.8

        Message: '--'

        Reserved for future use"
    ::= { pimNotificationsPrefix 8 }

pimNotification9 NOTIFICATION-TYPE
    STATUS current
    DESCRIPTION
        "Notification of Event PIM.9

        Message: '--'

        Reserved for future use"
    ::= { pimNotificationsPrefix 9 }

pimNotification10 NOTIFICATION-TYPE
    OBJECTS { 
              pim10_source_address 
            }
    STATUS current
    DESCRIPTION
        "Notification of Event PIM.10

        Message: 'Received PIM HELLO malformed from $1'

        Parameters list:
              $1: pim10_source_address

        Not enough bytes in the message as advertised"
    ::= { pimNotificationsPrefix 10 }

pimNotification11 NOTIFICATION-TYPE
    OBJECTS { 
              pim11_source_address, 
              pim11_option,
              pim11_option_length 
            }
    STATUS current
    DESCRIPTION
        "Notification of Event PIM.11

        Message: 'Received PIM HELLO $1 from $2: invalid OptionLength = $3'

        Parameters list:
              $1: pim11_source_address
              $2: pim11_option
              $3: pim11_option_length

        Invalid option length in PIM HELLO message"
    ::= { pimNotificationsPrefix 11 }

pimNotification12 NOTIFICATION-TYPE
    OBJECTS { 
              pim12_option_type, 
              pim12_source_address 
            }
    STATUS current
    DESCRIPTION
        "Notification of Event PIM.12

        Message: 'Ignoring unknown PIM HELLO option $1 from $2'

        Parameters list:
              $1: pim12_option_type
              $2: pim12_source_address

        Ignore any unknown HELLO options"
    ::= { pimNotificationsPrefix 12 }

pimNotification13 NOTIFICATION-TYPE
    OBJECTS { 
              pim13_source_address 
            }
    STATUS current
    DESCRIPTION
        "Notification of Event PIM.13

        Message: 'Ignoring PIM HELLO from non-neighbour router $1'

        Parameters list:
              $1: pim13_source_address

        Ignore a PIM HELLO message from non-neighbour router"
    ::= { pimNotificationsPrefix 13 }

pimNotification14 NOTIFICATION-TYPE
    OBJECTS { 
              pim14_source_address, 
              pim14_access-list-number 
            }
    STATUS current
    DESCRIPTION
        "Notification of Event PIM.14

        Message: 'Received PIM HELLO from $1, denied by neighbour filter ACL $2'

        Parameters list:
              $1: pim14_source_address
              $2: pim14_access-list-number

        Deny a PIM HELLO message by neighbour filter access-list"
    ::= { pimNotificationsPrefix 14 }

pimNotification15 NOTIFICATION-TYPE
    OBJECTS { 
              pim15_source-address, 
              pim15_holdtime,
              pim15_DR-priority,
              pim15_incomingifc 
            }
    STATUS current
    DESCRIPTION
        "Notification of Event PIM.15

        Message: 'Received PIM HELLO from $1 with holdtime $2$3 at incoming interface $4'

        Parameters list:
              $1: pim15_source-address
              $2: pim15_holdtime
              $3: pim15_DR-priority
              $4: pim15_incomingifc

        Received PIM HELLO with holdtime and DR priority at an interface"
    ::= { pimNotificationsPrefix 15 }

pimNotification16 NOTIFICATION-TYPE
    OBJECTS { 
              pim16_nbr-addr, 
              pim16_interface,
              pim16_message 
            }
    STATUS current
    DESCRIPTION
        "Notification of Event PIM.16

        Message: 'Neighbour $1 on interface $2: $3'

        Parameters list:
              $1: pim16_nbr-addr
              $2: pim16_interface
              $3: pim16_message

        Relevant action related to a neighbour"
    ::= { pimNotificationsPrefix 16 }

pimNotification17 NOTIFICATION-TYPE
    OBJECTS { 
              pim17_source-address, 
              pim17_holdtime,
              pim17_outgoingifc 
            }
    STATUS current
    DESCRIPTION
        "Notification of Event PIM.17

        Message: 'Sending PIM HELLO for IP $1 with holdtime $2 at outgoing interface $3'

        Parameters list:
              $1: pim17_source-address
              $2: pim17_holdtime
              $3: pim17_outgoingifc

        Sending PIM HELLO to all PIM routers group through an interface"
    ::= { pimNotificationsPrefix 17 }

pimNotification18 NOTIFICATION-TYPE
    OBJECTS { 
              pim18_interface, 
              pim18_address 
            }
    STATUS current
    DESCRIPTION
        "Notification of Event PIM.18

        Message: 'DR election: I am the new Designated Router on interface $1 with address $2'

        Parameters list:
              $1: pim18_interface
              $2: pim18_address

        DR election results in being the new DR"
    ::= { pimNotificationsPrefix 18 }

pimNotification19 NOTIFICATION-TYPE
    OBJECTS { 
              pim19_interface, 
              pim19_address 
            }
    STATUS current
    DESCRIPTION
        "Notification of Event PIM.19

        Message: 'DR election: the new Designated Router on interface $1 has IP address $2'

        Parameters list:
              $1: pim19_interface
              $2: pim19_address

        DR election results in another router being the new DR"
    ::= { pimNotificationsPrefix 19 }

pimNotification20 NOTIFICATION-TYPE
    STATUS current
    DESCRIPTION
        "Notification of Event PIM.20

        Message: '--'

        Reserved for future use"
    ::= { pimNotificationsPrefix 20 }

pimNotification21 NOTIFICATION-TYPE
    OBJECTS { 
              pim21_source_address, 
              pim21_error_message 
            }
    STATUS current
    DESCRIPTION
        "Notification of Event PIM.21

        Message: 'Received PIM REGISTER from $1, error: $2'

        Parameters list:
              $1: pim21_source_address
              $2: pim21_error_message

        Error receiving PIM REGISTER"
    ::= { pimNotificationsPrefix 21 }

pimNotification22 NOTIFICATION-TYPE
    OBJECTS { 
              pim22_source-address, 
              pim22_inner-src,
              pim22_inner-grp 
            }
    STATUS current
    DESCRIPTION
        "Notification of Event PIM.22

        Message: 'Received PIM REGISTER message from source $1, inner packet from source $2 to group $3'

        Parameters list:
              $1: pim22_source-address
              $2: pim22_inner-src
              $3: pim22_inner-grp

        Received PIM REGISTER from source, with encapsulated packet."
    ::= { pimNotificationsPrefix 22 }

pimNotification23 NOTIFICATION-TYPE
    OBJECTS { 
              pim23_source-address, 
              pim23_inner-src,
              pim23_inner-grp 
            }
    STATUS current
    DESCRIPTION
        "Notification of Event PIM.23

        Message: 'Received PIM NULL-REGISTER message from source $1, inner packet from source $2 to group $3'

        Parameters list:
              $1: pim23_source-address
              $2: pim23_inner-src
              $3: pim23_inner-grp

        Received PIM NULL-REGISTER from source, with dummy IP packet."
    ::= { pimNotificationsPrefix 23 }

pimNotification24 NOTIFICATION-TYPE
    OBJECTS { 
              pim24_rp_address, 
              pim24_destination_address,
              pim24_source_address,
              pim24_group_address 
            }
    STATUS current
    DESCRIPTION
        "Notification of Event PIM.24

        Message: 'Received PIM REGISTER STOP from RP $1 to $2 for ($3,$4)'

        Parameters list:
              $1: pim24_rp_address
              $2: pim24_destination_address
              $3: pim24_source_address
              $4: pim24_group_address

        Received a PIM REGISTER STOP from Rendevouz-Point"
    ::= { pimNotificationsPrefix 24 }

pimNotification25 NOTIFICATION-TYPE
    OBJECTS { 
              pim25_source-address, 
              pim25_destination-address,
              pim25_source_address,
              pim25_group_address 
            }
    STATUS current
    DESCRIPTION
        "Notification of Event PIM.25

        Message: 'Sending PIM REGISTER STOP message from $1 to $2 for ($3,$4)'

        Parameters list:
              $1: pim25_source-address
              $2: pim25_destination-address
              $3: pim25_source_address
              $4: pim25_group_address

        Sending PIM REGISTER STOP message from Rendezvous-Point (RP) to Designated Router (DR)"
    ::= { pimNotificationsPrefix 25 }

pimNotification26 NOTIFICATION-TYPE
    OBJECTS { 
              pim26_source-address, 
              pim26_group-address 
            }
    STATUS current
    DESCRIPTION
        "Notification of Event PIM.26

        Message: 'Sending PIM REGISTER message for state ($1,$2)'

        Parameters list:
              $1: pim26_source-address
              $2: pim26_group-address

        Sending PIM REGISTER message for a state from Designated Router (DR) to Rendezvous-Point (RP)"
    ::= { pimNotificationsPrefix 26 }

pimNotification27 NOTIFICATION-TYPE
    OBJECTS { 
              pim27_source-address, 
              pim27_group-address 
            }
    STATUS current
    DESCRIPTION
        "Notification of Event PIM.27

        Message: 'Sending PIM NULL REGISTER message for state ($1,$2)'

        Parameters list:
              $1: pim27_source-address
              $2: pim27_group-address

        Sending PIM NULL REGISTER message for a state from Designated Router (DR) to Rendezvous-Point (RP)"
    ::= { pimNotificationsPrefix 27 }

pimNotification28 NOTIFICATION-TYPE
    OBJECTS { 
              pim28_srcaddr, 
              pim28_grpaddr,
              pim28_message 
            }
    STATUS current
    DESCRIPTION
        "Notification of Event PIM.28

        Message: 'Register-Stop timer for ($1,$2): $3'

        Parameters list:
              $1: pim28_srcaddr
              $2: pim28_grpaddr
              $3: pim28_message

        Action related to Register-Stop timer"
    ::= { pimNotificationsPrefix 28 }

pimNotification29 NOTIFICATION-TYPE
    OBJECTS { 
              pim29_join-prune, 
              pim29_state,
              pim29_dest-address 
            }
    STATUS current
    DESCRIPTION
        "Notification of Event PIM.29

        Message: 'Add PIM $1 message $2 to $3'

        Parameters list:
              $1: pim29_join-prune
              $2: pim29_state
              $3: pim29_dest-address

        Add PIM JOIN/PRUNE entry to JP message"
    ::= { pimNotificationsPrefix 29 }

pimNotification30 NOTIFICATION-TYPE
    OBJECTS { 
              pim30_source-address, 
              pim30_destination-address,
              pim30_out-interface 
            }
    STATUS current
    DESCRIPTION
        "Notification of Event PIM.30

        Message: 'Sending PIM JOIN/PRUNE message from $1 to $2, outgoing interface $3'

        Parameters list:
              $1: pim30_source-address
              $2: pim30_destination-address
              $3: pim30_out-interface

        Sending PIM JOIN/PRUNE message to all PIM routers group"
    ::= { pimNotificationsPrefix 30 }

pimNotification31 NOTIFICATION-TYPE
    OBJECTS { 
              pim31_type, 
              pim31_error_message 
            }
    STATUS current
    DESCRIPTION
        "Notification of Event PIM.31

        Message: '$1 PIM JOIN/PRUNE message error: $2'

        Parameters list:
              $1: pim31_type
              $2: pim31_error_message

        Error seeing/receiving PIM JOIN/PRUNE"
    ::= { pimNotificationsPrefix 31 }

pimNotification32 NOTIFICATION-TYPE
    OBJECTS { 
              pim32_source-address, 
              pim32_destination-address,
              pim32_incoming-interface 
            }
    STATUS current
    DESCRIPTION
        "Notification of Event PIM.32

        Message: 'Received PIM JOIN/PRUNE message from $1 to $2 incoming interface $3'

        Parameters list:
              $1: pim32_source-address
              $2: pim32_destination-address
              $3: pim32_incoming-interface

        Received PIM JOIN/PRUNE message"
    ::= { pimNotificationsPrefix 32 }

pimNotification33 NOTIFICATION-TYPE
    OBJECTS { 
              pim33_state 
            }
    STATUS current
    DESCRIPTION
        "Notification of Event PIM.33

        Message: 'Received PIM JOIN $1'

        Parameters list:
              $1: pim33_state

        Received PIM JOIN"
    ::= { pimNotificationsPrefix 33 }

pimNotification34 NOTIFICATION-TYPE
    OBJECTS { 
              pim34_state 
            }
    STATUS current
    DESCRIPTION
        "Notification of Event PIM.34

        Message: 'Received PIM PRUNE $1'

        Parameters list:
              $1: pim34_state

        Received PIM PRUNE"
    ::= { pimNotificationsPrefix 34 }

pimNotification35 NOTIFICATION-TYPE
    OBJECTS { 
              pim35_source-address, 
              pim35_destination-address,
              pim35_incoming-interface 
            }
    STATUS current
    DESCRIPTION
        "Notification of Event PIM.35

        Message: 'See PIM JOIN/PRUNE message from $1 to $2 incoming interface $3'

        Parameters list:
              $1: pim35_source-address
              $2: pim35_destination-address
              $3: pim35_incoming-interface

        See a JOIN/PRUNE message not addressed to me."
    ::= { pimNotificationsPrefix 35 }

pimNotification36 NOTIFICATION-TYPE
    OBJECTS { 
              pim36_state 
            }
    STATUS current
    DESCRIPTION
        "Notification of Event PIM.36

        Message: 'See PIM JOIN $1'

        Parameters list:
              $1: pim36_state

        See PIM JOIN"
    ::= { pimNotificationsPrefix 36 }

pimNotification37 NOTIFICATION-TYPE
    OBJECTS { 
              pim37_state 
            }
    STATUS current
    DESCRIPTION
        "Notification of Event PIM.37

        Message: 'See PIM PRUNE $1'

        Parameters list:
              $1: pim37_state

        See PIM PRUNE"
    ::= { pimNotificationsPrefix 37 }

pimNotification38 NOTIFICATION-TYPE
    OBJECTS { 
              pim38_state, 
              pim38_info,
              pim38_prev-val,
              pim38_new-val 
            }
    STATUS current
    DESCRIPTION
        "Notification of Event PIM.38

        Message: '$1 for $2: from $3 to $4'

        Parameters list:
              $1: pim38_state
              $2: pim38_info
              $3: pim38_prev-val
              $4: pim38_new-val

        RPTJoinDesired/JoinDesired/PruneDesired changes"
    ::= { pimNotificationsPrefix 38 }

pimNotification39 NOTIFICATION-TYPE
    OBJECTS { 
              pim39_srcaddr, 
              pim39_grpaddr,
              pim39_message 
            }
    STATUS current
    DESCRIPTION
        "Notification of Event PIM.39

        Message: 'Override Timer for ($1,$2): $3'

        Parameters list:
              $1: pim39_srcaddr
              $2: pim39_grpaddr
              $3: pim39_message

        Action related to Override Timer"
    ::= { pimNotificationsPrefix 39 }

pimNotification40 NOTIFICATION-TYPE
    OBJECTS { 
              pim40_state, 
              pim40_message 
            }
    STATUS current
    DESCRIPTION
        "Notification of Event PIM.40

        Message: 'JOIN/PRUNE Timer for $1: $2'

        Parameters list:
              $1: pim40_state
              $2: pim40_message

        Action related to JOIN/PRUNE Timer"
    ::= { pimNotificationsPrefix 40 }

pimNotification41 NOTIFICATION-TYPE
    OBJECTS { 
              pim41_assert_type, 
              pim41_group-address,
              pim41_nbr-address 
            }
    STATUS current
    DESCRIPTION
        "Notification of Event PIM.41

        Message: 'Received PIM $1(*,G): group $2 from neighbour $3'

        Parameters list:
              $1: pim41_assert_type
              $2: pim41_group-address
              $3: pim41_nbr-address

        Received PIM ASSERT/ASSERT_CANCEL(*,G)"
    ::= { pimNotificationsPrefix 41 }

pimNotification42 NOTIFICATION-TYPE
    OBJECTS { 
              pim42_assert_type, 
              pim42_source-address,
              pim42_group-address,
              pim42_nbr-address 
            }
    STATUS current
    DESCRIPTION
        "Notification of Event PIM.42

        Message: 'Received PIM $1(S,G): source $2, group $3 from neighbour $4'

        Parameters list:
              $1: pim42_assert_type
              $2: pim42_source-address
              $3: pim42_group-address
              $4: pim42_nbr-address

        Received PIM ASSERT/ASSERT_CANCEL(S,G)"
    ::= { pimNotificationsPrefix 42 }

pimNotification43 NOTIFICATION-TYPE
    OBJECTS { 
              pim43_assert_type, 
              pim43_group-address,
              pim43_out-interface 
            }
    STATUS current
    DESCRIPTION
        "Notification of Event PIM.43

        Message: 'Sending PIM $1(*,G): group $2, outgoing interface $3'

        Parameters list:
              $1: pim43_assert_type
              $2: pim43_group-address
              $3: pim43_out-interface

        Sending PIM ASSERT/ASSERT_CANCEL(*,G) to all PIM routers group"
    ::= { pimNotificationsPrefix 43 }

pimNotification44 NOTIFICATION-TYPE
    OBJECTS { 
              pim44_assert_type, 
              pim44_source-address,
              pim44_group-address,
              pim44_out-interface 
            }
    STATUS current
    DESCRIPTION
        "Notification of Event PIM.44

        Message: 'Sending PIM $1(S,G): source $2, group $3, outgoing interface $4'

        Parameters list:
              $1: pim44_assert_type
              $2: pim44_source-address
              $3: pim44_group-address
              $4: pim44_out-interface

        Sending PIM ASSERT/ASSERT_CANCEL(S,G) to all PIM routers group"
    ::= { pimNotificationsPrefix 44 }

pimNotification45 NOTIFICATION-TYPE
    OBJECTS { 
              pim45_srcaddr, 
              pim45_grpaddr,
              pim45_interface,
              pim45_message 
            }
    STATUS current
    DESCRIPTION
        "Notification of Event PIM.45

        Message: 'Assert timer for ($1,$2) ifc $3: $4'

        Parameters list:
              $1: pim45_srcaddr
              $2: pim45_grpaddr
              $3: pim45_interface
              $4: pim45_message

        Action related to Assert timer"
    ::= { pimNotificationsPrefix 45 }

pimNotification46 NOTIFICATION-TYPE
    OBJECTS { 
              pim46_srcaddr, 
              pim46_grpaddr,
              pim46_interface,
              pim46_state_event 
            }
    STATUS current
    DESCRIPTION
        "Notification of Event PIM.46

        Message: 'Assert state for ($1,$2) interface $3: $4'

        Parameters list:
              $1: pim46_srcaddr
              $2: pim46_grpaddr
              $3: pim46_interface
              $4: pim46_state_event

        Assert state event for an interface in a MRT entry"
    ::= { pimNotificationsPrefix 46 }

pimNotification47 NOTIFICATION-TYPE
    OBJECTS { 
              pim47_srcaddr, 
              pim47_grpaddr,
              pim47_message 
            }
    STATUS current
    DESCRIPTION
        "Notification of Event PIM.47

        Message: 'Keepalive timer for ($1,$2): $3'

        Parameters list:
              $1: pim47_srcaddr
              $2: pim47_grpaddr
              $3: pim47_message

        Change in KAT for a (S,G) state"
    ::= { pimNotificationsPrefix 47 }

pimNotification48 NOTIFICATION-TYPE
    OBJECTS { 
              pim48_srcaddr, 
              pim48_grpaddr,
              pim48_message 
            }
    STATUS current
    DESCRIPTION
        "Notification of Event PIM.48

        Message: 'Shortest-Path Tree bit for ($1,$2): $3'

        Parameters list:
              $1: pim48_srcaddr
              $2: pim48_grpaddr
              $3: pim48_message

        Change in SPT bit for a (S,G) state"
    ::= { pimNotificationsPrefix 48 }

pimNotification49 NOTIFICATION-TYPE
    STATUS current
    DESCRIPTION
        "Notification of Event PIM.49

        Message: '--'

        Reserved for future use"
    ::= { pimNotificationsPrefix 49 }

pimNotification50 NOTIFICATION-TYPE
    OBJECTS { 
              pim50_add_del, 
              pim50_inc_exc,
              pim50_state,
              pim50_ifc,
              pim50_message 
            }
    STATUS current
    DESCRIPTION
        "Notification of Event PIM.50

        Message: 'IGMP error at $1 $2 for state $3 on interface $4: $5'

        Parameters list:
              $1: pim50_add_del
              $2: pim50_inc_exc
              $3: pim50_state
              $4: pim50_ifc
              $5: pim50_message

        Error while adding or deleting include or exclude on an
        interface"
    ::= { pimNotificationsPrefix 50 }

pimNotification51 NOTIFICATION-TYPE
    OBJECTS { 
              pim51_add_delete, 
              pim51_interface,
              pim51_group_address,
              pim51_source_address 
            }
    STATUS current
    DESCRIPTION
        "Notification of Event PIM.51

        Message: '$1 IGMP include interface $2 for group $3 and source $4'

        Parameters list:
              $1: pim51_add_delete
              $2: pim51_interface
              $3: pim51_group_address
              $4: pim51_source_address

        Add or delete an IGMP include (S,G) leaf"
    ::= { pimNotificationsPrefix 51 }

pimNotification52 NOTIFICATION-TYPE
    OBJECTS { 
              pim52_add_delete, 
              pim52_interface,
              pim52_group_address,
              pim52_source_address 
            }
    STATUS current
    DESCRIPTION
        "Notification of Event PIM.52

        Message: '$1 IGMP exclude interface $2 for group $3 and source $4'

        Parameters list:
              $1: pim52_add_delete
              $2: pim52_interface
              $3: pim52_group_address
              $4: pim52_source_address

        Add or delete an IGMP exclude (S,G) leaf"
    ::= { pimNotificationsPrefix 52 }

pimNotification53 NOTIFICATION-TYPE
    OBJECTS { 
              pim53_add_delete, 
              pim53_interface,
              pim53_group_address 
            }
    STATUS current
    DESCRIPTION
        "Notification of Event PIM.53

        Message: '$1 IGMP include interface $2 for group $3'

        Parameters list:
              $1: pim53_add_delete
              $2: pim53_interface
              $3: pim53_group_address

        Add or delete an IGMP include (*,G) leaf"
    ::= { pimNotificationsPrefix 53 }

pimNotification54 NOTIFICATION-TYPE
    OBJECTS { 
              pim54_source_address, 
              pim54_destination_address 
            }
    STATUS current
    DESCRIPTION
        "Notification of Event PIM.54

        Message: 'Error sending PIM multicast message from $1 to $2'

        Parameters list:
              $1: pim54_source_address
              $2: pim54_destination_address

        Error sending a PIM multicast message"
    ::= { pimNotificationsPrefix 54 }

pimNotification55 NOTIFICATION-TYPE
    OBJECTS { 
              pim55_source_address, 
              pim55_destination_address,
              pim55_outgoing_interface 
            }
    STATUS current
    DESCRIPTION
        "Notification of Event PIM.55

        Message: 'Sending PIM unicast message from $1 to $2 outgoing interface $3'

        Parameters list:
              $1: pim55_source_address
              $2: pim55_destination_address
              $3: pim55_outgoing_interface

        Sending a PIM unicast message"
    ::= { pimNotificationsPrefix 55 }

pimNotification56 NOTIFICATION-TYPE
    OBJECTS { 
              pim56_source_address, 
              pim56_destination_address,
              pim56_outgoing_interface 
            }
    STATUS current
    DESCRIPTION
        "Notification of Event PIM.56

        Message: 'Sending PIM multicast message from $1 to $2 outgoing interface $3'

        Parameters list:
              $1: pim56_source_address
              $2: pim56_destination_address
              $3: pim56_outgoing_interface

        Sending a PIM multicast message"
    ::= { pimNotificationsPrefix 56 }

pimNotification57 NOTIFICATION-TYPE
    STATUS current
    DESCRIPTION
        "Notification of Event PIM.57

        Message: '--'

        Reserved for future use"
    ::= { pimNotificationsPrefix 57 }

pimNotification58 NOTIFICATION-TYPE
    OBJECTS { 
              pim58_source_address, 
              pim58_group_address,
              pim58_incoming-interface 
            }
    STATUS current
    DESCRIPTION
        "Notification of Event PIM.58

        Message: 'Added/updated a Multicast Forwarding Cache entry: source $1, group $2, incoming interface $3'

        Parameters list:
              $1: pim58_source_address
              $2: pim58_group_address
              $3: pim58_incoming-interface

        An entry was added or updated in Multicast Forwarding Cache"
    ::= { pimNotificationsPrefix 58 }

pimNotification59 NOTIFICATION-TYPE
    OBJECTS { 
              pim59_source_address, 
              pim59_group_address 
            }
    STATUS current
    DESCRIPTION
        "Notification of Event PIM.59

        Message: 'Failed removing MFC entry src $1, grp $2, not found'

        Parameters list:
              $1: pim59_source_address
              $2: pim59_group_address

        A MFC entry was not found while trying to remove it."
    ::= { pimNotificationsPrefix 59 }

pimNotification60 NOTIFICATION-TYPE
    OBJECTS { 
              pim60_source_address, 
              pim60_group_address 
            }
    STATUS current
    DESCRIPTION
        "Notification of Event PIM.60

        Message: 'Deleting a Multicast Forwarding Cache entry for source $1 and group $2'

        Parameters list:
              $1: pim60_source_address
              $2: pim60_group_address

        Delete a Multicast Forwarding Cache entry"
    ::= { pimNotificationsPrefix 60 }

pimNotification61 NOTIFICATION-TYPE
    OBJECTS { 
              pim61_source-address, 
              pim61_group-address,
              pim61_incoming-interface 
            }
    STATUS current
    DESCRIPTION
        "Notification of Event PIM.61

        Message: 'Cache miss, source $1, group $2, incoming interface $3'

        Parameters list:
              $1: pim61_source-address
              $2: pim61_group-address
              $3: pim61_incoming-interface

        An entry is missing on Multicast Forwarding Cache"
    ::= { pimNotificationsPrefix 61 }

pimNotification62 NOTIFICATION-TYPE
    OBJECTS { 
              pim62_action, 
              pim62_source_address 
            }
    STATUS current
    DESCRIPTION
        "Notification of Event PIM.62

        Message: '$1 a source entry in Multicast Routing Table: source $2'

        Parameters list:
              $1: pim62_action
              $2: pim62_source_address

        Create/delete a source entry in Multicas Routing Table"
    ::= { pimNotificationsPrefix 62 }

pimNotification63 NOTIFICATION-TYPE
    OBJECTS { 
              pim63_action, 
              pim63_group_address,
              pim63_text 
            }
    STATUS current
    DESCRIPTION
        "Notification of Event PIM.63

        Message: '$1 a group entry $2 in Multicast Routing Table: $3'

        Parameters list:
              $1: pim63_action
              $2: pim63_group_address
              $3: pim63_text

        Create/delete/update a group entry in Multicast Routing Table"
    ::= { pimNotificationsPrefix 63 }

pimNotification64 NOTIFICATION-TYPE
    OBJECTS { 
              pim64_source_address, 
              pim64_group_address 
            }
    STATUS current
    DESCRIPTION
        "Notification of Event PIM.64

        Message: 'Multicast Routing Table inconsistency for source $1 and group $2'

        Parameters list:
              $1: pim64_source_address
              $2: pim64_group_address

        Multicast Routing Table inconsistency for an entry"
    ::= { pimNotificationsPrefix 64 }

pimNotification65 NOTIFICATION-TYPE
    OBJECTS { 
              pim65_pimstate, 
              pim65_message 
            }
    STATUS current
    DESCRIPTION
        "Notification of Event PIM.65

        Message: 'Multicast Routing Table entry $1: $2'

        Parameters list:
              $1: pim65_pimstate
              $2: pim65_message

        Event related to a Multicast Routing entry"
    ::= { pimNotificationsPrefix 65 }

pimNotification66 NOTIFICATION-TYPE
    OBJECTS { 
              pim66_type, 
              pim66_error_message 
            }
    STATUS current
    DESCRIPTION
        "Notification of Event PIM.66

        Message: '$1 PIM C-RP-Adv message error: $2'

        Parameters list:
              $1: pim66_type
              $2: pim66_error_message

        Error seeing/receiving PIM C-RP-Adv"
    ::= { pimNotificationsPrefix 66 }

pimNotification67 NOTIFICATION-TYPE
    OBJECTS { 
              pim67_message_size, 
              pim67_source_address,
              pim67_incoming-interface 
            }
    STATUS current
    DESCRIPTION
        "Notification of Event PIM.67

        Message: 'Received BOOTSTRAP message size($1) is too short from $2 incoming interface $3'

        Parameters list:
              $1: pim67_message_size
              $2: pim67_source_address
              $3: pim67_incoming-interface

        Check for the minimum length of Bootstrap message."
    ::= { pimNotificationsPrefix 67 }

pimNotification68 NOTIFICATION-TYPE
    OBJECTS { 
              pim68_message-size, 
              pim68_source-address,
              pim68_incoming-interface 
            }
    STATUS current
    DESCRIPTION
        "Notification of Event PIM.68

        Message: 'Received Candidate RP message size($1) is too short from $2 incoming interface $3'

        Parameters list:
              $1: pim68_message-size
              $2: pim68_source-address
              $3: pim68_incoming-interface

        Check for the minimum length of candidate RP message."
    ::= { pimNotificationsPrefix 68 }

pimNotification69 NOTIFICATION-TYPE
    OBJECTS { 
              pim69_source-address 
            }
    STATUS current
    DESCRIPTION
        "Notification of Event PIM.69

        Message: 'Ignored unicast BOOTSTRAP message from $1: cannot find incoming interface'

        Parameters list:
              $1: pim69_source-address

        Cannot find the receiving incoming interface toward that DR"
    ::= { pimNotificationsPrefix 69 }

pimNotification70 NOTIFICATION-TYPE
    OBJECTS { 
              pim70_source-address, 
              pim70_candidate-bsr-address,
              pim70_priority,
              pim70_incoming-interface 
            }
    STATUS current
    DESCRIPTION
        "Notification of Event PIM.70

        Message: 'Received PIM BOOTSTRAP message from $1 with address of C-BSR $2 and priority $3, incoming interface $4'

        Parameters list:
              $1: pim70_source-address
              $2: pim70_candidate-bsr-address
              $3: pim70_priority
              $4: pim70_incoming-interface

        Received PIM Bootstrap message"
    ::= { pimNotificationsPrefix 70 }

pimNotification71 NOTIFICATION-TYPE
    OBJECTS { 
              pim71_incoming-interface, 
              pim71_reason 
            }
    STATUS current
    DESCRIPTION
        "Notification of Event PIM.71

        Message: 'PIM BOOTSTRAP received at $1, ignored by $2'

        Parameters list:
              $1: pim71_incoming-interface
              $2: pim71_reason

        Received and ignored Bootstrap message"
    ::= { pimNotificationsPrefix 71 }

pimNotification72 NOTIFICATION-TYPE
    OBJECTS { 
              pim72_source-address, 
              pim72_destination-address,
              pim72_outgoing-interface 
            }
    STATUS current
    DESCRIPTION
        "Notification of Event PIM.72

        Message: 'Sending the BOOTSTRAP message from $1 to $2, outgoing interface $3'

        Parameters list:
              $1: pim72_source-address
              $2: pim72_destination-address
              $3: pim72_outgoing-interface

        Sending the BSR message to all PIM routers group"
    ::= { pimNotificationsPrefix 72 }

pimNotification73 NOTIFICATION-TYPE
    OBJECTS { 
              pim73_destination-address, 
              pim73_outgoing-interface 
            }
    STATUS current
    DESCRIPTION
        "Notification of Event PIM.73

        Message: 'PIM BOOTSTRAP unicast not sent to $1 at $2 because of BSR Border'

        Parameters list:
              $1: pim73_destination-address
              $2: pim73_outgoing-interface

        BSR Border cannot sent BSR unicast message."
    ::= { pimNotificationsPrefix 73 }

pimNotification74 NOTIFICATION-TYPE
    OBJECTS { 
              pim74_outgoing-interface 
            }
    STATUS current
    DESCRIPTION
        "Notification of Event PIM.74

        Message: 'PIM BOOTSTRAP message is not sent by oif $1 because of BSR Border configuration'

        Parameters list:
              $1: pim74_outgoing-interface

        Bootstrap message is not sent because of BSR Border configuration"
    ::= { pimNotificationsPrefix 74 }

pimNotification75 NOTIFICATION-TYPE
    OBJECTS { 
              pim75_source-address, 
              pim75_destination-address,
              pim75_outgoing-interface 
            }
    STATUS current
    DESCRIPTION
        "Notification of Event PIM.75

        Message: 'Forwarding BOOTSTRAP message from $1 to $2, outgoing interface $3'

        Parameters list:
              $1: pim75_source-address
              $2: pim75_destination-address
              $3: pim75_outgoing-interface

        Forwarding the BSR message to all PIM routers group"
    ::= { pimNotificationsPrefix 75 }

pimNotification76 NOTIFICATION-TYPE
    OBJECTS { 
              pim76_source-address, 
              pim76_holdtime,
              pim76_incoming-interface 
            }
    STATUS current
    DESCRIPTION
        "Notification of Event PIM.76

        Message: 'Received PIM CANDIDATE RP Advertisement from $1, holdtime $2, incoming interface $3'

        Parameters list:
              $1: pim76_source-address
              $2: pim76_holdtime
              $3: pim76_incoming-interface

        Received C-RP message, if I am the Bootstrap router, process the advertisement"
    ::= { pimNotificationsPrefix 76 }

pimNotification77 NOTIFICATION-TYPE
    OBJECTS { 
              pim77_C-RP-address, 
              pim77_holdtime,
              pim77_BSR-current-address,
              pim77_out-interface 
            }
    STATUS current
    DESCRIPTION
        "Notification of Event PIM.77

        Message: 'Sending PIM CANDIDATE RP Advertisement: my candidate RP $1 holdtime $2 to current BSR $3, outgoing interface $4'

        Parameters list:
              $1: pim77_C-RP-address
              $2: pim77_holdtime
              $3: pim77_BSR-current-address
              $4: pim77_out-interface

        Sending PIM CANDIDATE RP Advertisement"
    ::= { pimNotificationsPrefix 77 }

pimNotification78 NOTIFICATION-TYPE
    OBJECTS { 
              pim78_source-addres, 
              pim78_dest-address,
              pim78_out-interface 
            }
    STATUS current
    DESCRIPTION
        "Notification of Event PIM.78

        Message: 'Sending PIM RP-Set message to the new neighbour, from $1 to $2, outgoing interface $3'

        Parameters list:
              $1: pim78_source-addres
              $2: pim78_dest-address
              $3: pim78_out-interface

        I am the current DR on that interface, so send an RP-Set message to the new neighbour"
    ::= { pimNotificationsPrefix 78 }

pimNotification79 NOTIFICATION-TYPE
    OBJECTS { 
              pim79_cand-bsr-addr, 
              pim79_interface,
              pim79_timer_value 
            }
    STATUS current
    DESCRIPTION
        "Notification of Event PIM.79

        Message: 'Set Bootstrap Timer for BSR $1 on interface $2: $3s'

        Parameters list:
              $1: pim79_cand-bsr-addr
              $2: pim79_interface
              $3: pim79_timer_value

        Set Bootstrap Timer for BSR on interface"
    ::= { pimNotificationsPrefix 79 }

pimNotification80 NOTIFICATION-TYPE
    OBJECTS { 
              pim80_preferred-non_preferred, 
              pim80_new-cand-bsr,
              pim80_interface,
              pim80_old_state-new_state 
            }
    STATUS current
    DESCRIPTION
        "Notification of Event PIM.80

        Message: 'Receive $1 Bootstrap message from $2 interface $3: state change $4'

        Parameters list:
              $1: pim80_preferred-non_preferred
              $2: pim80_new-cand-bsr
              $3: pim80_interface
              $4: pim80_old_state-new_state

        Change Bootstrap state for cand-BSR/non-cand-BSR"
    ::= { pimNotificationsPrefix 80 }

pimNotification81 NOTIFICATION-TYPE
    OBJECTS { 
              pim81_bsr-address 
            }
    STATUS current
    DESCRIPTION
        "Notification of Event PIM.81

        Message: 'The Bootstrap Timer of BSR $1 has expired, new BSR election'

        Parameters list:
              $1: pim81_bsr-address

        BSR timer has expired, new BSR election"
    ::= { pimNotificationsPrefix 81 }

pimNotification82 NOTIFICATION-TYPE
    OBJECTS { 
              pim82_bsr-address, 
              pim82_state,
              pim82_bsr-timer 
            }
    STATUS current
    DESCRIPTION
        "Notification of Event PIM.82

        Message: 'I am a candidate-BSR $1, my state $2, my BSR timer: $3s'

        Parameters list:
              $1: pim82_bsr-address
              $2: pim82_state
              $3: pim82_bsr-timer

        I am a candidate-BSR with a state and a BSR timer"
    ::= { pimNotificationsPrefix 82 }

pimNotification83 NOTIFICATION-TYPE
    OBJECTS { 
              pim83_state 
            }
    STATUS current
    DESCRIPTION
        "Notification of Event PIM.83

        Message: 'I am not a candidate-BSR, my BSR state $1'

        Parameters list:
              $1: pim83_state

        I am not a candidate-BSR"
    ::= { pimNotificationsPrefix 83 }

pimNotification84 NOTIFICATION-TYPE
    OBJECTS { 
              pim84_rp-address, 
              pim84_group-address 
            }
    STATUS current
    DESCRIPTION
        "Notification of Event PIM.84

        Message: 'The holdtime of cand-RP-Set entry ($1/$2) has expired, the entry has been deleted'

        Parameters list:
              $1: pim84_rp-address
              $2: pim84_group-address

        The holdtime of cand-RP-Set entry has expired and it has been deleted"
    ::= { pimNotificationsPrefix 84 }

pimNotification85 NOTIFICATION-TYPE
    OBJECTS { 
              pim85_cand-rp-addr, 
              pim85_cand-bsr-addr 
            }
    STATUS current
    DESCRIPTION
        "Notification of Event PIM.85

        Message: 'I am a candidate-RP $1, and BSR has changed to $2, I must send CAND-RP Advertisement immediately'

        Parameters list:
              $1: pim85_cand-rp-addr
              $2: pim85_cand-bsr-addr

        Send CAND-RP Advertisement after the BSR has changed"
    ::= { pimNotificationsPrefix 85 }

pimNotification86 NOTIFICATION-TYPE
    OBJECTS { 
              pim86_source-address 
            }
    STATUS current
    DESCRIPTION
        "Notification of Event PIM.86

        Message: 'The source of BOOTSTRAP message $1, is not the upstream router toward BSR'

        Parameters list:
              $1: pim86_source-address

        The Boostrap message must be discarded"
    ::= { pimNotificationsPrefix 86 }

pimNotification87 NOTIFICATION-TYPE
    OBJECTS { 
              pim87_type, 
              pim87_rp,
              pim87_prefix,
              pim87_prefixlen,
              pim87_message 
            }
    STATUS current
    DESCRIPTION
        "Notification of Event PIM.87

        Message: '$1 RP address $2 - group prefix $3/$4 mapping: $5'

        Parameters list:
              $1: pim87_type
              $2: pim87_rp
              $3: pim87_prefix
              $4: pim87_prefixlen
              $5: pim87_message

        Event related to a RP group entry"
    ::= { pimNotificationsPrefix 87 }

pimNotification88 NOTIFICATION-TYPE
    STATUS current
    DESCRIPTION
        "Notification of Event PIM.88

        Message: '--'

        Reserved for future use"
    ::= { pimNotificationsPrefix 88 }

pimNotification89 NOTIFICATION-TYPE
    OBJECTS { 
              pim89_grp-address, 
              pim89_message 
            }
    STATUS current
    DESCRIPTION
        "Notification of Event PIM.89

        Message: 'Source-Specific Multicast group $1: $2'

        Parameters list:
              $1: pim89_grp-address
              $2: pim89_message

        Error detected due to a not allowed use of a SSM group"
    ::= { pimNotificationsPrefix 89 }


END
