-- file automatically created


TELDAT-TRAP-HDLC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


hdlcTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the HDLC event subsystem."
    REVISION "201401200930Z"
    DESCRIPTION "Initial implementation"
        ::= { telEventTraps 190 }


hdlcEventsGroup	OBJECT IDENTIFIER	::= { hdlcTrapsMIB 1 }

hdlcNotifications	OBJECT IDENTIFIER	::= { hdlcTrapsMIB 2 }
hdlcNotificationsPrefix	OBJECT IDENTIFIER	::= { hdlcNotifications 0 }

hdlcEventObjects1 OBJECT-IDENTITY
    STATUS current
    DESCRIPTION
        "Event HDLC.1
        Frame transmitted."
    ::= { hdlcEventsGroup 1 }

hdlc1_address OBJECT-TYPE
    SYNTAX Integer32
    MAX-ACCESS accessible-for-notify
    STATUS current
    DESCRIPTION
        "Parameter 'address' in event HDLC.1"
    ::= { hdlcEventObjects1 1 }

hdlc1_control OBJECT-TYPE
    SYNTAX Integer32
    MAX-ACCESS accessible-for-notify
    STATUS current
    DESCRIPTION
        "Parameter 'control' in event HDLC.1"
    ::= { hdlcEventObjects1 2 }

hdlc1_protocol OBJECT-TYPE
    SYNTAX Integer32
    MAX-ACCESS accessible-for-notify
    STATUS current
    DESCRIPTION
        "Parameter 'protocol' in event HDLC.1"
    ::= { hdlcEventObjects1 3 }

hdlc1_len OBJECT-TYPE
    SYNTAX Integer32
    MAX-ACCESS accessible-for-notify
    STATUS current
    DESCRIPTION
        "Parameter 'len' in event HDLC.1"
    ::= { hdlcEventObjects1 4 }

hdlc1_ifc_name OBJECT-TYPE
    SYNTAX DisplayString
    MAX-ACCESS accessible-for-notify
    STATUS current
    DESCRIPTION
        "Parameter 'ifc_name' in event HDLC.1"
    ::= { hdlcEventObjects1 5 }

hdlcEventObjects2 OBJECT-IDENTITY
    STATUS current
    DESCRIPTION
        "Event HDLC.2
        Frame received."
    ::= { hdlcEventsGroup 2 }

hdlc2_address OBJECT-TYPE
    SYNTAX Integer32
    MAX-ACCESS accessible-for-notify
    STATUS current
    DESCRIPTION
        "Parameter 'address' in event HDLC.2"
    ::= { hdlcEventObjects2 1 }

hdlc2_control OBJECT-TYPE
    SYNTAX Integer32
    MAX-ACCESS accessible-for-notify
    STATUS current
    DESCRIPTION
        "Parameter 'control' in event HDLC.2"
    ::= { hdlcEventObjects2 2 }

hdlc2_protocol OBJECT-TYPE
    SYNTAX Integer32
    MAX-ACCESS accessible-for-notify
    STATUS current
    DESCRIPTION
        "Parameter 'protocol' in event HDLC.2"
    ::= { hdlcEventObjects2 3 }

hdlc2_len OBJECT-TYPE
    SYNTAX Integer32
    MAX-ACCESS accessible-for-notify
    STATUS current
    DESCRIPTION
        "Parameter 'len' in event HDLC.2"
    ::= { hdlcEventObjects2 4 }

hdlc2_ifc_name OBJECT-TYPE
    SYNTAX DisplayString
    MAX-ACCESS accessible-for-notify
    STATUS current
    DESCRIPTION
        "Parameter 'ifc_name' in event HDLC.2"
    ::= { hdlcEventObjects2 5 }

hdlcEventObjects3 OBJECT-IDENTITY
    STATUS current
    DESCRIPTION
        "Event HDLC.3
        Keepalive state change"
    ::= { hdlcEventsGroup 3 }

hdlc3_line_state OBJECT-TYPE
    SYNTAX DisplayString
    MAX-ACCESS accessible-for-notify
    STATUS current
    DESCRIPTION
        "Parameter 'line_state' in event HDLC.3"
    ::= { hdlcEventObjects3 1 }

hdlc3_ifc_name OBJECT-TYPE
    SYNTAX DisplayString
    MAX-ACCESS accessible-for-notify
    STATUS current
    DESCRIPTION
        "Parameter 'ifc_name' in event HDLC.3"
    ::= { hdlcEventObjects3 2 }

hdlcEventObjects4 OBJECT-IDENTITY
    STATUS current
    DESCRIPTION
        "Event HDLC.4
        Keepalive sequence transmitted. Status."
    ::= { hdlcEventsGroup 4 }

hdlc4_myseq OBJECT-TYPE
    SYNTAX Integer32
    MAX-ACCESS accessible-for-notify
    STATUS current
    DESCRIPTION
        "Parameter 'myseq' in event HDLC.4"
    ::= { hdlcEventObjects4 1 }

hdlc4_mineseen OBJECT-TYPE
    SYNTAX Integer32
    MAX-ACCESS accessible-for-notify
    STATUS current
    DESCRIPTION
        "Parameter 'mineseen' in event HDLC.4"
    ::= { hdlcEventObjects4 2 }

hdlc4_slarped OBJECT-TYPE
    SYNTAX DisplayString
    MAX-ACCESS accessible-for-notify
    STATUS current
    DESCRIPTION
        "Parameter 'slarped' in event HDLC.4"
    ::= { hdlcEventObjects4 3 }

hdlc4_yoursseen OBJECT-TYPE
    SYNTAX Integer32
    MAX-ACCESS accessible-for-notify
    STATUS current
    DESCRIPTION
        "Parameter 'yoursseen' in event HDLC.4"
    ::= { hdlcEventObjects4 4 }

hdlc4_line_state OBJECT-TYPE
    SYNTAX DisplayString
    MAX-ACCESS accessible-for-notify
    STATUS current
    DESCRIPTION
        "Parameter 'line_state' in event HDLC.4"
    ::= { hdlcEventObjects4 5 }

hdlc4_loop_state OBJECT-TYPE
    SYNTAX DisplayString
    MAX-ACCESS accessible-for-notify
    STATUS current
    DESCRIPTION
        "Parameter 'loop_state' in event HDLC.4"
    ::= { hdlcEventObjects4 6 }

hdlc4_ifc_name OBJECT-TYPE
    SYNTAX DisplayString
    MAX-ACCESS accessible-for-notify
    STATUS current
    DESCRIPTION
        "Parameter 'ifc_name' in event HDLC.4"
    ::= { hdlcEventObjects4 7 }

hdlcEventObjects5 OBJECT-IDENTITY
    STATUS current
    DESCRIPTION
        "Event HDLC.5
        Keepalive recived but none configured."
    ::= { hdlcEventsGroup 5 }

hdlc5_ifc_name OBJECT-TYPE
    SYNTAX DisplayString
    MAX-ACCESS accessible-for-notify
    STATUS current
    DESCRIPTION
        "Parameter 'ifc_name' in event HDLC.5"
    ::= { hdlcEventObjects5 1 }

hdlcEventObjects6 OBJECT-IDENTITY
    STATUS current
    DESCRIPTION
        "Event HDLC.6
        Keepalive time mismatch"
    ::= { hdlcEventsGroup 6 }

hdlc6_expected OBJECT-TYPE
    SYNTAX Integer32
    MAX-ACCESS accessible-for-notify
    STATUS current
    DESCRIPTION
        "Parameter 'expected' in event HDLC.6"
    ::= { hdlcEventObjects6 1 }

hdlc6_meassured OBJECT-TYPE
    SYNTAX Integer32
    MAX-ACCESS accessible-for-notify
    STATUS current
    DESCRIPTION
        "Parameter 'meassured' in event HDLC.6"
    ::= { hdlcEventObjects6 2 }

hdlc6_ifc_name OBJECT-TYPE
    SYNTAX DisplayString
    MAX-ACCESS accessible-for-notify
    STATUS current
    DESCRIPTION
        "Parameter 'ifc_name' in event HDLC.6"
    ::= { hdlcEventObjects6 3 }

hdlcEventObjects7 OBJECT-IDENTITY
    STATUS current
    DESCRIPTION
        "Event HDLC.7
        Invalid length of control packet."
    ::= { hdlcEventsGroup 7 }

hdlc7_len OBJECT-TYPE
    SYNTAX Integer32
    MAX-ACCESS accessible-for-notify
    STATUS current
    DESCRIPTION
        "Parameter 'len' in event HDLC.7"
    ::= { hdlcEventObjects7 1 }

hdlc7_ifc_name OBJECT-TYPE
    SYNTAX DisplayString
    MAX-ACCESS accessible-for-notify
    STATUS current
    DESCRIPTION
        "Parameter 'ifc_name' in event HDLC.7"
    ::= { hdlcEventObjects7 2 }

hdlcEventObjects8 OBJECT-IDENTITY
    STATUS current
    DESCRIPTION
        "Event HDLC.8
        Unexpected IP address reply."
    ::= { hdlcEventsGroup 8 }

hdlc8_ifc_name OBJECT-TYPE
    SYNTAX DisplayString
    MAX-ACCESS accessible-for-notify
    STATUS current
    DESCRIPTION
        "Parameter 'ifc_name' in event HDLC.8"
    ::= { hdlcEventObjects8 1 }

hdlcEventObjects9 OBJECT-IDENTITY
    STATUS current
    DESCRIPTION
        "Event HDLC.9
        IP address request."
    ::= { hdlcEventsGroup 9 }

hdlc9_ifc_name OBJECT-TYPE
    SYNTAX DisplayString
    MAX-ACCESS accessible-for-notify
    STATUS current
    DESCRIPTION
        "Parameter 'ifc_name' in event HDLC.9"
    ::= { hdlcEventObjects9 1 }

hdlcEventObjects10 OBJECT-IDENTITY
    STATUS current
    DESCRIPTION
        "Event HDLC.10
        Unsupported protocol."
    ::= { hdlcEventsGroup 10 }

hdlc10_protocol OBJECT-TYPE
    SYNTAX Integer32
    MAX-ACCESS accessible-for-notify
    STATUS current
    DESCRIPTION
        "Parameter 'protocol' in event HDLC.10"
    ::= { hdlcEventObjects10 1 }

hdlc10_ifc_name OBJECT-TYPE
    SYNTAX DisplayString
    MAX-ACCESS accessible-for-notify
    STATUS current
    DESCRIPTION
        "Parameter 'ifc_name' in event HDLC.10"
    ::= { hdlcEventObjects10 2 }

hdlcEventObjects11 OBJECT-IDENTITY
    STATUS current
    DESCRIPTION
        "Event HDLC.11
        Invalid addr of control packet."
    ::= { hdlcEventsGroup 11 }

hdlc11_bad_add OBJECT-TYPE
    SYNTAX Integer32
    MAX-ACCESS accessible-for-notify
    STATUS current
    DESCRIPTION
        "Parameter 'bad_add' in event HDLC.11"
    ::= { hdlcEventObjects11 1 }

hdlc11_ifc_name OBJECT-TYPE
    SYNTAX DisplayString
    MAX-ACCESS accessible-for-notify
    STATUS current
    DESCRIPTION
        "Parameter 'ifc_name' in event HDLC.11"
    ::= { hdlcEventObjects11 2 }

hdlcEventObjects12 OBJECT-IDENTITY
    STATUS current
    DESCRIPTION
        "Event HDLC.12
        Event received."
    ::= { hdlcEventsGroup 12 }

hdlc12_event OBJECT-TYPE
    SYNTAX Integer32
    MAX-ACCESS accessible-for-notify
    STATUS current
    DESCRIPTION
        "Parameter 'event' in event HDLC.12"
    ::= { hdlcEventObjects12 1 }

hdlc12_state OBJECT-TYPE
    SYNTAX Integer32
    MAX-ACCESS accessible-for-notify
    STATUS current
    DESCRIPTION
        "Parameter 'state' in event HDLC.12"
    ::= { hdlcEventObjects12 2 }

hdlc12_ifc_name OBJECT-TYPE
    SYNTAX DisplayString
    MAX-ACCESS accessible-for-notify
    STATUS current
    DESCRIPTION
        "Parameter 'ifc_name' in event HDLC.12"
    ::= { hdlcEventObjects12 3 }

hdlcEventObjects13 OBJECT-IDENTITY
    STATUS current
    DESCRIPTION
        "Event HDLC.13
        FSM state change."
    ::= { hdlcEventsGroup 13 }

hdlc13_old_state OBJECT-TYPE
    SYNTAX Integer32
    MAX-ACCESS accessible-for-notify
    STATUS current
    DESCRIPTION
        "Parameter 'old_state' in event HDLC.13"
    ::= { hdlcEventObjects13 1 }

hdlc13_new_state OBJECT-TYPE
    SYNTAX Integer32
    MAX-ACCESS accessible-for-notify
    STATUS current
    DESCRIPTION
        "Parameter 'new_state' in event HDLC.13"
    ::= { hdlcEventObjects13 2 }

hdlc13_ifc_name OBJECT-TYPE
    SYNTAX DisplayString
    MAX-ACCESS accessible-for-notify
    STATUS current
    DESCRIPTION
        "Parameter 'ifc_name' in event HDLC.13"
    ::= { hdlcEventObjects13 3 }

hdlcEventObjects14 OBJECT-IDENTITY
    STATUS current
    DESCRIPTION
        "Event HDLC.14
        Frame received dropped because Keepalive is down."
    ::= { hdlcEventsGroup 14 }

hdlc14_ifc_name OBJECT-TYPE
    SYNTAX DisplayString
    MAX-ACCESS accessible-for-notify
    STATUS current
    DESCRIPTION
        "Parameter 'ifc_name' in event HDLC.14"
    ::= { hdlcEventObjects14 1 }

hdlcEventObjects15 OBJECT-IDENTITY
    STATUS current
    DESCRIPTION
        "Event HDLC.15
        Debug indication."
    ::= { hdlcEventsGroup 15 }

hdlc15_Debug_string OBJECT-TYPE
    SYNTAX DisplayString
    MAX-ACCESS accessible-for-notify
    STATUS current
    DESCRIPTION
        "Parameter 'Debug_string' in event HDLC.15"
    ::= { hdlcEventObjects15 1 }

hdlc15_ifc_name OBJECT-TYPE
    SYNTAX DisplayString
    MAX-ACCESS accessible-for-notify
    STATUS current
    DESCRIPTION
        "Parameter 'ifc_name' in event HDLC.15"
    ::= { hdlcEventObjects15 2 }


hdlcNotification1 NOTIFICATION-TYPE
    OBJECTS { 
              hdlc1_address, 
              hdlc1_control,
              hdlc1_protocol,
              hdlc1_len,
              hdlc1_ifc_name 
            }
    STATUS current
    DESCRIPTION
        "Notification of Event HDLC.1

        Message: 'Transmit frame address $1 control $2 protocol $3 len $4 on interface $5'

        Parameters list:
              $1: hdlc1_address
              $2: hdlc1_control
              $3: hdlc1_protocol
              $4: hdlc1_len
              $5: hdlc1_ifc_name

        Frame transmitted."
    ::= { hdlcNotificationsPrefix 1 }

hdlcNotification2 NOTIFICATION-TYPE
    OBJECTS { 
              hdlc2_address, 
              hdlc2_control,
              hdlc2_protocol,
              hdlc2_len,
              hdlc2_ifc_name 
            }
    STATUS current
    DESCRIPTION
        "Notification of Event HDLC.2

        Message: 'Receive frame address $1 control $2 protocol $3 len $4 on interface $5'

        Parameters list:
              $1: hdlc2_address
              $2: hdlc2_control
              $3: hdlc2_protocol
              $4: hdlc2_len
              $5: hdlc2_ifc_name

        Frame received."
    ::= { hdlcNotificationsPrefix 2 }

hdlcNotification3 NOTIFICATION-TYPE
    OBJECTS { 
              hdlc3_line_state, 
              hdlc3_ifc_name 
            }
    STATUS current
    DESCRIPTION
        "Notification of Event HDLC.3

        Message: 'Keepalive change state to $1 on interface $2'

        Parameters list:
              $1: hdlc3_line_state
              $2: hdlc3_ifc_name

        Keepalive state change"
    ::= { hdlcNotificationsPrefix 3 }

hdlcNotification4 NOTIFICATION-TYPE
    OBJECTS { 
              hdlc4_myseq, 
              hdlc4_mineseen,
              hdlc4_slarped,
              hdlc4_yoursseen,
              hdlc4_line_state,
              hdlc4_loop_state,
              hdlc4_ifc_name 
            }
    STATUS current
    DESCRIPTION
        "Notification of Event HDLC.4

        Message: 'Keepalive myseq:$1 mineseen:$2$3 yoursseen:$4, line $5 $6 on interface $7'

        Parameters list:
              $1: hdlc4_myseq
              $2: hdlc4_mineseen
              $3: hdlc4_slarped
              $4: hdlc4_yoursseen
              $5: hdlc4_line_state
              $6: hdlc4_loop_state
              $7: hdlc4_ifc_name

        Keepalive sequence transmitted. Status."
    ::= { hdlcNotificationsPrefix 4 }

hdlcNotification5 NOTIFICATION-TYPE
    OBJECTS { 
              hdlc5_ifc_name 
            }
    STATUS current
    DESCRIPTION
        "Notification of Event HDLC.5

        Message: 'Got keepalive with none configured  on interface $1'

        Parameters list:
              $1: hdlc5_ifc_name

        Keepalive recived but none configured."
    ::= { hdlcNotificationsPrefix 5 }

hdlcNotification6 NOTIFICATION-TYPE
    OBJECTS { 
              hdlc6_expected, 
              hdlc6_meassured,
              hdlc6_ifc_name 
            }
    STATUS current
    DESCRIPTION
        "Notification of Event HDLC.6

        Message: 'Keepalive time mismatch - should be $1 secs, is $2  on interface $3'

        Parameters list:
              $1: hdlc6_expected
              $2: hdlc6_meassured
              $3: hdlc6_ifc_name

        Keepalive time mismatch"
    ::= { hdlcNotificationsPrefix 6 }

hdlcNotification7 NOTIFICATION-TYPE
    OBJECTS { 
              hdlc7_len, 
              hdlc7_ifc_name 
            }
    STATUS current
    DESCRIPTION
        "Notification of Event HDLC.7

        Message: 'Invalid length of control packet ($1 bytes) on interface $2'

        Parameters list:
              $1: hdlc7_len
              $2: hdlc7_ifc_name

        Invalid length of control packet."
    ::= { hdlcNotificationsPrefix 7 }

hdlcNotification8 NOTIFICATION-TYPE
    OBJECTS { 
              hdlc8_ifc_name 
            }
    STATUS current
    DESCRIPTION
        "Notification of Event HDLC.8

        Message: 'Unexpected IP address reply on interface $1'

        Parameters list:
              $1: hdlc8_ifc_name

        Unexpected IP address reply."
    ::= { hdlcNotificationsPrefix 8 }

hdlcNotification9 NOTIFICATION-TYPE
    OBJECTS { 
              hdlc9_ifc_name 
            }
    STATUS current
    DESCRIPTION
        "Notification of Event HDLC.9

        Message: 'IP address request on interface $1'

        Parameters list:
              $1: hdlc9_ifc_name

        IP address request."
    ::= { hdlcNotificationsPrefix 9 }

hdlcNotification10 NOTIFICATION-TYPE
    OBJECTS { 
              hdlc10_protocol, 
              hdlc10_ifc_name 
            }
    STATUS current
    DESCRIPTION
        "Notification of Event HDLC.10

        Message: 'Unsupported protocol $1 on interface $2'

        Parameters list:
              $1: hdlc10_protocol
              $2: hdlc10_ifc_name

        Unsupported protocol."
    ::= { hdlcNotificationsPrefix 10 }

hdlcNotification11 NOTIFICATION-TYPE
    OBJECTS { 
              hdlc11_bad_add, 
              hdlc11_ifc_name 
            }
    STATUS current
    DESCRIPTION
        "Notification of Event HDLC.11

        Message: 'Invalid address ($1) of control packet on interface $2'

        Parameters list:
              $1: hdlc11_bad_add
              $2: hdlc11_ifc_name

        Invalid addr of control packet."
    ::= { hdlcNotificationsPrefix 11 }

hdlcNotification12 NOTIFICATION-TYPE
    OBJECTS { 
              hdlc12_event, 
              hdlc12_state,
              hdlc12_ifc_name 
            }
    STATUS current
    DESCRIPTION
        "Notification of Event HDLC.12

        Message: 'Received event $1 on state $2 on interface $3'

        Parameters list:
              $1: hdlc12_event
              $2: hdlc12_state
              $3: hdlc12_ifc_name

        Event received."
    ::= { hdlcNotificationsPrefix 12 }

hdlcNotification13 NOTIFICATION-TYPE
    OBJECTS { 
              hdlc13_old_state, 
              hdlc13_new_state,
              hdlc13_ifc_name 
            }
    STATUS current
    DESCRIPTION
        "Notification of Event HDLC.13

        Message: 'FSM state change old state $1 new state $2 on interface $3'

        Parameters list:
              $1: hdlc13_old_state
              $2: hdlc13_new_state
              $3: hdlc13_ifc_name

        FSM state change."
    ::= { hdlcNotificationsPrefix 13 }

hdlcNotification14 NOTIFICATION-TYPE
    OBJECTS { 
              hdlc14_ifc_name 
            }
    STATUS current
    DESCRIPTION
        "Notification of Event HDLC.14

        Message: 'Drop frame on interface $1'

        Parameters list:
              $1: hdlc14_ifc_name

        Frame received dropped because Keepalive is down."
    ::= { hdlcNotificationsPrefix 14 }

hdlcNotification15 NOTIFICATION-TYPE
    OBJECTS { 
              hdlc15_Debug_string, 
              hdlc15_ifc_name 
            }
    STATUS current
    DESCRIPTION
        "Notification of Event HDLC.15

        Message: '$1 on interface $2'

        Parameters list:
              $1: hdlc15_Debug_string
              $2: hdlc15_ifc_name

        Debug indication."
    ::= { hdlcNotificationsPrefix 15 }


END
