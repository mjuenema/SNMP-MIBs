-- file automatically created


TELDAT-TRAP-BRS-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


brsTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the BRS event subsystem."
    REVISION "201401200930Z"
    DESCRIPTION "Initial implementation"
        ::= { telEventTraps 3 }


brsEventsGroup	OBJECT IDENTIFIER	::= { brsTrapsMIB 1 }

brsNotifications	OBJECT IDENTIFIER	::= { brsTrapsMIB 2 }
brsNotificationsPrefix	OBJECT IDENTIFIER	::= { brsNotifications 0 }

brsEventObjects1 OBJECT-IDENTITY
    STATUS current
    DESCRIPTION
        "Event BRS.1
        A packet is placed in the class based on its protocol."
    ::= { brsEventsGroup 1 }

brs1_msg_prot_type OBJECT-TYPE
    SYNTAX DisplayString
    MAX-ACCESS accessible-for-notify
    STATUS current
    DESCRIPTION
        "Parameter 'msg prot type' in event BRS.1"
    ::= { brsEventObjects1 1 }

brs1_class_name OBJECT-TYPE
    SYNTAX DisplayString
    MAX-ACCESS accessible-for-notify
    STATUS current
    DESCRIPTION
        "Parameter 'class name' in event BRS.1"
    ::= { brsEventObjects1 2 }

brs1_interface OBJECT-TYPE
    SYNTAX DisplayString
    MAX-ACCESS accessible-for-notify
    STATUS current
    DESCRIPTION
        "Parameter 'interface' in event BRS.1"
    ::= { brsEventObjects1 3 }

brsEventObjects2 OBJECT-IDENTITY
    STATUS current
    DESCRIPTION
        "Event BRS.2
        Notifies on all packet overflows."
    ::= { brsEventsGroup 2 }

brs2_msg_prot_type OBJECT-TYPE
    SYNTAX DisplayString
    MAX-ACCESS accessible-for-notify
    STATUS current
    DESCRIPTION
        "Parameter 'msg prot type' in event BRS.2"
    ::= { brsEventObjects2 1 }

brs2_interface OBJECT-TYPE
    SYNTAX DisplayString
    MAX-ACCESS accessible-for-notify
    STATUS current
    DESCRIPTION
        "Parameter 'interface' in event BRS.2"
    ::= { brsEventObjects2 2 }

brsEventObjects3 OBJECT-IDENTITY
    STATUS current
    DESCRIPTION
        "Event BRS.3
        Message showed when zero length packets are dumped."
    ::= { brsEventsGroup 3 }

brs3_msg_prot_type OBJECT-TYPE
    SYNTAX DisplayString
    MAX-ACCESS accessible-for-notify
    STATUS current
    DESCRIPTION
        "Parameter 'msg prot type' in event BRS.3"
    ::= { brsEventObjects3 1 }

brs3_interface OBJECT-TYPE
    SYNTAX DisplayString
    MAX-ACCESS accessible-for-notify
    STATUS current
    DESCRIPTION
        "Parameter 'interface' in event BRS.3"
    ::= { brsEventObjects3 2 }

brsEventObjects4 OBJECT-IDENTITY
    STATUS current
    DESCRIPTION
        "Event BRS.4
        A packet is placed from handler struct to driver queue
        to be transmitted."
    ::= { brsEventsGroup 4 }

brs4_class_name OBJECT-TYPE
    SYNTAX DisplayString
    MAX-ACCESS accessible-for-notify
    STATUS current
    DESCRIPTION
        "Parameter 'class name' in event BRS.4"
    ::= { brsEventObjects4 1 }

brs4_interface OBJECT-TYPE
    SYNTAX DisplayString
    MAX-ACCESS accessible-for-notify
    STATUS current
    DESCRIPTION
        "Parameter 'interface' in event BRS.4"
    ::= { brsEventObjects4 2 }

brsEventObjects5 OBJECT-IDENTITY
    STATUS current
    DESCRIPTION
        "Event BRS.5
        No traffic-shape-group can transmit due to congestion."
    ::= { brsEventsGroup 5 }

brs5_class OBJECT-TYPE
    SYNTAX DisplayString
    MAX-ACCESS accessible-for-notify
    STATUS current
    DESCRIPTION
        "Parameter 'class' in event BRS.5"
    ::= { brsEventObjects5 1 }

brs5_interface OBJECT-TYPE
    SYNTAX DisplayString
    MAX-ACCESS accessible-for-notify
    STATUS current
    DESCRIPTION
        "Parameter 'interface' in event BRS.5"
    ::= { brsEventObjects5 2 }

brs5_ticks-left OBJECT-TYPE
    SYNTAX Integer32
    MAX-ACCESS accessible-for-notify
    STATUS current
    DESCRIPTION
        "Parameter 'ticks-left' in event BRS.5"
    ::= { brsEventObjects5 3 }

brsEventObjects6 OBJECT-IDENTITY
    STATUS current
    DESCRIPTION
        "Event BRS.6
        A timer is launch to check for de-congestion of any class."
    ::= { brsEventsGroup 6 }

brs6_interface OBJECT-TYPE
    SYNTAX DisplayString
    MAX-ACCESS accessible-for-notify
    STATUS current
    DESCRIPTION
        "Parameter 'interface' in event BRS.6"
    ::= { brsEventObjects6 1 }

brs6_class OBJECT-TYPE
    SYNTAX DisplayString
    MAX-ACCESS accessible-for-notify
    STATUS current
    DESCRIPTION
        "Parameter 'class' in event BRS.6"
    ::= { brsEventObjects6 2 }

brs6_new_time OBJECT-TYPE
    SYNTAX Integer32
    MAX-ACCESS accessible-for-notify
    STATUS current
    DESCRIPTION
        "Parameter 'new time' in event BRS.6"
    ::= { brsEventObjects6 3 }

brs6_new_time-out OBJECT-TYPE
    SYNTAX Integer32
    MAX-ACCESS accessible-for-notify
    STATUS current
    DESCRIPTION
        "Parameter 'new time-out' in event BRS.6"
    ::= { brsEventObjects6 4 }

brs6_old_time OBJECT-TYPE
    SYNTAX Integer32
    MAX-ACCESS accessible-for-notify
    STATUS current
    DESCRIPTION
        "Parameter 'old time' in event BRS.6"
    ::= { brsEventObjects6 5 }

brs6_old_time-out OBJECT-TYPE
    SYNTAX Integer32
    MAX-ACCESS accessible-for-notify
    STATUS current
    DESCRIPTION
        "Parameter 'old time-out' in event BRS.6"
    ::= { brsEventObjects6 6 }

brsEventObjects7 OBJECT-IDENTITY
    STATUS current
    DESCRIPTION
        "Event BRS.7
        A timer has expired."
    ::= { brsEventsGroup 7 }

brs7_interface OBJECT-TYPE
    SYNTAX DisplayString
    MAX-ACCESS accessible-for-notify
    STATUS current
    DESCRIPTION
        "Parameter 'interface' in event BRS.7"
    ::= { brsEventObjects7 1 }

brsEventObjects8 OBJECT-IDENTITY
    STATUS current
    DESCRIPTION
        "Event BRS.8
        A packet has been tagged with a new dscp value."
    ::= { brsEventsGroup 8 }

brs8_source_IP OBJECT-TYPE
    SYNTAX IpAddress
    MAX-ACCESS accessible-for-notify
    STATUS current
    DESCRIPTION
        "Parameter 'source IP' in event BRS.8"
    ::= { brsEventObjects8 1 }

brs8_destination_IP OBJECT-TYPE
    SYNTAX IpAddress
    MAX-ACCESS accessible-for-notify
    STATUS current
    DESCRIPTION
        "Parameter 'destination IP' in event BRS.8"
    ::= { brsEventObjects8 2 }

brs8_class OBJECT-TYPE
    SYNTAX DisplayString
    MAX-ACCESS accessible-for-notify
    STATUS current
    DESCRIPTION
        "Parameter 'class' in event BRS.8"
    ::= { brsEventObjects8 3 }

brs8_new_dscp_value OBJECT-TYPE
    SYNTAX Integer32
    MAX-ACCESS accessible-for-notify
    STATUS current
    DESCRIPTION
        "Parameter 'new dscp value' in event BRS.8"
    ::= { brsEventObjects8 4 }

brsEventObjects9 OBJECT-IDENTITY
    STATUS current
    DESCRIPTION
        "Event BRS.9
        A packet has been tagged with a new cos value."
    ::= { brsEventsGroup 9 }

brs9_source_IP OBJECT-TYPE
    SYNTAX IpAddress
    MAX-ACCESS accessible-for-notify
    STATUS current
    DESCRIPTION
        "Parameter 'source IP' in event BRS.9"
    ::= { brsEventObjects9 1 }

brs9_destination_IP OBJECT-TYPE
    SYNTAX IpAddress
    MAX-ACCESS accessible-for-notify
    STATUS current
    DESCRIPTION
        "Parameter 'destination IP' in event BRS.9"
    ::= { brsEventObjects9 2 }

brs9_class OBJECT-TYPE
    SYNTAX DisplayString
    MAX-ACCESS accessible-for-notify
    STATUS current
    DESCRIPTION
        "Parameter 'class' in event BRS.9"
    ::= { brsEventObjects9 3 }

brs9_new_cos_value OBJECT-TYPE
    SYNTAX Integer32
    MAX-ACCESS accessible-for-notify
    STATUS current
    DESCRIPTION
        "Parameter 'new cos value' in event BRS.9"
    ::= { brsEventObjects9 4 }

brsEventObjects10 OBJECT-IDENTITY
    STATUS current
    DESCRIPTION
        "Event BRS.10
        A packet has been tagged with ATM CLP."
    ::= { brsEventsGroup 10 }

brs10_source_IP OBJECT-TYPE
    SYNTAX IpAddress
    MAX-ACCESS accessible-for-notify
    STATUS current
    DESCRIPTION
        "Parameter 'source IP' in event BRS.10"
    ::= { brsEventObjects10 1 }

brs10_destination_IP OBJECT-TYPE
    SYNTAX IpAddress
    MAX-ACCESS accessible-for-notify
    STATUS current
    DESCRIPTION
        "Parameter 'destination IP' in event BRS.10"
    ::= { brsEventObjects10 2 }

brs10_class OBJECT-TYPE
    SYNTAX DisplayString
    MAX-ACCESS accessible-for-notify
    STATUS current
    DESCRIPTION
        "Parameter 'class' in event BRS.10"
    ::= { brsEventObjects10 3 }

brsEventObjects11 OBJECT-IDENTITY
    STATUS current
    DESCRIPTION
        "Event BRS.11
        A preclassified packet has been tagged with a new dscp value."
    ::= { brsEventsGroup 11 }

brs11_source_IP OBJECT-TYPE
    SYNTAX IpAddress
    MAX-ACCESS accessible-for-notify
    STATUS current
    DESCRIPTION
        "Parameter 'source IP' in event BRS.11"
    ::= { brsEventObjects11 1 }

brs11_destination_IP OBJECT-TYPE
    SYNTAX IpAddress
    MAX-ACCESS accessible-for-notify
    STATUS current
    DESCRIPTION
        "Parameter 'destination IP' in event BRS.11"
    ::= { brsEventObjects11 2 }

brs11_class OBJECT-TYPE
    SYNTAX DisplayString
    MAX-ACCESS accessible-for-notify
    STATUS current
    DESCRIPTION
        "Parameter 'class' in event BRS.11"
    ::= { brsEventObjects11 3 }

brs11_new_dscp_value OBJECT-TYPE
    SYNTAX Integer32
    MAX-ACCESS accessible-for-notify
    STATUS current
    DESCRIPTION
        "Parameter 'new dscp value' in event BRS.11"
    ::= { brsEventObjects11 4 }

brsEventObjects12 OBJECT-IDENTITY
    STATUS current
    DESCRIPTION
        "Event BRS.12
        A packet has been tagged with PTM low/high latency or low/high priority transmission preferred."
    ::= { brsEventsGroup 12 }

brs12_source_IP OBJECT-TYPE
    SYNTAX IpAddress
    MAX-ACCESS accessible-for-notify
    STATUS current
    DESCRIPTION
        "Parameter 'source IP' in event BRS.12"
    ::= { brsEventObjects12 1 }

brs12_destination_IP OBJECT-TYPE
    SYNTAX IpAddress
    MAX-ACCESS accessible-for-notify
    STATUS current
    DESCRIPTION
        "Parameter 'destination IP' in event BRS.12"
    ::= { brsEventObjects12 2 }

brs12_class OBJECT-TYPE
    SYNTAX DisplayString
    MAX-ACCESS accessible-for-notify
    STATUS current
    DESCRIPTION
        "Parameter 'class' in event BRS.12"
    ::= { brsEventObjects12 3 }

brs12_latency_priority OBJECT-TYPE
    SYNTAX DisplayString
    MAX-ACCESS accessible-for-notify
    STATUS current
    DESCRIPTION
        "Parameter 'latency/priority' in event BRS.12"
    ::= { brsEventObjects12 4 }

brsEventObjects13 OBJECT-IDENTITY
    STATUS current
    DESCRIPTION
        "Event BRS.13
        A level-indicator has been updated because a rate has been exceeded in a class"
    ::= { brsEventsGroup 13 }

brs13_levindid OBJECT-TYPE
    SYNTAX Integer32
    MAX-ACCESS accessible-for-notify
    STATUS current
    DESCRIPTION
        "Parameter 'levindid' in event BRS.13"
    ::= { brsEventObjects13 1 }

brs13_class OBJECT-TYPE
    SYNTAX DisplayString
    MAX-ACCESS accessible-for-notify
    STATUS current
    DESCRIPTION
        "Parameter 'class' in event BRS.13"
    ::= { brsEventObjects13 2 }

brs13_operation OBJECT-TYPE
    SYNTAX DisplayString
    MAX-ACCESS accessible-for-notify
    STATUS current
    DESCRIPTION
        "Parameter 'operation' in event BRS.13"
    ::= { brsEventObjects13 3 }

brs13_value OBJECT-TYPE
    SYNTAX Integer32
    MAX-ACCESS accessible-for-notify
    STATUS current
    DESCRIPTION
        "Parameter 'value' in event BRS.13"
    ::= { brsEventObjects13 4 }

brsEventObjects14 OBJECT-IDENTITY
    STATUS current
    DESCRIPTION
        "Event BRS.14
        A rate limit configured as percentage of available bandwidth of a interface
        has been recalculated for a traffic class."
    ::= { brsEventsGroup 14 }

brs14_rate OBJECT-TYPE
    SYNTAX Integer32
    MAX-ACCESS accessible-for-notify
    STATUS current
    DESCRIPTION
        "Parameter 'rate' in event BRS.14"
    ::= { brsEventObjects14 1 }

brs14_class OBJECT-TYPE
    SYNTAX DisplayString
    MAX-ACCESS accessible-for-notify
    STATUS current
    DESCRIPTION
        "Parameter 'class' in event BRS.14"
    ::= { brsEventObjects14 2 }

brs14_interface OBJECT-TYPE
    SYNTAX DisplayString
    MAX-ACCESS accessible-for-notify
    STATUS current
    DESCRIPTION
        "Parameter 'interface' in event BRS.14"
    ::= { brsEventObjects14 3 }

brsEventObjects15 OBJECT-IDENTITY
    STATUS current
    DESCRIPTION
        "Event BRS.15
        A rate limit configured as percentage of available bandwidth of a interface
        has been recalculated."
    ::= { brsEventsGroup 15 }

brs15_rate OBJECT-TYPE
    SYNTAX Integer32
    MAX-ACCESS accessible-for-notify
    STATUS current
    DESCRIPTION
        "Parameter 'rate' in event BRS.15"
    ::= { brsEventObjects15 1 }

brs15_interface OBJECT-TYPE
    SYNTAX DisplayString
    MAX-ACCESS accessible-for-notify
    STATUS current
    DESCRIPTION
        "Parameter 'interface' in event BRS.15"
    ::= { brsEventObjects15 2 }

brsEventObjects16 OBJECT-IDENTITY
    STATUS current
    DESCRIPTION
        "Event BRS.16
        Notifies on packet discarded because of class queue overflow."
    ::= { brsEventsGroup 16 }

brs16_msg_prot_type OBJECT-TYPE
    SYNTAX DisplayString
    MAX-ACCESS accessible-for-notify
    STATUS current
    DESCRIPTION
        "Parameter 'msg prot type' in event BRS.16"
    ::= { brsEventObjects16 1 }

brs16_class OBJECT-TYPE
    SYNTAX DisplayString
    MAX-ACCESS accessible-for-notify
    STATUS current
    DESCRIPTION
        "Parameter 'class' in event BRS.16"
    ::= { brsEventObjects16 2 }

brs16_queue_length OBJECT-TYPE
    SYNTAX Integer32
    MAX-ACCESS accessible-for-notify
    STATUS current
    DESCRIPTION
        "Parameter 'queue length' in event BRS.16"
    ::= { brsEventObjects16 3 }

brs16_interface OBJECT-TYPE
    SYNTAX DisplayString
    MAX-ACCESS accessible-for-notify
    STATUS current
    DESCRIPTION
        "Parameter 'interface' in event BRS.16"
    ::= { brsEventObjects16 4 }

brsEventObjects17 OBJECT-IDENTITY
    STATUS current
    DESCRIPTION
        "Event BRS.17
        A rate limit has been enabled or disabled for a class by a cellular link advisor"
    ::= { brsEventsGroup 17 }

brs17_technology OBJECT-TYPE
    SYNTAX Integer32
    MAX-ACCESS accessible-for-notify
    STATUS current
    DESCRIPTION
        "Parameter 'technology' in event BRS.17"
    ::= { brsEventObjects17 1 }

brs17_new_state OBJECT-TYPE
    SYNTAX DisplayString
    MAX-ACCESS accessible-for-notify
    STATUS current
    DESCRIPTION
        "Parameter 'new state' in event BRS.17"
    ::= { brsEventObjects17 2 }

brs17_class OBJECT-TYPE
    SYNTAX DisplayString
    MAX-ACCESS accessible-for-notify
    STATUS current
    DESCRIPTION
        "Parameter 'class' in event BRS.17"
    ::= { brsEventObjects17 3 }

brs17_interface OBJECT-TYPE
    SYNTAX DisplayString
    MAX-ACCESS accessible-for-notify
    STATUS current
    DESCRIPTION
        "Parameter 'interface' in event BRS.17"
    ::= { brsEventObjects17 4 }

brsEventObjects18 OBJECT-IDENTITY
    STATUS current
    DESCRIPTION
        "Event BRS.18
        Global rate limit has been enabled or disabled by a cellular link advisor"
    ::= { brsEventsGroup 18 }

brs18_technology OBJECT-TYPE
    SYNTAX Integer32
    MAX-ACCESS accessible-for-notify
    STATUS current
    DESCRIPTION
        "Parameter 'technology' in event BRS.18"
    ::= { brsEventObjects18 1 }

brs18_new_state OBJECT-TYPE
    SYNTAX DisplayString
    MAX-ACCESS accessible-for-notify
    STATUS current
    DESCRIPTION
        "Parameter 'new state' in event BRS.18"
    ::= { brsEventObjects18 2 }

brs18_interface OBJECT-TYPE
    SYNTAX DisplayString
    MAX-ACCESS accessible-for-notify
    STATUS current
    DESCRIPTION
        "Parameter 'interface' in event BRS.18"
    ::= { brsEventObjects18 3 }

brsEventObjects19 OBJECT-IDENTITY
    STATUS current
    DESCRIPTION
        "Event BRS.19
        Error has occurred when registering or unregistering a cellular advisor upcall"
    ::= { brsEventsGroup 19 }

brs19_register_action OBJECT-TYPE
    SYNTAX DisplayString
    MAX-ACCESS accessible-for-notify
    STATUS current
    DESCRIPTION
        "Parameter 'register action' in event BRS.19"
    ::= { brsEventObjects19 1 }

brs19_interface OBJECT-TYPE
    SYNTAX DisplayString
    MAX-ACCESS accessible-for-notify
    STATUS current
    DESCRIPTION
        "Parameter 'interface' in event BRS.19"
    ::= { brsEventObjects19 2 }


brsNotification1 NOTIFICATION-TYPE
    OBJECTS { 
              brs1_msg_prot_type, 
              brs1_class_name,
              brs1_interface 
            }
    STATUS current
    DESCRIPTION
        "Notification of Event BRS.1

        Message: 'protocol $1 is placed in class $2 interface $3'

        Parameters list:
              $1: brs1_msg_prot_type
              $2: brs1_class_name
              $3: brs1_interface

        A packet is placed in the class based on its protocol."
    ::= { brsNotificationsPrefix 1 }

brsNotification2 NOTIFICATION-TYPE
    OBJECTS { 
              brs2_msg_prot_type, 
              brs2_interface 
            }
    STATUS current
    DESCRIPTION
        "Notification of Event BRS.2

        Message: 'a packet of protocol $1 is discarded because of queue overflow on interface $2'

        Parameters list:
              $1: brs2_msg_prot_type
              $2: brs2_interface

        Notifies on all packet overflows."
    ::= { brsNotificationsPrefix 2 }

brsNotification3 NOTIFICATION-TYPE
    OBJECTS { 
              brs3_msg_prot_type, 
              brs3_interface 
            }
    STATUS current
    DESCRIPTION
        "Notification of Event BRS.3

        Message: 'a zero length packet of protocol $1 is discarded interface $2'

        Parameters list:
              $1: brs3_msg_prot_type
              $2: brs3_interface

        Message showed when zero length packets are dumped."
    ::= { brsNotificationsPrefix 3 }

brsNotification4 NOTIFICATION-TYPE
    OBJECTS { 
              brs4_class_name, 
              brs4_interface 
            }
    STATUS current
    DESCRIPTION
        "Notification of Event BRS.4

        Message: 'packet transmitted from class $1 interface $2'

        Parameters list:
              $1: brs4_class_name
              $2: brs4_interface

        A packet is placed from handler struct to driver queue
        to be transmitted."
    ::= { brsNotificationsPrefix 4 }

brsNotification5 NOTIFICATION-TYPE
    OBJECTS { 
              brs5_class, 
              brs5_interface,
              brs5_ticks-left 
            }
    STATUS current
    DESCRIPTION
        "Notification of Event BRS.5

        Message: 'class $1 congested interface $2 ticks to transmit $3'

        Parameters list:
              $1: brs5_class
              $2: brs5_interface
              $3: brs5_ticks-left

        No traffic-shape-group can transmit due to congestion."
    ::= { brsNotificationsPrefix 5 }

brsNotification6 NOTIFICATION-TYPE
    OBJECTS { 
              brs6_interface, 
              brs6_class,
              brs6_new_time,
              brs6_new_time-out,
              brs6_old_time,
              brs6_old_time-out 
            }
    STATUS current
    DESCRIPTION
        "Notification of Event BRS.6

        Message: 'timer launch interface $1 class $2 new time $3 new time-out $4 old time $5 old time-out $6'

        Parameters list:
              $1: brs6_interface
              $2: brs6_class
              $3: brs6_new_time
              $4: brs6_new_time-out
              $5: brs6_old_time
              $6: brs6_old_time-out

        A timer is launch to check for de-congestion of any class."
    ::= { brsNotificationsPrefix 6 }

brsNotification7 NOTIFICATION-TYPE
    OBJECTS { 
              brs7_interface 
            }
    STATUS current
    DESCRIPTION
        "Notification of Event BRS.7

        Message: 'time-out interface $1'

        Parameters list:
              $1: brs7_interface

        A timer has expired."
    ::= { brsNotificationsPrefix 7 }

brsNotification8 NOTIFICATION-TYPE
    OBJECTS { 
              brs8_source_IP, 
              brs8_destination_IP,
              brs8_class,
              brs8_new_dscp_value 
            }
    STATUS current
    DESCRIPTION
        "Notification of Event BRS.8

        Message: 'Packet from $1 to $2 class $3 tagged with $4'

        Parameters list:
              $1: brs8_source_IP
              $2: brs8_destination_IP
              $3: brs8_class
              $4: brs8_new_dscp_value

        A packet has been tagged with a new dscp value."
    ::= { brsNotificationsPrefix 8 }

brsNotification9 NOTIFICATION-TYPE
    OBJECTS { 
              brs9_source_IP, 
              brs9_destination_IP,
              brs9_class,
              brs9_new_cos_value 
            }
    STATUS current
    DESCRIPTION
        "Notification of Event BRS.9

        Message: 'Packet from $1 to $2 class $3 cos tagged with $4'

        Parameters list:
              $1: brs9_source_IP
              $2: brs9_destination_IP
              $3: brs9_class
              $4: brs9_new_cos_value

        A packet has been tagged with a new cos value."
    ::= { brsNotificationsPrefix 9 }

brsNotification10 NOTIFICATION-TYPE
    OBJECTS { 
              brs10_source_IP, 
              brs10_destination_IP,
              brs10_class 
            }
    STATUS current
    DESCRIPTION
        "Notification of Event BRS.10

        Message: 'Packet from $1 to $2 class $3 atm clp set'

        Parameters list:
              $1: brs10_source_IP
              $2: brs10_destination_IP
              $3: brs10_class

        A packet has been tagged with ATM CLP."
    ::= { brsNotificationsPrefix 10 }

brsNotification11 NOTIFICATION-TYPE
    OBJECTS { 
              brs11_source_IP, 
              brs11_destination_IP,
              brs11_class,
              brs11_new_dscp_value 
            }
    STATUS current
    DESCRIPTION
        "Notification of Event BRS.11

        Message: 'Preclassified packet from $1 to $2 class $3 tagged with $4'

        Parameters list:
              $1: brs11_source_IP
              $2: brs11_destination_IP
              $3: brs11_class
              $4: brs11_new_dscp_value

        A preclassified packet has been tagged with a new dscp value."
    ::= { brsNotificationsPrefix 11 }

brsNotification12 NOTIFICATION-TYPE
    OBJECTS { 
              brs12_source_IP, 
              brs12_destination_IP,
              brs12_class,
              brs12_latency_priority 
            }
    STATUS current
    DESCRIPTION
        "Notification of Event BRS.12

        Message: 'Packet from $1 to $2 class $3 ptm $4 set'

        Parameters list:
              $1: brs12_source_IP
              $2: brs12_destination_IP
              $3: brs12_class
              $4: brs12_latency_priority

        A packet has been tagged with PTM low/high latency or low/high priority transmission preferred."
    ::= { brsNotificationsPrefix 12 }

brsNotification13 NOTIFICATION-TYPE
    OBJECTS { 
              brs13_levindid, 
              brs13_class,
              brs13_operation,
              brs13_value 
            }
    STATUS current
    DESCRIPTION
        "Notification of Event BRS.13

        Message: 'Level-indicator id $1 associated to class $2 has been updated $3 $4'

        Parameters list:
              $1: brs13_levindid
              $2: brs13_class
              $3: brs13_operation
              $4: brs13_value

        A level-indicator has been updated because a rate has been exceeded in a class"
    ::= { brsNotificationsPrefix 13 }

brsNotification14 NOTIFICATION-TYPE
    OBJECTS { 
              brs14_rate, 
              brs14_class,
              brs14_interface 
            }
    STATUS current
    DESCRIPTION
        "Notification of Event BRS.14

        Message: 'new rate limit $1 kbps for class $2 in interface $3'

        Parameters list:
              $1: brs14_rate
              $2: brs14_class
              $3: brs14_interface

        A rate limit configured as percentage of available bandwidth of a interface
        has been recalculated for a traffic class."
    ::= { brsNotificationsPrefix 14 }

brsNotification15 NOTIFICATION-TYPE
    OBJECTS { 
              brs15_rate, 
              brs15_interface 
            }
    STATUS current
    DESCRIPTION
        "Notification of Event BRS.15

        Message: 'new global rate limit $1 kbps for interface $2'

        Parameters list:
              $1: brs15_rate
              $2: brs15_interface

        A rate limit configured as percentage of available bandwidth of a interface
        has been recalculated."
    ::= { brsNotificationsPrefix 15 }

brsNotification16 NOTIFICATION-TYPE
    OBJECTS { 
              brs16_msg_prot_type, 
              brs16_class,
              brs16_queue_length,
              brs16_interface 
            }
    STATUS current
    DESCRIPTION
        "Notification of Event BRS.16

        Message: 'discarded packet of protocol $1 in class $2 with queue length $3 because of overflow on interface $4'

        Parameters list:
              $1: brs16_msg_prot_type
              $2: brs16_class
              $3: brs16_queue_length
              $4: brs16_interface

        Notifies on packet discarded because of class queue overflow."
    ::= { brsNotificationsPrefix 16 }

brsNotification17 NOTIFICATION-TYPE
    OBJECTS { 
              brs17_technology, 
              brs17_new_state,
              brs17_class,
              brs17_interface 
            }
    STATUS current
    DESCRIPTION
        "Notification of Event BRS.17

        Message: 'cellualr technology $1 $2 rate limit for class $3 on interface $4'

        Parameters list:
              $1: brs17_technology
              $2: brs17_new_state
              $3: brs17_class
              $4: brs17_interface

        A rate limit has been enabled or disabled for a class by a cellular link advisor"
    ::= { brsNotificationsPrefix 17 }

brsNotification18 NOTIFICATION-TYPE
    OBJECTS { 
              brs18_technology, 
              brs18_new_state,
              brs18_interface 
            }
    STATUS current
    DESCRIPTION
        "Notification of Event BRS.18

        Message: 'cellular technology $1 $2 global rate limit on interface $3'

        Parameters list:
              $1: brs18_technology
              $2: brs18_new_state
              $3: brs18_interface

        Global rate limit has been enabled or disabled by a cellular link advisor"
    ::= { brsNotificationsPrefix 18 }

brsNotification19 NOTIFICATION-TYPE
    OBJECTS { 
              brs19_register_action, 
              brs19_interface 
            }
    STATUS current
    DESCRIPTION
        "Notification of Event BRS.19

        Message: 'cellular advisor upcall not $1 on base interface $2'

        Parameters list:
              $1: brs19_register_action
              $2: brs19_interface

        Error has occurred when registering or unregistering a cellular advisor upcall"
    ::= { brsNotificationsPrefix 19 }


END
