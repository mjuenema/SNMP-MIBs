-- file automatically created


TELDAT-TRAP-LDAP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ldapTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the LDAP event subsystem."
    REVISION "201401200930Z"
    DESCRIPTION "Initial implementation"
        ::= { telEventTraps 146 }


ldapEventsGroup	OBJECT IDENTIFIER	::= { ldapTrapsMIB 1 }

ldapNotifications	OBJECT IDENTIFIER	::= { ldapTrapsMIB 2 }
ldapNotificationsPrefix	OBJECT IDENTIFIER	::= { ldapNotifications 0 }

ldapEventObjects1 OBJECT-IDENTITY
    STATUS current
    DESCRIPTION
        "Event LDAP.1
        Succesfull Bind Operation. A requested bind operation finished
        with a correct connection establishment."
    ::= { ldapEventsGroup 1 }

ldap1_ldap_sequence OBJECT-TYPE
    SYNTAX Integer32
    MAX-ACCESS accessible-for-notify
    STATUS current
    DESCRIPTION
        "Parameter 'ldap_sequence' in event LDAP.1"
    ::= { ldapEventObjects1 1 }

ldap1_ip_source OBJECT-TYPE
    SYNTAX DisplayString
    MAX-ACCESS accessible-for-notify
    STATUS current
    DESCRIPTION
        "Parameter 'ip_source' in event LDAP.1"
    ::= { ldapEventObjects1 2 }

ldap1_ip_destination OBJECT-TYPE
    SYNTAX DisplayString
    MAX-ACCESS accessible-for-notify
    STATUS current
    DESCRIPTION
        "Parameter 'ip_destination' in event LDAP.1"
    ::= { ldapEventObjects1 3 }

ldapEventObjects2 OBJECT-IDENTITY
    STATUS current
    DESCRIPTION
        "Event LDAP.2
        Unsuccesfull bind operation between a source an a destination returned
        no room available. Bind was right but when trying to send connection
        information the router tell us there is no space left to send it."
    ::= { ldapEventsGroup 2 }

ldap2_ldap_sequence OBJECT-TYPE
    SYNTAX Integer32
    MAX-ACCESS accessible-for-notify
    STATUS current
    DESCRIPTION
        "Parameter 'ldap_sequence' in event LDAP.2"
    ::= { ldapEventObjects2 1 }

ldap2_ip_source OBJECT-TYPE
    SYNTAX DisplayString
    MAX-ACCESS accessible-for-notify
    STATUS current
    DESCRIPTION
        "Parameter 'ip_source' in event LDAP.2"
    ::= { ldapEventObjects2 2 }

ldap2_ip_destination OBJECT-TYPE
    SYNTAX DisplayString
    MAX-ACCESS accessible-for-notify
    STATUS current
    DESCRIPTION
        "Parameter 'ip_destination' in event LDAP.2"
    ::= { ldapEventObjects2 3 }

ldapEventObjects3 OBJECT-IDENTITY
    STATUS current
    DESCRIPTION
        "Event LDAP.3
        Unsuccesfull bind operation between a source an a destination returned
        timeout."
    ::= { ldapEventsGroup 3 }

ldap3_ldap_sequence OBJECT-TYPE
    SYNTAX Integer32
    MAX-ACCESS accessible-for-notify
    STATUS current
    DESCRIPTION
        "Parameter 'ldap_sequence' in event LDAP.3"
    ::= { ldapEventObjects3 1 }

ldap3_ip_source OBJECT-TYPE
    SYNTAX DisplayString
    MAX-ACCESS accessible-for-notify
    STATUS current
    DESCRIPTION
        "Parameter 'ip_source' in event LDAP.3"
    ::= { ldapEventObjects3 2 }

ldap3_ip_destination OBJECT-TYPE
    SYNTAX DisplayString
    MAX-ACCESS accessible-for-notify
    STATUS current
    DESCRIPTION
        "Parameter 'ip_destination' in event LDAP.3"
    ::= { ldapEventObjects3 3 }

ldapEventObjects4 OBJECT-IDENTITY
    STATUS current
    DESCRIPTION
        "Event LDAP.4
        An operation was requested by an LDAP client and LDAP Server
        returned OK."
    ::= { ldapEventsGroup 4 }

ldap4_ldap_sequence OBJECT-TYPE
    SYNTAX Integer32
    MAX-ACCESS accessible-for-notify
    STATUS current
    DESCRIPTION
        "Parameter 'ldap_sequence' in event LDAP.4"
    ::= { ldapEventObjects4 1 }

ldap4_operation OBJECT-TYPE
    SYNTAX DisplayString
    MAX-ACCESS accessible-for-notify
    STATUS current
    DESCRIPTION
        "Parameter 'operation' in event LDAP.4"
    ::= { ldapEventObjects4 2 }

ldap4_ip_source OBJECT-TYPE
    SYNTAX DisplayString
    MAX-ACCESS accessible-for-notify
    STATUS current
    DESCRIPTION
        "Parameter 'ip_source' in event LDAP.4"
    ::= { ldapEventObjects4 3 }

ldap4_ip_destination OBJECT-TYPE
    SYNTAX DisplayString
    MAX-ACCESS accessible-for-notify
    STATUS current
    DESCRIPTION
        "Parameter 'ip_destination' in event LDAP.4"
    ::= { ldapEventObjects4 4 }

ldapEventObjects5 OBJECT-IDENTITY
    STATUS current
    DESCRIPTION
        "Event LDAP.5
        An operation was requested by an LDAP client and LDAP Server returned
        any value meaning error."
    ::= { ldapEventsGroup 5 }

ldap5_ldap_sequence OBJECT-TYPE
    SYNTAX Integer32
    MAX-ACCESS accessible-for-notify
    STATUS current
    DESCRIPTION
        "Parameter 'ldap_sequence' in event LDAP.5"
    ::= { ldapEventObjects5 1 }

ldap5_operation OBJECT-TYPE
    SYNTAX DisplayString
    MAX-ACCESS accessible-for-notify
    STATUS current
    DESCRIPTION
        "Parameter 'operation' in event LDAP.5"
    ::= { ldapEventObjects5 2 }

ldap5_ip_source OBJECT-TYPE
    SYNTAX DisplayString
    MAX-ACCESS accessible-for-notify
    STATUS current
    DESCRIPTION
        "Parameter 'ip_source' in event LDAP.5"
    ::= { ldapEventObjects5 3 }

ldap5_ip_destination OBJECT-TYPE
    SYNTAX DisplayString
    MAX-ACCESS accessible-for-notify
    STATUS current
    DESCRIPTION
        "Parameter 'ip_destination' in event LDAP.5"
    ::= { ldapEventObjects5 4 }

ldap5_result_desc OBJECT-TYPE
    SYNTAX DisplayString
    MAX-ACCESS accessible-for-notify
    STATUS current
    DESCRIPTION
        "Parameter 'result_desc' in event LDAP.5"
    ::= { ldapEventObjects5 5 }

ldap5_result_code OBJECT-TYPE
    SYNTAX Integer32
    MAX-ACCESS accessible-for-notify
    STATUS current
    DESCRIPTION
        "Parameter 'result_code' in event LDAP.5"
    ::= { ldapEventObjects5 6 }

ldap5_dn_affected OBJECT-TYPE
    SYNTAX DisplayString
    MAX-ACCESS accessible-for-notify
    STATUS current
    DESCRIPTION
        "Parameter 'dn_affected' in event LDAP.5"
    ::= { ldapEventObjects5 7 }

ldap5_error_message OBJECT-TYPE
    SYNTAX DisplayString
    MAX-ACCESS accessible-for-notify
    STATUS current
    DESCRIPTION
        "Parameter 'error_message' in event LDAP.5"
    ::= { ldapEventObjects5 8 }

ldapEventObjects6 OBJECT-IDENTITY
    STATUS current
    DESCRIPTION
        "Event LDAP.6
        All operations are composed by a set of sub-operations. The flow of
        this sub-operations is followed through a state machine. In this case
        a sub-operation appears when other was expected."
    ::= { ldapEventsGroup 6 }

ldap6_ldap_sequence OBJECT-TYPE
    SYNTAX Integer32
    MAX-ACCESS accessible-for-notify
    STATUS current
    DESCRIPTION
        "Parameter 'ldap_sequence' in event LDAP.6"
    ::= { ldapEventObjects6 1 }

ldap6_actual_state OBJECT-TYPE
    SYNTAX DisplayString
    MAX-ACCESS accessible-for-notify
    STATUS current
    DESCRIPTION
        "Parameter 'actual_state' in event LDAP.6"
    ::= { ldapEventObjects6 2 }

ldap6_expected_state OBJECT-TYPE
    SYNTAX DisplayString
    MAX-ACCESS accessible-for-notify
    STATUS current
    DESCRIPTION
        "Parameter 'expected_state' in event LDAP.6"
    ::= { ldapEventObjects6 3 }

ldapEventObjects7 OBJECT-IDENTITY
    STATUS current
    DESCRIPTION
        "Event LDAP.7
        Unsuccesfull unbind operation between a source an a destination
        returned timeout."
    ::= { ldapEventsGroup 7 }

ldap7_ldap_sequence OBJECT-TYPE
    SYNTAX Integer32
    MAX-ACCESS accessible-for-notify
    STATUS current
    DESCRIPTION
        "Parameter 'ldap_sequence' in event LDAP.7"
    ::= { ldapEventObjects7 1 }

ldap7_ip_source OBJECT-TYPE
    SYNTAX DisplayString
    MAX-ACCESS accessible-for-notify
    STATUS current
    DESCRIPTION
        "Parameter 'ip_source' in event LDAP.7"
    ::= { ldapEventObjects7 2 }

ldap7_ip_destination OBJECT-TYPE
    SYNTAX DisplayString
    MAX-ACCESS accessible-for-notify
    STATUS current
    DESCRIPTION
        "Parameter 'ip_destination' in event LDAP.7"
    ::= { ldapEventObjects7 3 }

ldapEventObjects8 OBJECT-IDENTITY
    STATUS current
    DESCRIPTION
        "Event LDAP.8
        An error occurred when allocating memory for a command buffer."
    ::= { ldapEventsGroup 8 }

ldap8_ldap_sequence OBJECT-TYPE
    SYNTAX Integer32
    MAX-ACCESS accessible-for-notify
    STATUS current
    DESCRIPTION
        "Parameter 'ldap_sequence' in event LDAP.8"
    ::= { ldapEventObjects8 1 }

ldap8_command OBJECT-TYPE
    SYNTAX DisplayString
    MAX-ACCESS accessible-for-notify
    STATUS current
    DESCRIPTION
        "Parameter 'command' in event LDAP.8"
    ::= { ldapEventObjects8 2 }

ldapEventObjects9 OBJECT-IDENTITY
    STATUS current
    DESCRIPTION
        "Event LDAP.9
        An LDAP Timeout occurred while performing request operation between
        client and server."
    ::= { ldapEventsGroup 9 }

ldap9_ldap_sequence OBJECT-TYPE
    SYNTAX Integer32
    MAX-ACCESS accessible-for-notify
    STATUS current
    DESCRIPTION
        "Parameter 'ldap_sequence' in event LDAP.9"
    ::= { ldapEventObjects9 1 }

ldap9_ip_source OBJECT-TYPE
    SYNTAX DisplayString
    MAX-ACCESS accessible-for-notify
    STATUS current
    DESCRIPTION
        "Parameter 'ip_source' in event LDAP.9"
    ::= { ldapEventObjects9 2 }

ldap9_ip_destination OBJECT-TYPE
    SYNTAX DisplayString
    MAX-ACCESS accessible-for-notify
    STATUS current
    DESCRIPTION
        "Parameter 'ip_destination' in event LDAP.9"
    ::= { ldapEventObjects9 3 }

ldapEventObjects10 OBJECT-IDENTITY
    STATUS current
    DESCRIPTION
        "Event LDAP.10
        After a request operation an unexpected frame is received."
    ::= { ldapEventsGroup 10 }

ldap10_ldap_sequence OBJECT-TYPE
    SYNTAX Integer32
    MAX-ACCESS accessible-for-notify
    STATUS current
    DESCRIPTION
        "Parameter 'ldap_sequence' in event LDAP.10"
    ::= { ldapEventObjects10 1 }

ldap10_operation OBJECT-TYPE
    SYNTAX DisplayString
    MAX-ACCESS accessible-for-notify
    STATUS current
    DESCRIPTION
        "Parameter 'operation' in event LDAP.10"
    ::= { ldapEventObjects10 2 }

ldap10_ip_source OBJECT-TYPE
    SYNTAX DisplayString
    MAX-ACCESS accessible-for-notify
    STATUS current
    DESCRIPTION
        "Parameter 'ip_source' in event LDAP.10"
    ::= { ldapEventObjects10 3 }

ldap10_ip_destination OBJECT-TYPE
    SYNTAX DisplayString
    MAX-ACCESS accessible-for-notify
    STATUS current
    DESCRIPTION
        "Parameter 'ip_destination' in event LDAP.10"
    ::= { ldapEventObjects10 4 }

ldap10_frame_data OBJECT-TYPE
    SYNTAX DisplayString
    MAX-ACCESS accessible-for-notify
    STATUS current
    DESCRIPTION
        "Parameter 'frame_data' in event LDAP.10"
    ::= { ldapEventObjects10 5 }

ldapEventObjects11 OBJECT-IDENTITY
    STATUS current
    DESCRIPTION
        "Event LDAP.11
        Shows the evolution on the LDAP TCP STATE MACHINE."
    ::= { ldapEventsGroup 11 }

ldap11_origin OBJECT-TYPE
    SYNTAX Integer32
    MAX-ACCESS accessible-for-notify
    STATUS current
    DESCRIPTION
        "Parameter 'origin' in event LDAP.11"
    ::= { ldapEventObjects11 1 }

ldap11_destination OBJECT-TYPE
    SYNTAX Integer32
    MAX-ACCESS accessible-for-notify
    STATUS current
    DESCRIPTION
        "Parameter 'destination' in event LDAP.11"
    ::= { ldapEventObjects11 2 }

ldapEventObjects12 OBJECT-IDENTITY
    STATUS current
    DESCRIPTION
        "Event LDAP.12
        Shows the bytes sent to LDAP Server."
    ::= { ldapEventsGroup 12 }

ldap12_bytes OBJECT-TYPE
    SYNTAX DisplayString
    MAX-ACCESS accessible-for-notify
    STATUS current
    DESCRIPTION
        "Parameter 'bytes' in event LDAP.12"
    ::= { ldapEventObjects12 1 }

ldapEventObjects13 OBJECT-IDENTITY
    STATUS current
    DESCRIPTION
        "Event LDAP.13
        Shows the bytes received from LDAP Server."
    ::= { ldapEventsGroup 13 }

ldap13_bytes OBJECT-TYPE
    SYNTAX DisplayString
    MAX-ACCESS accessible-for-notify
    STATUS current
    DESCRIPTION
        "Parameter 'bytes' in event LDAP.13"
    ::= { ldapEventObjects13 1 }

ldapEventObjects14 OBJECT-IDENTITY
    STATUS current
    DESCRIPTION
        "Event LDAP.14
        When a search operation is requested, LDAP Server sends results to
        the client. This results are stored into buffers. Users can establish
        how many buffers are to be filled. When they are reached
        operation is finished OK."
    ::= { ldapEventsGroup 14 }

ldap14_ldap_sequence OBJECT-TYPE
    SYNTAX Integer32
    MAX-ACCESS accessible-for-notify
    STATUS current
    DESCRIPTION
        "Parameter 'ldap_sequence' in event LDAP.14"
    ::= { ldapEventObjects14 1 }

ldap14_ip_source OBJECT-TYPE
    SYNTAX DisplayString
    MAX-ACCESS accessible-for-notify
    STATUS current
    DESCRIPTION
        "Parameter 'ip_source' in event LDAP.14"
    ::= { ldapEventObjects14 2 }

ldap14_ip_destination OBJECT-TYPE
    SYNTAX DisplayString
    MAX-ACCESS accessible-for-notify
    STATUS current
    DESCRIPTION
        "Parameter 'ip_destination' in event LDAP.14"
    ::= { ldapEventObjects14 3 }

ldapEventObjects15 OBJECT-IDENTITY
    STATUS current
    DESCRIPTION
        "Event LDAP.15
        When a search operation is requested, LDAP Server sends results to
        the client. This results are stored into buffers. The size of
        the reception buffer is determined by the window size. If Server sends
        data and client is no able to store it then this error occurs."
    ::= { ldapEventsGroup 15 }

ldap15_ldap_sequence OBJECT-TYPE
    SYNTAX Integer32
    MAX-ACCESS accessible-for-notify
    STATUS current
    DESCRIPTION
        "Parameter 'ldap_sequence' in event LDAP.15"
    ::= { ldapEventObjects15 1 }

ldap15_ip_source OBJECT-TYPE
    SYNTAX DisplayString
    MAX-ACCESS accessible-for-notify
    STATUS current
    DESCRIPTION
        "Parameter 'ip_source' in event LDAP.15"
    ::= { ldapEventObjects15 2 }

ldap15_ip_destination OBJECT-TYPE
    SYNTAX DisplayString
    MAX-ACCESS accessible-for-notify
    STATUS current
    DESCRIPTION
        "Parameter 'ip_destination' in event LDAP.15"
    ::= { ldapEventObjects15 3 }

ldap15_window_size OBJECT-TYPE
    SYNTAX Integer32
    MAX-ACCESS accessible-for-notify
    STATUS current
    DESCRIPTION
        "Parameter 'window_size' in event LDAP.15"
    ::= { ldapEventObjects15 4 }

ldap15_window_needed OBJECT-TYPE
    SYNTAX Integer32
    MAX-ACCESS accessible-for-notify
    STATUS current
    DESCRIPTION
        "Parameter 'window_needed' in event LDAP.15"
    ::= { ldapEventObjects15 5 }

ldapEventObjects16 OBJECT-IDENTITY
    STATUS current
    DESCRIPTION
        "Event LDAP.16
        For any reason the client sends an Abandon Request to the LDAP Server."
    ::= { ldapEventsGroup 16 }

ldap16_ldap_sequence OBJECT-TYPE
    SYNTAX Integer32
    MAX-ACCESS accessible-for-notify
    STATUS current
    DESCRIPTION
        "Parameter 'ldap_sequence' in event LDAP.16"
    ::= { ldapEventObjects16 1 }

ldap16_reason OBJECT-TYPE
    SYNTAX DisplayString
    MAX-ACCESS accessible-for-notify
    STATUS current
    DESCRIPTION
        "Parameter 'reason' in event LDAP.16"
    ::= { ldapEventObjects16 2 }


ldapNotification1 NOTIFICATION-TYPE
    OBJECTS { 
              ldap1_ldap_sequence, 
              ldap1_ip_source,
              ldap1_ip_destination 
            }
    STATUS current
    DESCRIPTION
        "Notification of Event LDAP.1

        Message: '($1) Connection established between $2 <--> $3. Bind Operation completed successfully.'

        Parameters list:
              $1: ldap1_ldap_sequence
              $2: ldap1_ip_source
              $3: ldap1_ip_destination

        Succesfull Bind Operation. A requested bind operation finished
        with a correct connection establishment."
    ::= { ldapNotificationsPrefix 1 }

ldapNotification2 NOTIFICATION-TYPE
    OBJECTS { 
              ldap2_ldap_sequence, 
              ldap2_ip_source,
              ldap2_ip_destination 
            }
    STATUS current
    DESCRIPTION
        "Notification of Event LDAP.2

        Message: '($1) There is no room in the router to send data between $2 <--> $3. Operation aborted.'

        Parameters list:
              $1: ldap2_ldap_sequence
              $2: ldap2_ip_source
              $3: ldap2_ip_destination

        Unsuccesfull bind operation between a source an a destination returned
        no room available. Bind was right but when trying to send connection
        information the router tell us there is no space left to send it."
    ::= { ldapNotificationsPrefix 2 }

ldapNotification3 NOTIFICATION-TYPE
    OBJECTS { 
              ldap3_ldap_sequence, 
              ldap3_ip_source,
              ldap3_ip_destination 
            }
    STATUS current
    DESCRIPTION
        "Notification of Event LDAP.3

        Message: '($1) Timeout expired for a bind operation between $2 as source IP and $3 as destiny IP'

        Parameters list:
              $1: ldap3_ldap_sequence
              $2: ldap3_ip_source
              $3: ldap3_ip_destination

        Unsuccesfull bind operation between a source an a destination returned
        timeout."
    ::= { ldapNotificationsPrefix 3 }

ldapNotification4 NOTIFICATION-TYPE
    OBJECTS { 
              ldap4_ldap_sequence, 
              ldap4_operation,
              ldap4_ip_source,
              ldap4_ip_destination 
            }
    STATUS current
    DESCRIPTION
        "Notification of Event LDAP.4

        Message: '($1) Data negotiation successfull. $2 sent $3 operation request $4 answered LDAPResult with OK message.'

        Parameters list:
              $1: ldap4_ldap_sequence
              $2: ldap4_operation
              $3: ldap4_ip_source
              $4: ldap4_ip_destination

        An operation was requested by an LDAP client and LDAP Server
        returned OK."
    ::= { ldapNotificationsPrefix 4 }

ldapNotification5 NOTIFICATION-TYPE
    OBJECTS { 
              ldap5_ldap_sequence, 
              ldap5_operation,
              ldap5_ip_source,
              ldap5_ip_destination,
              ldap5_result_desc,
              ldap5_result_code,
              ldap5_dn_affected,
              ldap5_error_message 
            }
    STATUS current
    DESCRIPTION
        "Notification of Event LDAP.5

        Message: '($1) Requested $2 operation was unsuccessfull. $3 requests operation to $4.LDAPResult: $5 ($6).DN        : $7.Message   : $8'

        Parameters list:
              $1: ldap5_ldap_sequence
              $2: ldap5_operation
              $3: ldap5_ip_source
              $4: ldap5_ip_destination
              $5: ldap5_result_desc
              $6: ldap5_result_code
              $7: ldap5_dn_affected
              $8: ldap5_error_message

        An operation was requested by an LDAP client and LDAP Server returned
        any value meaning error."
    ::= { ldapNotificationsPrefix 5 }

ldapNotification6 NOTIFICATION-TYPE
    OBJECTS { 
              ldap6_ldap_sequence, 
              ldap6_actual_state,
              ldap6_expected_state 
            }
    STATUS current
    DESCRIPTION
        "Notification of Event LDAP.6

        Message: '($1) Requested operation finished at this state ($2) when other ($3) was expected. State machine corrupted.'

        Parameters list:
              $1: ldap6_ldap_sequence
              $2: ldap6_actual_state
              $3: ldap6_expected_state

        All operations are composed by a set of sub-operations. The flow of
        this sub-operations is followed through a state machine. In this case
        a sub-operation appears when other was expected."
    ::= { ldapNotificationsPrefix 6 }

ldapNotification7 NOTIFICATION-TYPE
    OBJECTS { 
              ldap7_ldap_sequence, 
              ldap7_ip_source,
              ldap7_ip_destination 
            }
    STATUS current
    DESCRIPTION
        "Notification of Event LDAP.7

        Message: '($1) Disconnection for a bind operation between $2 as source IP and $3 as destiny IP'

        Parameters list:
              $1: ldap7_ldap_sequence
              $2: ldap7_ip_source
              $3: ldap7_ip_destination

        Unsuccesfull unbind operation between a source an a destination
        returned timeout."
    ::= { ldapNotificationsPrefix 7 }

ldapNotification8 NOTIFICATION-TYPE
    OBJECTS { 
              ldap8_ldap_sequence, 
              ldap8_command 
            }
    STATUS current
    DESCRIPTION
        "Notification of Event LDAP.8

        Message: '($1) Error allocating memory for the $2 operation in LDAP ObtenerComando'

        Parameters list:
              $1: ldap8_ldap_sequence
              $2: ldap8_command

        An error occurred when allocating memory for a command buffer."
    ::= { ldapNotificationsPrefix 8 }

ldapNotification9 NOTIFICATION-TYPE
    OBJECTS { 
              ldap9_ldap_sequence, 
              ldap9_ip_source,
              ldap9_ip_destination 
            }
    STATUS current
    DESCRIPTION
        "Notification of Event LDAP.9

        Message: '($1) LDAP Timeout occurred while performing request operation between $2 as client and $3 as server.'

        Parameters list:
              $1: ldap9_ldap_sequence
              $2: ldap9_ip_source
              $3: ldap9_ip_destination

        An LDAP Timeout occurred while performing request operation between
        client and server."
    ::= { ldapNotificationsPrefix 9 }

ldapNotification10 NOTIFICATION-TYPE
    OBJECTS { 
              ldap10_ldap_sequence, 
              ldap10_operation,
              ldap10_ip_source,
              ldap10_ip_destination,
              ldap10_frame_data 
            }
    STATUS current
    DESCRIPTION
        "Notification of Event LDAP.10

        Message: '($1) LDAP Error. Unexpected Frame from LDAP Server at operation $2 between $3 as client and $4 as server.Following data was received from LDAP Server:$5'

        Parameters list:
              $1: ldap10_ldap_sequence
              $2: ldap10_operation
              $3: ldap10_ip_source
              $4: ldap10_ip_destination
              $5: ldap10_frame_data

        After a request operation an unexpected frame is received."
    ::= { ldapNotificationsPrefix 10 }

ldapNotification11 NOTIFICATION-TYPE
    OBJECTS { 
              ldap11_origin, 
              ldap11_destination 
            }
    STATUS current
    DESCRIPTION
        "Notification of Event LDAP.11

        Message: 'FROM STATE $1 ---------> TO STATE $2'

        Parameters list:
              $1: ldap11_origin
              $2: ldap11_destination

        Shows the evolution on the LDAP TCP STATE MACHINE."
    ::= { ldapNotificationsPrefix 11 }

ldapNotification12 NOTIFICATION-TYPE
    OBJECTS { 
              ldap12_bytes 
            }
    STATUS current
    DESCRIPTION
        "Notification of Event LDAP.12

        Message: 'LDAP CLIENT:$1'

        Parameters list:
              $1: ldap12_bytes

        Shows the bytes sent to LDAP Server."
    ::= { ldapNotificationsPrefix 12 }

ldapNotification13 NOTIFICATION-TYPE
    OBJECTS { 
              ldap13_bytes 
            }
    STATUS current
    DESCRIPTION
        "Notification of Event LDAP.13

        Message: 'LDAP SERVER:$1'

        Parameters list:
              $1: ldap13_bytes

        Shows the bytes received from LDAP Server."
    ::= { ldapNotificationsPrefix 13 }

ldapNotification14 NOTIFICATION-TYPE
    OBJECTS { 
              ldap14_ldap_sequence, 
              ldap14_ip_source,
              ldap14_ip_destination 
            }
    STATUS current
    DESCRIPTION
        "Notification of Event LDAP.14

        Message: '($1) Search operation successfull. The operation between $2 and $3 finished OK afer the fullfillment of max results buffer.'

        Parameters list:
              $1: ldap14_ldap_sequence
              $2: ldap14_ip_source
              $3: ldap14_ip_destination

        When a search operation is requested, LDAP Server sends results to
        the client. This results are stored into buffers. Users can establish
        how many buffers are to be filled. When they are reached
        operation is finished OK."
    ::= { ldapNotificationsPrefix 14 }

ldapNotification15 NOTIFICATION-TYPE
    OBJECTS { 
              ldap15_ldap_sequence, 
              ldap15_ip_source,
              ldap15_ip_destination,
              ldap15_window_size,
              ldap15_window_needed 
            }
    STATUS current
    DESCRIPTION
        "Notification of Event LDAP.15

        Message: '($1) Search operation unsuccessfull. The operation between $2 and $3 finished with error because window size is set as $4 bytes and $5 bytes is required.'

        Parameters list:
              $1: ldap15_ldap_sequence
              $2: ldap15_ip_source
              $3: ldap15_ip_destination
              $4: ldap15_window_size
              $5: ldap15_window_needed

        When a search operation is requested, LDAP Server sends results to
        the client. This results are stored into buffers. The size of
        the reception buffer is determined by the window size. If Server sends
        data and client is no able to store it then this error occurs."
    ::= { ldapNotificationsPrefix 15 }

ldapNotification16 NOTIFICATION-TYPE
    OBJECTS { 
              ldap16_ldap_sequence, 
              ldap16_reason 
            }
    STATUS current
    DESCRIPTION
        "Notification of Event LDAP.16

        Message: '($1) LDAP Client sends an Abandon Request to LDAP Server. Reason is $2'

        Parameters list:
              $1: ldap16_ldap_sequence
              $2: ldap16_reason

        For any reason the client sends an Abandon Request to the LDAP Server."
    ::= { ldapNotificationsPrefix 16 }


END
