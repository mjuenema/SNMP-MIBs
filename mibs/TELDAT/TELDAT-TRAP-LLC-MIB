-- file automatically created


TELDAT-TRAP-LLC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


llcTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the LLC event subsystem."
    REVISION "201401200930Z"
    DESCRIPTION "Initial implementation"
        ::= { telEventTraps 103 }


llcEventsGroup	OBJECT IDENTIFIER	::= { llcTrapsMIB 1 }

llcNotifications	OBJECT IDENTIFIER	::= { llcTrapsMIB 2 }
llcNotificationsPrefix	OBJECT IDENTIFIER	::= { llcNotifications 0 }

llcEventObjects1 OBJECT-IDENTITY
    STATUS current
    DESCRIPTION
        "Event LLC.1
        LLC is sending a frame. Possible frame types are:
        SABME_C0 or SABME_C1 (Set Asynchronous Balanced Mode Extended),
        DM_R0 or DM_R1 (Disconnected Mode), DISC_C0 or DISC_C1 (Disconnect),
        RR_C0 or RR_C1 or RR_R0 or RR_R1 (Receiver Ready),
        RNR_C0 or RNR_C1 or RNR_R0 or RNR_R1 (Receiver Not Ready),
        REJ_C0 or REJ_C1 or REJ_R0 or REJ_R1 (Reject),
        UA_R0 or UA_R1 (Unnumbered Acknowledgement),
        FRMR_R0 or FRMR_R1 (Frame Reject), and
        I_C0 or I_C1 or I_R0 or I_R1 (Information Frame).
        The abbrevation suffixes are C0 (command, poll bit off),
        C1 (command, poll bit on), R0 (response, final bit off) and
        R1 (response, final bit on)."
    ::= { llcEventsGroup 1 }

llc1_frame_type OBJECT-TYPE
    SYNTAX DisplayString
    MAX-ACCESS accessible-for-notify
    STATUS current
    DESCRIPTION
        "Parameter 'frame_type' in event LLC.1"
    ::= { llcEventObjects1 1 }

llc1_src_mac OBJECT-TYPE
    SYNTAX DisplayString
    MAX-ACCESS accessible-for-notify
    STATUS current
    DESCRIPTION
        "Parameter 'src_mac' in event LLC.1"
    ::= { llcEventObjects1 2 }

llc1_dst_mac OBJECT-TYPE
    SYNTAX DisplayString
    MAX-ACCESS accessible-for-notify
    STATUS current
    DESCRIPTION
        "Parameter 'dst_mac' in event LLC.1"
    ::= { llcEventObjects1 3 }

llc1_rif OBJECT-TYPE
    SYNTAX DisplayString
    MAX-ACCESS accessible-for-notify
    STATUS current
    DESCRIPTION
        "Parameter 'rif' in event LLC.1"
    ::= { llcEventObjects1 4 }

llc1_src_sap OBJECT-TYPE
    SYNTAX Integer32
    MAX-ACCESS accessible-for-notify
    STATUS current
    DESCRIPTION
        "Parameter 'src_sap' in event LLC.1"
    ::= { llcEventObjects1 5 }

llc1_dst_sap OBJECT-TYPE
    SYNTAX Integer32
    MAX-ACCESS accessible-for-notify
    STATUS current
    DESCRIPTION
        "Parameter 'dst_sap' in event LLC.1"
    ::= { llcEventObjects1 6 }

llc1_interface OBJECT-TYPE
    SYNTAX DisplayString
    MAX-ACCESS accessible-for-notify
    STATUS current
    DESCRIPTION
        "Parameter 'interface' in event LLC.1"
    ::= { llcEventObjects1 7 }

llcEventObjects2 OBJECT-IDENTITY
    STATUS current
    DESCRIPTION
        "Event LLC.2
        An event occurred on an llc2 connection. The LLC2 FSM (Finite State
        Machine) has been called to process the event.
        The LLC2 connection is uniquely identified by the combination
        destination MAC address, source MAC address, destination sap and
        source sap on a particular interface.
        The possible events are:
        SET_ABME (user request to connect to remote),
        SET_ADM (user request to disconnect from remote),
        SEND_BTU (user request to send data),
        FLOW_REQ_ON (user request to turn off local busy condition),
        FLOW_REQ_OFF (user request to turn on local busy condition),
        T1_EXP (T1 timer expiration), T2_EXP (T2 timer expiration),
        Ti_EXP (Ti timer epiration), OS_I_C0 or OS_I_C1 or OS_I_R0 or OS_I_R1
        (Ns on I-frame is out of sequence), I_C0 or I_C1 or I_R0 or I_R1
        (valid I-frame received), RR_C0 or RR_C1 or RR_R0 or RR_R1
        (RR frame received), RNR_C0 or RNR_C1 or RNR_R0 or RNR_R1
        (RNR frame received), REJ_C0 or REJ_C1 or REJ_R0 or REJ_R1
        (REJ frame received), UA_R0 or UA_R1 (UA frame received),
        DISC_C0 or DISC_C1 (DISC frame received), DM_R0 or DM_R1
        (DM frame received), FRMR_R0 or FRMR_R1 (FRMR  frame received),
        BAD_FRAME_0 or BAD_FRAME_1 (received frame will generate FRMR),
        SABME_C0 or SABME_C1 (SABME frame received), and
        SEND_I_POLL (Sending I frame with Poll bit on).
        The abbrevation suffixes are C0 (command, poll bit off),
        C1 (command, poll bit on), R0 (response, final bit off) and
        R1 (response, final bit on)."
    ::= { llcEventsGroup 2 }

llc2_llc_event OBJECT-TYPE
    SYNTAX DisplayString
    MAX-ACCESS accessible-for-notify
    STATUS current
    DESCRIPTION
        "Parameter 'llc_event' in event LLC.2"
    ::= { llcEventObjects2 1 }

llc2_llc_state OBJECT-TYPE
    SYNTAX DisplayString
    MAX-ACCESS accessible-for-notify
    STATUS current
    DESCRIPTION
        "Parameter 'llc_state' in event LLC.2"
    ::= { llcEventObjects2 2 }

llc2_llc2_connection OBJECT-TYPE
    SYNTAX DisplayString
    MAX-ACCESS accessible-for-notify
    STATUS current
    DESCRIPTION
        "Parameter 'llc2_connection' in event LLC.2"
    ::= { llcEventObjects2 3 }

llc2_llc2_sap OBJECT-TYPE
    SYNTAX Integer32
    MAX-ACCESS accessible-for-notify
    STATUS current
    DESCRIPTION
        "Parameter 'llc2_sap' in event LLC.2"
    ::= { llcEventObjects2 4 }

llc2_interface OBJECT-TYPE
    SYNTAX DisplayString
    MAX-ACCESS accessible-for-notify
    STATUS current
    DESCRIPTION
        "Parameter 'interface' in event LLC.2"
    ::= { llcEventObjects2 5 }

llcEventObjects3 OBJECT-IDENTITY
    STATUS current
    DESCRIPTION
        "Event LLC.3
        There is LLC2 state change.
        The possible states are:
        DISCONNECTED (initial state),
        LINK_OPENING (link establishment in progress),
        DISCONNECTING (DISC sent, awaiting DM),
        FRMR_SENT (frmr sent),
        LINK_OPENED (normal state),
        LOCAL_BUSY (local is busy),
        REJECTION (remote sent an out of sequence frame),
        CHECKPOINTING (poll sent, awaiting response sending of data supended),
        CKPT_LB (combination state),
        CKPT_REJ (combination state),
        RESETTING (awaiting user response to reset),
        REMOTE_BUSY (remote is busy),
        LB_RB (combination state),
        REJ_LB (combination state),
        REJ_RB (combination state),
        CKPT_REJ_LB (combination state),
        CKPT_CLR (clearing from CKPT_LB state),
        CKPT_REJ_CLR (clearing from CKPT_REJ_LB state),
        REJ_LB_RB (combination state),
        FRMR_RECEIVED (received frmr).
        The abbreviations above are: CKPT=CHECKPOINTING, CLR=CLEARING,
        LB=LOCAL BUSY, RB=REMOTE BUSY, and REJ=REJECTION."
    ::= { llcEventsGroup 3 }

llc3_llc_old_state OBJECT-TYPE
    SYNTAX DisplayString
    MAX-ACCESS accessible-for-notify
    STATUS current
    DESCRIPTION
        "Parameter 'llc_old_state' in event LLC.3"
    ::= { llcEventObjects3 1 }

llc3_llc_new_state OBJECT-TYPE
    SYNTAX DisplayString
    MAX-ACCESS accessible-for-notify
    STATUS current
    DESCRIPTION
        "Parameter 'llc_new_state' in event LLC.3"
    ::= { llcEventObjects3 2 }

llc3_llc2_connection OBJECT-TYPE
    SYNTAX DisplayString
    MAX-ACCESS accessible-for-notify
    STATUS current
    DESCRIPTION
        "Parameter 'llc2_connection' in event LLC.3"
    ::= { llcEventObjects3 3 }

llc3_llc2_sap OBJECT-TYPE
    SYNTAX Integer32
    MAX-ACCESS accessible-for-notify
    STATUS current
    DESCRIPTION
        "Parameter 'llc2_sap' in event LLC.3"
    ::= { llcEventObjects3 4 }

llc3_interface OBJECT-TYPE
    SYNTAX DisplayString
    MAX-ACCESS accessible-for-notify
    STATUS current
    DESCRIPTION
        "Parameter 'interface' in event LLC.3"
    ::= { llcEventObjects3 5 }

llcEventObjects4 OBJECT-IDENTITY
    STATUS current
    DESCRIPTION
        "Event LLC.4
        LLC2 event upcall is occuring.
        Some of the arguments on the upcall are shown.
        User Cookie is meaningful to the router software running over
        the LLC subsystem.
        Event reason sometimes further specifies the event.
        The possible upcall events are:
        CONN_IND (cookie=session, reason=none),
        CONN_IND_PASS (cookie=sap, reason=none),
        CONN_CONFIRM (cookie=session, reason=none),
        DISC_IND (cookie=session, possible reasons: local term (disconnecting),
        remote term, conn refused, local term (disconnected)),
        RESET_IND (cookie=session, possible reasons: local reset,
        remote reset, frmr rcvd, frmr sent),
        RESET_CONF (cookie=session, reason=none),
        FLOW_IND (cookie=session, possible reasons: flow off, flow on), and
        DISC_CONFIRM (cookie=session, reason=none)."
    ::= { llcEventsGroup 4 }

llc4_user_event OBJECT-TYPE
    SYNTAX DisplayString
    MAX-ACCESS accessible-for-notify
    STATUS current
    DESCRIPTION
        "Parameter 'user_event' in event LLC.4"
    ::= { llcEventObjects4 1 }

llc4_user_value OBJECT-TYPE
    SYNTAX Integer32
    MAX-ACCESS accessible-for-notify
    STATUS current
    DESCRIPTION
        "Parameter 'user_value' in event LLC.4"
    ::= { llcEventObjects4 2 }

llc4_event_reason OBJECT-TYPE
    SYNTAX DisplayString
    MAX-ACCESS accessible-for-notify
    STATUS current
    DESCRIPTION
        "Parameter 'event_reason' in event LLC.4"
    ::= { llcEventObjects4 3 }

llc4_llc2_connection OBJECT-TYPE
    SYNTAX DisplayString
    MAX-ACCESS accessible-for-notify
    STATUS current
    DESCRIPTION
        "Parameter 'llc2_connection' in event LLC.4"
    ::= { llcEventObjects4 4 }

llc4_llc2_sap OBJECT-TYPE
    SYNTAX Integer32
    MAX-ACCESS accessible-for-notify
    STATUS current
    DESCRIPTION
        "Parameter 'llc2_sap' in event LLC.4"
    ::= { llcEventObjects4 5 }

llc4_interface OBJECT-TYPE
    SYNTAX DisplayString
    MAX-ACCESS accessible-for-notify
    STATUS current
    DESCRIPTION
        "Parameter 'interface' in event LLC.4"
    ::= { llcEventObjects4 6 }

llcEventObjects5 OBJECT-IDENTITY
    STATUS current
    DESCRIPTION
        "Event LLC.5
        A sap-releated LLC user-primitive was called.
        The possible SAP primitives are:
        OPEN_SAP,
        CLOSE_SAP,
        CLOSE_SAP_FORCED,
        MODIFY_SAP,
        OPEN_STATION, and
        UNITDATA."
    ::= { llcEventsGroup 5 }

llc5_user_primitive OBJECT-TYPE
    SYNTAX DisplayString
    MAX-ACCESS accessible-for-notify
    STATUS current
    DESCRIPTION
        "Parameter 'user_primitive' in event LLC.5"
    ::= { llcEventObjects5 1 }

llc5_SAP_value OBJECT-TYPE
    SYNTAX Integer32
    MAX-ACCESS accessible-for-notify
    STATUS current
    DESCRIPTION
        "Parameter 'SAP_value' in event LLC.5"
    ::= { llcEventObjects5 2 }

llc5_interface OBJECT-TYPE
    SYNTAX DisplayString
    MAX-ACCESS accessible-for-notify
    STATUS current
    DESCRIPTION
        "Parameter 'interface' in event LLC.5"
    ::= { llcEventObjects5 3 }

llcEventObjects6 OBJECT-IDENTITY
    STATUS current
    DESCRIPTION
        "Event LLC.6
        A llc2 connection non-data user-primitive was called.
        The possible primitives are:
        CLOSE_STATION,
        CLOSE_STATION_FORCED,
        CONNECT_REQUEST,
        CONNECT_RESPONSE,
        DISCONNECT_REQUEST,
        RESET_REQUEST,
        RESET_RESPONSE,
        FLOW_REQ."
    ::= { llcEventsGroup 6 }

llc6_user_primitive OBJECT-TYPE
    SYNTAX DisplayString
    MAX-ACCESS accessible-for-notify
    STATUS current
    DESCRIPTION
        "Parameter 'user_primitive' in event LLC.6"
    ::= { llcEventObjects6 1 }

llc6_llc2_connection OBJECT-TYPE
    SYNTAX DisplayString
    MAX-ACCESS accessible-for-notify
    STATUS current
    DESCRIPTION
        "Parameter 'llc2_connection' in event LLC.6"
    ::= { llcEventObjects6 2 }

llc6_llc2_sap OBJECT-TYPE
    SYNTAX Integer32
    MAX-ACCESS accessible-for-notify
    STATUS current
    DESCRIPTION
        "Parameter 'llc2_sap' in event LLC.6"
    ::= { llcEventObjects6 3 }

llc6_interface OBJECT-TYPE
    SYNTAX DisplayString
    MAX-ACCESS accessible-for-notify
    STATUS current
    DESCRIPTION
        "Parameter 'interface' in event LLC.6"
    ::= { llcEventObjects6 4 }

llcEventObjects7 OBJECT-IDENTITY
    STATUS current
    DESCRIPTION
        "Event LLC.7
        A DATA_REQUEST data primitive was called. DATA_REQUEST passes the data
        in buffer memory."
    ::= { llcEventsGroup 7 }

llc7_llc2_connection OBJECT-TYPE
    SYNTAX DisplayString
    MAX-ACCESS accessible-for-notify
    STATUS current
    DESCRIPTION
        "Parameter 'llc2_connection' in event LLC.7"
    ::= { llcEventObjects7 1 }

llc7_llc2_sap OBJECT-TYPE
    SYNTAX Integer32
    MAX-ACCESS accessible-for-notify
    STATUS current
    DESCRIPTION
        "Parameter 'llc2_sap' in event LLC.7"
    ::= { llcEventObjects7 2 }

llc7_interface OBJECT-TYPE
    SYNTAX DisplayString
    MAX-ACCESS accessible-for-notify
    STATUS current
    DESCRIPTION
        "Parameter 'interface' in event LLC.7"
    ::= { llcEventObjects7 3 }

llcEventObjects8 OBJECT-IDENTITY
    STATUS current
    DESCRIPTION
        "Event LLC.8
        A DATA_LOCAL data primitive was called. DATA_LOCAL passes the data
        in data memory."
    ::= { llcEventsGroup 8 }

llc8_llc2_connection OBJECT-TYPE
    SYNTAX DisplayString
    MAX-ACCESS accessible-for-notify
    STATUS current
    DESCRIPTION
        "Parameter 'llc2_connection' in event LLC.8"
    ::= { llcEventObjects8 1 }

llc8_llc2_sap OBJECT-TYPE
    SYNTAX Integer32
    MAX-ACCESS accessible-for-notify
    STATUS current
    DESCRIPTION
        "Parameter 'llc2_sap' in event LLC.8"
    ::= { llcEventObjects8 2 }

llc8_interface OBJECT-TYPE
    SYNTAX DisplayString
    MAX-ACCESS accessible-for-notify
    STATUS current
    DESCRIPTION
        "Parameter 'interface' in event LLC.8"
    ::= { llcEventObjects8 3 }

llcEventObjects9 OBJECT-IDENTITY
    STATUS current
    DESCRIPTION
        "Event LLC.9
        A UNITDATA llc1 data primitive was called."
    ::= { llcEventsGroup 9 }

llc9_SAP_value OBJECT-TYPE
    SYNTAX Integer32
    MAX-ACCESS accessible-for-notify
    STATUS current
    DESCRIPTION
        "Parameter 'SAP_value' in event LLC.9"
    ::= { llcEventObjects9 1 }

llc9_interface OBJECT-TYPE
    SYNTAX DisplayString
    MAX-ACCESS accessible-for-notify
    STATUS current
    DESCRIPTION
        "Parameter 'interface' in event LLC.9"
    ::= { llcEventObjects9 2 }

llcEventObjects10 OBJECT-IDENTITY
    STATUS current
    DESCRIPTION
        "Event LLC.10
        The oubound queue has grown grossly large. The llc2 connection is being
        automatically terminated."
    ::= { llcEventsGroup 10 }

llc10_llc2_connection OBJECT-TYPE
    SYNTAX DisplayString
    MAX-ACCESS accessible-for-notify
    STATUS current
    DESCRIPTION
        "Parameter 'llc2_connection' in event LLC.10"
    ::= { llcEventObjects10 1 }

llc10_llc2_sap OBJECT-TYPE
    SYNTAX Integer32
    MAX-ACCESS accessible-for-notify
    STATUS current
    DESCRIPTION
        "Parameter 'llc2_sap' in event LLC.10"
    ::= { llcEventObjects10 2 }

llc10_interface OBJECT-TYPE
    SYNTAX DisplayString
    MAX-ACCESS accessible-for-notify
    STATUS current
    DESCRIPTION
        "Parameter 'interface' in event LLC.10"
    ::= { llcEventObjects10 3 }

llcEventObjects11 OBJECT-IDENTITY
    STATUS current
    DESCRIPTION
        "Event LLC.11
        No buffer available to duplicate I-frame."
    ::= { llcEventsGroup 11 }

llc11_llc2_connection OBJECT-TYPE
    SYNTAX DisplayString
    MAX-ACCESS accessible-for-notify
    STATUS current
    DESCRIPTION
        "Parameter 'llc2_connection' in event LLC.11"
    ::= { llcEventObjects11 1 }

llc11_llc2_sap OBJECT-TYPE
    SYNTAX Integer32
    MAX-ACCESS accessible-for-notify
    STATUS current
    DESCRIPTION
        "Parameter 'llc2_sap' in event LLC.11"
    ::= { llcEventObjects11 2 }

llc11_interface OBJECT-TYPE
    SYNTAX DisplayString
    MAX-ACCESS accessible-for-notify
    STATUS current
    DESCRIPTION
        "Parameter 'interface' in event LLC.11"
    ::= { llcEventObjects11 3 }

llcEventObjects12 OBJECT-IDENTITY
    STATUS current
    DESCRIPTION
        "Event LLC.12
        No memory to duplicate I-frame."
    ::= { llcEventsGroup 12 }

llc12_llc2_connection OBJECT-TYPE
    SYNTAX DisplayString
    MAX-ACCESS accessible-for-notify
    STATUS current
    DESCRIPTION
        "Parameter 'llc2_connection' in event LLC.12"
    ::= { llcEventObjects12 1 }

llc12_llc2_sap OBJECT-TYPE
    SYNTAX Integer32
    MAX-ACCESS accessible-for-notify
    STATUS current
    DESCRIPTION
        "Parameter 'llc2_sap' in event LLC.12"
    ::= { llcEventObjects12 2 }

llc12_interface OBJECT-TYPE
    SYNTAX DisplayString
    MAX-ACCESS accessible-for-notify
    STATUS current
    DESCRIPTION
        "Parameter 'interface' in event LLC.12"
    ::= { llcEventObjects12 3 }

llcEventObjects13 OBJECT-IDENTITY
    STATUS current
    DESCRIPTION
        "Event LLC.13
        A buffer could not be obtained to to build an LLC Supervisory or
        Unnumbered frame. No loss of data integrity has occurred yet, but
        unless buffers for this purpose become available within a few seconds,
        the other end of the LLC2 connection will most likely terminate
        this LLC connection as part of the normal LLC2 protocol."
    ::= { llcEventsGroup 13 }

llc13_llc2_connection OBJECT-TYPE
    SYNTAX DisplayString
    MAX-ACCESS accessible-for-notify
    STATUS current
    DESCRIPTION
        "Parameter 'llc2_connection' in event LLC.13"
    ::= { llcEventObjects13 1 }

llc13_llc2_sap OBJECT-TYPE
    SYNTAX Integer32
    MAX-ACCESS accessible-for-notify
    STATUS current
    DESCRIPTION
        "Parameter 'llc2_sap' in event LLC.13"
    ::= { llcEventObjects13 2 }

llc13_interface OBJECT-TYPE
    SYNTAX DisplayString
    MAX-ACCESS accessible-for-notify
    STATUS current
    DESCRIPTION
        "Parameter 'interface' in event LLC.13"
    ::= { llcEventObjects13 3 }

llcEventObjects14 OBJECT-IDENTITY
    STATUS current
    DESCRIPTION
        "Event LLC.14
        The frame type the LLC is trying to build is invalid."
    ::= { llcEventsGroup 14 }

llc14_llc2_connection OBJECT-TYPE
    SYNTAX DisplayString
    MAX-ACCESS accessible-for-notify
    STATUS current
    DESCRIPTION
        "Parameter 'llc2_connection' in event LLC.14"
    ::= { llcEventObjects14 1 }

llc14_llc2_sap OBJECT-TYPE
    SYNTAX Integer32
    MAX-ACCESS accessible-for-notify
    STATUS current
    DESCRIPTION
        "Parameter 'llc2_sap' in event LLC.14"
    ::= { llcEventObjects14 2 }

llc14_interface OBJECT-TYPE
    SYNTAX DisplayString
    MAX-ACCESS accessible-for-notify
    STATUS current
    DESCRIPTION
        "Parameter 'interface' in event LLC.14"
    ::= { llcEventObjects14 3 }

llcEventObjects15 OBJECT-IDENTITY
    STATUS current
    DESCRIPTION
        "Event LLC.15
        The LLC2 Finite State Machine (FSM) was called with an event that was
        out of range."
    ::= { llcEventsGroup 15 }

llc15_event_code_number OBJECT-TYPE
    SYNTAX Integer32
    MAX-ACCESS accessible-for-notify
    STATUS current
    DESCRIPTION
        "Parameter 'event_code_number' in event LLC.15"
    ::= { llcEventObjects15 1 }

llcEventObjects16 OBJECT-IDENTITY
    STATUS current
    DESCRIPTION
        "Event LLC.16
        An OPEN SAP operation was tried on a network type that LLC does not
        support. Network types Token-Ring, Ethernet, and FDDI are supported."
    ::= { llcEventsGroup 16 }

llc16_network_type OBJECT-TYPE
    SYNTAX Integer32
    MAX-ACCESS accessible-for-notify
    STATUS current
    DESCRIPTION
        "Parameter 'network_type' in event LLC.16"
    ::= { llcEventObjects16 1 }

llc16_interface OBJECT-TYPE
    SYNTAX DisplayString
    MAX-ACCESS accessible-for-notify
    STATUS current
    DESCRIPTION
        "Parameter 'interface' in event LLC.16"
    ::= { llcEventObjects16 2 }

llcEventObjects17 OBJECT-IDENTITY
    STATUS current
    DESCRIPTION
        "Event LLC.17
        A OPEN SAP operation was tried on a sap that has already been opened."
    ::= { llcEventsGroup 17 }

llc17_SAP_value OBJECT-TYPE
    SYNTAX Integer32
    MAX-ACCESS accessible-for-notify
    STATUS current
    DESCRIPTION
        "Parameter 'SAP_value' in event LLC.17"
    ::= { llcEventObjects17 1 }

llc17_interface OBJECT-TYPE
    SYNTAX DisplayString
    MAX-ACCESS accessible-for-notify
    STATUS current
    DESCRIPTION
        "Parameter 'interface' in event LLC.17"
    ::= { llcEventObjects17 2 }

llcEventObjects18 OBJECT-IDENTITY
    STATUS current
    DESCRIPTION
        "Event LLC.18
        Unable to allocate memory for SAP control block."
    ::= { llcEventsGroup 18 }

llc18_interface OBJECT-TYPE
    SYNTAX DisplayString
    MAX-ACCESS accessible-for-notify
    STATUS current
    DESCRIPTION
        "Parameter 'interface' in event LLC.18"
    ::= { llcEventObjects18 1 }

llcEventObjects19 OBJECT-IDENTITY
    STATUS current
    DESCRIPTION
        "Event LLC.19
        Unable to allocate memory for station control block."
    ::= { llcEventsGroup 19 }

llc19_interface OBJECT-TYPE
    SYNTAX DisplayString
    MAX-ACCESS accessible-for-notify
    STATUS current
    DESCRIPTION
        "Parameter 'interface' in event LLC.19"
    ::= { llcEventObjects19 1 }

llcEventObjects20 OBJECT-IDENTITY
    STATUS current
    DESCRIPTION
        "Event LLC.20
        UI frame refused by the local application within the router."
    ::= { llcEventsGroup 20 }

llc20_llc2_connection OBJECT-TYPE
    SYNTAX DisplayString
    MAX-ACCESS accessible-for-notify
    STATUS current
    DESCRIPTION
        "Parameter 'llc2_connection' in event LLC.20"
    ::= { llcEventObjects20 1 }

llc20_llc2_sap OBJECT-TYPE
    SYNTAX Integer32
    MAX-ACCESS accessible-for-notify
    STATUS current
    DESCRIPTION
        "Parameter 'llc2_sap' in event LLC.20"
    ::= { llcEventObjects20 2 }

llc20_interface OBJECT-TYPE
    SYNTAX DisplayString
    MAX-ACCESS accessible-for-notify
    STATUS current
    DESCRIPTION
        "Parameter 'interface' in event LLC.20"
    ::= { llcEventObjects20 3 }

llcEventObjects21 OBJECT-IDENTITY
    STATUS current
    DESCRIPTION
        "Event LLC.21
        TEST frame refused by the local application within the router.
        The frame is passed on to the bridge code, etc."
    ::= { llcEventsGroup 21 }

llc21_llc2_connection OBJECT-TYPE
    SYNTAX DisplayString
    MAX-ACCESS accessible-for-notify
    STATUS current
    DESCRIPTION
        "Parameter 'llc2_connection' in event LLC.21"
    ::= { llcEventObjects21 1 }

llc21_llc2_sap OBJECT-TYPE
    SYNTAX Integer32
    MAX-ACCESS accessible-for-notify
    STATUS current
    DESCRIPTION
        "Parameter 'llc2_sap' in event LLC.21"
    ::= { llcEventObjects21 2 }

llc21_interface OBJECT-TYPE
    SYNTAX DisplayString
    MAX-ACCESS accessible-for-notify
    STATUS current
    DESCRIPTION
        "Parameter 'interface' in event LLC.21"
    ::= { llcEventObjects21 3 }

llcEventObjects22 OBJECT-IDENTITY
    STATUS current
    DESCRIPTION
        "Event LLC.22
        XID frame refused by the local application within the router.
        The frame is passed on to the bridge code, etc."
    ::= { llcEventsGroup 22 }

llc22_llc2_connection OBJECT-TYPE
    SYNTAX DisplayString
    MAX-ACCESS accessible-for-notify
    STATUS current
    DESCRIPTION
        "Parameter 'llc2_connection' in event LLC.22"
    ::= { llcEventObjects22 1 }

llc22_llc2_sap OBJECT-TYPE
    SYNTAX Integer32
    MAX-ACCESS accessible-for-notify
    STATUS current
    DESCRIPTION
        "Parameter 'llc2_sap' in event LLC.22"
    ::= { llcEventObjects22 2 }

llc22_interface OBJECT-TYPE
    SYNTAX DisplayString
    MAX-ACCESS accessible-for-notify
    STATUS current
    DESCRIPTION
        "Parameter 'interface' in event LLC.22"
    ::= { llcEventObjects22 3 }

llcEventObjects23 OBJECT-IDENTITY
    STATUS current
    DESCRIPTION
        "Event LLC.23
        LLC makes an upcall providing the LLC with a unitdata frame.
        The possible unitdata frames are:
        TEST_C0 or TEST_C1 or TEST_R0 or TEST_R1 (TEST frame),
        XID_C0 or XID_C1 or XID_R0 or XID_R1 (Exchange Identification frame),
        UI_C0 or UI_R0 (Unnumbered Information).
        The abbrevation suffixes are C0 (command, poll bit off),
        C1 (command, poll bit on), R0 (response, final bit off) and
        R1 (response, final bit on)."
    ::= { llcEventsGroup 23 }

llc23_frame_type OBJECT-TYPE
    SYNTAX DisplayString
    MAX-ACCESS accessible-for-notify
    STATUS current
    DESCRIPTION
        "Parameter 'frame_type' in event LLC.23"
    ::= { llcEventObjects23 1 }

llc23_src_mac OBJECT-TYPE
    SYNTAX DisplayString
    MAX-ACCESS accessible-for-notify
    STATUS current
    DESCRIPTION
        "Parameter 'src_mac' in event LLC.23"
    ::= { llcEventObjects23 2 }

llc23_dst_mac OBJECT-TYPE
    SYNTAX DisplayString
    MAX-ACCESS accessible-for-notify
    STATUS current
    DESCRIPTION
        "Parameter 'dst_mac' in event LLC.23"
    ::= { llcEventObjects23 3 }

llc23_rif OBJECT-TYPE
    SYNTAX DisplayString
    MAX-ACCESS accessible-for-notify
    STATUS current
    DESCRIPTION
        "Parameter 'rif' in event LLC.23"
    ::= { llcEventObjects23 4 }

llc23_src_sap OBJECT-TYPE
    SYNTAX Integer32
    MAX-ACCESS accessible-for-notify
    STATUS current
    DESCRIPTION
        "Parameter 'src_sap' in event LLC.23"
    ::= { llcEventObjects23 5 }

llc23_dst_sap OBJECT-TYPE
    SYNTAX Integer32
    MAX-ACCESS accessible-for-notify
    STATUS current
    DESCRIPTION
        "Parameter 'dst_sap' in event LLC.23"
    ::= { llcEventObjects23 6 }

llc23_interface OBJECT-TYPE
    SYNTAX DisplayString
    MAX-ACCESS accessible-for-notify
    STATUS current
    DESCRIPTION
        "Parameter 'interface' in event LLC.23"
    ::= { llcEventObjects23 7 }

llcEventObjects24 OBJECT-IDENTITY
    STATUS current
    DESCRIPTION
        "Event LLC.24
        The sending of an LLC2 related outbound frame failed.
        The reason_code is the internal error code for the failure."
    ::= { llcEventsGroup 24 }

llc24_reason_code OBJECT-TYPE
    SYNTAX Integer32
    MAX-ACCESS accessible-for-notify
    STATUS current
    DESCRIPTION
        "Parameter 'reason_code' in event LLC.24"
    ::= { llcEventObjects24 1 }

llc24_llc2_connection OBJECT-TYPE
    SYNTAX DisplayString
    MAX-ACCESS accessible-for-notify
    STATUS current
    DESCRIPTION
        "Parameter 'llc2_connection' in event LLC.24"
    ::= { llcEventObjects24 2 }

llc24_llc2_sap OBJECT-TYPE
    SYNTAX Integer32
    MAX-ACCESS accessible-for-notify
    STATUS current
    DESCRIPTION
        "Parameter 'llc2_sap' in event LLC.24"
    ::= { llcEventObjects24 3 }

llc24_interface_name OBJECT-TYPE
    SYNTAX DisplayString
    MAX-ACCESS accessible-for-notify
    STATUS current
    DESCRIPTION
        "Parameter 'interface_name' in event LLC.24"
    ::= { llcEventObjects24 4 }

llcEventObjects25 OBJECT-IDENTITY
    STATUS current
    DESCRIPTION
        "Event LLC.25
        The sending of the user's UNITDATA or an LLC-generated XID or TEST
        response outbound frame failed.
        The possible frame test are:
        TEST_C0 or TEST_C1 or TEST_R0 or TEST_R1 (TEST frame),
        XID_C0 or XID_C1 or XID_R0 or XID_R1 (Exchange Identification frame),
        UI_C0 or UI_R0 (Unnumbered Information frame) and
        unexpected (not one of the above types).
        The abbrevation suffixes are C0 (command, poll bit off),
        C1 (command, poll bit on),
        R0 (response, final bit off), and R1 (response, final bit on)."
    ::= { llcEventsGroup 25 }

llc25_frame_type OBJECT-TYPE
    SYNTAX DisplayString
    MAX-ACCESS accessible-for-notify
    STATUS current
    DESCRIPTION
        "Parameter 'frame_type' in event LLC.25"
    ::= { llcEventObjects25 1 }

llc25_reason_code OBJECT-TYPE
    SYNTAX Integer32
    MAX-ACCESS accessible-for-notify
    STATUS current
    DESCRIPTION
        "Parameter 'reason_code' in event LLC.25"
    ::= { llcEventObjects25 2 }

llc25_llc2_connection OBJECT-TYPE
    SYNTAX DisplayString
    MAX-ACCESS accessible-for-notify
    STATUS current
    DESCRIPTION
        "Parameter 'llc2_connection' in event LLC.25"
    ::= { llcEventObjects25 3 }

llc25_llc2_sap OBJECT-TYPE
    SYNTAX Integer32
    MAX-ACCESS accessible-for-notify
    STATUS current
    DESCRIPTION
        "Parameter 'llc2_sap' in event LLC.25"
    ::= { llcEventObjects25 4 }

llc25_interface OBJECT-TYPE
    SYNTAX DisplayString
    MAX-ACCESS accessible-for-notify
    STATUS current
    DESCRIPTION
        "Parameter 'interface' in event LLC.25"
    ::= { llcEventObjects25 5 }

llcEventObjects26 OBJECT-IDENTITY
    STATUS current
    DESCRIPTION
        "Event LLC.26
        Unable to allocate memory for an LLC_CONF_BLOCK at initialization time.
        LLC configuration defaults are used."
    ::= { llcEventsGroup 26 }

llc26_interface OBJECT-TYPE
    SYNTAX DisplayString
    MAX-ACCESS accessible-for-notify
    STATUS current
    DESCRIPTION
        "Parameter 'interface' in event LLC.26"
    ::= { llcEventObjects26 1 }

llcEventObjects27 OBJECT-IDENTITY
    STATUS current
    DESCRIPTION
        "Event LLC.27
        LLC Configuration record read for this network. This only occurs
        at initialization time. The values in the LLC configuration record
        are used as default value on the interface."
    ::= { llcEventsGroup 27 }

llc27_interface OBJECT-TYPE
    SYNTAX DisplayString
    MAX-ACCESS accessible-for-notify
    STATUS current
    DESCRIPTION
        "Parameter 'interface' in event LLC.27"
    ::= { llcEventObjects27 1 }

llcEventObjects28 OBJECT-IDENTITY
    STATUS current
    DESCRIPTION
        "Event LLC.28
        access_priority, on an interface that is not a token ring must be
        zero because it is not used."
    ::= { llcEventsGroup 28 }

llc28_access_priority OBJECT-TYPE
    SYNTAX Integer32
    MAX-ACCESS accessible-for-notify
    STATUS current
    DESCRIPTION
        "Parameter 'access_priority' in event LLC.28"
    ::= { llcEventObjects28 1 }

llc28_interface OBJECT-TYPE
    SYNTAX DisplayString
    MAX-ACCESS accessible-for-notify
    STATUS current
    DESCRIPTION
        "Parameter 'interface' in event LLC.28"
    ::= { llcEventObjects28 2 }

llcEventObjects29 OBJECT-IDENTITY
    STATUS current
    DESCRIPTION
        "Event LLC.29
        The access priority is greater than 7. A default of 0 is used."
    ::= { llcEventsGroup 29 }

llc29_access_priority OBJECT-TYPE
    SYNTAX Integer32
    MAX-ACCESS accessible-for-notify
    STATUS current
    DESCRIPTION
        "Parameter 'access_priority' in event LLC.29"
    ::= { llcEventObjects29 1 }

llc29_interface OBJECT-TYPE
    SYNTAX DisplayString
    MAX-ACCESS accessible-for-notify
    STATUS current
    DESCRIPTION
        "Parameter 'interface' in event LLC.29"
    ::= { llcEventObjects29 2 }

llcEventObjects30 OBJECT-IDENTITY
    STATUS current
    DESCRIPTION
        "Event LLC.30
        An LLC config record exists for an interface that does not have a
        LAN hardware type."
    ::= { llcEventsGroup 30 }

llc30_hardware_type OBJECT-TYPE
    SYNTAX Integer32
    MAX-ACCESS accessible-for-notify
    STATUS current
    DESCRIPTION
        "Parameter 'hardware_type' in event LLC.30"
    ::= { llcEventObjects30 1 }

llc30_interface OBJECT-TYPE
    SYNTAX DisplayString
    MAX-ACCESS accessible-for-notify
    STATUS current
    DESCRIPTION
        "Parameter 'interface' in event LLC.30"
    ::= { llcEventObjects30 2 }

llcEventObjects31 OBJECT-IDENTITY
    STATUS current
    DESCRIPTION
        "Event LLC.31
        An LLC config record exists for an interface that does not exist."
    ::= { llcEventsGroup 31 }

llc31_interface_number OBJECT-TYPE
    SYNTAX Integer32
    MAX-ACCESS accessible-for-notify
    STATUS current
    DESCRIPTION
        "Parameter 'interface_number' in event LLC.31"
    ::= { llcEventObjects31 1 }

llcEventObjects32 OBJECT-IDENTITY
    STATUS current
    DESCRIPTION
        "Event LLC.32
        LLC user is sending a frame, or LLC itself is sending a
        TEST or XID response frame.
        The possible frame types are:
        TEST_C0 or TEST_C1 or TEST_R0 or TEST_R1 (TEST frame),
        XID_C0 or XID_C1 or XID_R0 or XID_R1 (Exchange Identification frame),
        UI_C0 or UI_R0 (Unnumbered Information frame).
        The abbrevation suffixes are C0 (command, poll bit off),
        C1 (command, poll bit on), R0 (response, final bit off) and
        R1 (response, final bit on)."
    ::= { llcEventsGroup 32 }

llc32_frame_type OBJECT-TYPE
    SYNTAX DisplayString
    MAX-ACCESS accessible-for-notify
    STATUS current
    DESCRIPTION
        "Parameter 'frame_type' in event LLC.32"
    ::= { llcEventObjects32 1 }

llc32_src_mac OBJECT-TYPE
    SYNTAX DisplayString
    MAX-ACCESS accessible-for-notify
    STATUS current
    DESCRIPTION
        "Parameter 'src_mac' in event LLC.32"
    ::= { llcEventObjects32 2 }

llc32_dst_mac OBJECT-TYPE
    SYNTAX DisplayString
    MAX-ACCESS accessible-for-notify
    STATUS current
    DESCRIPTION
        "Parameter 'dst_mac' in event LLC.32"
    ::= { llcEventObjects32 3 }

llc32_rif OBJECT-TYPE
    SYNTAX DisplayString
    MAX-ACCESS accessible-for-notify
    STATUS current
    DESCRIPTION
        "Parameter 'rif' in event LLC.32"
    ::= { llcEventObjects32 4 }

llc32_src_sap OBJECT-TYPE
    SYNTAX Integer32
    MAX-ACCESS accessible-for-notify
    STATUS current
    DESCRIPTION
        "Parameter 'src_sap' in event LLC.32"
    ::= { llcEventObjects32 5 }

llc32_dst_sap OBJECT-TYPE
    SYNTAX Integer32
    MAX-ACCESS accessible-for-notify
    STATUS current
    DESCRIPTION
        "Parameter 'dst_sap' in event LLC.32"
    ::= { llcEventObjects32 6 }

llc32_interface OBJECT-TYPE
    SYNTAX DisplayString
    MAX-ACCESS accessible-for-notify
    STATUS current
    DESCRIPTION
        "Parameter 'interface' in event LLC.32"
    ::= { llcEventObjects32 7 }

llcEventObjects33 OBJECT-IDENTITY
    STATUS current
    DESCRIPTION
        "Event LLC.33
        LLC subsystem itself is responding to a TEST or XID frame.
        The possible frame types are:
        TEST_C0 or TEST_C1 (TEST frame), and
        XID_C0 or XID_C1 (Exchange Identification frame).
        The abbrevation suffixes are:
        C0=(command, poll  bit off) and
        C1=(command, poll  bit on)."
    ::= { llcEventsGroup 33 }

llc33_frame_type OBJECT-TYPE
    SYNTAX DisplayString
    MAX-ACCESS accessible-for-notify
    STATUS current
    DESCRIPTION
        "Parameter 'frame_type' in event LLC.33"
    ::= { llcEventObjects33 1 }

llc33_src_mac OBJECT-TYPE
    SYNTAX DisplayString
    MAX-ACCESS accessible-for-notify
    STATUS current
    DESCRIPTION
        "Parameter 'src_mac' in event LLC.33"
    ::= { llcEventObjects33 2 }

llc33_dst_mac OBJECT-TYPE
    SYNTAX DisplayString
    MAX-ACCESS accessible-for-notify
    STATUS current
    DESCRIPTION
        "Parameter 'dst_mac' in event LLC.33"
    ::= { llcEventObjects33 3 }

llc33_rif OBJECT-TYPE
    SYNTAX DisplayString
    MAX-ACCESS accessible-for-notify
    STATUS current
    DESCRIPTION
        "Parameter 'rif' in event LLC.33"
    ::= { llcEventObjects33 4 }

llc33_src_sap OBJECT-TYPE
    SYNTAX Integer32
    MAX-ACCESS accessible-for-notify
    STATUS current
    DESCRIPTION
        "Parameter 'src_sap' in event LLC.33"
    ::= { llcEventObjects33 5 }

llc33_dst_sap OBJECT-TYPE
    SYNTAX Integer32
    MAX-ACCESS accessible-for-notify
    STATUS current
    DESCRIPTION
        "Parameter 'dst_sap' in event LLC.33"
    ::= { llcEventObjects33 6 }

llc33_interface OBJECT-TYPE
    SYNTAX DisplayString
    MAX-ACCESS accessible-for-notify
    STATUS current
    DESCRIPTION
        "Parameter 'interface' in event LLC.33"
    ::= { llcEventObjects33 7 }


llcNotification1 NOTIFICATION-TYPE
    OBJECTS { 
              llc1_frame_type, 
              llc1_src_mac,
              llc1_dst_mac,
              llc1_rif,
              llc1_src_sap,
              llc1_dst_sap,
              llc1_interface 
            }
    STATUS current
    DESCRIPTION
        "Notification of Event LLC.1

        Message: 'Sent $1, $2->$3, $4 saps $5->$6, interface $7'

        Parameters list:
              $1: llc1_frame_type
              $2: llc1_src_mac
              $3: llc1_dst_mac
              $4: llc1_rif
              $5: llc1_src_sap
              $6: llc1_dst_sap
              $7: llc1_interface

        LLC is sending a frame. Possible frame types are:
        SABME_C0 or SABME_C1 (Set Asynchronous Balanced Mode Extended),
        DM_R0 or DM_R1 (Disconnected Mode), DISC_C0 or DISC_C1 (Disconnect),
        RR_C0 or RR_C1 or RR_R0 or RR_R1 (Receiver Ready),
        RNR_C0 or RNR_C1 or RNR_R0 or RNR_R1 (Receiver Not Ready),
        REJ_C0 or REJ_C1 or REJ_R0 or REJ_R1 (Reject),
        UA_R0 or UA_R1 (Unnumbered Acknowledgement),
        FRMR_R0 or FRMR_R1 (Frame Reject), and
        I_C0 or I_C1 or I_R0 or I_R1 (Information Frame).
        The abbrevation suffixes are C0 (command, poll bit off),
        C1 (command, poll bit on), R0 (response, final bit off) and
        R1 (response, final bit on)."
    ::= { llcNotificationsPrefix 1 }

llcNotification2 NOTIFICATION-TYPE
    OBJECTS { 
              llc2_llc_event, 
              llc2_llc_state,
              llc2_llc2_connection,
              llc2_llc2_connection,
              llc2_llc2_sap,
              llc2_llc2_sap,
              llc2_interface 
            }
    STATUS current
    DESCRIPTION
        "Notification of Event LLC.2

        Message: 'event=$1 in state=$2, $3->$4, saps $5->$6, interface $7'

        Parameters list:
              $1: llc2_llc_event
              $2: llc2_llc_state
              $3: llc2_llc2_connection
              $4: llc2_llc2_connection
              $5: llc2_llc2_sap
              $6: llc2_llc2_sap
              $7: llc2_interface

        An event occurred on an llc2 connection. The LLC2 FSM (Finite State
        Machine) has been called to process the event.
        The LLC2 connection is uniquely identified by the combination
        destination MAC address, source MAC address, destination sap and
        source sap on a particular interface.
        The possible events are:
        SET_ABME (user request to connect to remote),
        SET_ADM (user request to disconnect from remote),
        SEND_BTU (user request to send data),
        FLOW_REQ_ON (user request to turn off local busy condition),
        FLOW_REQ_OFF (user request to turn on local busy condition),
        T1_EXP (T1 timer expiration), T2_EXP (T2 timer expiration),
        Ti_EXP (Ti timer epiration), OS_I_C0 or OS_I_C1 or OS_I_R0 or OS_I_R1
        (Ns on I-frame is out of sequence), I_C0 or I_C1 or I_R0 or I_R1
        (valid I-frame received), RR_C0 or RR_C1 or RR_R0 or RR_R1
        (RR frame received), RNR_C0 or RNR_C1 or RNR_R0 or RNR_R1
        (RNR frame received), REJ_C0 or REJ_C1 or REJ_R0 or REJ_R1
        (REJ frame received), UA_R0 or UA_R1 (UA frame received),
        DISC_C0 or DISC_C1 (DISC frame received), DM_R0 or DM_R1
        (DM frame received), FRMR_R0 or FRMR_R1 (FRMR  frame received),
        BAD_FRAME_0 or BAD_FRAME_1 (received frame will generate FRMR),
        SABME_C0 or SABME_C1 (SABME frame received), and
        SEND_I_POLL (Sending I frame with Poll bit on).
        The abbrevation suffixes are C0 (command, poll bit off),
        C1 (command, poll bit on), R0 (response, final bit off) and
        R1 (response, final bit on)."
    ::= { llcNotificationsPrefix 2 }

llcNotification3 NOTIFICATION-TYPE
    OBJECTS { 
              llc3_llc_old_state, 
              llc3_llc_new_state,
              llc3_llc2_connection,
              llc3_llc2_connection,
              llc3_llc2_sap,
              llc3_llc2_sap,
              llc3_interface 
            }
    STATUS current
    DESCRIPTION
        "Notification of Event LLC.3

        Message: '$1 to $2, $3->$4, saps $5->$6, interface $7'

        Parameters list:
              $1: llc3_llc_old_state
              $2: llc3_llc_new_state
              $3: llc3_llc2_connection
              $4: llc3_llc2_connection
              $5: llc3_llc2_sap
              $6: llc3_llc2_sap
              $7: llc3_interface

        There is LLC2 state change.
        The possible states are:
        DISCONNECTED (initial state),
        LINK_OPENING (link establishment in progress),
        DISCONNECTING (DISC sent, awaiting DM),
        FRMR_SENT (frmr sent),
        LINK_OPENED (normal state),
        LOCAL_BUSY (local is busy),
        REJECTION (remote sent an out of sequence frame),
        CHECKPOINTING (poll sent, awaiting response sending of data supended),
        CKPT_LB (combination state),
        CKPT_REJ (combination state),
        RESETTING (awaiting user response to reset),
        REMOTE_BUSY (remote is busy),
        LB_RB (combination state),
        REJ_LB (combination state),
        REJ_RB (combination state),
        CKPT_REJ_LB (combination state),
        CKPT_CLR (clearing from CKPT_LB state),
        CKPT_REJ_CLR (clearing from CKPT_REJ_LB state),
        REJ_LB_RB (combination state),
        FRMR_RECEIVED (received frmr).
        The abbreviations above are: CKPT=CHECKPOINTING, CLR=CLEARING,
        LB=LOCAL BUSY, RB=REMOTE BUSY, and REJ=REJECTION."
    ::= { llcNotificationsPrefix 3 }

llcNotification4 NOTIFICATION-TYPE
    OBJECTS { 
              llc4_user_event, 
              llc4_user_value,
              llc4_event_reason,
              llc4_llc2_connection,
              llc4_llc2_connection,
              llc4_llc2_sap,
              llc4_llc2_sap,
              llc4_interface 
            }
    STATUS current
    DESCRIPTION
        "Notification of Event LLC.4

        Message: 'Upcall user event $1 args $2/$3 on $4->$5, saps $6->$7, interface $8'

        Parameters list:
              $1: llc4_user_event
              $2: llc4_user_value
              $3: llc4_event_reason
              $4: llc4_llc2_connection
              $5: llc4_llc2_connection
              $6: llc4_llc2_sap
              $7: llc4_llc2_sap
              $8: llc4_interface

        LLC2 event upcall is occuring.
        Some of the arguments on the upcall are shown.
        User Cookie is meaningful to the router software running over
        the LLC subsystem.
        Event reason sometimes further specifies the event.
        The possible upcall events are:
        CONN_IND (cookie=session, reason=none),
        CONN_IND_PASS (cookie=sap, reason=none),
        CONN_CONFIRM (cookie=session, reason=none),
        DISC_IND (cookie=session, possible reasons: local term (disconnecting),
        remote term, conn refused, local term (disconnected)),
        RESET_IND (cookie=session, possible reasons: local reset,
        remote reset, frmr rcvd, frmr sent),
        RESET_CONF (cookie=session, reason=none),
        FLOW_IND (cookie=session, possible reasons: flow off, flow on), and
        DISC_CONFIRM (cookie=session, reason=none)."
    ::= { llcNotificationsPrefix 4 }

llcNotification5 NOTIFICATION-TYPE
    OBJECTS { 
              llc5_user_primitive, 
              llc5_SAP_value,
              llc5_interface 
            }
    STATUS current
    DESCRIPTION
        "Notification of Event LLC.5

        Message: 'user primitive $1 sap $2 on interface $3'

        Parameters list:
              $1: llc5_user_primitive
              $2: llc5_SAP_value
              $3: llc5_interface

        A sap-releated LLC user-primitive was called.
        The possible SAP primitives are:
        OPEN_SAP,
        CLOSE_SAP,
        CLOSE_SAP_FORCED,
        MODIFY_SAP,
        OPEN_STATION, and
        UNITDATA."
    ::= { llcNotificationsPrefix 5 }

llcNotification6 NOTIFICATION-TYPE
    OBJECTS { 
              llc6_user_primitive, 
              llc6_llc2_connection,
              llc6_llc2_connection,
              llc6_llc2_sap,
              llc6_llc2_sap,
              llc6_interface 
            }
    STATUS current
    DESCRIPTION
        "Notification of Event LLC.6

        Message: 'primitive $1, $2->$3, saps $4->$5, interface $6'

        Parameters list:
              $1: llc6_user_primitive
              $2: llc6_llc2_connection
              $3: llc6_llc2_connection
              $4: llc6_llc2_sap
              $5: llc6_llc2_sap
              $6: llc6_interface

        A llc2 connection non-data user-primitive was called.
        The possible primitives are:
        CLOSE_STATION,
        CLOSE_STATION_FORCED,
        CONNECT_REQUEST,
        CONNECT_RESPONSE,
        DISCONNECT_REQUEST,
        RESET_REQUEST,
        RESET_RESPONSE,
        FLOW_REQ."
    ::= { llcNotificationsPrefix 6 }

llcNotification7 NOTIFICATION-TYPE
    OBJECTS { 
              llc7_llc2_connection, 
              llc7_llc2_connection,
              llc7_llc2_sap,
              llc7_llc2_sap,
              llc7_interface 
            }
    STATUS current
    DESCRIPTION
        "Notification of Event LLC.7

        Message: 'data primitive, $1->$2, saps $3->$4, interface $5'

        Parameters list:
              $1: llc7_llc2_connection
              $2: llc7_llc2_connection
              $3: llc7_llc2_sap
              $4: llc7_llc2_sap
              $5: llc7_interface

        A DATA_REQUEST data primitive was called. DATA_REQUEST passes the data
        in buffer memory."
    ::= { llcNotificationsPrefix 7 }

llcNotification8 NOTIFICATION-TYPE
    OBJECTS { 
              llc8_llc2_connection, 
              llc8_llc2_connection,
              llc8_llc2_sap,
              llc8_llc2_sap,
              llc8_interface 
            }
    STATUS current
    DESCRIPTION
        "Notification of Event LLC.8

        Message: 'data primitive, $1->$2, saps $3->$4, interface $5'

        Parameters list:
              $1: llc8_llc2_connection
              $2: llc8_llc2_connection
              $3: llc8_llc2_sap
              $4: llc8_llc2_sap
              $5: llc8_interface

        A DATA_LOCAL data primitive was called. DATA_LOCAL passes the data
        in data memory."
    ::= { llcNotificationsPrefix 8 }

llcNotification9 NOTIFICATION-TYPE
    OBJECTS { 
              llc9_SAP_value, 
              llc9_interface 
            }
    STATUS current
    DESCRIPTION
        "Notification of Event LLC.9

        Message: 'unitdata primitive, sap $1 interface $2'

        Parameters list:
              $1: llc9_SAP_value
              $2: llc9_interface

        A UNITDATA llc1 data primitive was called."
    ::= { llcNotificationsPrefix 9 }

llcNotification10 NOTIFICATION-TYPE
    OBJECTS { 
              llc10_llc2_connection, 
              llc10_llc2_connection,
              llc10_llc2_sap,
              llc10_llc2_sap,
              llc10_interface 
            }
    STATUS current
    DESCRIPTION
        "Notification of Event LLC.10

        Message: 'outbound queue too big, $1->$2, saps $3->$4, interface $5'

        Parameters list:
              $1: llc10_llc2_connection
              $2: llc10_llc2_connection
              $3: llc10_llc2_sap
              $4: llc10_llc2_sap
              $5: llc10_interface

        The oubound queue has grown grossly large. The llc2 connection is being
        automatically terminated."
    ::= { llcNotificationsPrefix 10 }

llcNotification11 NOTIFICATION-TYPE
    OBJECTS { 
              llc11_llc2_connection, 
              llc11_llc2_connection,
              llc11_llc2_sap,
              llc11_llc2_sap,
              llc11_interface 
            }
    STATUS current
    DESCRIPTION
        "Notification of Event LLC.11

        Message: 'No buffer available to duplicate I-frame, $1->$2, saps $3->$4, interface $5'

        Parameters list:
              $1: llc11_llc2_connection
              $2: llc11_llc2_connection
              $3: llc11_llc2_sap
              $4: llc11_llc2_sap
              $5: llc11_interface

        No buffer available to duplicate I-frame."
    ::= { llcNotificationsPrefix 11 }

llcNotification12 NOTIFICATION-TYPE
    OBJECTS { 
              llc12_llc2_connection, 
              llc12_llc2_connection,
              llc12_llc2_sap,
              llc12_llc2_sap,
              llc12_interface 
            }
    STATUS current
    DESCRIPTION
        "Notification of Event LLC.12

        Message: 'No memory available to duplicate I-frame, $1->$2, saps $3->$4, interface $5'

        Parameters list:
              $1: llc12_llc2_connection
              $2: llc12_llc2_connection
              $3: llc12_llc2_sap
              $4: llc12_llc2_sap
              $5: llc12_interface

        No memory to duplicate I-frame."
    ::= { llcNotificationsPrefix 12 }

llcNotification13 NOTIFICATION-TYPE
    OBJECTS { 
              llc13_llc2_connection, 
              llc13_llc2_connection,
              llc13_llc2_sap,
              llc13_llc2_sap,
              llc13_interface 
            }
    STATUS current
    DESCRIPTION
        "Notification of Event LLC.13

        Message: 'No buffer for LLC frame, $1->$2, saps $3->$4, interface $5'

        Parameters list:
              $1: llc13_llc2_connection
              $2: llc13_llc2_connection
              $3: llc13_llc2_sap
              $4: llc13_llc2_sap
              $5: llc13_interface

        A buffer could not be obtained to to build an LLC Supervisory or
        Unnumbered frame. No loss of data integrity has occurred yet, but
        unless buffers for this purpose become available within a few seconds,
        the other end of the LLC2 connection will most likely terminate
        this LLC connection as part of the normal LLC2 protocol."
    ::= { llcNotificationsPrefix 13 }

llcNotification14 NOTIFICATION-TYPE
    OBJECTS { 
              llc14_llc2_connection, 
              llc14_llc2_connection,
              llc14_llc2_sap,
              llc14_llc2_sap,
              llc14_interface 
            }
    STATUS current
    DESCRIPTION
        "Notification of Event LLC.14

        Message: 'frame type invalid, $1->$2, saps $3->$4, interface $5'

        Parameters list:
              $1: llc14_llc2_connection
              $2: llc14_llc2_connection
              $3: llc14_llc2_sap
              $4: llc14_llc2_sap
              $5: llc14_interface

        The frame type the LLC is trying to build is invalid."
    ::= { llcNotificationsPrefix 14 }

llcNotification15 NOTIFICATION-TYPE
    OBJECTS { 
              llc15_event_code_number 
            }
    STATUS current
    DESCRIPTION
        "Notification of Event LLC.15

        Message: 'Invalid LLC2 FSM event $1'

        Parameters list:
              $1: llc15_event_code_number

        The LLC2 Finite State Machine (FSM) was called with an event that was
        out of range."
    ::= { llcNotificationsPrefix 15 }

llcNotification16 NOTIFICATION-TYPE
    OBJECTS { 
              llc16_network_type, 
              llc16_interface 
            }
    STATUS current
    DESCRIPTION
        "Notification of Event LLC.16

        Message: 'invalid network type $1 on interface $2'

        Parameters list:
              $1: llc16_network_type
              $2: llc16_interface

        An OPEN SAP operation was tried on a network type that LLC does not
        support. Network types Token-Ring, Ethernet, and FDDI are supported."
    ::= { llcNotificationsPrefix 16 }

llcNotification17 NOTIFICATION-TYPE
    OBJECTS { 
              llc17_SAP_value, 
              llc17_interface 
            }
    STATUS current
    DESCRIPTION
        "Notification of Event LLC.17

        Message: 'duplicate sap $1 on interface $2'

        Parameters list:
              $1: llc17_SAP_value
              $2: llc17_interface

        A OPEN SAP operation was tried on a sap that has already been opened."
    ::= { llcNotificationsPrefix 17 }

llcNotification18 NOTIFICATION-TYPE
    OBJECTS { 
              llc18_interface 
            }
    STATUS current
    DESCRIPTION
        "Notification of Event LLC.18

        Message: 'No memory for SAP control block on interface $1'

        Parameters list:
              $1: llc18_interface

        Unable to allocate memory for SAP control block."
    ::= { llcNotificationsPrefix 18 }

llcNotification19 NOTIFICATION-TYPE
    OBJECTS { 
              llc19_interface 
            }
    STATUS current
    DESCRIPTION
        "Notification of Event LLC.19

        Message: 'No memory for station control block on interface $1'

        Parameters list:
              $1: llc19_interface

        Unable to allocate memory for station control block."
    ::= { llcNotificationsPrefix 19 }

llcNotification20 NOTIFICATION-TYPE
    OBJECTS { 
              llc20_llc2_connection, 
              llc20_llc2_connection,
              llc20_llc2_sap,
              llc20_llc2_sap,
              llc20_interface 
            }
    STATUS current
    DESCRIPTION
        "Notification of Event LLC.20

        Message: 'UI frame dropped, $1->$2, saps $3->$4, interface $5'

        Parameters list:
              $1: llc20_llc2_connection
              $2: llc20_llc2_connection
              $3: llc20_llc2_sap
              $4: llc20_llc2_sap
              $5: llc20_interface

        UI frame refused by the local application within the router."
    ::= { llcNotificationsPrefix 20 }

llcNotification21 NOTIFICATION-TYPE
    OBJECTS { 
              llc21_llc2_connection, 
              llc21_llc2_connection,
              llc21_llc2_sap,
              llc21_llc2_sap,
              llc21_interface 
            }
    STATUS current
    DESCRIPTION
        "Notification of Event LLC.21

        Message: 'TEST frame refused, $1->$2, saps $3->$4, interface $5'

        Parameters list:
              $1: llc21_llc2_connection
              $2: llc21_llc2_connection
              $3: llc21_llc2_sap
              $4: llc21_llc2_sap
              $5: llc21_interface

        TEST frame refused by the local application within the router.
        The frame is passed on to the bridge code, etc."
    ::= { llcNotificationsPrefix 21 }

llcNotification22 NOTIFICATION-TYPE
    OBJECTS { 
              llc22_llc2_connection, 
              llc22_llc2_connection,
              llc22_llc2_sap,
              llc22_llc2_sap,
              llc22_interface 
            }
    STATUS current
    DESCRIPTION
        "Notification of Event LLC.22

        Message: 'XID frame refused, $1->$2, saps $3->$4, interface $5'

        Parameters list:
              $1: llc22_llc2_connection
              $2: llc22_llc2_connection
              $3: llc22_llc2_sap
              $4: llc22_llc2_sap
              $5: llc22_interface

        XID frame refused by the local application within the router.
        The frame is passed on to the bridge code, etc."
    ::= { llcNotificationsPrefix 22 }

llcNotification23 NOTIFICATION-TYPE
    OBJECTS { 
              llc23_frame_type, 
              llc23_src_mac,
              llc23_dst_mac,
              llc23_rif,
              llc23_src_sap,
              llc23_dst_sap,
              llc23_interface 
            }
    STATUS current
    DESCRIPTION
        "Notification of Event LLC.23

        Message: 'Upcall frame $1, $2->$3, $4 saps $5->$6, interface $7'

        Parameters list:
              $1: llc23_frame_type
              $2: llc23_src_mac
              $3: llc23_dst_mac
              $4: llc23_rif
              $5: llc23_src_sap
              $6: llc23_dst_sap
              $7: llc23_interface

        LLC makes an upcall providing the LLC with a unitdata frame.
        The possible unitdata frames are:
        TEST_C0 or TEST_C1 or TEST_R0 or TEST_R1 (TEST frame),
        XID_C0 or XID_C1 or XID_R0 or XID_R1 (Exchange Identification frame),
        UI_C0 or UI_R0 (Unnumbered Information).
        The abbrevation suffixes are C0 (command, poll bit off),
        C1 (command, poll bit on), R0 (response, final bit off) and
        R1 (response, final bit on)."
    ::= { llcNotificationsPrefix 23 }

llcNotification24 NOTIFICATION-TYPE
    OBJECTS { 
              llc24_reason_code, 
              llc24_llc2_connection,
              llc24_llc2_connection,
              llc24_llc2_sap,
              llc24_llc2_sap,
              llc24_interface_name 
            }
    STATUS current
    DESCRIPTION
        "Notification of Event LLC.24

        Message: 'llc2 outbound frame dropped, reason $1, $2->$3, saps $4->$5, interface $6'

        Parameters list:
              $1: llc24_reason_code
              $2: llc24_llc2_connection
              $3: llc24_llc2_connection
              $4: llc24_llc2_sap
              $5: llc24_llc2_sap
              $6: llc24_interface_name

        The sending of an LLC2 related outbound frame failed.
        The reason_code is the internal error code for the failure."
    ::= { llcNotificationsPrefix 24 }

llcNotification25 NOTIFICATION-TYPE
    OBJECTS { 
              llc25_frame_type, 
              llc25_reason_code,
              llc25_llc2_connection,
              llc25_llc2_connection,
              llc25_llc2_sap,
              llc25_llc2_sap,
              llc25_interface 
            }
    STATUS current
    DESCRIPTION
        "Notification of Event LLC.25

        Message: '$1 outbound frame dropped, reason $2, $3->$4, saps $5->$6, interface $7'

        Parameters list:
              $1: llc25_frame_type
              $2: llc25_reason_code
              $3: llc25_llc2_connection
              $4: llc25_llc2_connection
              $5: llc25_llc2_sap
              $6: llc25_llc2_sap
              $7: llc25_interface

        The sending of the user's UNITDATA or an LLC-generated XID or TEST
        response outbound frame failed.
        The possible frame test are:
        TEST_C0 or TEST_C1 or TEST_R0 or TEST_R1 (TEST frame),
        XID_C0 or XID_C1 or XID_R0 or XID_R1 (Exchange Identification frame),
        UI_C0 or UI_R0 (Unnumbered Information frame) and
        unexpected (not one of the above types).
        The abbrevation suffixes are C0 (command, poll bit off),
        C1 (command, poll bit on),
        R0 (response, final bit off), and R1 (response, final bit on)."
    ::= { llcNotificationsPrefix 25 }

llcNotification26 NOTIFICATION-TYPE
    OBJECTS { 
              llc26_interface 
            }
    STATUS current
    DESCRIPTION
        "Notification of Event LLC.26

        Message: 'No memory for LLC CONF BLOCK on interface $1'

        Parameters list:
              $1: llc26_interface

        Unable to allocate memory for an LLC_CONF_BLOCK at initialization time.
        LLC configuration defaults are used."
    ::= { llcNotificationsPrefix 26 }

llcNotification27 NOTIFICATION-TYPE
    OBJECTS { 
              llc27_interface 
            }
    STATUS current
    DESCRIPTION
        "Notification of Event LLC.27

        Message: 'Read LLC Configuration record for interface $1'

        Parameters list:
              $1: llc27_interface

        LLC Configuration record read for this network. This only occurs
        at initialization time. The values in the LLC configuration record
        are used as default value on the interface."
    ::= { llcNotificationsPrefix 27 }

llcNotification28 NOTIFICATION-TYPE
    OBJECTS { 
              llc28_access_priority, 
              llc28_interface 
            }
    STATUS current
    DESCRIPTION
        "Notification of Event LLC.28

        Message: 'Inv access priority $1 for interface $2'

        Parameters list:
              $1: llc28_access_priority
              $2: llc28_interface

        access_priority, on an interface that is not a token ring must be
        zero because it is not used."
    ::= { llcNotificationsPrefix 28 }

llcNotification29 NOTIFICATION-TYPE
    OBJECTS { 
              llc29_access_priority, 
              llc29_interface 
            }
    STATUS current
    DESCRIPTION
        "Notification of Event LLC.29

        Message: 'Inv acc $1 for interface $2'

        Parameters list:
              $1: llc29_access_priority
              $2: llc29_interface

        The access priority is greater than 7. A default of 0 is used."
    ::= { llcNotificationsPrefix 29 }

llcNotification30 NOTIFICATION-TYPE
    OBJECTS { 
              llc30_hardware_type, 
              llc30_interface 
            }
    STATUS current
    DESCRIPTION
        "Notification of Event LLC.30

        Message: 'Invalid hardware type $1 for interface $2'

        Parameters list:
              $1: llc30_hardware_type
              $2: llc30_interface

        An LLC config record exists for an interface that does not have a
        LAN hardware type."
    ::= { llcNotificationsPrefix 30 }

llcNotification31 NOTIFICATION-TYPE
    OBJECTS { 
              llc31_interface_number 
            }
    STATUS current
    DESCRIPTION
        "Notification of Event LLC.31

        Message: 'Invalid interface $1 in config'

        Parameters list:
              $1: llc31_interface_number

        An LLC config record exists for an interface that does not exist."
    ::= { llcNotificationsPrefix 31 }

llcNotification32 NOTIFICATION-TYPE
    OBJECTS { 
              llc32_frame_type, 
              llc32_src_mac,
              llc32_dst_mac,
              llc32_rif,
              llc32_src_sap,
              llc32_dst_sap,
              llc32_interface 
            }
    STATUS current
    DESCRIPTION
        "Notification of Event LLC.32

        Message: 'Sent $1, $2->$3, $4 saps $5->$6, interface $7'

        Parameters list:
              $1: llc32_frame_type
              $2: llc32_src_mac
              $3: llc32_dst_mac
              $4: llc32_rif
              $5: llc32_src_sap
              $6: llc32_dst_sap
              $7: llc32_interface

        LLC user is sending a frame, or LLC itself is sending a
        TEST or XID response frame.
        The possible frame types are:
        TEST_C0 or TEST_C1 or TEST_R0 or TEST_R1 (TEST frame),
        XID_C0 or XID_C1 or XID_R0 or XID_R1 (Exchange Identification frame),
        UI_C0 or UI_R0 (Unnumbered Information frame).
        The abbrevation suffixes are C0 (command, poll bit off),
        C1 (command, poll bit on), R0 (response, final bit off) and
        R1 (response, final bit on)."
    ::= { llcNotificationsPrefix 32 }

llcNotification33 NOTIFICATION-TYPE
    OBJECTS { 
              llc33_frame_type, 
              llc33_src_mac,
              llc33_dst_mac,
              llc33_rif,
              llc33_src_sap,
              llc33_dst_sap,
              llc33_interface 
            }
    STATUS current
    DESCRIPTION
        "Notification of Event LLC.33

        Message: 'frm to LLC, frm $1, $2->$3, $4 saps $5->$6, interface $7'

        Parameters list:
              $1: llc33_frame_type
              $2: llc33_src_mac
              $3: llc33_dst_mac
              $4: llc33_rif
              $5: llc33_src_sap
              $6: llc33_dst_sap
              $7: llc33_interface

        LLC subsystem itself is responding to a TEST or XID frame.
        The possible frame types are:
        TEST_C0 or TEST_C1 (TEST frame), and
        XID_C0 or XID_C1 (Exchange Identification frame).
        The abbrevation suffixes are:
        C0=(command, poll  bit off) and
        C1=(command, poll  bit on)."
    ::= { llcNotificationsPrefix 33 }


END
