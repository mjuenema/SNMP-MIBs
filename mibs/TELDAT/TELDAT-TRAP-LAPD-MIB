-- file automatically created


TELDAT-TRAP-LAPD-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


lapdTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the LAPD event subsystem."
    REVISION "201401200930Z"
    DESCRIPTION "Initial implementation"
        ::= { telEventTraps 119 }


lapdEventsGroup	OBJECT IDENTIFIER	::= { lapdTrapsMIB 1 }

lapdNotifications	OBJECT IDENTIFIER	::= { lapdTrapsMIB 2 }
lapdNotificationsPrefix	OBJECT IDENTIFIER	::= { lapdNotifications 0 }

lapdEventObjects1 OBJECT-IDENTITY
    STATUS current
    DESCRIPTION
        "Event LAPD.1
        Unnumebered frame transmitted."
    ::= { lapdEventsGroup 1 }

lapd1_SAPI OBJECT-TYPE
    SYNTAX Integer32
    MAX-ACCESS accessible-for-notify
    STATUS current
    DESCRIPTION
        "Parameter 'SAPI' in event LAPD.1"
    ::= { lapdEventObjects1 1 }

lapd1_TEI OBJECT-TYPE
    SYNTAX Integer32
    MAX-ACCESS accessible-for-notify
    STATUS current
    DESCRIPTION
        "Parameter 'TEI' in event LAPD.1"
    ::= { lapdEventObjects1 2 }

lapd1_frame OBJECT-TYPE
    SYNTAX DisplayString
    MAX-ACCESS accessible-for-notify
    STATUS current
    DESCRIPTION
        "Parameter 'frame' in event LAPD.1"
    ::= { lapdEventObjects1 3 }

lapd1_bit_pf OBJECT-TYPE
    SYNTAX Integer32
    MAX-ACCESS accessible-for-notify
    STATUS current
    DESCRIPTION
        "Parameter 'bit_pf' in event LAPD.1"
    ::= { lapdEventObjects1 4 }

lapd1_interface OBJECT-TYPE
    SYNTAX DisplayString
    MAX-ACCESS accessible-for-notify
    STATUS current
    DESCRIPTION
        "Parameter 'interface' in event LAPD.1"
    ::= { lapdEventObjects1 5 }

lapdEventObjects2 OBJECT-IDENTITY
    STATUS current
    DESCRIPTION
        "Event LAPD.2
        Supervisory frame transmitted."
    ::= { lapdEventsGroup 2 }

lapd2_SAPI OBJECT-TYPE
    SYNTAX Integer32
    MAX-ACCESS accessible-for-notify
    STATUS current
    DESCRIPTION
        "Parameter 'SAPI' in event LAPD.2"
    ::= { lapdEventObjects2 1 }

lapd2_TEI OBJECT-TYPE
    SYNTAX Integer32
    MAX-ACCESS accessible-for-notify
    STATUS current
    DESCRIPTION
        "Parameter 'TEI' in event LAPD.2"
    ::= { lapdEventObjects2 2 }

lapd2_frame OBJECT-TYPE
    SYNTAX DisplayString
    MAX-ACCESS accessible-for-notify
    STATUS current
    DESCRIPTION
        "Parameter 'frame' in event LAPD.2"
    ::= { lapdEventObjects2 3 }

lapd2_bit_pf OBJECT-TYPE
    SYNTAX Integer32
    MAX-ACCESS accessible-for-notify
    STATUS current
    DESCRIPTION
        "Parameter 'bit_pf' in event LAPD.2"
    ::= { lapdEventObjects2 4 }

lapd2_nr OBJECT-TYPE
    SYNTAX Integer32
    MAX-ACCESS accessible-for-notify
    STATUS current
    DESCRIPTION
        "Parameter 'nr' in event LAPD.2"
    ::= { lapdEventObjects2 5 }

lapd2_interface OBJECT-TYPE
    SYNTAX DisplayString
    MAX-ACCESS accessible-for-notify
    STATUS current
    DESCRIPTION
        "Parameter 'interface' in event LAPD.2"
    ::= { lapdEventObjects2 6 }

lapdEventObjects3 OBJECT-IDENTITY
    STATUS current
    DESCRIPTION
        "Event LAPD.3
        RNR or REJ Supervisory frame transmitted."
    ::= { lapdEventsGroup 3 }

lapd3_SAPI OBJECT-TYPE
    SYNTAX Integer32
    MAX-ACCESS accessible-for-notify
    STATUS current
    DESCRIPTION
        "Parameter 'SAPI' in event LAPD.3"
    ::= { lapdEventObjects3 1 }

lapd3_TEI OBJECT-TYPE
    SYNTAX Integer32
    MAX-ACCESS accessible-for-notify
    STATUS current
    DESCRIPTION
        "Parameter 'TEI' in event LAPD.3"
    ::= { lapdEventObjects3 2 }

lapd3_frame OBJECT-TYPE
    SYNTAX DisplayString
    MAX-ACCESS accessible-for-notify
    STATUS current
    DESCRIPTION
        "Parameter 'frame' in event LAPD.3"
    ::= { lapdEventObjects3 3 }

lapd3_bit_pf OBJECT-TYPE
    SYNTAX Integer32
    MAX-ACCESS accessible-for-notify
    STATUS current
    DESCRIPTION
        "Parameter 'bit_pf' in event LAPD.3"
    ::= { lapdEventObjects3 4 }

lapd3_nr OBJECT-TYPE
    SYNTAX Integer32
    MAX-ACCESS accessible-for-notify
    STATUS current
    DESCRIPTION
        "Parameter 'nr' in event LAPD.3"
    ::= { lapdEventObjects3 5 }

lapd3_interface OBJECT-TYPE
    SYNTAX DisplayString
    MAX-ACCESS accessible-for-notify
    STATUS current
    DESCRIPTION
        "Parameter 'interface' in event LAPD.3"
    ::= { lapdEventObjects3 6 }

lapdEventObjects4 OBJECT-IDENTITY
    STATUS current
    DESCRIPTION
        "Event LAPD.4
        Info frame transmitted."
    ::= { lapdEventsGroup 4 }

lapd4_SAPI OBJECT-TYPE
    SYNTAX Integer32
    MAX-ACCESS accessible-for-notify
    STATUS current
    DESCRIPTION
        "Parameter 'SAPI' in event LAPD.4"
    ::= { lapdEventObjects4 1 }

lapd4_TEI OBJECT-TYPE
    SYNTAX Integer32
    MAX-ACCESS accessible-for-notify
    STATUS current
    DESCRIPTION
        "Parameter 'TEI' in event LAPD.4"
    ::= { lapdEventObjects4 2 }

lapd4_frame OBJECT-TYPE
    SYNTAX DisplayString
    MAX-ACCESS accessible-for-notify
    STATUS current
    DESCRIPTION
        "Parameter 'frame' in event LAPD.4"
    ::= { lapdEventObjects4 3 }

lapd4_bit_pf OBJECT-TYPE
    SYNTAX Integer32
    MAX-ACCESS accessible-for-notify
    STATUS current
    DESCRIPTION
        "Parameter 'bit_pf' in event LAPD.4"
    ::= { lapdEventObjects4 4 }

lapd4_ns OBJECT-TYPE
    SYNTAX Integer32
    MAX-ACCESS accessible-for-notify
    STATUS current
    DESCRIPTION
        "Parameter 'ns' in event LAPD.4"
    ::= { lapdEventObjects4 5 }

lapd4_nr OBJECT-TYPE
    SYNTAX Integer32
    MAX-ACCESS accessible-for-notify
    STATUS current
    DESCRIPTION
        "Parameter 'nr' in event LAPD.4"
    ::= { lapdEventObjects4 6 }

lapd4_interface OBJECT-TYPE
    SYNTAX DisplayString
    MAX-ACCESS accessible-for-notify
    STATUS current
    DESCRIPTION
        "Parameter 'interface' in event LAPD.4"
    ::= { lapdEventObjects4 7 }

lapdEventObjects5 OBJECT-IDENTITY
    STATUS current
    DESCRIPTION
        "Event LAPD.5
        Unnumebered frame received."
    ::= { lapdEventsGroup 5 }

lapd5_SAPI OBJECT-TYPE
    SYNTAX Integer32
    MAX-ACCESS accessible-for-notify
    STATUS current
    DESCRIPTION
        "Parameter 'SAPI' in event LAPD.5"
    ::= { lapdEventObjects5 1 }

lapd5_TEI OBJECT-TYPE
    SYNTAX Integer32
    MAX-ACCESS accessible-for-notify
    STATUS current
    DESCRIPTION
        "Parameter 'TEI' in event LAPD.5"
    ::= { lapdEventObjects5 2 }

lapd5_frame OBJECT-TYPE
    SYNTAX DisplayString
    MAX-ACCESS accessible-for-notify
    STATUS current
    DESCRIPTION
        "Parameter 'frame' in event LAPD.5"
    ::= { lapdEventObjects5 3 }

lapd5_bit_pf OBJECT-TYPE
    SYNTAX Integer32
    MAX-ACCESS accessible-for-notify
    STATUS current
    DESCRIPTION
        "Parameter 'bit_pf' in event LAPD.5"
    ::= { lapdEventObjects5 4 }

lapd5_interface OBJECT-TYPE
    SYNTAX DisplayString
    MAX-ACCESS accessible-for-notify
    STATUS current
    DESCRIPTION
        "Parameter 'interface' in event LAPD.5"
    ::= { lapdEventObjects5 5 }

lapdEventObjects6 OBJECT-IDENTITY
    STATUS current
    DESCRIPTION
        "Event LAPD.6
        RR Supervisory frame received."
    ::= { lapdEventsGroup 6 }

lapd6_SAPI OBJECT-TYPE
    SYNTAX Integer32
    MAX-ACCESS accessible-for-notify
    STATUS current
    DESCRIPTION
        "Parameter 'SAPI' in event LAPD.6"
    ::= { lapdEventObjects6 1 }

lapd6_TEI OBJECT-TYPE
    SYNTAX Integer32
    MAX-ACCESS accessible-for-notify
    STATUS current
    DESCRIPTION
        "Parameter 'TEI' in event LAPD.6"
    ::= { lapdEventObjects6 2 }

lapd6_frame OBJECT-TYPE
    SYNTAX DisplayString
    MAX-ACCESS accessible-for-notify
    STATUS current
    DESCRIPTION
        "Parameter 'frame' in event LAPD.6"
    ::= { lapdEventObjects6 3 }

lapd6_bit_pf OBJECT-TYPE
    SYNTAX Integer32
    MAX-ACCESS accessible-for-notify
    STATUS current
    DESCRIPTION
        "Parameter 'bit_pf' in event LAPD.6"
    ::= { lapdEventObjects6 4 }

lapd6_nr OBJECT-TYPE
    SYNTAX Integer32
    MAX-ACCESS accessible-for-notify
    STATUS current
    DESCRIPTION
        "Parameter 'nr' in event LAPD.6"
    ::= { lapdEventObjects6 5 }

lapd6_interface OBJECT-TYPE
    SYNTAX DisplayString
    MAX-ACCESS accessible-for-notify
    STATUS current
    DESCRIPTION
        "Parameter 'interface' in event LAPD.6"
    ::= { lapdEventObjects6 6 }

lapdEventObjects7 OBJECT-IDENTITY
    STATUS current
    DESCRIPTION
        "Event LAPD.7
        RNR or REJ Supervisory frame received."
    ::= { lapdEventsGroup 7 }

lapd7_SAPI OBJECT-TYPE
    SYNTAX Integer32
    MAX-ACCESS accessible-for-notify
    STATUS current
    DESCRIPTION
        "Parameter 'SAPI' in event LAPD.7"
    ::= { lapdEventObjects7 1 }

lapd7_TEI OBJECT-TYPE
    SYNTAX Integer32
    MAX-ACCESS accessible-for-notify
    STATUS current
    DESCRIPTION
        "Parameter 'TEI' in event LAPD.7"
    ::= { lapdEventObjects7 2 }

lapd7_frame OBJECT-TYPE
    SYNTAX DisplayString
    MAX-ACCESS accessible-for-notify
    STATUS current
    DESCRIPTION
        "Parameter 'frame' in event LAPD.7"
    ::= { lapdEventObjects7 3 }

lapd7_bit_pf OBJECT-TYPE
    SYNTAX Integer32
    MAX-ACCESS accessible-for-notify
    STATUS current
    DESCRIPTION
        "Parameter 'bit_pf' in event LAPD.7"
    ::= { lapdEventObjects7 4 }

lapd7_nr OBJECT-TYPE
    SYNTAX Integer32
    MAX-ACCESS accessible-for-notify
    STATUS current
    DESCRIPTION
        "Parameter 'nr' in event LAPD.7"
    ::= { lapdEventObjects7 5 }

lapd7_interface OBJECT-TYPE
    SYNTAX DisplayString
    MAX-ACCESS accessible-for-notify
    STATUS current
    DESCRIPTION
        "Parameter 'interface' in event LAPD.7"
    ::= { lapdEventObjects7 6 }

lapdEventObjects8 OBJECT-IDENTITY
    STATUS current
    DESCRIPTION
        "Event LAPD.8
        Info frame transmitted."
    ::= { lapdEventsGroup 8 }

lapd8_SAPI OBJECT-TYPE
    SYNTAX Integer32
    MAX-ACCESS accessible-for-notify
    STATUS current
    DESCRIPTION
        "Parameter 'SAPI' in event LAPD.8"
    ::= { lapdEventObjects8 1 }

lapd8_TEI OBJECT-TYPE
    SYNTAX Integer32
    MAX-ACCESS accessible-for-notify
    STATUS current
    DESCRIPTION
        "Parameter 'TEI' in event LAPD.8"
    ::= { lapdEventObjects8 2 }

lapd8_frame OBJECT-TYPE
    SYNTAX DisplayString
    MAX-ACCESS accessible-for-notify
    STATUS current
    DESCRIPTION
        "Parameter 'frame' in event LAPD.8"
    ::= { lapdEventObjects8 3 }

lapd8_bit_pf OBJECT-TYPE
    SYNTAX Integer32
    MAX-ACCESS accessible-for-notify
    STATUS current
    DESCRIPTION
        "Parameter 'bit_pf' in event LAPD.8"
    ::= { lapdEventObjects8 4 }

lapd8_ns OBJECT-TYPE
    SYNTAX Integer32
    MAX-ACCESS accessible-for-notify
    STATUS current
    DESCRIPTION
        "Parameter 'ns' in event LAPD.8"
    ::= { lapdEventObjects8 5 }

lapd8_nr OBJECT-TYPE
    SYNTAX Integer32
    MAX-ACCESS accessible-for-notify
    STATUS current
    DESCRIPTION
        "Parameter 'nr' in event LAPD.8"
    ::= { lapdEventObjects8 6 }

lapd8_interface OBJECT-TYPE
    SYNTAX DisplayString
    MAX-ACCESS accessible-for-notify
    STATUS current
    DESCRIPTION
        "Parameter 'interface' in event LAPD.8"
    ::= { lapdEventObjects8 7 }

lapdEventObjects9 OBJECT-IDENTITY
    STATUS current
    DESCRIPTION
        "Event LAPD.9
        Informational. Lapd error detectec according Q.921."
    ::= { lapdEventsGroup 9 }

lapd9_SAPI OBJECT-TYPE
    SYNTAX Integer32
    MAX-ACCESS accessible-for-notify
    STATUS current
    DESCRIPTION
        "Parameter 'SAPI' in event LAPD.9"
    ::= { lapdEventObjects9 1 }

lapd9_TEI OBJECT-TYPE
    SYNTAX Integer32
    MAX-ACCESS accessible-for-notify
    STATUS current
    DESCRIPTION
        "Parameter 'TEI' in event LAPD.9"
    ::= { lapdEventObjects9 2 }

lapd9_Code OBJECT-TYPE
    SYNTAX DisplayString
    MAX-ACCESS accessible-for-notify
    STATUS current
    DESCRIPTION
        "Parameter 'Code' in event LAPD.9"
    ::= { lapdEventObjects9 3 }

lapd9_interface OBJECT-TYPE
    SYNTAX DisplayString
    MAX-ACCESS accessible-for-notify
    STATUS current
    DESCRIPTION
        "Parameter 'interface' in event LAPD.9"
    ::= { lapdEventObjects9 4 }

lapdEventObjects10 OBJECT-IDENTITY
    STATUS current
    DESCRIPTION
        "Event LAPD.10
        Notify port state changed"
    ::= { lapdEventsGroup 10 }

lapd10_SAPI OBJECT-TYPE
    SYNTAX Integer32
    MAX-ACCESS accessible-for-notify
    STATUS current
    DESCRIPTION
        "Parameter 'SAPI' in event LAPD.10"
    ::= { lapdEventObjects10 1 }

lapd10_TEI OBJECT-TYPE
    SYNTAX Integer32
    MAX-ACCESS accessible-for-notify
    STATUS current
    DESCRIPTION
        "Parameter 'TEI' in event LAPD.10"
    ::= { lapdEventObjects10 2 }

lapd10_state OBJECT-TYPE
    SYNTAX DisplayString
    MAX-ACCESS accessible-for-notify
    STATUS current
    DESCRIPTION
        "Parameter 'state' in event LAPD.10"
    ::= { lapdEventObjects10 3 }

lapd10_interface OBJECT-TYPE
    SYNTAX DisplayString
    MAX-ACCESS accessible-for-notify
    STATUS current
    DESCRIPTION
        "Parameter 'interface' in event LAPD.10"
    ::= { lapdEventObjects10 4 }

lapdEventObjects11 OBJECT-IDENTITY
    STATUS current
    DESCRIPTION
        "Event LAPD.11
        Notify port state changed"
    ::= { lapdEventsGroup 11 }

lapd11_SAPI OBJECT-TYPE
    SYNTAX Integer32
    MAX-ACCESS accessible-for-notify
    STATUS current
    DESCRIPTION
        "Parameter 'SAPI' in event LAPD.11"
    ::= { lapdEventObjects11 1 }

lapd11_TEI OBJECT-TYPE
    SYNTAX Integer32
    MAX-ACCESS accessible-for-notify
    STATUS current
    DESCRIPTION
        "Parameter 'TEI' in event LAPD.11"
    ::= { lapdEventObjects11 2 }

lapd11_state OBJECT-TYPE
    SYNTAX DisplayString
    MAX-ACCESS accessible-for-notify
    STATUS current
    DESCRIPTION
        "Parameter 'state' in event LAPD.11"
    ::= { lapdEventObjects11 3 }

lapd11_interface OBJECT-TYPE
    SYNTAX DisplayString
    MAX-ACCESS accessible-for-notify
    STATUS current
    DESCRIPTION
        "Parameter 'interface' in event LAPD.11"
    ::= { lapdEventObjects11 4 }


lapdNotification1 NOTIFICATION-TYPE
    OBJECTS { 
              lapd1_SAPI, 
              lapd1_TEI,
              lapd1_frame,
              lapd1_bit_pf,
              lapd1_interface 
            }
    STATUS current
    DESCRIPTION
        "Notification of Event LAPD.1

        Message: 'S:$1 T:$2 Tx $3 P/F=$4 interface $5'

        Parameters list:
              $1: lapd1_SAPI
              $2: lapd1_TEI
              $3: lapd1_frame
              $4: lapd1_bit_pf
              $5: lapd1_interface

        Unnumebered frame transmitted."
    ::= { lapdNotificationsPrefix 1 }

lapdNotification2 NOTIFICATION-TYPE
    OBJECTS { 
              lapd2_SAPI, 
              lapd2_TEI,
              lapd2_frame,
              lapd2_bit_pf,
              lapd2_nr,
              lapd2_interface 
            }
    STATUS current
    DESCRIPTION
        "Notification of Event LAPD.2

        Message: 'S:$1 T:$2 Tx $3 P/F=$4		N(R)=$5 interface $6'

        Parameters list:
              $1: lapd2_SAPI
              $2: lapd2_TEI
              $3: lapd2_frame
              $4: lapd2_bit_pf
              $5: lapd2_nr
              $6: lapd2_interface

        Supervisory frame transmitted."
    ::= { lapdNotificationsPrefix 2 }

lapdNotification3 NOTIFICATION-TYPE
    OBJECTS { 
              lapd3_SAPI, 
              lapd3_TEI,
              lapd3_frame,
              lapd3_bit_pf,
              lapd3_nr,
              lapd3_interface 
            }
    STATUS current
    DESCRIPTION
        "Notification of Event LAPD.3

        Message: 'S:$1 T:$2 Tx $3 P/F=$4		N(R)=$5 interface $6'

        Parameters list:
              $1: lapd3_SAPI
              $2: lapd3_TEI
              $3: lapd3_frame
              $4: lapd3_bit_pf
              $5: lapd3_nr
              $6: lapd3_interface

        RNR or REJ Supervisory frame transmitted."
    ::= { lapdNotificationsPrefix 3 }

lapdNotification4 NOTIFICATION-TYPE
    OBJECTS { 
              lapd4_SAPI, 
              lapd4_TEI,
              lapd4_frame,
              lapd4_bit_pf,
              lapd4_ns,
              lapd4_nr,
              lapd4_interface 
            }
    STATUS current
    DESCRIPTION
        "Notification of Event LAPD.4

        Message: 'S:$1 T:$2 Tx $3 P/F=$4 N(S)=$5 N(R)=$6 interface $7'

        Parameters list:
              $1: lapd4_SAPI
              $2: lapd4_TEI
              $3: lapd4_frame
              $4: lapd4_bit_pf
              $5: lapd4_ns
              $6: lapd4_nr
              $7: lapd4_interface

        Info frame transmitted."
    ::= { lapdNotificationsPrefix 4 }

lapdNotification5 NOTIFICATION-TYPE
    OBJECTS { 
              lapd5_SAPI, 
              lapd5_TEI,
              lapd5_frame,
              lapd5_bit_pf,
              lapd5_interface 
            }
    STATUS current
    DESCRIPTION
        "Notification of Event LAPD.5

        Message: 'S:$1 T:$2 Rx $3 P/F=$4 interface $5'

        Parameters list:
              $1: lapd5_SAPI
              $2: lapd5_TEI
              $3: lapd5_frame
              $4: lapd5_bit_pf
              $5: lapd5_interface

        Unnumebered frame received."
    ::= { lapdNotificationsPrefix 5 }

lapdNotification6 NOTIFICATION-TYPE
    OBJECTS { 
              lapd6_SAPI, 
              lapd6_TEI,
              lapd6_frame,
              lapd6_bit_pf,
              lapd6_nr,
              lapd6_interface 
            }
    STATUS current
    DESCRIPTION
        "Notification of Event LAPD.6

        Message: 'S:$1 T:$2 Rx $3 P/F=$4		N(R)=$5 interface $6'

        Parameters list:
              $1: lapd6_SAPI
              $2: lapd6_TEI
              $3: lapd6_frame
              $4: lapd6_bit_pf
              $5: lapd6_nr
              $6: lapd6_interface

        RR Supervisory frame received."
    ::= { lapdNotificationsPrefix 6 }

lapdNotification7 NOTIFICATION-TYPE
    OBJECTS { 
              lapd7_SAPI, 
              lapd7_TEI,
              lapd7_frame,
              lapd7_bit_pf,
              lapd7_nr,
              lapd7_interface 
            }
    STATUS current
    DESCRIPTION
        "Notification of Event LAPD.7

        Message: 'S:$1 T:$2 Rx $3 P/F=$4		N(R)=$5 interface $6'

        Parameters list:
              $1: lapd7_SAPI
              $2: lapd7_TEI
              $3: lapd7_frame
              $4: lapd7_bit_pf
              $5: lapd7_nr
              $6: lapd7_interface

        RNR or REJ Supervisory frame received."
    ::= { lapdNotificationsPrefix 7 }

lapdNotification8 NOTIFICATION-TYPE
    OBJECTS { 
              lapd8_SAPI, 
              lapd8_TEI,
              lapd8_frame,
              lapd8_bit_pf,
              lapd8_ns,
              lapd8_nr,
              lapd8_interface 
            }
    STATUS current
    DESCRIPTION
        "Notification of Event LAPD.8

        Message: 'S:$1 T:$2 Rx $3 P/F=$4 N(S)=$5 N(R)=$6 interface $7'

        Parameters list:
              $1: lapd8_SAPI
              $2: lapd8_TEI
              $3: lapd8_frame
              $4: lapd8_bit_pf
              $5: lapd8_ns
              $6: lapd8_nr
              $7: lapd8_interface

        Info frame transmitted."
    ::= { lapdNotificationsPrefix 8 }

lapdNotification9 NOTIFICATION-TYPE
    OBJECTS { 
              lapd9_SAPI, 
              lapd9_TEI,
              lapd9_Code,
              lapd9_interface 
            }
    STATUS current
    DESCRIPTION
        "Notification of Event LAPD.9

        Message: 'S:$1 T:$2 Error Description $3 interface $4'

        Parameters list:
              $1: lapd9_SAPI
              $2: lapd9_TEI
              $3: lapd9_Code
              $4: lapd9_interface

        Informational. Lapd error detectec according Q.921."
    ::= { lapdNotificationsPrefix 9 }

lapdNotification10 NOTIFICATION-TYPE
    OBJECTS { 
              lapd10_SAPI, 
              lapd10_TEI,
              lapd10_state,
              lapd10_interface 
            }
    STATUS current
    DESCRIPTION
        "Notification of Event LAPD.10

        Message: 'S:$1 T:$2 State changed to $3 interface $4'

        Parameters list:
              $1: lapd10_SAPI
              $2: lapd10_TEI
              $3: lapd10_state
              $4: lapd10_interface

        Notify port state changed"
    ::= { lapdNotificationsPrefix 10 }

lapdNotification11 NOTIFICATION-TYPE
    OBJECTS { 
              lapd11_SAPI, 
              lapd11_TEI,
              lapd11_state,
              lapd11_interface 
            }
    STATUS current
    DESCRIPTION
        "Notification of Event LAPD.11

        Message: 'S:$1 T:$2 Operational state changed to $3 interface $4'

        Parameters list:
              $1: lapd11_SAPI
              $2: lapd11_TEI
              $3: lapd11_state
              $4: lapd11_interface

        Notify port state changed"
    ::= { lapdNotificationsPrefix 11 }


END
