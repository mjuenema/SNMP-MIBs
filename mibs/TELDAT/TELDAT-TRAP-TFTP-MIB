-- file automatically created


TELDAT-TRAP-TFTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tftpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TFTP event subsystem."
    REVISION "201401200930Z"
    DESCRIPTION "Initial implementation"
        ::= { telEventTraps 19 }


tftpEventsGroup	OBJECT IDENTIFIER	::= { tftpTrapsMIB 1 }

tftpNotifications	OBJECT IDENTIFIER	::= { tftpTrapsMIB 2 }
tftpNotificationsPrefix	OBJECT IDENTIFIER	::= { tftpNotifications 0 }

tftpEventObjects1 OBJECT-IDENTITY
    STATUS current
    DESCRIPTION
        "Event TFTP.1
        TFTP connection created."
    ::= { tftpEventsGroup 1 }

tftp1_conn OBJECT-TYPE
    SYNTAX Integer32
    MAX-ACCESS accessible-for-notify
    STATUS current
    DESCRIPTION
        "Parameter 'conn' in event TFTP.1"
    ::= { tftpEventObjects1 1 }

tftp1_ip_address OBJECT-TYPE
    SYNTAX IpAddress
    MAX-ACCESS accessible-for-notify
    STATUS current
    DESCRIPTION
        "Parameter 'ip_address' in event TFTP.1"
    ::= { tftpEventObjects1 2 }

tftpEventObjects2 OBJECT-IDENTITY
    STATUS current
    DESCRIPTION
        "Event TFTP.2
        TFTP packet sent."
    ::= { tftpEventsGroup 2 }

tftp2_string OBJECT-TYPE
    SYNTAX DisplayString
    MAX-ACCESS accessible-for-notify
    STATUS current
    DESCRIPTION
        "Parameter 'string' in event TFTP.2"
    ::= { tftpEventObjects2 1 }

tftp2_conn OBJECT-TYPE
    SYNTAX Integer32
    MAX-ACCESS accessible-for-notify
    STATUS current
    DESCRIPTION
        "Parameter 'conn' in event TFTP.2"
    ::= { tftpEventObjects2 2 }

tftpEventObjects3 OBJECT-IDENTITY
    STATUS current
    DESCRIPTION
        "Event TFTP.3
        TFTP packet sent."
    ::= { tftpEventsGroup 3 }

tftp3_string OBJECT-TYPE
    SYNTAX DisplayString
    MAX-ACCESS accessible-for-notify
    STATUS current
    DESCRIPTION
        "Parameter 'string' in event TFTP.3"
    ::= { tftpEventObjects3 1 }

tftp3_conn OBJECT-TYPE
    SYNTAX Integer32
    MAX-ACCESS accessible-for-notify
    STATUS current
    DESCRIPTION
        "Parameter 'conn' in event TFTP.3"
    ::= { tftpEventObjects3 2 }

tftpEventObjects4 OBJECT-IDENTITY
    STATUS current
    DESCRIPTION
        "Event TFTP.4
        TFTP packet sent retry."
    ::= { tftpEventsGroup 4 }

tftp4_n_retry OBJECT-TYPE
    SYNTAX Integer32
    MAX-ACCESS accessible-for-notify
    STATUS current
    DESCRIPTION
        "Parameter 'n_retry' in event TFTP.4"
    ::= { tftpEventObjects4 1 }

tftp4_conn OBJECT-TYPE
    SYNTAX Integer32
    MAX-ACCESS accessible-for-notify
    STATUS current
    DESCRIPTION
        "Parameter 'conn' in event TFTP.4"
    ::= { tftpEventObjects4 2 }

tftpEventObjects5 OBJECT-IDENTITY
    STATUS current
    DESCRIPTION
        "Event TFTP.5
        Maximum TFTP packet retries reached. The connection will be closed."
    ::= { tftpEventsGroup 5 }

tftp5_conn OBJECT-TYPE
    SYNTAX Integer32
    MAX-ACCESS accessible-for-notify
    STATUS current
    DESCRIPTION
        "Parameter 'conn' in event TFTP.5"
    ::= { tftpEventObjects5 1 }

tftpEventObjects6 OBJECT-IDENTITY
    STATUS current
    DESCRIPTION
        "Event TFTP.6
        TFTP connection destroyed."
    ::= { tftpEventsGroup 6 }

tftp6_conn OBJECT-TYPE
    SYNTAX Integer32
    MAX-ACCESS accessible-for-notify
    STATUS current
    DESCRIPTION
        "Parameter 'conn' in event TFTP.6"
    ::= { tftpEventObjects6 1 }


tftpNotification1 NOTIFICATION-TYPE
    OBJECTS { 
              tftp1_conn, 
              tftp1_ip_address 
            }
    STATUS current
    DESCRIPTION
        "Notification of Event TFTP.1

        Message: 'TFTP connection 0x$1 created, ip destination $2'

        Parameters list:
              $1: tftp1_conn
              $2: tftp1_ip_address

        TFTP connection created."
    ::= { tftpNotificationsPrefix 1 }

tftpNotification2 NOTIFICATION-TYPE
    OBJECTS { 
              tftp2_string, 
              tftp2_conn 
            }
    STATUS current
    DESCRIPTION
        "Notification of Event TFTP.2

        Message: 'Sending $1 conn 0x$2'

        Parameters list:
              $1: tftp2_string
              $2: tftp2_conn

        TFTP packet sent."
    ::= { tftpNotificationsPrefix 2 }

tftpNotification3 NOTIFICATION-TYPE
    OBJECTS { 
              tftp3_string, 
              tftp3_conn 
            }
    STATUS current
    DESCRIPTION
        "Notification of Event TFTP.3

        Message: 'Received $1 conn 0x$2'

        Parameters list:
              $1: tftp3_string
              $2: tftp3_conn

        TFTP packet sent."
    ::= { tftpNotificationsPrefix 3 }

tftpNotification4 NOTIFICATION-TYPE
    OBJECTS { 
              tftp4_n_retry, 
              tftp4_conn 
            }
    STATUS current
    DESCRIPTION
        "Notification of Event TFTP.4

        Message: 'retrying $1 last packet sent, conn 0x$2'

        Parameters list:
              $1: tftp4_n_retry
              $2: tftp4_conn

        TFTP packet sent retry."
    ::= { tftpNotificationsPrefix 4 }

tftpNotification5 NOTIFICATION-TYPE
    OBJECTS { 
              tftp5_conn 
            }
    STATUS current
    DESCRIPTION
        "Notification of Event TFTP.5

        Message: 'max retries reached, conn 0x$1'

        Parameters list:
              $1: tftp5_conn

        Maximum TFTP packet retries reached. The connection will be closed."
    ::= { tftpNotificationsPrefix 5 }

tftpNotification6 NOTIFICATION-TYPE
    OBJECTS { 
              tftp6_conn 
            }
    STATUS current
    DESCRIPTION
        "Notification of Event TFTP.6

        Message: 'TFTP connection 0x$1 destroyed'

        Parameters list:
              $1: tftp6_conn

        TFTP connection destroyed."
    ::= { tftpNotificationsPrefix 6 }


END
