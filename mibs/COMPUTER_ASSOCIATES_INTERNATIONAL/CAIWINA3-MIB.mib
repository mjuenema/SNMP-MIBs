--MibName=caiWinA3
--	------------------------------------------------------------------------
--
--	This material contains, and is a part of a computer software program
--	which is, proprietary and confidential information owned by:
--	               COMPUTER ASSOCIATES INTERNATIONAL, INC.
--	The program, including this material, may not be duplicated, disclosed
--	or reproduced in whole or in part for any purpose without the express
--	written authorisation of COMPUTER ASSOCIATES.  All authorised
--	reproductions must be marked with this legend.
--
--	        Copyright 2006 Computer Associates International, Inc.
--	                 The Software that Manages eBusiness
--
--	------------------------------------------------------------------------

--
--	------------------------------------------------------------------------
--	$Header: $
--	------------------------------------------------------------------------
--
--	Description
--		Definition file for caiWinA3 MIB.
--
--	Development History
--
--		File generated by cagenagt
--
--	========================================================================
--
--	NOTE: This file was automatically generated - Please do not edit!
--
--	This is the caiWinA3 MIB for the Unicenter NSM Windows System Agent.
--
--	caiWinA3 contains four major groups:
--
--	winA3ConfigGroup specifies the agent configuration
--	winA3StatusGroup contains status information on the monitored entities
--	winA3AvailableGroup specifies available entities for monitoring
--	winA3HistoryGroup records status trap history
--
--	caiWinA3 monitors the following resources:
--
--	  System Summary
--	  CPUs
--	  Memories
--	  Logical Volumes
--	  Mounts
--	  Distributed File System Links
--	  Quotas
--	  Directories
--	  Files
--	  Processes
--	  Services
--	  Jobs
--	  Sessions
--	  Printers
--	  Network Interfaces
--	  Registry Entries
--	  Hardware Resources (e.g. Power Supplies, Fans, Temperatures)
--	  Programmable Resources (arbitrary user configurable resources)
--
--	caiWinA3 provides the following tables of available resources used or
--	provided by Windows System:
--
--	  Logical Volumes
--	  Mounts
--	  Distributed File System Links
--	  Quotas
--	  Processes
--	  Services
--	  Jobs
--	  Sessions
--	  Printers
--	  Hardware Resources
--	  Programmable Resources
--
--
--	caiWinA3 records status traps in a history table.
--
--	========================================================================

CAIWINA3-MIB DEFINITIONS ::= BEGIN

IMPORTS
	enterprises,
	IpAddress,
	Counter,
	Gauge         FROM RFC1155-SMI

	PhysAddress,
	DisplayString FROM RFC1213-MIB

	OBJECT-TYPE   FROM RFC-1212

	TRAP-TYPE     FROM RFC-1215;

-- FROM RFC1514-MIB
KBytes ::= INTEGER (0..2147483647)

cai       OBJECT IDENTIFIER ::= { enterprises 791 }
caiSysMgr OBJECT IDENTIFIER ::= { cai 2 }
tng       OBJECT IDENTIFIER ::= { caiSysMgr 10 }
agents    OBJECT IDENTIFIER ::= { tng 2 }

caiWinA3 OBJECT IDENTIFIER ::= { agents 90 }

--
-- The Config Group
--

winA3ConfigGroup OBJECT IDENTIFIER ::= { caiWinA3 1 }

winA3ConfigGeneralGroup OBJECT IDENTIFIER ::= { winA3ConfigGroup 1 }
winA3ConfigSysGroup OBJECT IDENTIFIER ::= { winA3ConfigGroup 2 }
winA3ConfigCPUGroup OBJECT IDENTIFIER ::= { winA3ConfigGroup 3 }
winA3ConfigMemGroup OBJECT IDENTIFIER ::= { winA3ConfigGroup 4 }
winA3ConfigLVolGroup OBJECT IDENTIFIER ::= { winA3ConfigGroup 5 }
winA3ConfigMntGroup OBJECT IDENTIFIER ::= { winA3ConfigGroup 6 }
winA3ConfigDfsGroup OBJECT IDENTIFIER ::= { winA3ConfigGroup 7 }
winA3ConfigQuotaGroup OBJECT IDENTIFIER ::= { winA3ConfigGroup 8 }
winA3ConfigDirGroup OBJECT IDENTIFIER ::= { winA3ConfigGroup 9 }
winA3ConfigFileGroup OBJECT IDENTIFIER ::= { winA3ConfigGroup 10 }
winA3ConfigProcGroup OBJECT IDENTIFIER ::= { winA3ConfigGroup 11 }
winA3ConfigSrvcGroup OBJECT IDENTIFIER ::= { winA3ConfigGroup 12 }
winA3ConfigJobGroup OBJECT IDENTIFIER ::= { winA3ConfigGroup 13 }
winA3ConfigSessGroup OBJECT IDENTIFIER ::= { winA3ConfigGroup 14 }
winA3ConfigPrnGroup OBJECT IDENTIFIER ::= { winA3ConfigGroup 15 }
winA3ConfigNetGroup OBJECT IDENTIFIER ::= { winA3ConfigGroup 16 }
winA3ConfigRegGroup OBJECT IDENTIFIER ::= { winA3ConfigGroup 17 }
winA3ConfigHardwrGroup OBJECT IDENTIFIER ::= { winA3ConfigGroup 18 }
winA3ConfigProgrmGroup OBJECT IDENTIFIER ::= { winA3ConfigGroup 19 }

--
-- The Status Group
--

winA3StatusGroup OBJECT IDENTIFIER ::= { caiWinA3 2 }

winA3StatusGeneralGroup OBJECT IDENTIFIER ::= { winA3StatusGroup 1 }
winA3StatusCPUGroup OBJECT IDENTIFIER ::= { winA3StatusGroup 3 }
winA3StatusMemGroup OBJECT IDENTIFIER ::= { winA3StatusGroup 4 }
winA3StatusLVolGroup OBJECT IDENTIFIER ::= { winA3StatusGroup 5 }
winA3StatusMntGroup OBJECT IDENTIFIER ::= { winA3StatusGroup 6 }
winA3StatusDfsGroup OBJECT IDENTIFIER ::= { winA3StatusGroup 7 }
winA3StatusQuotaGroup OBJECT IDENTIFIER ::= { winA3StatusGroup 8 }
winA3StatusDirGroup OBJECT IDENTIFIER ::= { winA3StatusGroup 9 }
winA3StatusFileGroup OBJECT IDENTIFIER ::= { winA3StatusGroup 10 }
winA3StatusProcGroup OBJECT IDENTIFIER ::= { winA3StatusGroup 11 }
winA3StatusSrvcGroup OBJECT IDENTIFIER ::= { winA3StatusGroup 12 }
winA3StatusJobGroup OBJECT IDENTIFIER ::= { winA3StatusGroup 13 }
winA3StatusSessGroup OBJECT IDENTIFIER ::= { winA3StatusGroup 14 }
winA3StatusPrnGroup OBJECT IDENTIFIER ::= { winA3StatusGroup 15 }
winA3StatusNetGroup OBJECT IDENTIFIER ::= { winA3StatusGroup 16 }
winA3StatusRegGroup OBJECT IDENTIFIER ::= { winA3StatusGroup 17 }
winA3StatusHardwrGroup OBJECT IDENTIFIER ::= { winA3StatusGroup 18 }
winA3StatusProgrmGroup OBJECT IDENTIFIER ::= { winA3StatusGroup 19 }

--
-- The Available Group
--

winA3AvailableGroup OBJECT IDENTIFIER ::= { caiWinA3 3 }

winA3AvailLVolGroup OBJECT IDENTIFIER ::= { winA3AvailableGroup 5 }
winA3AvailMntGroup OBJECT IDENTIFIER ::= { winA3AvailableGroup 6 }
winA3AvailDfsGroup OBJECT IDENTIFIER ::= { winA3AvailableGroup 7 }
winA3AvailQuotaGroup OBJECT IDENTIFIER ::= { winA3AvailableGroup 8 }
winA3AvailProcGroup OBJECT IDENTIFIER ::= { winA3AvailableGroup 11 }
winA3AvailSrvcGroup OBJECT IDENTIFIER ::= { winA3AvailableGroup 12 }
winA3AvailJobGroup OBJECT IDENTIFIER ::= { winA3AvailableGroup 13 }
winA3AvailSessGroup OBJECT IDENTIFIER ::= { winA3AvailableGroup 14 }
winA3AvailPrnGroup OBJECT IDENTIFIER ::= { winA3AvailableGroup 15 }
winA3AvailHardwrGroup OBJECT IDENTIFIER ::= { winA3AvailableGroup 18 }
winA3AvailProgrmGroup OBJECT IDENTIFIER ::= { winA3AvailableGroup 19 }

--
-- The History Group
--

winA3HistoryGroup OBJECT IDENTIFIER ::= { caiWinA3 4 }

--
-- The ConfigGeneral Group
--

winA3ConfigGeneralAgentVersion OBJECT-TYPE
	SYNTAX DisplayString
	ACCESS read-only
	STATUS mandatory
	DESCRIPTION "&<caiWinA3.101>Currently installed version of the agent."
	::= { winA3ConfigGeneralGroup 1 }

winA3ConfigGeneralColdStartTime OBJECT-TYPE
	SYNTAX DisplayString
	ACCESS read-only
	STATUS mandatory
	DESCRIPTION "&<caiWinA3.102>Date and time that the agent was last started."
	::= { winA3ConfigGeneralGroup 2 }

winA3ConfigGeneralWarmStartTime OBJECT-TYPE
	SYNTAX DisplayString
	ACCESS read-only
	STATUS mandatory
	DESCRIPTION "&<caiWinA3.103>Date and time that the agent's configuration was last changed."
	::= { winA3ConfigGeneralGroup 3 }

winA3ConfigGeneralCPUPollTime OBJECT-TYPE
	SYNTAX DisplayString
	ACCESS read-only
	STATUS mandatory
	DESCRIPTION "&<caiWinA3.104>Date and time that the agent last collected CPU information."
	::= { winA3ConfigGeneralGroup 4 }

winA3ConfigGeneralMemPollTime OBJECT-TYPE
	SYNTAX DisplayString
	ACCESS read-only
	STATUS mandatory
	DESCRIPTION "&<caiWinA3.105>Date and time that the agent last collected memory information."
	::= { winA3ConfigGeneralGroup 5 }

winA3ConfigGeneralLVolPollTime OBJECT-TYPE
	SYNTAX DisplayString
	ACCESS read-only
	STATUS mandatory
	DESCRIPTION "&<caiWinA3.106>Date and time that the agent last collected logical volume information."
	::= { winA3ConfigGeneralGroup 6 }

winA3ConfigGeneralMntPollTime OBJECT-TYPE
	SYNTAX DisplayString
	ACCESS read-only
	STATUS mandatory
	DESCRIPTION "&<caiWinA3.107>Date and time that the agent last collected mount information."
	::= { winA3ConfigGeneralGroup 7 }

winA3ConfigGeneralDfsPollTime OBJECT-TYPE
	SYNTAX DisplayString
	ACCESS read-only
	STATUS mandatory
	DESCRIPTION "&<caiWinA3.108>Date and time that the agent last collected distributed file system link information."
	::= { winA3ConfigGeneralGroup 8 }

winA3ConfigGeneralQuotaPollTime OBJECT-TYPE
	SYNTAX DisplayString
	ACCESS read-only
	STATUS mandatory
	DESCRIPTION "&<caiWinA3.109>Date and time that the agent last collected quota information."
	::= { winA3ConfigGeneralGroup 9 }

winA3ConfigGeneralDirPollTime OBJECT-TYPE
	SYNTAX DisplayString
	ACCESS read-only
	STATUS mandatory
	DESCRIPTION "&<caiWinA3.110>Date and time that the agent last collected directory information."
	::= { winA3ConfigGeneralGroup 10 }

winA3ConfigGeneralFilePollTime OBJECT-TYPE
	SYNTAX DisplayString
	ACCESS read-only
	STATUS mandatory
	DESCRIPTION "&<caiWinA3.111>Date and time that the agent last collected file information."
	::= { winA3ConfigGeneralGroup 11 }

winA3ConfigGeneralProcPollTime OBJECT-TYPE
	SYNTAX DisplayString
	ACCESS read-only
	STATUS mandatory
	DESCRIPTION "&<caiWinA3.112>Date and time that the agent last collected process information."
	::= { winA3ConfigGeneralGroup 12 }

winA3ConfigGeneralSrvcPollTime OBJECT-TYPE
	SYNTAX DisplayString
	ACCESS read-only
	STATUS mandatory
	DESCRIPTION "&<caiWinA3.113>Date and time that the agent last collected service information."
	::= { winA3ConfigGeneralGroup 13 }

winA3ConfigGeneralJobPollTime OBJECT-TYPE
	SYNTAX DisplayString
	ACCESS read-only
	STATUS mandatory
	DESCRIPTION "&<caiWinA3.114>Date and time that the agent last collected job information."
	::= { winA3ConfigGeneralGroup 14 }

winA3ConfigGeneralSessPollTime OBJECT-TYPE
	SYNTAX DisplayString
	ACCESS read-only
	STATUS mandatory
	DESCRIPTION "&<caiWinA3.115>Date and time that the agent last collected terminal session information."
	::= { winA3ConfigGeneralGroup 15 }

winA3ConfigGeneralPrnPollTime OBJECT-TYPE
	SYNTAX DisplayString
	ACCESS read-only
	STATUS mandatory
	DESCRIPTION "&<caiWinA3.116>Date and time that the agent last collected printer information."
	::= { winA3ConfigGeneralGroup 16 }

winA3ConfigGeneralNetPollTime OBJECT-TYPE
	SYNTAX DisplayString
	ACCESS read-only
	STATUS mandatory
	DESCRIPTION "&<caiWinA3.117>Date and time that the agent last collected network interface information."
	::= { winA3ConfigGeneralGroup 17 }

winA3ConfigGeneralRegPollTime OBJECT-TYPE
	SYNTAX DisplayString
	ACCESS read-only
	STATUS mandatory
	DESCRIPTION "&<caiWinA3.118>Date and time that the agent last collected registry entry information."
	::= { winA3ConfigGeneralGroup 18 }

winA3ConfigGeneralHardwrPollTime OBJECT-TYPE
	SYNTAX DisplayString
	ACCESS read-only
	STATUS mandatory
	DESCRIPTION "&<caiWinA3.119>Date and time that the agent last collected hardware resource information."
	::= { winA3ConfigGeneralGroup 19 }

winA3ConfigGeneralProgrmPollTime OBJECT-TYPE
	SYNTAX DisplayString
	ACCESS read-only
	STATUS mandatory
	DESCRIPTION "&<caiWinA3.120>Date and time that the agent last collected programmable resource information."
	::= { winA3ConfigGeneralGroup 20 }

--
-- The ConfigSys Group
--

winA3ConfigSysNodeName OBJECT-TYPE
	SYNTAX DisplayString
	ACCESS read-only
	STATUS mandatory
	DESCRIPTION "&<caiWinA3.121>The computer name of the system."
	::= { winA3ConfigSysGroup 1 }

winA3ConfigSysClusterName OBJECT-TYPE
	SYNTAX DisplayString
	ACCESS read-only
	STATUS mandatory
	DESCRIPTION "&<caiWinA3.122>The name and type of the cluster of which this system is a member of. For an unclustered system this attribute is set to '-'."
	::= { winA3ConfigSysGroup 2 }

winA3ConfigSysOsVersion OBJECT-TYPE
	SYNTAX DisplayString
	ACCESS read-only
	STATUS mandatory
	DESCRIPTION "&<caiWinA3.123>Details about the installed OS version."
	::= { winA3ConfigSysGroup 3 }

winA3ConfigSysBiosVersion OBJECT-TYPE
	SYNTAX DisplayString
	ACCESS read-only
	STATUS mandatory
	DESCRIPTION "&<caiWinA3.124>Details about the BIOS version."
	::= { winA3ConfigSysGroup 4 }

winA3ConfigSysHyperThread OBJECT-TYPE
	SYNTAX INTEGER {
		unknown(1),
		not-supported(2),
		supported-disabled(3),
		supported-inactive(4),
		supported-active(5)
	}
	ACCESS read-only
	STATUS mandatory
	DESCRIPTION "&<caiWinA3.125>This attribute can be one of the following values: unknown(1) - The agent cannot access all processors and hence cannot determine the HT support. not-supported(2) - The processors architecture is Pentium 4 without HT, Pentium 3 or below. supported-disabled(3) - The processors architecture is Pentium 4 with HT, but only one logical CPU is configured per physical CPU. supported-inactive(4) - The processors architecture is Pentium 4 with HT and two or more logical CPUs are configured per physical CPU, but only one logical CPU is used per physical CPU by the system. supported-active(5) - The processors architecture is Pentium 4 with HT and two or more logical CPUs are configured per physical CPU, and all logical CPUs are used by the system."
	::= { winA3ConfigSysGroup 5 }

winA3ConfigSysPhysicalCpu OBJECT-TYPE
	SYNTAX DisplayString
	ACCESS read-only
	STATUS mandatory
	DESCRIPTION "&<caiWinA3.126>The number of the physical processors on the system. This value equals the number of CPUs displayed in the CPU status table. Exception: If the value of SysHyperThread is supported-active(5), the number of CPUs displayed in the CPU status table equals the number of logical processors."
	::= { winA3ConfigSysGroup 6 }

winA3ConfigSysLogicalCpu OBJECT-TYPE
	SYNTAX DisplayString
	ACCESS read-only
	STATUS mandatory
	DESCRIPTION "&<caiWinA3.127>The number of the logical processors on the system. This value will only be greater than the number of the physical processors if the value of SysHyperThread is supported-inactive(4) or supported-active(5). In the later case, this value equals the number of CPUs displayed in the CPU status table."
	::= { winA3ConfigSysGroup 7 }

winA3ConfigSysLicensedCpu OBJECT-TYPE
	SYNTAX DisplayString
	ACCESS read-only
	STATUS mandatory
	DESCRIPTION "&<caiWinA3.128>The number of processors licensed by the installed OS."
	::= { winA3ConfigSysGroup 8 }

winA3ConfigSysColdStartTime OBJECT-TYPE
	SYNTAX DisplayString
	ACCESS read-only
	STATUS mandatory
	DESCRIPTION "&<caiWinA3.129>The point in time the system was booted."
	::= { winA3ConfigSysGroup 9 }

winA3ConfigSysAutoReboot OBJECT-TYPE
	SYNTAX DisplayString
	ACCESS read-only
	STATUS mandatory
	DESCRIPTION "&<caiWinA3.130>If the value is 1 (true), the system is configured to automatically reboot after a system crash."
	::= { winA3ConfigSysGroup 10 }

--
-- The ConfigCPU Group
--

winA3ConfigCPUPollInterval OBJECT-TYPE
	SYNTAX INTEGER
	ACCESS read-write
	STATUS mandatory
	DESCRIPTION "&<caiWinA3.131>Time, in seconds, between collections of CPU information. Valid range: 30 seconds or greater."
	DEFVAL { 60 }
	::= { winA3ConfigCPUGroup 1 }

winA3ConfigCPUPollMethod OBJECT-TYPE
	SYNTAX INTEGER {
		disabled(1),
		poll-interval-only(2),
		poll-interval-and-query(3),
		query-only(4)
	}
	ACCESS read-write
	STATUS mandatory
	DESCRIPTION "&<caiWinA3.132>Specifies how and when the agent collects CPU information. If set to 1 (disabled), the agent does not retrieve the CPU information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigCPUGroup 2 }

winA3ConfigCPUAggLag OBJECT-TYPE
	SYNTAX INTEGER
	ACCESS read-write
	STATUS mandatory
	DESCRIPTION "&<caiWinA3.133>Default aggregate lag setting for the CPU watcher to add. Specifies the consecutive number of times at which any status is not in the ok state, before the aggregate status changes. This value must be greater than 0."
	DEFVAL { 10 }
	::= { winA3ConfigCPUGroup 3 }

winA3ConfigCPULoadWarnMin OBJECT-TYPE
	SYNTAX DisplayString
	ACCESS read-write
	STATUS mandatory
	DESCRIPTION "&<caiWinA3.134>Default warning minimum threshold, in percent, for the CPU utilization monitoring of the CPU watcher to add. This value represents a declining threshold and must be equal to or greater than 0.0, less than or equal to 100.0, equal to or greater than the critical minimum threshold, but cannot be greater than the warning maximum threshold. A value of -1 disables the evaluation of this threshold."
	DEFVAL { "-1" }
	::= { winA3ConfigCPUGroup 4 }

winA3ConfigCPULoadWarnMax OBJECT-TYPE
	SYNTAX DisplayString
	ACCESS read-write
	STATUS mandatory
	DESCRIPTION "&<caiWinA3.135>Default warning maximum threshold, in percent, for the CPU utilization monitoring of the CPU watcher to add. This value represents a rising threshold and must be equal to or greater than 0.0, less than or equal to 100.0, equal to or greater than the warning minimum threshold, but cannot be greater than the critical maximum threshold. A value of -1 disables the evaluation of this threshold."
	DEFVAL { "70.0" }
	::= { winA3ConfigCPUGroup 5 }

winA3ConfigCPULoadCritMin OBJECT-TYPE
	SYNTAX DisplayString
	ACCESS read-write
	STATUS mandatory
	DESCRIPTION "&<caiWinA3.136>Default critical minimum threshold, in percent, for the CPU utilization monitoring of the CPU watcher to add. This value represents a declining threshold and must be equal to or greater than 0.0, less than or equal to 100.0, but cannot be greater than the warning minimum threshold. A value of -1 disables the evaluation of this threshold."
	DEFVAL { "-1" }
	::= { winA3ConfigCPUGroup 6 }

winA3ConfigCPULoadCritMax OBJECT-TYPE
	SYNTAX DisplayString
	ACCESS read-write
	STATUS mandatory
	DESCRIPTION "&<caiWinA3.137>Default critical maximum threshold, in percent, for the CPU utilization monitoring of the CPU watcher to add. This value represents a rising threshold and must be equal to or greater than 0.0, less than or equal to 100.0, but cannot be less than the warning maximum threshold. A value of -1 disables the evaluation of this threshold."
	DEFVAL { "90.0" }
	::= { winA3ConfigCPUGroup 7 }

winA3ConfigCPULoadMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.138>Default monitor level for the CPU utilization monitoring of the CPU watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 1 }
	::= { winA3ConfigCPUGroup 8 }

winA3ConfigCPUQueueWarn OBJECT-TYPE
	SYNTAX DisplayString
	ACCESS read-write
	STATUS mandatory
	DESCRIPTION "&<caiWinA3.139>Default warning threshold for the CPU queue length monitoring of the CPU watcher to add. This value represents a rising threshold and must be greater than 0.0, but cannot be greater than the critical threshold."
	DEFVAL { "2.0" }
	::= { winA3ConfigCPUGroup 9 }

winA3ConfigCPUQueueCrit OBJECT-TYPE
	SYNTAX DisplayString
	ACCESS read-write
	STATUS mandatory
	DESCRIPTION "&<caiWinA3.140>Default critical threshold for the CPU queue length monitoring of the CPU watcher to add. This value represents a rising threshold and must be greater than 0.0, but cannot be less than the warning threshold."
	DEFVAL { "4.0" }
	::= { winA3ConfigCPUGroup 10 }

winA3ConfigCPUQueueMonitor OBJECT-TYPE
	SYNTAX INTEGER {
		do-not-monitor(1),
		warning-only(2),
		critical-only(3),
		both(4)
	}
	ACCESS read-write
	STATUS mandatory
	DESCRIPTION "&<caiWinA3.141>Default monitor level for the CPU queue length monitoring of the CPU watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { winA3ConfigCPUGroup 11 }

winA3ConfigCPULossAction OBJECT-TYPE
	SYNTAX INTEGER {
		remove(1),
		up(2),
		down-warning(3),
		down-critical(4)
	}
	ACCESS read-write
	STATUS mandatory
	DESCRIPTION "&<caiWinA3.142>Default loss action for the CPU watcher to add. Specifies the action to take if the monitored CPU is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigCPUGroup 12 }

--
-- The ConfigMem Group
--

winA3ConfigMemPollInterval OBJECT-TYPE
	SYNTAX INTEGER
	ACCESS read-write
	STATUS mandatory
	DESCRIPTION "&<caiWinA3.143>Time, in seconds, between collections of memory information. Valid range: 30 seconds or greater."
	DEFVAL { 60 }
	::= { winA3ConfigMemGroup 1 }

winA3ConfigMemPollMethod OBJECT-TYPE
	SYNTAX INTEGER {
		disabled(1),
		poll-interval-only(2),
		poll-interval-and-query(3),
		query-only(4)
	}
	ACCESS read-write
	STATUS mandatory
	DESCRIPTION "&<caiWinA3.144>Specifies how and when the agent collects memory information. If set to 1 (disabled), the agent does not retrieve the memory information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigMemGroup 2 }

--
-- The ConfigLVol Group
--

winA3ConfigLVolPollInterval OBJECT-TYPE
	SYNTAX INTEGER
	ACCESS read-write
	STATUS mandatory
	DESCRIPTION "&<caiWinA3.145>Time, in seconds, between collections of logical volume information. Valid range: 30 seconds or greater."
	DEFVAL { 300 }
	::= { winA3ConfigLVolGroup 1 }

winA3ConfigLVolPollMethod OBJECT-TYPE
	SYNTAX INTEGER {
		disabled(1),
		poll-interval-only(2),
		poll-interval-and-query(3),
		query-only(4)
	}
	ACCESS read-write
	STATUS mandatory
	DESCRIPTION "&<caiWinA3.146>Specifies how and when the agent collects logical volume information. If set to 1 (disabled), the agent does not retrieve the logical volume information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigLVolGroup 2 }

winA3ConfigLVolAutoPollInterval OBJECT-TYPE
	SYNTAX INTEGER
	ACCESS read-write
	STATUS mandatory
	DESCRIPTION "&<caiWinA3.147>Time, in minutes, between the processing of the logical volume auto watchers. Valid range: -1 (suspended), 30 minutes or greater."
	DEFVAL { 60 }
	::= { winA3ConfigLVolGroup 3 }

winA3ConfigLVolName OBJECT-TYPE
	SYNTAX DisplayString
	ACCESS read-write
	STATUS mandatory
	DESCRIPTION "&<caiWinA3.148>Name of the logical volume for which to add or remove a watcher. A fully qualified logical volume name can be in drive letter format (e.g. C:) or in GUID format (e.g. Volume{2ab0a340-997c-11d6-9d96-00b0d09b7d72}). If used as a filter element for auto discovery, this name can be a regular expression (case-insensitive). In this case, it restricts the resources to be searched for during an auto discovery run."
	::= { winA3ConfigLVolGroup 4 }

winA3ConfigLVolMounts OBJECT-TYPE
	SYNTAX DisplayString
	ACCESS read-write
	STATUS mandatory
	DESCRIPTION "&<caiWinA3.149>A list of the mount points (seperated by pipe signs), where this logical volume is mounted on. This attribute is only used as a filter element for auto discovery and can be a regular expression (case-insensitive). It restricts the resources to be searched for during an auto discovery run."
	DEFVAL { ".*" }
	::= { winA3ConfigLVolGroup 5 }

winA3ConfigLVolInfo OBJECT-TYPE
	SYNTAX DisplayString
	ACCESS read-write
	STATUS mandatory
	DESCRIPTION "&<caiWinA3.150>Information about the label, the filesystem (e.g. NTFS) and the alternate name (e.g. used in performance monitor) of the logical volume. This string has the format 'Label (FSys) (Alternate)'. 'Label' resp. 'FSys' are set to '-', if no label is defined, if the logical volume is not formatted or if it currently is in a clustered-passive state. 'Alternate' may be missing if not applicable (typically if the logical volume can be adressed by a drive letter). This attribute is only used as a filter element for auto discovery and can be a regular expression (case-insensitive). It restricts the resources to be searched for during an auto discovery run."
	DEFVAL { ".*" }
	::= { winA3ConfigLVolGroup 6 }

winA3ConfigLVolClusterType OBJECT-TYPE
	SYNTAX INTEGER {
		not-clustered(1),
		clustered-active(2),
		clustered-passive(3),
		any(4)
	}
	ACCESS read-write
	STATUS mandatory
	DESCRIPTION "&<caiWinA3.151>Cluster type of the logical volume to be searched for during an auto discovery run. This attribute is only used when adding an auto watcher. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { winA3ConfigLVolGroup 7 }

winA3ConfigLVolDescription OBJECT-TYPE
	SYNTAX DisplayString
	ACCESS read-write
	STATUS mandatory
	DESCRIPTION "&<caiWinA3.152>Default description for the logical volume watcher to add."
	::= { winA3ConfigLVolGroup 8 }

winA3ConfigLVolAggLag OBJECT-TYPE
	SYNTAX INTEGER
	ACCESS read-write
	STATUS mandatory
	DESCRIPTION "&<caiWinA3.153>Default aggregate lag setting for the logical volume watcher to add. Specifies the consecutive number of times at which any status is not in the ok state, before the aggregate status changes. This value must be greater than 0."
	DEFVAL { 3 }
	::= { winA3ConfigLVolGroup 9 }

winA3ConfigLVolSizeWarn OBJECT-TYPE
	SYNTAX DisplayString
	ACCESS read-write
	STATUS mandatory
	DESCRIPTION "&<caiWinA3.154>Default warning threshold, in megabytes, for the logical volume utilization monitoring of the logical volume watcher to add. The active warning threshold is derived from this value and represents a rising threshold. The derived value must be greater than 0.0, less than or equal to the total value (maximum capacity) of the monitored resource as specified in winA3StatusLVolSizeTotal, but cannot be greater than the active critical threshold. These constraints will be maintained by the agent during all configuration actions. The threshold can be specified as either an absolute value (n) or a percentage (n%). It can also be specified as the absolute value left free (nF). The value of winA3StatusLVolSizeTotal will be the reference value for n% and nF notations."
	DEFVAL { "85.0%" }
	::= { winA3ConfigLVolGroup 10 }

winA3ConfigLVolSizeCrit OBJECT-TYPE
	SYNTAX DisplayString
	ACCESS read-write
	STATUS mandatory
	DESCRIPTION "&<caiWinA3.155>Default critical threshold, in megabytes, for the logical volume utilization monitoring of the logical volume watcher to add. The active critical threshold is derived from this value and represents a rising threshold. The derived value must be greater than 0.0, less than or equal to the total value (maximum capacity) of the monitored resource as specified in winA3StatusLVolSizeTotal, but cannot be less than the active warning threshold. These constraints will be maintained by the agent during all configuration actions. The threshold can be specified as either an absolute value (n) or a percentage (n%). It can also be specified as the absolute value left free (nF). The value of winA3StatusLVolSizeTotal will be the reference value for n% and nF notations."
	DEFVAL { "95.0%" }
	::= { winA3ConfigLVolGroup 11 }

winA3ConfigLVolSizeMonitor OBJECT-TYPE
	SYNTAX INTEGER {
		do-not-monitor(1),
		warning-only(2),
		critical-only(3),
		both(4)
	}
	ACCESS read-write
	STATUS mandatory
	DESCRIPTION "&<caiWinA3.156>Default monitor level for the logical volume utilization monitoring of the logical volume watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigLVolGroup 12 }

winA3ConfigLVolSizeDWarn OBJECT-TYPE
	SYNTAX DisplayString
	ACCESS read-write
	STATUS mandatory
	DESCRIPTION "&<caiWinA3.157>Default warning threshold, in megabytes, for the delta logical volume utilization monitoring of the logical volume watcher to add. The active warning threshold is derived from this value and represents a rising threshold. The derived value must be greater than 0.0, less than or equal to the total value (maximum capacity) of the monitored resource as specified in winA3StatusLVolSizeTotal, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of winA3StatusLVolSizeTotal will be the reference value for n% notations."
	DEFVAL { "3.0%" }
	::= { winA3ConfigLVolGroup 13 }

winA3ConfigLVolSizeDCrit OBJECT-TYPE
	SYNTAX DisplayString
	ACCESS read-write
	STATUS mandatory
	DESCRIPTION "&<caiWinA3.158>Default critical threshold, in megabytes, for the delta logical volume utilization monitoring of the logical volume watcher to add. The active critical threshold is derived from this value and represents a rising threshold. The derived value must be greater than 0.0, less than or equal to the total value (maximum capacity) of the monitored resource as specified in winA3StatusLVolSizeTotal, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of winA3StatusLVolSizeTotal will be the reference value for n% notations."
	DEFVAL { "5.0%" }
	::= { winA3ConfigLVolGroup 14 }

winA3ConfigLVolSizeDMonitor OBJECT-TYPE
	SYNTAX INTEGER {
		do-not-monitor(1),
		warning-only(2),
		critical-only(3),
		both(4)
	}
	ACCESS read-write
	STATUS mandatory
	DESCRIPTION "&<caiWinA3.159>Default monitor level for the delta logical volume utilization monitoring of the logical volume watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigLVolGroup 15 }

winA3ConfigLVolMiscMode OBJECT-TYPE
	SYNTAX INTEGER {
		throughput(1),
		queue-length(2)
	}
	ACCESS read-write
	STATUS mandatory
	DESCRIPTION "&<caiWinA3.160>This attribute determines which value (throughput or queue-length) should be calculated by this metric. The option throughput(1) is expressed in KBytes/sec. The option queue-length(2) is expressed as an average number."
	DEFVAL { 2 }
	::= { winA3ConfigLVolGroup 16 }

winA3ConfigLVolMiscWarn OBJECT-TYPE
	SYNTAX DisplayString
	ACCESS read-write
	STATUS mandatory
	DESCRIPTION "&<caiWinA3.161>Default warning threshold for the miscellaneous data monitoring of the logical volume watcher to add. This value represents a rising threshold and must be greater than 0.0, but cannot be greater than the critical threshold."
	DEFVAL { "4.0" }
	::= { winA3ConfigLVolGroup 17 }

winA3ConfigLVolMiscCrit OBJECT-TYPE
	SYNTAX DisplayString
	ACCESS read-write
	STATUS mandatory
	DESCRIPTION "&<caiWinA3.162>Default critical threshold for the miscellaneous data monitoring of the logical volume watcher to add. This value represents a rising threshold and must be greater than 0.0, but cannot be less than the warning threshold."
	DEFVAL { "6.0" }
	::= { winA3ConfigLVolGroup 18 }

winA3ConfigLVolMiscMonitor OBJECT-TYPE
	SYNTAX INTEGER {
		do-not-monitor(1),
		warning-only(2),
		critical-only(3),
		both(4)
	}
	ACCESS read-write
	STATUS mandatory
	DESCRIPTION "&<caiWinA3.163>Default monitor level for the miscellaneous data monitoring of the logical volume watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigLVolGroup 19 }

winA3ConfigLVolFragmtMode OBJECT-TYPE
	SYNTAX INTEGER {
		file-fragmentation(1),
		total-fragmentation(2)
	}
	ACCESS read-write
	STATUS mandatory
	DESCRIPTION "&<caiWinA3.164>This attribute determines which mode of fragmentation (file or total) should be calculated. The option total-fragmentation(2) is only supported on Windows 2003/XP."
	DEFVAL { 1 }
	::= { winA3ConfigLVolGroup 20 }

winA3ConfigLVolFragmtInterval OBJECT-TYPE
	SYNTAX INTEGER
	ACCESS read-write
	STATUS mandatory
	DESCRIPTION "&<caiWinA3.165>Time, in hours, between collections of fragmentation information (always triggered by the next polling or a get request). The agent will not calculate the fragmentation every standard poll interval, because it is an expensive task. Valid range: 1 hour or greater, or -1 to disable the fragmentation calculation."
	DEFVAL { 8 }
	::= { winA3ConfigLVolGroup 21 }

winA3ConfigLVolFragmtWarn OBJECT-TYPE
	SYNTAX INTEGER
	ACCESS read-write
	STATUS mandatory
	DESCRIPTION "&<caiWinA3.166>Default warning threshold, in percent, for the fragmentation monitoring of the logical volume watcher to add. This value represents a rising threshold and must be greater than 0, less than or equal to 100, but cannot be greater than the critical threshold."
	DEFVAL { 35 }
	::= { winA3ConfigLVolGroup 22 }

winA3ConfigLVolFragmtCrit OBJECT-TYPE
	SYNTAX INTEGER
	ACCESS read-write
	STATUS mandatory
	DESCRIPTION "&<caiWinA3.167>Default critical threshold, in percent, for the fragmentation monitoring of the logical volume watcher to add. This value represents a rising threshold and must be greater than 0, less than or equal to 100, but cannot be less than the warning threshold."
	DEFVAL { 45 }
	::= { winA3ConfigLVolGroup 23 }

winA3ConfigLVolFragmtMonitor OBJECT-TYPE
	SYNTAX INTEGER {
		do-not-monitor(1),
		warning-only(2),
		critical-only(3),
		both(4)
	}
	ACCESS read-write
	STATUS mandatory
	DESCRIPTION "&<caiWinA3.168>Default monitor level for the fragmentation monitoring of the logical volume watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { winA3ConfigLVolGroup 24 }

winA3ConfigLVolLossAction OBJECT-TYPE
	SYNTAX INTEGER {
		remove(1),
		up(2),
		down-warning(3),
		down-critical(4)
	}
	ACCESS read-write
	STATUS mandatory
	DESCRIPTION "&<caiWinA3.169>Default loss action for the logical volume watcher to add. Specifies the action to take if the monitored logical volume is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigLVolGroup 25 }

winA3ConfigLVolAutoTableWatcherName OBJECT-TYPE
	SYNTAX DisplayString
	ACCESS read-write
	STATUS mandatory
	DESCRIPTION "&<caiWinA3.170>Name of the logical volume auto watcher to add or remove."
	::= { winA3ConfigLVolGroup 26 }

winA3ConfigLVolAutoTableWatcherMatchType OBJECT-TYPE
	SYNTAX INTEGER {
		positive(1),
		negative(2)
	}
	ACCESS read-write
	STATUS mandatory
	DESCRIPTION "&<caiWinA3.171>Default search algorithm for the logical volume auto watcher to add. The filter is the logical AND of all attributes used to identify or otherwise narrow down resources. If set to 1 (positive), the agent searches for logical volume resources that match the filter. If set to 2 (negative), the agent searches for logical volume resources that do not match the filter."
	DEFVAL { 1 }
	::= { winA3ConfigLVolGroup 27 }

winA3ConfigLVolAutoTableWatcherLimit OBJECT-TYPE
	SYNTAX INTEGER
	ACCESS read-write
	STATUS mandatory
	DESCRIPTION "&<caiWinA3.172>Default minimum number of matches that causes a lock of the logical volume auto watcher to add."
	DEFVAL { 100 }
	::= { winA3ConfigLVolGroup 28 }

winA3ConfigLVolButton OBJECT-TYPE
	SYNTAX INTEGER {
		none(1),
		add(2),
		remove(3),
		add-auto(4),
		remove-auto(5)
	}
	ACCESS read-write
	STATUS mandatory
	DESCRIPTION "&<caiWinA3.173>This attribute is used to add or remove the logical volume watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigLVolGroup 29 }

winA3ConfigLVolAutoCount OBJECT-TYPE
	SYNTAX INTEGER
	ACCESS read-only
	STATUS mandatory
	DESCRIPTION "&<caiWinA3.174>Number of auto watchers in the logical volume auto configuration table."
	::= { winA3ConfigLVolGroup 30 }

winA3ConfigLVolAutoLocked OBJECT-TYPE
	SYNTAX INTEGER
	ACCESS read-only
	STATUS mandatory
	DESCRIPTION "&<caiWinA3.175>Number of auto watchers in the logical volume auto configuration table which are currently locked."
	::= { winA3ConfigLVolGroup 31 }

winA3ConfigLVolAutoTable OBJECT-TYPE
	SYNTAX SEQUENCE OF WinA3ConfigLVolAutoEntry
	ACCESS not-accessible
	STATUS mandatory
	DESCRIPTION "&<caiWinA3.176>Configuration table containing a list of logical volume auto watchers."
	::= { winA3ConfigLVolGroup 32 }

winA3ConfigLVolAutoEntry OBJECT-TYPE
	SYNTAX WinA3ConfigLVolAutoEntry
	ACCESS not-accessible
	STATUS mandatory
	DESCRIPTION "&<caiWinA3.177>Entry in the logical volume auto watcher configuration table."
	INDEX {
		winA3ConfigLVolAutoWatcherName
	}
	::= { winA3ConfigLVolAutoTable 1 }

WinA3ConfigLVolAutoEntry ::= SEQUENCE {
	winA3ConfigLVolAutoWatcherName DisplayString,
	winA3ConfigLVolAutoName DisplayString,
	winA3ConfigLVolAutoMounts DisplayString,
	winA3ConfigLVolAutoInfo DisplayString,
	winA3ConfigLVolAutoClusterType INTEGER,
	winA3ConfigLVolAutoDescription DisplayString,
	winA3ConfigLVolAutoWatcherMatchType INTEGER,
	winA3ConfigLVolAutoWatcherLimit INTEGER,
	winA3ConfigLVolAutoWatcherLastMatched INTEGER,
	winA3ConfigLVolAutoAggLag INTEGER,
	winA3ConfigLVolAutoSizeWarn DisplayString,
	winA3ConfigLVolAutoSizeCrit DisplayString,
	winA3ConfigLVolAutoSizeMonitor INTEGER,
	winA3ConfigLVolAutoSizeDWarn DisplayString,
	winA3ConfigLVolAutoSizeDCrit DisplayString,
	winA3ConfigLVolAutoSizeDMonitor INTEGER,
	winA3ConfigLVolAutoMiscMode INTEGER,
	winA3ConfigLVolAutoMiscWarn DisplayString,
	winA3ConfigLVolAutoMiscCrit DisplayString,
	winA3ConfigLVolAutoMiscMonitor INTEGER,
	winA3ConfigLVolAutoFragmtMode INTEGER,
	winA3ConfigLVolAutoFragmtInterval INTEGER,
	winA3ConfigLVolAutoFragmtWarn INTEGER,
	winA3ConfigLVolAutoFragmtCrit INTEGER,
	winA3ConfigLVolAutoFragmtMonitor INTEGER,
	winA3ConfigLVolAutoLossAction INTEGER,
	winA3ConfigLVolAutoButton INTEGER
}

winA3ConfigLVolAutoWatcherName OBJECT-TYPE
	SYNTAX DisplayString
	ACCESS read-only
	STATUS mandatory
	DESCRIPTION "&<caiWinA3.178>Name of the logical volume auto watcher."
	::= { winA3ConfigLVolAutoEntry 1 }

winA3ConfigLVolAutoName OBJECT-TYPE
	SYNTAX DisplayString
	ACCESS read-write
	STATUS mandatory
	DESCRIPTION "&<caiWinA3.179>Name of the logical volume to be searched for during an auto discovery run. A fully qualified logical volume name can be in drive letter format (e.g. C:) or in GUID format (e.g. Volume{2ab0a340-997c-11d6-9d96-00b0d09b7d72}). This name is used as a filter element for auto discovery and can be a regular expression (case-insensitive). It restricts the resources to be searched for during an auto discovery run."
	::= { winA3ConfigLVolAutoEntry 2 }

winA3ConfigLVolAutoMounts OBJECT-TYPE
	SYNTAX DisplayString
	ACCESS read-write
	STATUS mandatory
	DESCRIPTION "&<caiWinA3.180>A list of the mount points (seperated by pipe signs), where this logical volume is mounted on. This attribute is used as a filter element for auto discovery and can be a regular expression (case-insensitive). It restricts the resources to be searched for during an auto discovery run."
	::= { winA3ConfigLVolAutoEntry 3 }

winA3ConfigLVolAutoInfo OBJECT-TYPE
	SYNTAX DisplayString
	ACCESS read-write
	STATUS mandatory
	DESCRIPTION "&<caiWinA3.181>Information about the label, the filesystem (e.g. NTFS) and the alternate name (e.g. used in performance monitor) of the logical volume. This string has the format 'Label (FSys) (Alternate)'. 'Label' resp. 'FSys' are set to '-', if no label is defined, if the logical volume is not formatted or if it currently is in a clustered-passive state. 'Alternate' may be missing if not applicable (typically if the logical volume can be adressed by a drive letter). This attribute is used as a filter element for auto discovery and can be a regular expression (case-insensitive). It restricts the resources to be searched for during an auto discovery run."
	::= { winA3ConfigLVolAutoEntry 4 }

winA3ConfigLVolAutoClusterType OBJECT-TYPE
	SYNTAX INTEGER {
		not-clustered(1),
		clustered-active(2),
		clustered-passive(3),
		any(4)
	}
	ACCESS read-write
	STATUS mandatory
	DESCRIPTION "&<caiWinA3.182>Cluster type of the logical volume to be searched for during an auto discovery run. If set to 1 (not-clustered), the search is restricted to not-clustered resources only. If set to 2 (clustered-active), the search is restricted to clustered-active resources only. If set to 3 (clustered-passive), the search is restricted to clustered-passive resources only. If set to 4 (any), the cluster type does not affect the search."
	DEFVAL { 0 }
	::= { winA3ConfigLVolAutoEntry 5 }

winA3ConfigLVolAutoDescription OBJECT-TYPE
	SYNTAX DisplayString
	ACCESS read-write
	STATUS mandatory
	DESCRIPTION "&<caiWinA3.183>Current description for the logical volume auto watcher."
	::= { winA3ConfigLVolAutoEntry 6 }

winA3ConfigLVolAutoWatcherMatchType OBJECT-TYPE
	SYNTAX INTEGER {
		positive(1),
		negative(2)
	}
	ACCESS read-write
	STATUS mandatory
	DESCRIPTION "&<caiWinA3.184>Current search algorithm for the logical volume auto watcher. The filter is the logical AND of all attributes used to identify or otherwise narrow down resources. If set to 1 (positive), the agent searches for logical volume resources that match the filter. If set to 2 (negative), the agent searches for logical volume resources that do not match the filter."
	DEFVAL { 0 }
	::= { winA3ConfigLVolAutoEntry 7 }

winA3ConfigLVolAutoWatcherLimit OBJECT-TYPE
	SYNTAX INTEGER
	ACCESS read-write
	STATUS mandatory
	DESCRIPTION "&<caiWinA3.185>Current minimum number of matches that causes the logical volume auto watcher to be locked."
	::= { winA3ConfigLVolAutoEntry 8 }

winA3ConfigLVolAutoWatcherLastMatched OBJECT-TYPE
	SYNTAX INTEGER
	ACCESS read-only
	STATUS mandatory
	DESCRIPTION "&<caiWinA3.186>Number of matches for the last logical volume auto discovery run."
	::= { winA3ConfigLVolAutoEntry 9 }

winA3ConfigLVolAutoAggLag OBJECT-TYPE
	SYNTAX INTEGER
	ACCESS read-write
	STATUS mandatory
	DESCRIPTION "&<caiWinA3.187>Current lag setting for the logical volume auto watcher. Specifies the consecutive number of times at which any status is not in the ok state, before the aggregate status changes. This value must be greater than 0."
	::= { winA3ConfigLVolAutoEntry 10 }

winA3ConfigLVolAutoSizeWarn OBJECT-TYPE
	SYNTAX DisplayString
	ACCESS read-write
	STATUS mandatory
	DESCRIPTION "&<caiWinA3.188>Default warning threshold, in megabytes, for the logical volume utilization monitoring of any logical volume watcher created by the auto watcher. The active warning threshold is derived from this value and represents a rising threshold. The derived value must be greater than 0.0, less than or equal to the total value (maximum capacity) of the monitored resource as specified in winA3StatusLVolSizeTotal, but cannot be greater than the active critical threshold. These constraints will be maintained by the agent during all configuration actions. The threshold can be specified as either an absolute value (n) or a percentage (n%). It can also be specified as the absolute value left free (nF). The value of winA3StatusLVolSizeTotal will be the reference value for n% and nF notations."
	::= { winA3ConfigLVolAutoEntry 11 }

winA3ConfigLVolAutoSizeCrit OBJECT-TYPE
	SYNTAX DisplayString
	ACCESS read-write
	STATUS mandatory
	DESCRIPTION "&<caiWinA3.189>Default critical threshold, in megabytes, for the logical volume utilization monitoring of any logical volume watcher created by the auto watcher. The active critical threshold is derived from this value and represents a rising threshold. The derived value must be greater than 0.0, less than or equal to the total value (maximum capacity) of the monitored resource as specified in winA3StatusLVolSizeTotal, but cannot be less than the active warning threshold. These constraints will be maintained by the agent during all configuration actions. The threshold can be specified as either an absolute value (n) or a percentage (n%). It can also be specified as the absolute value left free (nF). The value of winA3StatusLVolSizeTotal will be the reference value for n% and nF notations."
	::= { winA3ConfigLVolAutoEntry 12 }

winA3ConfigLVolAutoSizeMonitor OBJECT-TYPE
	SYNTAX INTEGER {
		do-not-monitor(1),
		warning-only(2),
		critical-only(3),
		both(4)
	}
	ACCESS read-write
	STATUS mandatory
	DESCRIPTION "&<caiWinA3.190>Default monitor level for the logical volume utilization monitoring of any logical volume watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigLVolAutoEntry 13 }

winA3ConfigLVolAutoSizeDWarn OBJECT-TYPE
	SYNTAX DisplayString
	ACCESS read-write
	STATUS mandatory
	DESCRIPTION "&<caiWinA3.191>Default warning threshold, in megabytes, for the delta logical volume utilization monitoring of any logical volume watcher created by the auto watcher. The active warning threshold is derived from this value and represents a rising threshold. The derived value must be greater than 0.0, less than or equal to the total value (maximum capacity) of the monitored resource as specified in winA3StatusLVolSizeTotal, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of winA3StatusLVolSizeTotal will be the reference value for n% notations."
	::= { winA3ConfigLVolAutoEntry 14 }

winA3ConfigLVolAutoSizeDCrit OBJECT-TYPE
	SYNTAX DisplayString
	ACCESS read-write
	STATUS mandatory
	DESCRIPTION "&<caiWinA3.192>Default critical threshold, in megabytes, for the delta logical volume utilization monitoring of any logical volume watcher created by the auto watcher. The active critical threshold is derived from this value and represents a rising threshold. The derived value must be greater than 0.0, less than or equal to the total value (maximum capacity) of the monitored resource as specified in winA3StatusLVolSizeTotal, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of winA3StatusLVolSizeTotal will be the reference value for n% notations."
	::= { winA3ConfigLVolAutoEntry 15 }

winA3ConfigLVolAutoSizeDMonitor OBJECT-TYPE
	SYNTAX INTEGER {
		do-not-monitor(1),
		warning-only(2),
		critical-only(3),
		both(4)
	}
	ACCESS read-write
	STATUS mandatory
	DESCRIPTION "&<caiWinA3.193>Default monitor level for the delta logical volume utilization monitoring of any logical volume watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigLVolAutoEntry 16 }

winA3ConfigLVolAutoMiscMode OBJECT-TYPE
	SYNTAX INTEGER {
		throughput(1),
		queue-length(2)
	}
	ACCESS read-write
	STATUS mandatory
	DESCRIPTION "&<caiWinA3.194>This attribute determines which value (throughput or queue-length) should be calculated by this metric. The option throughput(1) is expressed in KBytes/sec. The option queue-length(2) is expressed as an average number."
	DEFVAL { 0 }
	::= { winA3ConfigLVolAutoEntry 17 }

winA3ConfigLVolAutoMiscWarn OBJECT-TYPE
	SYNTAX DisplayString
	ACCESS read-write
	STATUS mandatory
	DESCRIPTION "&<caiWinA3.195>Default warning threshold for the miscellaneous data monitoring of any logical volume watcher created by the auto watcher. This value represents a rising threshold and must be greater than 0.0, but cannot be greater than the critical threshold."
	::= { winA3ConfigLVolAutoEntry 18 }

winA3ConfigLVolAutoMiscCrit OBJECT-TYPE
	SYNTAX DisplayString
	ACCESS read-write
	STATUS mandatory
	DESCRIPTION "&<caiWinA3.196>Default critical threshold for the miscellaneous data monitoring of any logical volume watcher created by the auto watcher. This value represents a rising threshold and must be greater than 0.0, but cannot be less than the warning threshold."
	::= { winA3ConfigLVolAutoEntry 19 }

winA3ConfigLVolAutoMiscMonitor OBJECT-TYPE
	SYNTAX INTEGER {
		do-not-monitor(1),
		warning-only(2),
		critical-only(3),
		both(4)
	}
	ACCESS read-write
	STATUS mandatory
	DESCRIPTION "&<caiWinA3.197>Default monitor level for the miscellaneous data monitoring of any logical volume watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigLVolAutoEntry 20 }

winA3ConfigLVolAutoFragmtMode OBJECT-TYPE
	SYNTAX INTEGER {
		file-fragmentation(1),
		total-fragmentation(2)
	}
	ACCESS read-write
	STATUS mandatory
	DESCRIPTION "&<caiWinA3.198>This attribute determines which mode of fragmentation (file or total) should be calculated. The option total-fragmentation(2) is only supported on Windows 2003/XP."
	DEFVAL { 0 }
	::= { winA3ConfigLVolAutoEntry 21 }

winA3ConfigLVolAutoFragmtInterval OBJECT-TYPE
	SYNTAX INTEGER
	ACCESS read-write
	STATUS mandatory
	DESCRIPTION "&<caiWinA3.199>Time, in hours, between collections of fragmentation information (always triggered by the next polling or a get request). The agent will not calculate the fragmentation every standard poll interval, because it is an expensive task. Valid range: 1 hour or greater, or -1 to disable the fragmentation calculation."
	::= { winA3ConfigLVolAutoEntry 22 }

winA3ConfigLVolAutoFragmtWarn OBJECT-TYPE
	SYNTAX INTEGER
	ACCESS read-write
	STATUS mandatory
	DESCRIPTION "&<caiWinA3.200>Default warning threshold, in percent, for the fragmentation monitoring of any logical volume watcher created by the auto watcher. This value represents a rising threshold and must be greater than 0, less than or equal to 100, but cannot be greater than the critical threshold."
	::= { winA3ConfigLVolAutoEntry 23 }

winA3ConfigLVolAutoFragmtCrit OBJECT-TYPE
	SYNTAX INTEGER
	ACCESS read-write
	STATUS mandatory
	DESCRIPTION "&<caiWinA3.201>Default critical threshold, in percent, for the fragmentation monitoring of any logical volume watcher created by the auto watcher. This value represents a rising threshold and must be greater than 0, less than or equal to 100, but cannot be less than the warning threshold."
	::= { winA3ConfigLVolAutoEntry 24 }

winA3ConfigLVolAutoFragmtMonitor OBJECT-TYPE
	SYNTAX INTEGER {
		do-not-monitor(1),
		warning-only(2),
		critical-only(3),
		both(4)
	}
	ACCESS read-write
	STATUS mandatory
	DESCRIPTION "&<caiWinA3.202>Default monitor level for the fragmentation monitoring of any logical volume watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigLVolAutoEntry 25 }

winA3ConfigLVolAutoLossAction OBJECT-TYPE
	SYNTAX INTEGER {
		remove(1),
		up(2),
		down-warning(3),
		down-critical(4)
	}
	ACCESS read-write
	STATUS mandatory
	DESCRIPTION "&<caiWinA3.203>Default loss action for any logical volume watcher created by the auto watcher. Specifies the action to take if the monitored logical volume is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3ConfigLVolAutoEntry 26 }

winA3ConfigLVolAutoButton OBJECT-TYPE
	SYNTAX INTEGER {
		active(1),
		remove(2),
		locked(3)
	}
	ACCESS read-write
	STATUS mandatory
	DESCRIPTION "&<caiWinA3.204>This attribute is used to enable/disable or remove the logical volume auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigLVolAutoEntry 27 }

--
-- The ConfigMnt Group
--

winA3ConfigMntPollInterval OBJECT-TYPE
	SYNTAX INTEGER
	ACCESS read-write
	STATUS mandatory
	DESCRIPTION "&<caiWinA3.205>Time, in seconds, between collections of mount information. Valid range: 30 seconds or greater."
	DEFVAL { 120 }
	::= { winA3ConfigMntGroup 1 }

winA3ConfigMntPollMethod OBJECT-TYPE
	SYNTAX INTEGER {
		disabled(1),
		poll-interval-only(2),
		poll-interval-and-query(3),
		query-only(4)
	}
	ACCESS read-write
	STATUS mandatory
	DESCRIPTION "&<caiWinA3.206>Specifies how and when the agent collects mount information. If set to 1 (disabled), the agent does not retrieve the mount information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigMntGroup 2 }

winA3ConfigMntAutoPollInterval OBJECT-TYPE
	SYNTAX INTEGER
	ACCESS read-write
	STATUS mandatory
	DESCRIPTION "&<caiWinA3.207>Time, in minutes, between the processing of the mount auto watchers. Valid range: -1 (suspended), 30 minutes or greater."
	DEFVAL { 60 }
	::= { winA3ConfigMntGroup 3 }

winA3ConfigMntName OBJECT-TYPE
	SYNTAX DisplayString
	ACCESS read-write
	STATUS mandatory
	DESCRIPTION "&<caiWinA3.208>Name of the mount for which to add or remove a watcher. If used as a filter element for auto discovery, this name can be a regular expression (case-insensitive). In this case, it restricts the resources to be searched for during an auto discovery run."
	::= { winA3ConfigMntGroup 4 }

winA3ConfigMntTarget OBJECT-TYPE
	SYNTAX DisplayString
	ACCESS read-write
	STATUS mandatory
	DESCRIPTION "&<caiWinA3.209>The name of the logical volume currently mounted by this mount. This attribute is only used as a filter element for auto discovery and can be a regular expression (case-insensitive). It restricts the resources to be searched for during an auto discovery run."
	DEFVAL { ".*" }
	::= { winA3ConfigMntGroup 5 }

winA3ConfigMntClusterType OBJECT-TYPE
	SYNTAX INTEGER {
		not-clustered(1),
		clustered-active(2),
		clustered-passive(3),
		any(4)
	}
	ACCESS read-write
	STATUS mandatory
	DESCRIPTION "&<caiWinA3.210>Cluster type of the mount to be searched for during an auto discovery run. This attribute is only used when adding an auto watcher. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { winA3ConfigMntGroup 6 }

winA3ConfigMntDescription OBJECT-TYPE
	SYNTAX DisplayString
	ACCESS read-write
	STATUS mandatory
	DESCRIPTION "&<caiWinA3.211>Default description for the mount watcher to add."
	::= { winA3ConfigMntGroup 7 }

winA3ConfigMntAggLag OBJECT-TYPE
	SYNTAX INTEGER
	ACCESS read-write
	STATUS mandatory
	DESCRIPTION "&<caiWinA3.212>Default aggregate lag setting for the mount watcher to add. Specifies the consecutive number of times at which any status is not in the ok state, before the aggregate status changes. This value must be greater than 0."
	DEFVAL { 1 }
	::= { winA3ConfigMntGroup 8 }

winA3ConfigMntTargetMonitor OBJECT-TYPE
	SYNTAX INTEGER {
		do-not-monitor(1),
		down-warning(2),
		down-critical(3)
	}
	ACCESS read-write
	STATUS mandatory
	DESCRIPTION "&<caiWinA3.213>Default monitor level for the target monitoring of the mount watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigMntGroup 9 }

winA3ConfigMntLossAction OBJECT-TYPE
	SYNTAX INTEGER {
		remove(1),
		up(2),
		down-warning(3),
		down-critical(4)
	}
	ACCESS read-write
	STATUS mandatory
	DESCRIPTION "&<caiWinA3.214>Default loss action for the mount watcher to add. Specifies the action to take if the monitored mount is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigMntGroup 10 }

winA3ConfigMntAutoTableWatcherName OBJECT-TYPE
	SYNTAX DisplayString
	ACCESS read-write
	STATUS mandatory
	DESCRIPTION "&<caiWinA3.215>Name of the mount auto watcher to add or remove."
	::= { winA3ConfigMntGroup 11 }

winA3ConfigMntAutoTableWatcherMatchType OBJECT-TYPE
	SYNTAX INTEGER {
		positive(1),
		negative(2)
	}
	ACCESS read-write
	STATUS mandatory
	DESCRIPTION "&<caiWinA3.216>Default search algorithm for the mount auto watcher to add. The filter is the logical AND of all attributes used to identify or otherwise narrow down resources. If set to 1 (positive), the agent searches for mount resources that match the filter. If set to 2 (negative), the agent searches for mount resources that do not match the filter."
	DEFVAL { 1 }
	::= { winA3ConfigMntGroup 12 }

winA3ConfigMntAutoTableWatcherLimit OBJECT-TYPE
	SYNTAX INTEGER
	ACCESS read-write
	STATUS mandatory
	DESCRIPTION "&<caiWinA3.217>Default minimum number of matches that causes a lock of the mount auto watcher to add."
	DEFVAL { 100 }
	::= { winA3ConfigMntGroup 13 }

winA3ConfigMntButton OBJECT-TYPE
	SYNTAX INTEGER {
		none(1),
		add(2),
		remove(3),
		add-auto(4),
		remove-auto(5)
	}
	ACCESS read-write
	STATUS mandatory
	DESCRIPTION "&<caiWinA3.218>This attribute is used to add or remove the mount watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigMntGroup 14 }

winA3ConfigMntAutoCount OBJECT-TYPE
	SYNTAX INTEGER
	ACCESS read-only
	STATUS mandatory
	DESCRIPTION "&<caiWinA3.219>Number of auto watchers in the mount auto configuration table."
	::= { winA3ConfigMntGroup 15 }

winA3ConfigMntAutoLocked OBJECT-TYPE
	SYNTAX INTEGER
	ACCESS read-only
	STATUS mandatory
	DESCRIPTION "&<caiWinA3.220>Number of auto watchers in the mount auto configuration table which are currently locked."
	::= { winA3ConfigMntGroup 16 }

winA3ConfigMntAutoTable OBJECT-TYPE
	SYNTAX SEQUENCE OF WinA3ConfigMntAutoEntry
	ACCESS not-accessible
	STATUS mandatory
	DESCRIPTION "&<caiWinA3.221>Configuration table containing a list of mount auto watchers."
	::= { winA3ConfigMntGroup 17 }

winA3ConfigMntAutoEntry OBJECT-TYPE
	SYNTAX WinA3ConfigMntAutoEntry
	ACCESS not-accessible
	STATUS mandatory
	DESCRIPTION "&<caiWinA3.222>Entry in the mount auto watcher configuration table."
	INDEX {
		winA3ConfigMntAutoWatcherName
	}
	::= { winA3ConfigMntAutoTable 1 }

WinA3ConfigMntAutoEntry ::= SEQUENCE {
	winA3ConfigMntAutoWatcherName DisplayString,
	winA3ConfigMntAutoName DisplayString,
	winA3ConfigMntAutoTarget DisplayString,
	winA3ConfigMntAutoClusterType INTEGER,
	winA3ConfigMntAutoDescription DisplayString,
	winA3ConfigMntAutoWatcherMatchType INTEGER,
	winA3ConfigMntAutoWatcherLimit INTEGER,
	winA3ConfigMntAutoWatcherLastMatched INTEGER,
	winA3ConfigMntAutoAggLag INTEGER,
	winA3ConfigMntAutoTargetMonitor INTEGER,
	winA3ConfigMntAutoLossAction INTEGER,
	winA3ConfigMntAutoButton INTEGER
}

winA3ConfigMntAutoWatcherName OBJECT-TYPE
	SYNTAX DisplayString
	ACCESS read-only
	STATUS mandatory
	DESCRIPTION "&<caiWinA3.223>Name of the mount auto watcher."
	::= { winA3ConfigMntAutoEntry 1 }

winA3ConfigMntAutoName OBJECT-TYPE
	SYNTAX DisplayString
	ACCESS read-write
	STATUS mandatory
	DESCRIPTION "&<caiWinA3.224>Name of the mount to be searched for during an auto discovery run. This name is used as a filter element for auto discovery and can be a regular expression (case-insensitive). It restricts the resources to be searched for during an auto discovery run."
	::= { winA3ConfigMntAutoEntry 2 }

winA3ConfigMntAutoTarget OBJECT-TYPE
	SYNTAX DisplayString
	ACCESS read-write
	STATUS mandatory
	DESCRIPTION "&<caiWinA3.225>The name of the logical volume currently mounted by this mount. This attribute is used as a filter element for auto discovery and can be a regular expression (case-insensitive). It restricts the resources to be searched for during an auto discovery run."
	::= { winA3ConfigMntAutoEntry 3 }

winA3ConfigMntAutoClusterType OBJECT-TYPE
	SYNTAX INTEGER {
		not-clustered(1),
		clustered-active(2),
		clustered-passive(3),
		any(4)
	}
	ACCESS read-write
	STATUS mandatory
	DESCRIPTION "&<caiWinA3.226>Cluster type of the mount to be searched for during an auto discovery run. If set to 1 (not-clustered), the search is restricted to not-clustered resources only. If set to 2 (clustered-active), the search is restricted to clustered-active resources only. If set to 3 (clustered-passive), the search is restricted to clustered-passive resources only. If set to 4 (any), the cluster type does not affect the search."
	DEFVAL { 0 }
	::= { winA3ConfigMntAutoEntry 4 }

winA3ConfigMntAutoDescription OBJECT-TYPE
	SYNTAX DisplayString
	ACCESS read-write
	STATUS mandatory
	DESCRIPTION "&<caiWinA3.227>Current description for the mount auto watcher."
	::= { winA3ConfigMntAutoEntry 5 }

winA3ConfigMntAutoWatcherMatchType OBJECT-TYPE
	SYNTAX INTEGER {
		positive(1),
		negative(2)
	}
	ACCESS read-write
	STATUS mandatory
	DESCRIPTION "&<caiWinA3.228>Current search algorithm for the mount auto watcher. The filter is the logical AND of all attributes used to identify or otherwise narrow down resources. If set to 1 (positive), the agent searches for mount resources that match the filter. If set to 2 (negative), the agent searches for mount resources that do not match the filter."
	DEFVAL { 0 }
	::= { winA3ConfigMntAutoEntry 6 }

winA3ConfigMntAutoWatcherLimit OBJECT-TYPE
	SYNTAX INTEGER
	ACCESS read-write
	STATUS mandatory
	DESCRIPTION "&<caiWinA3.229>Current minimum number of matches that causes the mount auto watcher to be locked."
	::= { winA3ConfigMntAutoEntry 7 }

winA3ConfigMntAutoWatcherLastMatched OBJECT-TYPE
	SYNTAX INTEGER
	ACCESS read-only
	STATUS mandatory
	DESCRIPTION "&<caiWinA3.230>Number of matches for the last mount auto discovery run."
	::= { winA3ConfigMntAutoEntry 8 }

winA3ConfigMntAutoAggLag OBJECT-TYPE
	SYNTAX INTEGER
	ACCESS read-write
	STATUS mandatory
	DESCRIPTION "&<caiWinA3.231>Current lag setting for the mount auto watcher. Specifies the consecutive number of times at which any status is not in the ok state, before the aggregate status changes. This value must be greater than 0."
	::= { winA3ConfigMntAutoEntry 9 }

winA3ConfigMntAutoTargetMonitor OBJECT-TYPE
	SYNTAX INTEGER {
		do-not-monitor(1),
		down-warning(2),
		down-critical(3)
	}
	ACCESS read-write
	STATUS mandatory
	DESCRIPTION "&<caiWinA3.232>Default monitor level for the target monitoring of any mount watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3ConfigMntAutoEntry 10 }

winA3ConfigMntAutoLossAction OBJECT-TYPE
	SYNTAX INTEGER {
		remove(1),
		up(2),
		down-warning(3),
		down-critical(4)
	}
	ACCESS read-write
	STATUS mandatory
	DESCRIPTION "&<caiWinA3.233>Default loss action for any mount watcher created by the auto watcher. Specifies the action to take if the monitored mount is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3ConfigMntAutoEntry 11 }

winA3ConfigMntAutoButton OBJECT-TYPE
	SYNTAX INTEGER {
		active(1),
		remove(2),
		locked(3)
	}
	ACCESS read-write
	STATUS mandatory
	DESCRIPTION "&<caiWinA3.234>This attribute is used to enable/disable or remove the mount auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigMntAutoEntry 12 }

--
-- The ConfigDfs Group
--

winA3ConfigDfsPollInterval OBJECT-TYPE
	SYNTAX INTEGER
	ACCESS read-write
	STATUS mandatory
	DESCRIPTION "&<caiWinA3.235>Time, in seconds, between collections of distributed file system link information. Valid range: 30 seconds or greater."
	DEFVAL { 120 }
	::= { winA3ConfigDfsGroup 1 }

winA3ConfigDfsPollMethod OBJECT-TYPE
	SYNTAX INTEGER {
		disabled(1),
		poll-interval-only(2),
		poll-interval-and-query(3),
		query-only(4)
	}
	ACCESS read-write
	STATUS mandatory
	DESCRIPTION "&<caiWinA3.236>Specifies how and when the agent collects distributed file system link information. If set to 1 (disabled), the agent does not retrieve the distributed file system link information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigDfsGroup 2 }

winA3ConfigDfsAutoPollInterval OBJECT-TYPE
	SYNTAX INTEGER
	ACCESS read-write
	STATUS mandatory
	DESCRIPTION "&<caiWinA3.237>Time, in minutes, between the processing of the distributed file system link auto watchers. Valid range: -1 (suspended), 30 minutes or greater."
	DEFVAL { 60 }
	::= { winA3ConfigDfsGroup 3 }

winA3ConfigDfsName OBJECT-TYPE
	SYNTAX DisplayString
	ACCESS read-write
	STATUS mandatory
	DESCRIPTION "&<caiWinA3.238>Name of the distributed file system link for which to add or remove a watcher. A fully qualified Dfs name consists of the Dfs root name followed by the Dfs link name. These two names are concatenated by a back-slash. A single Dfs root name can also be used, allowing to monitor all Dfs links of this Dfs root. In that case the values are calculated as the sum of all DFS links of this DFS root and no loss action will be triggered if no Dfs link exists for this DFS root. If used as a filter element for auto discovery, this name can be a regular expression (case-insensitive). In this case, it restricts the resources to be searched for during an auto discovery run. Note that monitoring of DFS links is not applicable on Windows XP and on Windows 2000 Professional."
	::= { winA3ConfigDfsGroup 4 }

winA3ConfigDfsTargetsList OBJECT-TYPE
	SYNTAX DisplayString
	ACCESS read-write
	STATUS mandatory
	DESCRIPTION "&<caiWinA3.239>A list of the targets (seperated by pipe signs), currently configured for this Dfs link. This attribute is only used as a filter element for auto discovery and can be a regular expression (case-insensitive). It restricts the resources to be searched for during an auto discovery run."
	DEFVAL { ".*" }
	::= { winA3ConfigDfsGroup 5 }

winA3ConfigDfsDescription OBJECT-TYPE
	SYNTAX DisplayString
	ACCESS read-write
	STATUS mandatory
	DESCRIPTION "&<caiWinA3.240>Default description for the distributed file system link watcher to add."
	::= { winA3ConfigDfsGroup 6 }

winA3ConfigDfsAggLag OBJECT-TYPE
	SYNTAX INTEGER
	ACCESS read-write
	STATUS mandatory
	DESCRIPTION "&<caiWinA3.241>Default aggregate lag setting for the distributed file system link watcher to add. Specifies the consecutive number of times at which any status is not in the ok state, before the aggregate status changes. This value must be greater than 0."
	DEFVAL { 2 }
	::= { winA3ConfigDfsGroup 7 }

winA3ConfigDfsTargetsWarn OBJECT-TYPE
	SYNTAX INTEGER
	ACCESS read-write
	STATUS mandatory
	DESCRIPTION "&<caiWinA3.242>Default warning threshold for the target monitoring of the distributed file system link watcher to add. This value represents a rising threshold and must be greater than 0, less than or equal to the total value (maximum capacity) of the monitored resource as specified in winA3StatusDfsTargetsTotal, but cannot be greater than the critical threshold."
	DEFVAL { 1 }
	::= { winA3ConfigDfsGroup 8 }

winA3ConfigDfsTargetsCrit OBJECT-TYPE
	SYNTAX INTEGER
	ACCESS read-write
	STATUS mandatory
	DESCRIPTION "&<caiWinA3.243>Default critical threshold for the target monitoring of the distributed file system link watcher to add. This value represents a rising threshold and must be greater than 0, less than or equal to the total value (maximum capacity) of the monitored resource as specified in winA3StatusDfsTargetsTotal, but cannot be less than the warning threshold."
	DEFVAL { 3 }
	::= { winA3ConfigDfsGroup 9 }

winA3ConfigDfsTargetsMonitor OBJECT-TYPE
	SYNTAX INTEGER {
		do-not-monitor(1),
		warning-only(2),
		critical-only(3),
		both(4)
	}
	ACCESS read-write
	STATUS mandatory
	DESCRIPTION "&<caiWinA3.244>Default monitor level for the target monitoring of the distributed file system link watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigDfsGroup 10 }

winA3ConfigDfsLossAction OBJECT-TYPE
	SYNTAX INTEGER {
		remove(1),
		up(2),
		down-warning(3),
		down-critical(4)
	}
	ACCESS read-write
	STATUS mandatory
	DESCRIPTION "&<caiWinA3.245>Default loss action for the distributed file system link watcher to add. Specifies the action to take if the monitored distributed file system link is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigDfsGroup 11 }

winA3ConfigDfsAutoTableWatcherName OBJECT-TYPE
	SYNTAX DisplayString
	ACCESS read-write
	STATUS mandatory
	DESCRIPTION "&<caiWinA3.246>Name of the distributed file system link auto watcher to add or remove."
	::= { winA3ConfigDfsGroup 12 }

winA3ConfigDfsAutoTableWatcherMatchType OBJECT-TYPE
	SYNTAX INTEGER {
		positive(1),
		negative(2)
	}
	ACCESS read-write
	STATUS mandatory
	DESCRIPTION "&<caiWinA3.247>Default search algorithm for the distributed file system link auto watcher to add. The filter is the logical AND of all attributes used to identify or otherwise narrow down resources. If set to 1 (positive), the agent searches for distributed file system link resources that match the filter. If set to 2 (negative), the agent searches for distributed file system link resources that do not match the filter."
	DEFVAL { 1 }
	::= { winA3ConfigDfsGroup 13 }

winA3ConfigDfsAutoTableWatcherLimit OBJECT-TYPE
	SYNTAX INTEGER
	ACCESS read-write
	STATUS mandatory
	DESCRIPTION "&<caiWinA3.248>Default minimum number of matches that causes a lock of the distributed file system link auto watcher to add."
	DEFVAL { 100 }
	::= { winA3ConfigDfsGroup 14 }

winA3ConfigDfsButton OBJECT-TYPE
	SYNTAX INTEGER {
		none(1),
		add(2),
		remove(3),
		add-auto(4),
		remove-auto(5)
	}
	ACCESS read-write
	STATUS mandatory
	DESCRIPTION "&<caiWinA3.249>This attribute is used to add or remove the distributed file system link watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigDfsGroup 15 }

winA3ConfigDfsAutoCount OBJECT-TYPE
	SYNTAX INTEGER
	ACCESS read-only
	STATUS mandatory
	DESCRIPTION "&<caiWinA3.250>Number of auto watchers in the distributed file system link auto configuration table."
	::= { winA3ConfigDfsGroup 16 }

winA3ConfigDfsAutoLocked OBJECT-TYPE
	SYNTAX INTEGER
	ACCESS read-only
	STATUS mandatory
	DESCRIPTION "&<caiWinA3.251>Number of auto watchers in the distributed file system link auto configuration table which are currently locked."
	::= { winA3ConfigDfsGroup 17 }

winA3ConfigDfsAutoTable OBJECT-TYPE
	SYNTAX SEQUENCE OF WinA3ConfigDfsAutoEntry
	ACCESS not-accessible
	STATUS mandatory
	DESCRIPTION "&<caiWinA3.252>Configuration table containing a list of distributed file system link auto watchers."
	::= { winA3ConfigDfsGroup 18 }

winA3ConfigDfsAutoEntry OBJECT-TYPE
	SYNTAX WinA3ConfigDfsAutoEntry
	ACCESS not-accessible
	STATUS mandatory
	DESCRIPTION "&<caiWinA3.253>Entry in the distributed file system link auto watcher configuration table."
	INDEX {
		winA3ConfigDfsAutoWatcherName
	}
	::= { winA3ConfigDfsAutoTable 1 }

WinA3ConfigDfsAutoEntry ::= SEQUENCE {
	winA3ConfigDfsAutoWatcherName DisplayString,
	winA3ConfigDfsAutoName DisplayString,
	winA3ConfigDfsAutoTargetsList DisplayString,
	winA3ConfigDfsAutoDescription DisplayString,
	winA3ConfigDfsAutoWatcherMatchType INTEGER,
	winA3ConfigDfsAutoWatcherLimit INTEGER,
	winA3ConfigDfsAutoWatcherLastMatched INTEGER,
	winA3ConfigDfsAutoAggLag INTEGER,
	winA3ConfigDfsAutoTargetsWarn INTEGER,
	winA3ConfigDfsAutoTargetsCrit INTEGER,
	winA3ConfigDfsAutoTargetsMonitor INTEGER,
	winA3ConfigDfsAutoLossAction INTEGER,
	winA3ConfigDfsAutoButton INTEGER
}

winA3ConfigDfsAutoWatcherName OBJECT-TYPE
	SYNTAX DisplayString
	ACCESS read-only
	STATUS mandatory
	DESCRIPTION "&<caiWinA3.254>Name of the distributed file system link auto watcher."
	::= { winA3ConfigDfsAutoEntry 1 }

winA3ConfigDfsAutoName OBJECT-TYPE
	SYNTAX DisplayString
	ACCESS read-write
	STATUS mandatory
	DESCRIPTION "&<caiWinA3.255>Name of the distributed file system link to be searched for during an auto discovery run. A fully qualified Dfs name consists of the Dfs root name followed by the Dfs link name. These two names are concatenated by a back-slash. This name is used as a filter element for auto discovery and can be a regular expression (case-insensitive). It restricts the resources to be searched for during an auto discovery run."
	::= { winA3ConfigDfsAutoEntry 2 }

winA3ConfigDfsAutoTargetsList OBJECT-TYPE
	SYNTAX DisplayString
	ACCESS read-write
	STATUS mandatory
	DESCRIPTION "&<caiWinA3.256>A list of the targets (seperated by pipe signs), currently configured for this Dfs link. This attribute is used as a filter element for auto discovery and can be a regular expression (case-insensitive). It restricts the resources to be searched for during an auto discovery run."
	::= { winA3ConfigDfsAutoEntry 3 }

winA3ConfigDfsAutoDescription OBJECT-TYPE
	SYNTAX DisplayString
	ACCESS read-write
	STATUS mandatory
	DESCRIPTION "&<caiWinA3.257>Current description for the distributed file system link auto watcher."
	::= { winA3ConfigDfsAutoEntry 4 }

winA3ConfigDfsAutoWatcherMatchType OBJECT-TYPE
	SYNTAX INTEGER {
		positive(1),
		negative(2)
	}
	ACCESS read-write
	STATUS mandatory
	DESCRIPTION "&<caiWinA3.258>Current search algorithm for the distributed file system link auto watcher. The filter is the logical AND of all attributes used to identify or otherwise narrow down resources. If set to 1 (positive), the agent searches for distributed file system link resources that match the filter. If set to 2 (negative), the agent searches for distributed file system link resources that do not match the filter."
	DEFVAL { 0 }
	::= { winA3ConfigDfsAutoEntry 5 }

winA3ConfigDfsAutoWatcherLimit OBJECT-TYPE
	SYNTAX INTEGER
	ACCESS read-write
	STATUS mandatory
	DESCRIPTION "&<caiWinA3.259>Current minimum number of matches that causes the distributed file system link auto watcher to be locked."
	::= { winA3ConfigDfsAutoEntry 6 }

winA3ConfigDfsAutoWatcherLastMatched OBJECT-TYPE
	SYNTAX INTEGER
	ACCESS read-only
	STATUS mandatory
	DESCRIPTION "&<caiWinA3.260>Number of matches for the last distributed file system link auto discovery run."
	::= { winA3ConfigDfsAutoEntry 7 }

winA3ConfigDfsAutoAggLag OBJECT-TYPE
	SYNTAX INTEGER
	ACCESS read-write
	STATUS mandatory
	DESCRIPTION "&<caiWinA3.261>Current lag setting for the distributed file system link auto watcher. Specifies the consecutive number of times at which any status is not in the ok state, before the aggregate status changes. This value must be greater than 0."
	::= { winA3ConfigDfsAutoEntry 8 }

winA3ConfigDfsAutoTargetsWarn OBJECT-TYPE
	SYNTAX INTEGER
	ACCESS read-write
	STATUS mandatory
	DESCRIPTION "&<caiWinA3.262>Default warning threshold for the target monitoring of any distributed file system link watcher created by the auto watcher. This value represents a rising threshold and must be greater than 0, less than or equal to the total value (maximum capacity) of the monitored resource as specified in winA3StatusDfsTargetsTotal, but cannot be greater than the critical threshold."
	::= { winA3ConfigDfsAutoEntry 9 }

winA3ConfigDfsAutoTargetsCrit OBJECT-TYPE
	SYNTAX INTEGER
	ACCESS read-write
	STATUS mandatory
	DESCRIPTION "&<caiWinA3.263>Default critical threshold for the target monitoring of any distributed file system link watcher created by the auto watcher. This value represents a rising threshold and must be greater than 0, less than or equal to the total value (maximum capacity) of the monitored resource as specified in winA3StatusDfsTargetsTotal, but cannot be less than the warning threshold."
	::= { winA3ConfigDfsAutoEntry 10 }

winA3ConfigDfsAutoTargetsMonitor OBJECT-TYPE
	SYNTAX INTEGER {
		do-not-monitor(1),
		warning-only(2),
		critical-only(3),
		both(4)
	}
	ACCESS read-write
	STATUS mandatory
	DESCRIPTION "&<caiWinA3.264>Default monitor level for the target monitoring of any distributed file system link watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigDfsAutoEntry 11 }

winA3ConfigDfsAutoLossAction OBJECT-TYPE
	SYNTAX INTEGER {
		remove(1),
		up(2),
		down-warning(3),
		down-critical(4)
	}
	ACCESS read-write
	STATUS mandatory
	DESCRIPTION "&<caiWinA3.265>Default loss action for any distributed file system link watcher created by the auto watcher. Specifies the action to take if the monitored distributed file system link is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3ConfigDfsAutoEntry 12 }

winA3ConfigDfsAutoButton OBJECT-TYPE
	SYNTAX INTEGER {
		active(1),
		remove(2),
		locked(3)
	}
	ACCESS read-write
	STATUS mandatory
	DESCRIPTION "&<caiWinA3.266>This attribute is used to enable/disable or remove the distributed file system link auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigDfsAutoEntry 13 }

--
-- The ConfigQuota Group
--

winA3ConfigQuotaPollInterval OBJECT-TYPE
	SYNTAX INTEGER
	ACCESS read-write
	STATUS mandatory
	DESCRIPTION "&<caiWinA3.267>Time, in seconds, between collections of quota information. Valid range: 30 seconds or greater."
	DEFVAL { 120 }
	::= { winA3ConfigQuotaGroup 1 }

winA3ConfigQuotaPollMethod OBJECT-TYPE
	SYNTAX INTEGER {
		disabled(1),
		poll-interval-only(2),
		poll-interval-and-query(3),
		query-only(4)
	}
	ACCESS read-write
	STATUS mandatory
	DESCRIPTION "&<caiWinA3.268>Specifies how and when the agent collects quota information. If set to 1 (disabled), the agent does not retrieve the quota information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigQuotaGroup 2 }

winA3ConfigQuotaAutoPollInterval OBJECT-TYPE
	SYNTAX INTEGER
	ACCESS read-write
	STATUS mandatory
	DESCRIPTION "&<caiWinA3.269>Time, in minutes, between the processing of the quota auto watchers. Valid range: -1 (suspended), 30 minutes or greater."
	DEFVAL { 60 }
	::= { winA3ConfigQuotaGroup 3 }

winA3ConfigQuotaLVolName OBJECT-TYPE
	SYNTAX DisplayString
	ACCESS read-write
	STATUS mandatory
	DESCRIPTION "&<caiWinA3.270>LVol name part of the quota for which to add or remove a watcher. A fully qualified name specifies the logical volume on which this quota exists. If used as a filter element for auto discovery, this name can be a regular expression (case-insensitive). In this case, it restricts the resources to be searched for during an auto discovery run."
	::= { winA3ConfigQuotaGroup 4 }

winA3ConfigQuotaUserName OBJECT-TYPE
	SYNTAX DisplayString
	ACCESS read-write
	STATUS mandatory
	DESCRIPTION "&<caiWinA3.271>User name part of the quota for which to add or remove a watcher. A fully qualified name specifies the user for whom this quota exists and is in the form 'domainName\\userName' or 'userName@domainName'. If used as a filter element for auto discovery, this name can be a regular expression (case-insensitive). In this case, it restricts the resources to be searched for during an auto discovery run."
	::= { winA3ConfigQuotaGroup 5 }

winA3ConfigQuotaWarnLevel OBJECT-TYPE
	SYNTAX DisplayString
	ACCESS read-write
	STATUS mandatory
	DESCRIPTION "&<caiWinA3.272>The warning level, in kilobytes, for this quota, as defined in the Windows quota management. A value of zero means 'No Limit'. This attribute is only used as a filter element for auto discovery and can be greater or equal to 0, filtering out all values being greater or equal. It restricts the resources to be searched for during an auto discovery run."
	DEFVAL { "0.0" }
	::= { winA3ConfigQuotaGroup 6 }

winA3ConfigQuotaLimit OBJECT-TYPE
	SYNTAX DisplayString
	ACCESS read-write
	STATUS mandatory
	DESCRIPTION "&<caiWinA3.273>The limit, in kilobytes, for this quota, as defined in the Windows quota management. A value of zero means 'No Limit'. This attribute is only used as a filter element for auto discovery and can be greater or equal to 0, filtering out all values being greater or equal. It restricts the resources to be searched for during an auto discovery run."
	DEFVAL { "0.0" }
	::= { winA3ConfigQuotaGroup 7 }

winA3ConfigQuotaDescription OBJECT-TYPE
	SYNTAX DisplayString
	ACCESS read-write
	STATUS mandatory
	DESCRIPTION "&<caiWinA3.274>Default description for the quota watcher to add."
	::= { winA3ConfigQuotaGroup 8 }

winA3ConfigQuotaAggLag OBJECT-TYPE
	SYNTAX INTEGER
	ACCESS read-write
	STATUS mandatory
	DESCRIPTION "&<caiWinA3.275>Default aggregate lag setting for the quota watcher to add. Specifies the consecutive number of times at which any status is not in the ok state, before the aggregate status changes. This value must be greater than 0."
	DEFVAL { 2 }
	::= { winA3ConfigQuotaGroup 9 }

winA3ConfigQuotaSizeWarn OBJECT-TYPE
	SYNTAX DisplayString
	ACCESS read-write
	STATUS mandatory
	DESCRIPTION "&<caiWinA3.276>Default warning threshold, in kilobytes, for the quota size utilization monitoring of the quota watcher to add. The active warning threshold is derived from this value and represents a rising threshold. The derived value must be greater than 0.0, less than or equal to the total value (maximum capacity) of the monitored resource as specified in winA3StatusQuotaSizeTotal, but cannot be greater than the active critical threshold. These constraints will be maintained by the agent during all configuration actions. The threshold can be specified as either an absolute value (n) or a percentage (n%). The value of winA3StatusQuotaSizeTotal will be the reference value for n% notations."
	DEFVAL { "2.0%" }
	::= { winA3ConfigQuotaGroup 10 }

winA3ConfigQuotaSizeCrit OBJECT-TYPE
	SYNTAX DisplayString
	ACCESS read-write
	STATUS mandatory
	DESCRIPTION "&<caiWinA3.277>Default critical threshold, in kilobytes, for the quota size utilization monitoring of the quota watcher to add. The active critical threshold is derived from this value and represents a rising threshold. The derived value must be greater than 0.0, less than or equal to the total value (maximum capacity) of the monitored resource as specified in winA3StatusQuotaSizeTotal, but cannot be less than the active warning threshold. These constraints will be maintained by the agent during all configuration actions. The threshold can be specified as either an absolute value (n) or a percentage (n%). The value of winA3StatusQuotaSizeTotal will be the reference value for n% notations."
	DEFVAL { "4.0%" }
	::= { winA3ConfigQuotaGroup 11 }

winA3ConfigQuotaSizeMonitor OBJECT-TYPE
	SYNTAX INTEGER {
		do-not-monitor(1),
		warning-only(2),
		critical-only(3),
		both(4)
	}
	ACCESS read-write
	STATUS mandatory
	DESCRIPTION "&<caiWinA3.278>Default monitor level for the quota size utilization monitoring of the quota watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigQuotaGroup 12 }

winA3ConfigQuotaLossAction OBJECT-TYPE
	SYNTAX INTEGER {
		remove(1),
		up(2),
		down-warning(3),
		down-critical(4)
	}
	ACCESS read-write
	STATUS mandatory
	DESCRIPTION "&<caiWinA3.279>Default loss action for the quota watcher to add. Specifies the action to take if the monitored quota is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigQuotaGroup 13 }

winA3ConfigQuotaAutoTableWatcherName OBJECT-TYPE
	SYNTAX DisplayString
	ACCESS read-write
	STATUS mandatory
	DESCRIPTION "&<caiWinA3.280>Name of the quota auto watcher to add or remove."
	::= { winA3ConfigQuotaGroup 14 }

winA3ConfigQuotaAutoTableWatcherMatchType OBJECT-TYPE
	SYNTAX INTEGER {
		positive(1),
		negative(2)
	}
	ACCESS read-write
	STATUS mandatory
	DESCRIPTION "&<caiWinA3.281>Default search algorithm for the quota auto watcher to add. The filter is the logical AND of all attributes used to identify or otherwise narrow down resources. If set to 1 (positive), the agent searches for quota resources that match the filter. If set to 2 (negative), the agent searches for quota resources that do not match the filter."
	DEFVAL { 1 }
	::= { winA3ConfigQuotaGroup 15 }

winA3ConfigQuotaAutoTableWatcherLimit OBJECT-TYPE
	SYNTAX INTEGER
	ACCESS read-write
	STATUS mandatory
	DESCRIPTION "&<caiWinA3.282>Default minimum number of matches that causes a lock of the quota auto watcher to add."
	DEFVAL { 100 }
	::= { winA3ConfigQuotaGroup 16 }

winA3ConfigQuotaButton OBJECT-TYPE
	SYNTAX INTEGER {
		none(1),
		add(2),
		remove(3),
		add-auto(4),
		remove-auto(5)
	}
	ACCESS read-write
	STATUS mandatory
	DESCRIPTION "&<caiWinA3.283>This attribute is used to add or remove the quota watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigQuotaGroup 17 }

winA3ConfigQuotaAutoCount OBJECT-TYPE
	SYNTAX INTEGER
	ACCESS read-only
	STATUS mandatory
	DESCRIPTION "&<caiWinA3.284>Number of auto watchers in the quota auto configuration table."
	::= { winA3ConfigQuotaGroup 18 }

winA3ConfigQuotaAutoLocked OBJECT-TYPE
	SYNTAX INTEGER
	ACCESS read-only
	STATUS mandatory
	DESCRIPTION "&<caiWinA3.285>Number of auto watchers in the quota auto configuration table which are currently locked."
	::= { winA3ConfigQuotaGroup 19 }

winA3ConfigQuotaAutoTable OBJECT-TYPE
	SYNTAX SEQUENCE OF WinA3ConfigQuotaAutoEntry
	ACCESS not-accessible
	STATUS mandatory
	DESCRIPTION "&<caiWinA3.286>Configuration table containing a list of quota auto watchers."
	::= { winA3ConfigQuotaGroup 20 }

winA3ConfigQuotaAutoEntry OBJECT-TYPE
	SYNTAX WinA3ConfigQuotaAutoEntry
	ACCESS not-accessible
	STATUS mandatory
	DESCRIPTION "&<caiWinA3.287>Entry in the quota auto watcher configuration table."
	INDEX {
		winA3ConfigQuotaAutoWatcherName
	}
	::= { winA3ConfigQuotaAutoTable 1 }

WinA3ConfigQuotaAutoEntry ::= SEQUENCE {
	winA3ConfigQuotaAutoWatcherName DisplayString,
	winA3ConfigQuotaAutoLVolName DisplayString,
	winA3ConfigQuotaAutoUserName DisplayString,
	winA3ConfigQuotaAutoWarnLevel DisplayString,
	winA3ConfigQuotaAutoLimit DisplayString,
	winA3ConfigQuotaAutoDescription DisplayString,
	winA3ConfigQuotaAutoWatcherMatchType INTEGER,
	winA3ConfigQuotaAutoWatcherLimit INTEGER,
	winA3ConfigQuotaAutoWatcherLastMatched INTEGER,
	winA3ConfigQuotaAutoAggLag INTEGER,
	winA3ConfigQuotaAutoSizeWarn DisplayString,
	winA3ConfigQuotaAutoSizeCrit DisplayString,
	winA3ConfigQuotaAutoSizeMonitor INTEGER,
	winA3ConfigQuotaAutoLossAction INTEGER,
	winA3ConfigQuotaAutoButton INTEGER
}

winA3ConfigQuotaAutoWatcherName OBJECT-TYPE
	SYNTAX DisplayString
	ACCESS read-only
	STATUS mandatory
	DESCRIPTION "&<caiWinA3.288>Name of the quota auto watcher."
	::= { winA3ConfigQuotaAutoEntry 1 }

winA3ConfigQuotaAutoLVolName OBJECT-TYPE
	SYNTAX DisplayString
	ACCESS read-write
	STATUS mandatory
	DESCRIPTION "&<caiWinA3.289>LVol name part of the quota to be searched for during an auto discovery run. A fully qualified name specifies the logical volume on which this quota exists. This name is used as a filter element for auto discovery and can be a regular expression (case-insensitive). It restricts the resources to be searched for during an auto discovery run."
	::= { winA3ConfigQuotaAutoEntry 2 }

winA3ConfigQuotaAutoUserName OBJECT-TYPE
	SYNTAX DisplayString
	ACCESS read-write
	STATUS mandatory
	DESCRIPTION "&<caiWinA3.290>User name part of the quota to be searched for during an auto discovery run. A fully qualified name specifies the user for whom this quota exists and is in the form 'domainName\\userName' or 'userName@domainName'. This name is used as a filter element for auto discovery and can be a regular expression (case-insensitive). It restricts the resources to be searched for during an auto discovery run."
	::= { winA3ConfigQuotaAutoEntry 3 }

winA3ConfigQuotaAutoWarnLevel OBJECT-TYPE
	SYNTAX DisplayString
	ACCESS read-write
	STATUS mandatory
	DESCRIPTION "&<caiWinA3.291>The warning level, in kilobytes, for this quota, as defined in the Windows quota management. A value of zero means 'No Limit'. This attribute is used as a filter element for auto discovery and can be greater or equal to 0, filtering out all values being greater or equal. It restricts the resources to be searched for during an auto discovery run."
	::= { winA3ConfigQuotaAutoEntry 4 }

winA3ConfigQuotaAutoLimit OBJECT-TYPE
	SYNTAX DisplayString
	ACCESS read-write
	STATUS mandatory
	DESCRIPTION "&<caiWinA3.292>The limit, in kilobytes, for this quota, as defined in the Windows quota management. A value of zero means 'No Limit'. This attribute is used as a filter element for auto discovery and can be greater or equal to 0, filtering out all values being greater or equal. It restricts the resources to be searched for during an auto discovery run."
	::= { winA3ConfigQuotaAutoEntry 5 }

winA3ConfigQuotaAutoDescription OBJECT-TYPE
	SYNTAX DisplayString
	ACCESS read-write
	STATUS mandatory
	DESCRIPTION "&<caiWinA3.293>Current description for the quota auto watcher."
	::= { winA3ConfigQuotaAutoEntry 6 }

winA3ConfigQuotaAutoWatcherMatchType OBJECT-TYPE
	SYNTAX INTEGER {
		positive(1),
		negative(2)
	}
	ACCESS read-write
	STATUS mandatory
	DESCRIPTION "&<caiWinA3.294>Current search algorithm for the quota auto watcher. The filter is the logical AND of all attributes used to identify or otherwise narrow down resources. If set to 1 (positive), the agent searches for quota resources that match the filter. If set to 2 (negative), the agent searches for quota resources that do not match the filter."
	DEFVAL { 0 }
	::= { winA3ConfigQuotaAutoEntry 7 }

winA3ConfigQuotaAutoWatcherLimit OBJECT-TYPE
	SYNTAX INTEGER
	ACCESS read-write
	STATUS mandatory
	DESCRIPTION "&<caiWinA3.295>Current minimum number of matches that causes the quota auto watcher to be locked."
	::= { winA3ConfigQuotaAutoEntry 8 }

winA3ConfigQuotaAutoWatcherLastMatched OBJECT-TYPE
	SYNTAX INTEGER
	ACCESS read-only
	STATUS mandatory
	DESCRIPTION "&<caiWinA3.296>Number of matches for the last quota auto discovery run."
	::= { winA3ConfigQuotaAutoEntry 9 }

winA3ConfigQuotaAutoAggLag OBJECT-TYPE
	SYNTAX INTEGER
	ACCESS read-write
	STATUS mandatory
	DESCRIPTION "&<caiWinA3.297>Current lag setting for the quota auto watcher. Specifies the consecutive number of times at which any status is not in the ok state, before the aggregate status changes. This value must be greater than 0."
	::= { winA3ConfigQuotaAutoEntry 10 }

winA3ConfigQuotaAutoSizeWarn OBJECT-TYPE
	SYNTAX DisplayString
	ACCESS read-write
	STATUS mandatory
	DESCRIPTION "&<caiWinA3.298>Default warning threshold, in kilobytes, for the quota size utilization monitoring of any quota watcher created by the auto watcher. The active warning threshold is derived from this value and represents a rising threshold. The derived value must be greater than 0.0, less than or equal to the total value (maximum capacity) of the monitored resource as specified in winA3StatusQuotaSizeTotal, but cannot be greater than the active critical threshold. These constraints will be maintained by the agent during all configuration actions. The threshold can be specified as either an absolute value (n) or a percentage (n%). The value of winA3StatusQuotaSizeTotal will be the reference value for n% notations."
	::= { winA3ConfigQuotaAutoEntry 11 }

winA3ConfigQuotaAutoSizeCrit OBJECT-TYPE
	SYNTAX DisplayString
	ACCESS read-write
	STATUS mandatory
	DESCRIPTION "&<caiWinA3.299>Default critical threshold, in kilobytes, for the quota size utilization monitoring of any quota watcher created by the auto watcher. The active critical threshold is derived from this value and represents a rising threshold. The derived value must be greater than 0.0, less than or equal to the total value (maximum capacity) of the monitored resource as specified in winA3StatusQuotaSizeTotal, but cannot be less than the active warning threshold. These constraints will be maintained by the agent during all configuration actions. The threshold can be specified as either an absolute value (n) or a percentage (n%). The value of winA3StatusQuotaSizeTotal will be the reference value for n% notations."
	::= { winA3ConfigQuotaAutoEntry 12 }

winA3ConfigQuotaAutoSizeMonitor OBJECT-TYPE
	SYNTAX INTEGER {
		do-not-monitor(1),
		warning-only(2),
		critical-only(3),
		both(4)
	}
	ACCESS read-write
	STATUS mandatory
	DESCRIPTION "&<caiWinA3.300>Default monitor level for the quota size utilization monitoring of any quota watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigQuotaAutoEntry 13 }

winA3ConfigQuotaAutoLossAction OBJECT-TYPE
	SYNTAX INTEGER {
		remove(1),
		up(2),
		down-warning(3),
		down-critical(4)
	}
	ACCESS read-write
	STATUS mandatory
	DESCRIPTION "&<caiWinA3.301>Default loss action for any quota watcher created by the auto watcher. Specifies the action to take if the monitored quota is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3ConfigQuotaAutoEntry 14 }

winA3ConfigQuotaAutoButton OBJECT-TYPE
	SYNTAX INTEGER {
		active(1),
		remove(2),
		locked(3)
	}
	ACCESS read-write
	STATUS mandatory
	DESCRIPTION "&<caiWinA3.302>This attribute is used to enable/disable or remove the quota auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigQuotaAutoEntry 15 }

--
-- The ConfigDir Group
--

winA3ConfigDirPollInterval OBJECT-TYPE
	SYNTAX INTEGER
	ACCESS read-write
	STATUS mandatory
	DESCRIPTION "&<caiWinA3.303>Time, in seconds, between collections of directory information. Valid range: 30 seconds or greater."
	DEFVAL { 120 }
	::= { winA3ConfigDirGroup 1 }

winA3ConfigDirPollMethod OBJECT-TYPE
	SYNTAX INTEGER {
		disabled(1),
		poll-interval-only(2),
		poll-interval-and-query(3),
		query-only(4)
	}
	ACCESS read-write
	STATUS mandatory
	DESCRIPTION "&<caiWinA3.304>Specifies how and when the agent collects directory information. If set to 1 (disabled), the agent does not retrieve the directory information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigDirGroup 2 }

winA3ConfigDirWatcherName OBJECT-TYPE
	SYNTAX DisplayString
	ACCESS read-write
	STATUS mandatory
	DESCRIPTION "&<caiWinA3.305>An arbitrary name for the watcher."
	::= { winA3ConfigDirGroup 3 }

winA3ConfigDirName OBJECT-TYPE
	SYNTAX DisplayString
	ACCESS read-write
	STATUS mandatory
	DESCRIPTION "&<caiWinA3.306>Name of the directory for which to add or remove a watcher. This must be a fully qualified name that may contain environment variables."
	::= { winA3ConfigDirGroup 4 }

winA3ConfigDirRecursivePolicy OBJECT-TYPE
	SYNTAX INTEGER {
		no(1),
		yes(2)
	}
	ACCESS read-write
	STATUS mandatory
	DESCRIPTION "&<caiWinA3.307>If set to yes(2), the scope of the watcher, to calculate the values from, is the complete subtree of the given directory. If set to no(1), the scope is just the (flat) directory."
	DEFVAL { 1 }
	::= { winA3ConfigDirGroup 5 }

winA3ConfigDirDescription OBJECT-TYPE
	SYNTAX DisplayString
	ACCESS read-write
	STATUS mandatory
	DESCRIPTION "&<caiWinA3.308>Default description for the directory watcher to add."
	::= { winA3ConfigDirGroup 6 }

winA3ConfigDirAggLag OBJECT-TYPE
	SYNTAX INTEGER
	ACCESS read-write
	STATUS mandatory
	DESCRIPTION "&<caiWinA3.309>Default aggregate lag setting for the directory watcher to add. Specifies the consecutive number of times at which any status is not in the ok state, before the aggregate status changes. This value must be greater than 0."
	DEFVAL { 2 }
	::= { winA3ConfigDirGroup 7 }

winA3ConfigDirSizeWarnMin OBJECT-TYPE
	SYNTAX DisplayString
	ACCESS read-write
	STATUS mandatory
	DESCRIPTION "&<caiWinA3.310>Default warning minimum threshold, in kilobytes, for the size utilization monitoring of the directory watcher to add. This value represents a declining threshold and must be equal to or greater than 0.0, equal to or greater than the critical minimum threshold, but cannot be greater than the warning maximum threshold. A value of -1 disables the evaluation of this threshold. The threshold can be specified as either an absolute value (n) or a percentage (n%). The value of winA3StatusDirSizeTotal will be the reference value for n% notations."
	DEFVAL { "-1" }
	::= { winA3ConfigDirGroup 8 }

winA3ConfigDirSizeWarnMax OBJECT-TYPE
	SYNTAX DisplayString
	ACCESS read-write
	STATUS mandatory
	DESCRIPTION "&<caiWinA3.311>Default warning maximum threshold, in kilobytes, for the size utilization monitoring of the directory watcher to add. This value represents a rising threshold and must be equal to or greater than 0.0, equal to or greater than the warning minimum threshold, but cannot be greater than the critical maximum threshold. A value of -1 disables the evaluation of this threshold. The threshold can be specified as either an absolute value (n) or a percentage (n%). The value of winA3StatusDirSizeTotal will be the reference value for n% notations."
	DEFVAL { "150.0%" }
	::= { winA3ConfigDirGroup 9 }

winA3ConfigDirSizeCritMin OBJECT-TYPE
	SYNTAX DisplayString
	ACCESS read-write
	STATUS mandatory
	DESCRIPTION "&<caiWinA3.312>Default critical minimum threshold, in kilobytes, for the size utilization monitoring of the directory watcher to add. This value represents a declining threshold and must be equal to or greater than 0.0, but cannot be greater than the warning minimum threshold. A value of -1 disables the evaluation of this threshold. The threshold can be specified as either an absolute value (n) or a percentage (n%). The value of winA3StatusDirSizeTotal will be the reference value for n% notations."
	DEFVAL { "-1" }
	::= { winA3ConfigDirGroup 10 }

winA3ConfigDirSizeCritMax OBJECT-TYPE
	SYNTAX DisplayString
	ACCESS read-write
	STATUS mandatory
	DESCRIPTION "&<caiWinA3.313>Default critical maximum threshold, in kilobytes, for the size utilization monitoring of the directory watcher to add. This value represents a rising threshold and must be equal to or greater than 0.0, but cannot be less than the warning maximum threshold. A value of -1 disables the evaluation of this threshold. The threshold can be specified as either an absolute value (n) or a percentage (n%). The value of winA3StatusDirSizeTotal will be the reference value for n% notations."
	DEFVAL { "200.0%" }
	::= { winA3ConfigDirGroup 11 }

winA3ConfigDirSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.314>Default monitor level for the size utilization monitoring of the directory watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3ConfigDirGroup 12 }

winA3ConfigDirSizeDWarn OBJECT-TYPE
	SYNTAX DisplayString
	ACCESS read-write
	STATUS mandatory
	DESCRIPTION "&<caiWinA3.315>Default warning threshold, in kilobytes, for the delta size utilization monitoring of the directory watcher to add. The active warning threshold is derived from this value and represents a rising threshold. The derived value must be greater than 0.0, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of winA3StatusDirSizeTotal will be the reference value for n% notations."
	DEFVAL { "20.0%" }
	::= { winA3ConfigDirGroup 13 }

winA3ConfigDirSizeDCrit OBJECT-TYPE
	SYNTAX DisplayString
	ACCESS read-write
	STATUS mandatory
	DESCRIPTION "&<caiWinA3.316>Default critical threshold, in kilobytes, for the delta size utilization monitoring of the directory watcher to add. The active critical threshold is derived from this value and represents a rising threshold. The derived value must be greater than 0.0, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of winA3StatusDirSizeTotal will be the reference value for n% notations."
	DEFVAL { "40.0%" }
	::= { winA3ConfigDirGroup 14 }

winA3ConfigDirSizeDMonitor OBJECT-TYPE
	SYNTAX INTEGER {
		do-not-monitor(1),
		warning-only(2),
		critical-only(3),
		both(4)
	}
	ACCESS read-write
	STATUS mandatory
	DESCRIPTION "&<caiWinA3.317>Default monitor level for the delta size utilization monitoring of the directory watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigDirGroup 15 }

winA3ConfigDirEntriesWarnMin OBJECT-TYPE
	SYNTAX DisplayString
	ACCESS read-write
	STATUS mandatory
	DESCRIPTION "&<caiWinA3.318>Default warning minimum threshold for the number of file and/or directory entries monitoring of the directory watcher to add. This value represents a declining threshold and must be equal to or greater than 0.0, equal to or greater than the critical minimum threshold, but cannot be greater than the warning maximum threshold. A value of -1 disables the evaluation of this threshold."
	DEFVAL { "-1" }
	::= { winA3ConfigDirGroup 16 }

winA3ConfigDirEntriesWarnMax OBJECT-TYPE
	SYNTAX DisplayString
	ACCESS read-write
	STATUS mandatory
	DESCRIPTION "&<caiWinA3.319>Default warning maximum threshold for the number of file and/or directory entries monitoring of the directory watcher to add. This value represents a rising threshold and must be equal to or greater than 0.0, equal to or greater than the warning minimum threshold, but cannot be greater than the critical maximum threshold. A value of -1 disables the evaluation of this threshold."
	DEFVAL { "100.0" }
	::= { winA3ConfigDirGroup 17 }

winA3ConfigDirEntriesCritMin OBJECT-TYPE
	SYNTAX DisplayString
	ACCESS read-write
	STATUS mandatory
	DESCRIPTION "&<caiWinA3.320>Default critical minimum threshold for the number of file and/or directory entries monitoring of the directory watcher to add. This value represents a declining threshold and must be equal to or greater than 0.0, but cannot be greater than the warning minimum threshold. A value of -1 disables the evaluation of this threshold."
	DEFVAL { "-1" }
	::= { winA3ConfigDirGroup 18 }

winA3ConfigDirEntriesCritMax OBJECT-TYPE
	SYNTAX DisplayString
	ACCESS read-write
	STATUS mandatory
	DESCRIPTION "&<caiWinA3.321>Default critical maximum threshold for the number of file and/or directory entries monitoring of the directory watcher to add. This value represents a rising threshold and must be equal to or greater than 0.0, but cannot be less than the warning maximum threshold. A value of -1 disables the evaluation of this threshold."
	DEFVAL { "200.0" }
	::= { winA3ConfigDirGroup 19 }

winA3ConfigDirEntriesMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.322>Default monitor level for the number of file and/or directory entries monitoring of the directory watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 1 }
	::= { winA3ConfigDirGroup 20 }

winA3ConfigDirTimeMode OBJECT-TYPE
	SYNTAX INTEGER {
		modification-time(1),
		access-time(2),
		creation-time(3)
	}
	ACCESS read-write
	STATUS mandatory
	DESCRIPTION "&<caiWinA3.323>This attribute determines which mode of time (modification, access or creation) should be used for the time monitoring."
	DEFVAL { 1 }
	::= { winA3ConfigDirGroup 21 }

winA3ConfigDirTimeInterval OBJECT-TYPE
	SYNTAX INTEGER
	ACCESS read-write
	STATUS mandatory
	DESCRIPTION "&<caiWinA3.324>Time, in seconds, defining the time frame during which the time monitoring is performed. Dependend from the policy, the status is set to 'down' if the time interval is elapsed and the time value changed or changed not. A value of zero stands for an infinite interval."
	DEFVAL { 0 }
	::= { winA3ConfigDirGroup 22 }

winA3ConfigDirTimePolicy OBJECT-TYPE
	SYNTAX INTEGER {
		should-not-change(1),
		should-change(2)
	}
	ACCESS read-write
	STATUS mandatory
	DESCRIPTION "&<caiWinA3.325>Default monitor policy for the time monitoring of the directory watcher to add. The policy indicates the expected behaviour of the time value during the given time interval."
	DEFVAL { 1 }
	::= { winA3ConfigDirGroup 23 }

winA3ConfigDirTimeMonitor OBJECT-TYPE
	SYNTAX INTEGER {
		do-not-monitor(1),
		down-warning(2),
		down-critical(3)
	}
	ACCESS read-write
	STATUS mandatory
	DESCRIPTION "&<caiWinA3.326>Default monitor level for the time monitoring of the directory watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { winA3ConfigDirGroup 24 }

winA3ConfigDirExistPolicy OBJECT-TYPE
	SYNTAX INTEGER {
		should-exist(1),
		should-not-exist(2)
	}
	ACCESS read-write
	STATUS mandatory
	DESCRIPTION "&<caiWinA3.327>Default monitor policy for the existence monitoring of the directory watcher to add. Specifies how the agent should evaluate the presence or absence of the monitored resource in order to determine whether the resource is in good condition. If set to 1 (should-exist), the resource is expected to be existent. If set to 2 (should-not-exist), the resource is expected to be nonexistent."
	DEFVAL { 1 }
	::= { winA3ConfigDirGroup 25 }

winA3ConfigDirExistMonitor OBJECT-TYPE
	SYNTAX INTEGER {
		do-not-monitor(1),
		down-warning(2),
		down-critical(3)
	}
	ACCESS read-write
	STATUS mandatory
	DESCRIPTION "&<caiWinA3.328>Default monitor level for the existence monitoring of the directory watcher to add. If set to 1 (do-not-monitor), the agent does not evaluate the actual state of the resource and sets the status to ok. If set to 2 (down-warning), the agent uses a warning severity if the resource is in bad condition. If set to 3 (down-critical), the agent uses a critical severity if the resource is in bad condition."
	DEFVAL { 3 }
	::= { winA3ConfigDirGroup 26 }

winA3ConfigDirButton OBJECT-TYPE
	SYNTAX INTEGER {
		none(1),
		add(2),
		remove(3)
	}
	ACCESS read-write
	STATUS mandatory
	DESCRIPTION "&<caiWinA3.329>This attribute is used to add or remove the directory watcher specified by the current setting of the watcher name attribute(s) in this group. If set to 2 (add), the agent adds the specified watcher to the status table using the current values of the remaining attributes as defaults. If set to 3 (remove), the agent removes the specified watcher from the status table. This attribute cannot be set to 1 (none)."
	DEFVAL { 1 }
	::= { winA3ConfigDirGroup 27 }

--
-- The ConfigFile Group
--

winA3ConfigFilePollInterval OBJECT-TYPE
	SYNTAX INTEGER
	ACCESS read-write
	STATUS mandatory
	DESCRIPTION "&<caiWinA3.330>Time, in seconds, between collections of file information. Valid range: 30 seconds or greater."
	DEFVAL { 120 }
	::= { winA3ConfigFileGroup 1 }

winA3ConfigFilePollMethod OBJECT-TYPE
	SYNTAX INTEGER {
		disabled(1),
		poll-interval-only(2),
		poll-interval-and-query(3),
		query-only(4)
	}
	ACCESS read-write
	STATUS mandatory
	DESCRIPTION "&<caiWinA3.331>Specifies how and when the agent collects file information. If set to 1 (disabled), the agent does not retrieve the file information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigFileGroup 2 }

winA3ConfigFileWatcherName OBJECT-TYPE
	SYNTAX DisplayString
	ACCESS read-write
	STATUS mandatory
	DESCRIPTION "&<caiWinA3.332>An arbitrary name for the watcher."
	::= { winA3ConfigFileGroup 3 }

winA3ConfigFileMatchType OBJECT-TYPE
	SYNTAX INTEGER {
		positive-regular-expression(1),
		negative-regular-expression(2),
		positive-string-compare(3),
		negative-string-compare(4)
	}
	ACCESS read-write
	STATUS mandatory
	DESCRIPTION "&<caiWinA3.333>Default search algorithm for the file watcher. The filter is the logical AND of all attributes used to identify or otherwise narrow down resources. If the value of one of these attributes includes 'wildcards', then the watcher will basically behave like a one-to-many watcher, i.e. it may monitor two or more resources simultaneously. If set to 1 (positive-regular-expression), the agent searches for file resources that match the filter as a regular expression (case-insensitive). If set to 2 (negative-regular-expression), the agent searches for file resources that do not match the filter as a regular expression (case-insensitive). If set to 3 (positive-string-compare), the agent searches for file resources that match the filter as string comparison (case-insensitive). If set to 4 (negative-string-compare), the agent searches for file resources that do not match the filter as string comparison (case-insensitive)."
	DEFVAL { 3 }
	::= { winA3ConfigFileGroup 4 }

winA3ConfigFileName OBJECT-TYPE
	SYNTAX DisplayString
	ACCESS read-write
	STATUS mandatory
	DESCRIPTION "&<caiWinA3.334>Name of the file for which to add or remove a watcher. This name may contain environment variables. This name is used as a filter element for one-to-many monitoring (one watcher monitors several resources simultaneously). The file name (not the path) can be a regular expression (case-insensitive). The expression '.*' always matches any string, independent from the match type."
	DEFVAL { ".*" }
	::= { winA3ConfigFileGroup 5 }

winA3ConfigFileEvalPolicy OBJECT-TYPE
	SYNTAX INTEGER {
		individual(1),
		min(2),
		max(3),
		sum(4),
		avg(5)
	}
	ACCESS read-write
	STATUS mandatory
	DESCRIPTION "&<caiWinA3.335>Default evaluation policy for the file watcher. Defines how metric values will be calculated and 'culprits' be determined if two or more file resources fall into the monitoring scope of a one-to-many watcher. If set to 1 (individual), metric values will be set to the worst values (lowest and/or highest) of all file instances; if the value of a metric violates the threshold condition, the respective 'culprits' list will contain all instances individually violating the most severe threshold. If set to 2 (min), metric values will be set to the lowest (minimum) values of all file instances; if the value of a metric violates the threshold condition, the respective 'culprits' list will contain all instances having the same minimum value. If set to 3 (max), metric values will be set to the highest (maximum) values of all file instances; if the value of a metric violates the threshold condition, the respective 'culprits' list will contain all instances having the same maximum value. If set to 4 (sum), metric values will be set to the cumulative values (sum) of all file instances; if the value of a metric violates the threshold condition, the respective 'culprits' list will contain all instances. If set to 5 (avg), metric values will be set to the average values of all file instances; if the value of a metric violates the threshold condition, the respective 'culprits' list will contain all instances individually violating the most severe threshold."
	DEFVAL { 1 }
	::= { winA3ConfigFileGroup 6 }

winA3ConfigFileDescription OBJECT-TYPE
	SYNTAX DisplayString
	ACCESS read-write
	STATUS mandatory
	DESCRIPTION "&<caiWinA3.336>Default description for the file watcher to add."
	::= { winA3ConfigFileGroup 7 }

winA3ConfigFileAggLag OBJECT-TYPE
	SYNTAX INTEGER
	ACCESS read-write
	STATUS mandatory
	DESCRIPTION "&<caiWinA3.337>Default aggregate lag setting for the file watcher to add. Specifies the consecutive number of times at which any status is not in the ok state, before the aggregate status changes. This value must be greater than 0."
	DEFVAL { 2 }
	::= { winA3ConfigFileGroup 8 }

winA3ConfigFileInstMin OBJECT-TYPE
	SYNTAX INTEGER
	ACCESS read-write
	STATUS mandatory
	DESCRIPTION "&<caiWinA3.338>Default minimum threshold for the instance count monitoring of the file watcher to add. This value represents a declining threshold and must be equal to or greater than 0, but cannot be greater than the maximum threshold. A value of -1 disables the evaluation of this threshold."
	DEFVAL { 1 }
	::= { winA3ConfigFileGroup 9 }

winA3ConfigFileInstMax OBJECT-TYPE
	SYNTAX INTEGER
	ACCESS read-write
	STATUS mandatory
	DESCRIPTION "&<caiWinA3.339>Default maximum threshold for the instance count monitoring of the file watcher to add. This value represents a rising threshold and must be equal to or greater than 0, but cannot be less than the minimum threshold. A value of -1 disables the evaluation of this threshold."
	DEFVAL { -1 }
	::= { winA3ConfigFileGroup 10 }

winA3ConfigFileInstMonitor OBJECT-TYPE
	SYNTAX INTEGER {
		do-not-monitor(1),
		down-warning(2),
		down-critical(3)
	}
	ACCESS read-write
	STATUS mandatory
	DESCRIPTION "&<caiWinA3.340>Default monitor level for the instance count monitoring of the file watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigFileGroup 11 }

winA3ConfigFileSizeWarnMin OBJECT-TYPE
	SYNTAX DisplayString
	ACCESS read-write
	STATUS mandatory
	DESCRIPTION "&<caiWinA3.341>Default warning minimum threshold, in kilobytes, for the size utilization monitoring of the file watcher to add. This value represents a declining threshold and must be equal to or greater than 0.0, equal to or greater than the critical minimum threshold, but cannot be greater than the warning maximum threshold. A value of -1 disables the evaluation of this threshold. The threshold can be specified as either an absolute value (n) or a percentage (n%). The value of winA3StatusFileSizeTotal will be the reference value for n% notations."
	DEFVAL { "-1" }
	::= { winA3ConfigFileGroup 12 }

winA3ConfigFileSizeWarnMax OBJECT-TYPE
	SYNTAX DisplayString
	ACCESS read-write
	STATUS mandatory
	DESCRIPTION "&<caiWinA3.342>Default warning maximum threshold, in kilobytes, for the size utilization monitoring of the file watcher to add. This value represents a rising threshold and must be equal to or greater than 0.0, equal to or greater than the warning minimum threshold, but cannot be greater than the critical maximum threshold. A value of -1 disables the evaluation of this threshold. The threshold can be specified as either an absolute value (n) or a percentage (n%). The value of winA3StatusFileSizeTotal will be the reference value for n% notations."
	DEFVAL { "150.0%" }
	::= { winA3ConfigFileGroup 13 }

winA3ConfigFileSizeCritMin OBJECT-TYPE
	SYNTAX DisplayString
	ACCESS read-write
	STATUS mandatory
	DESCRIPTION "&<caiWinA3.343>Default critical minimum threshold, in kilobytes, for the size utilization monitoring of the file watcher to add. This value represents a declining threshold and must be equal to or greater than 0.0, but cannot be greater than the warning minimum threshold. A value of -1 disables the evaluation of this threshold. The threshold can be specified as either an absolute value (n) or a percentage (n%). The value of winA3StatusFileSizeTotal will be the reference value for n% notations."
	DEFVAL { "-1" }
	::= { winA3ConfigFileGroup 14 }

winA3ConfigFileSizeCritMax OBJECT-TYPE
	SYNTAX DisplayString
	ACCESS read-write
	STATUS mandatory
	DESCRIPTION "&<caiWinA3.344>Default critical maximum threshold, in kilobytes, for the size utilization monitoring of the file watcher to add. This value represents a rising threshold and must be equal to or greater than 0.0, but cannot be less than the warning maximum threshold. A value of -1 disables the evaluation of this threshold. The threshold can be specified as either an absolute value (n) or a percentage (n%). The value of winA3StatusFileSizeTotal will be the reference value for n% notations."
	DEFVAL { "200.0%" }
	::= { winA3ConfigFileGroup 15 }

winA3ConfigFileSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.345>Default monitor level for the size utilization monitoring of the file watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3ConfigFileGroup 16 }

winA3ConfigFileSizeDWarn OBJECT-TYPE
	SYNTAX DisplayString
	ACCESS read-write
	STATUS mandatory
	DESCRIPTION "&<caiWinA3.346>Default warning threshold, in kilobytes, for the delta size utilization monitoring of the file watcher to add. The active warning threshold is derived from this value and represents a rising threshold. The derived value must be greater than 0.0, but cannot be greater than the active critical threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of winA3StatusFileSizeTotal will be the reference value for n% notations."
	DEFVAL { "20.0%" }
	::= { winA3ConfigFileGroup 17 }

winA3ConfigFileSizeDCrit OBJECT-TYPE
	SYNTAX DisplayString
	ACCESS read-write
	STATUS mandatory
	DESCRIPTION "&<caiWinA3.347>Default critical threshold, in kilobytes, for the delta size utilization monitoring of the file watcher to add. The active critical threshold is derived from this value and represents a rising threshold. The derived value must be greater than 0.0, but cannot be less than the active warning threshold. These constraints will be maintained by the agent during all configuration actions. The threshold can be specified as either an absolute value or a percentage and can denote a growth, shrinkage or change in either direction: Absolute shrinkage (n-), absolute growth (n+), absolute change in either direction (n), percentage shrinkage (n%-), percentage growth (n%+), or percentage change in either direction (n%). The value of winA3StatusFileSizeTotal will be the reference value for n% notations."
	DEFVAL { "40.0%" }
	::= { winA3ConfigFileGroup 18 }

winA3ConfigFileSizeDMonitor OBJECT-TYPE
	SYNTAX INTEGER {
		do-not-monitor(1),
		warning-only(2),
		critical-only(3),
		both(4)
	}
	ACCESS read-write
	STATUS mandatory
	DESCRIPTION "&<caiWinA3.348>Default monitor level for the delta size utilization monitoring of the file watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigFileGroup 19 }

winA3ConfigFileTimeMode OBJECT-TYPE
	SYNTAX INTEGER {
		modification-time(1),
		access-time(2),
		creation-time(3)
	}
	ACCESS read-write
	STATUS mandatory
	DESCRIPTION "&<caiWinA3.349>This attribute determines which mode of time (modification, access or creation) should be used for the time monitoring."
	DEFVAL { 1 }
	::= { winA3ConfigFileGroup 20 }

winA3ConfigFileTimeInterval OBJECT-TYPE
	SYNTAX INTEGER
	ACCESS read-write
	STATUS mandatory
	DESCRIPTION "&<caiWinA3.350>Time, in seconds, defining the time frame during which the time monitoring is performed. Dependend from the policy, the status is set to 'down' if the time interval is elapsed and the time value changed or changed not. A value of zero stands for an infinite interval."
	DEFVAL { 0 }
	::= { winA3ConfigFileGroup 21 }

winA3ConfigFileTimePolicy OBJECT-TYPE
	SYNTAX INTEGER {
		should-not-change(1),
		should-change(2)
	}
	ACCESS read-write
	STATUS mandatory
	DESCRIPTION "&<caiWinA3.351>Default monitor policy for the time monitoring of the file watcher to add. The policy indicates the expected behaviour of the time value during the given time interval."
	DEFVAL { 1 }
	::= { winA3ConfigFileGroup 22 }

winA3ConfigFileTimeMonitor OBJECT-TYPE
	SYNTAX INTEGER {
		do-not-monitor(1),
		down-warning(2),
		down-critical(3)
	}
	ACCESS read-write
	STATUS mandatory
	DESCRIPTION "&<caiWinA3.352>Default monitor level for the time monitoring of the file watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { winA3ConfigFileGroup 23 }

winA3ConfigFileButton OBJECT-TYPE
	SYNTAX INTEGER {
		none(1),
		add(2),
		remove(3)
	}
	ACCESS read-write
	STATUS mandatory
	DESCRIPTION "&<caiWinA3.353>This attribute is used to add or remove the file watcher specified by the current setting of the watcher name attribute(s) in this group. If set to 2 (add), the agent adds the specified watcher to the status table using the current values of the remaining attributes as defaults. If set to 3 (remove), the agent removes the specified watcher from the status table. This attribute cannot be set to 1 (none)."
	DEFVAL { 1 }
	::= { winA3ConfigFileGroup 24 }

--
-- The ConfigProc Group
--

winA3ConfigProcPollInterval OBJECT-TYPE
	SYNTAX INTEGER
	ACCESS read-write
	STATUS mandatory
	DESCRIPTION "&<caiWinA3.354>Time, in seconds, between collections of process information. Valid range: 30 seconds or greater."
	DEFVAL { 120 }
	::= { winA3ConfigProcGroup 1 }

winA3ConfigProcPollMethod OBJECT-TYPE
	SYNTAX INTEGER {
		disabled(1),
		poll-interval-only(2),
		poll-interval-and-query(3),
		query-only(4)
	}
	ACCESS read-write
	STATUS mandatory
	DESCRIPTION "&<caiWinA3.355>Specifies how and when the agent collects process information. If set to 1 (disabled), the agent does not retrieve the process information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigProcGroup 2 }

winA3ConfigProcWatcherName OBJECT-TYPE
	SYNTAX DisplayString
	ACCESS read-write
	STATUS mandatory
	DESCRIPTION "&<caiWinA3.356>An arbitrary name for the watcher."
	::= { winA3ConfigProcGroup 3 }

winA3ConfigProcMatchType OBJECT-TYPE
	SYNTAX INTEGER {
		positive-regular-expression(1),
		negative-regular-expression(2),
		positive-string-compare(3),
		negative-string-compare(4)
	}
	ACCESS read-write
	STATUS mandatory
	DESCRIPTION "&<caiWinA3.357>Default search algorithm for the process watcher. The filter is the logical AND of all attributes used to identify or otherwise narrow down resources. If the value of one of these attributes includes 'wildcards', then the watcher will basically behave like a one-to-many watcher, i.e. it may monitor two or more resources simultaneously. If set to 1 (positive-regular-expression), the agent searches for process resources that match the filter as a regular expression (case-insensitive). If set to 2 (negative-regular-expression), the agent searches for process resources that do not match the filter as a regular expression (case-insensitive). If set to 3 (positive-string-compare), the agent searches for process resources that match the filter as string comparison (case-insensitive). If set to 4 (negative-string-compare), the agent searches for process resources that do not match the filter as string comparison (case-insensitive)."
	DEFVAL { 3 }
	::= { winA3ConfigProcGroup 4 }

winA3ConfigProcName OBJECT-TYPE
	SYNTAX DisplayString
	ACCESS read-write
	STATUS mandatory
	DESCRIPTION "&<caiWinA3.358>Name of the process for which to add or remove a watcher. This name is used as a filter element for one-to-many monitoring (one watcher monitors several resources simultaneously) and can be a regular expression (case-insensitive). The expression '.*' always matches any string, independent from the match type."
	DEFVAL { ".*" }
	::= { winA3ConfigProcGroup 5 }

winA3ConfigProcPath OBJECT-TYPE
	SYNTAX DisplayString
	ACCESS read-write
	STATUS mandatory
	DESCRIPTION "&<caiWinA3.359>Path name of the process for which to add or remove a watcher. This name is used as a filter element for one-to-many monitoring (one watcher monitors several resources simultaneously) and can be a regular expression (case-insensitive). The expression '.*' always matches any string, independent from the match type."
	DEFVAL { ".*" }
	::= { winA3ConfigProcGroup 6 }

winA3ConfigProcUser OBJECT-TYPE
	SYNTAX DisplayString
	ACCESS read-write
	STATUS mandatory
	DESCRIPTION "&<caiWinA3.360>User name of the process for which to add or remove a watcher. This name is used as a filter element for one-to-many monitoring (one watcher monitors several resources simultaneously) and can be a regular expression (case-insensitive). The expression '.*' always matches any string, independent from the match type."
	DEFVAL { ".*" }
	::= { winA3ConfigProcGroup 7 }

winA3ConfigProcClusterResGroup OBJECT-TYPE
	SYNTAX DisplayString
	ACCESS read-write
	STATUS mandatory
	DESCRIPTION "&<caiWinA3.361>Name of the cluster resource group of the process. For an unclustered process this attribute is set to '-'."
	DEFVAL { "-" }
	::= { winA3ConfigProcGroup 8 }

winA3ConfigProcEvalPolicy OBJECT-TYPE
	SYNTAX INTEGER {
		individual(1),
		min(2),
		max(3),
		sum(4),
		avg(5)
	}
	ACCESS read-write
	STATUS mandatory
	DESCRIPTION "&<caiWinA3.362>Default evaluation policy for the process watcher. Defines how metric values will be calculated and 'culprits' be determined if two or more process resources fall into the monitoring scope of a one-to-many watcher. If set to 1 (individual), metric values will be set to the worst values (lowest and/or highest) of all process instances; if the value of a metric violates the threshold condition, the respective 'culprits' list will contain all instances individually violating the most severe threshold. If set to 2 (min), metric values will be set to the lowest (minimum) values of all process instances; if the value of a metric violates the threshold condition, the respective 'culprits' list will contain all instances having the same minimum value. If set to 3 (max), metric values will be set to the highest (maximum) values of all process instances; if the value of a metric violates the threshold condition, the respective 'culprits' list will contain all instances having the same maximum value. If set to 4 (sum), metric values will be set to the cumulative values (sum) of all process instances; if the value of a metric violates the threshold condition, the respective 'culprits' list will contain all instances. If set to 5 (avg), metric values will be set to the average values of all process instances; if the value of a metric violates the threshold condition, the respective 'culprits' list will contain all instances individually violating the most severe threshold."
	DEFVAL { 1 }
	::= { winA3ConfigProcGroup 9 }

winA3ConfigProcDescription OBJECT-TYPE
	SYNTAX DisplayString
	ACCESS read-write
	STATUS mandatory
	DESCRIPTION "&<caiWinA3.363>Default description for the process watcher to add."
	::= { winA3ConfigProcGroup 10 }

winA3ConfigProcAggLag OBJECT-TYPE
	SYNTAX INTEGER
	ACCESS read-write
	STATUS mandatory
	DESCRIPTION "&<caiWinA3.364>Default aggregate lag setting for the process watcher to add. Specifies the consecutive number of times at which any status is not in the ok state, before the aggregate status changes. This value must be greater than 0."
	DEFVAL { 3 }
	::= { winA3ConfigProcGroup 11 }

winA3ConfigProcInstMin OBJECT-TYPE
	SYNTAX INTEGER
	ACCESS read-write
	STATUS mandatory
	DESCRIPTION "&<caiWinA3.365>Default minimum threshold for the instance count monitoring of the process watcher to add. This value represents a declining threshold and must be equal to or greater than 0, but cannot be greater than the maximum threshold. A value of -1 disables the evaluation of this threshold."
	DEFVAL { 1 }
	::= { winA3ConfigProcGroup 12 }

winA3ConfigProcInstMax OBJECT-TYPE
	SYNTAX INTEGER
	ACCESS read-write
	STATUS mandatory
	DESCRIPTION "&<caiWinA3.366>Default maximum threshold for the instance count monitoring of the process watcher to add. This value represents a rising threshold and must be equal to or greater than 0, but cannot be less than the minimum threshold. A value of -1 disables the evaluation of this threshold."
	DEFVAL { -1 }
	::= { winA3ConfigProcGroup 13 }

winA3ConfigProcInstMonitor OBJECT-TYPE
	SYNTAX INTEGER {
		do-not-monitor(1),
		down-warning(2),
		down-critical(3)
	}
	ACCESS read-write
	STATUS mandatory
	DESCRIPTION "&<caiWinA3.367>Default monitor level for the instance count monitoring of the process watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigProcGroup 14 }

winA3ConfigProcSizeWarnMin OBJECT-TYPE
	SYNTAX DisplayString
	ACCESS read-write
	STATUS mandatory
	DESCRIPTION "&<caiWinA3.368>Default warning minimum threshold, in kilobytes, for the size utilization monitoring of the process watcher to add. This value represents a declining threshold and must be equal to or greater than 0.0, equal to or greater than the critical minimum threshold, but cannot be greater than the warning maximum threshold. A value of -1 disables the evaluation of this threshold."
	DEFVAL { "-1" }
	::= { winA3ConfigProcGroup 15 }

winA3ConfigProcSizeWarnMax OBJECT-TYPE
	SYNTAX DisplayString
	ACCESS read-write
	STATUS mandatory
	DESCRIPTION "&<caiWinA3.369>Default warning maximum threshold, in kilobytes, for the size utilization monitoring of the process watcher to add. This value represents a rising threshold and must be equal to or greater than 0.0, equal to or greater than the warning minimum threshold, but cannot be greater than the critical maximum threshold. A value of -1 disables the evaluation of this threshold."
	DEFVAL { "100000.0" }
	::= { winA3ConfigProcGroup 16 }

winA3ConfigProcSizeCritMin OBJECT-TYPE
	SYNTAX DisplayString
	ACCESS read-write
	STATUS mandatory
	DESCRIPTION "&<caiWinA3.370>Default critical minimum threshold, in kilobytes, for the size utilization monitoring of the process watcher to add. This value represents a declining threshold and must be equal to or greater than 0.0, but cannot be greater than the warning minimum threshold. A value of -1 disables the evaluation of this threshold."
	DEFVAL { "-1" }
	::= { winA3ConfigProcGroup 17 }

winA3ConfigProcSizeCritMax OBJECT-TYPE
	SYNTAX DisplayString
	ACCESS read-write
	STATUS mandatory
	DESCRIPTION "&<caiWinA3.371>Default critical maximum threshold, in kilobytes, for the size utilization monitoring of the process watcher to add. This value represents a rising threshold and must be equal to or greater than 0.0, but cannot be less than the warning maximum threshold. A value of -1 disables the evaluation of this threshold."
	DEFVAL { "150000.0" }
	::= { winA3ConfigProcGroup 18 }

winA3ConfigProcSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.372>Default monitor level for the size utilization monitoring of the process watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3ConfigProcGroup 19 }

winA3ConfigProcCpuInterval OBJECT-TYPE
	SYNTAX DisplayString
	ACCESS read-write
	STATUS mandatory
	DESCRIPTION "&<caiWinA3.373>Time, in seconds, defining the total value to use as base for the calculation of the cpu value. This means, the cpu usage of a process, in seconds, refers to this interval. Valid range: Greater 0 or '-1'. If set to '-1', the cpu value is calculated as the cpu usage, in seconds, used up to now since the start of the agent or the creation of the watcher. If the cpu interval is set to a value greater than the current poll interval and this time is not elapsed for the first time, the CPU value is extrapolated. If the cpu interval is set to a value smaller than the current poll interval, the CPU value is calculated as the appropriate fraction of the value for the last poll interval. If the cpu interval is set to a value greater than the current poll interval and this time is already elapsed, the CPU value is calculated as the sliding sum, i.e. the sum of the value for the current poll interval and the value calculated at the last poll, weighted according to it's fraction of the cpu interval. If the interval is set to '-1', any overloading (%) used for the thresholds will be ignored."
	DEFVAL { "1800.0" }
	::= { winA3ConfigProcGroup 20 }

winA3ConfigProcCpuWarnMin OBJECT-TYPE
	SYNTAX DisplayString
	ACCESS read-write
	STATUS mandatory
	DESCRIPTION "&<caiWinA3.374>Default warning minimum threshold, in seconds, for the cpu utilization monitoring of the process watcher to add. This value represents a declining threshold and must be equal to or greater than 0.0, less than or equal to the total value (maximum capacity) of the monitored resource as specified in winA3StatusProcCpuInterval, equal to or greater than the critical minimum threshold, but cannot be greater than the warning maximum threshold. A value of -1 disables the evaluation of this threshold. The threshold can be specified as either an absolute value (n) or a percentage (n%). The value of winA3StatusProcCpuInterval will be the reference value for n% notations."
	DEFVAL { "-1" }
	::= { winA3ConfigProcGroup 21 }

winA3ConfigProcCpuWarnMax OBJECT-TYPE
	SYNTAX DisplayString
	ACCESS read-write
	STATUS mandatory
	DESCRIPTION "&<caiWinA3.375>Default warning maximum threshold, in seconds, for the cpu utilization monitoring of the process watcher to add. This value represents a rising threshold and must be equal to or greater than 0.0, less than or equal to the total value (maximum capacity) of the monitored resource as specified in winA3StatusProcCpuInterval, equal to or greater than the warning minimum threshold, but cannot be greater than the critical maximum threshold. A value of -1 disables the evaluation of this threshold. The threshold can be specified as either an absolute value (n) or a percentage (n%). The value of winA3StatusProcCpuInterval will be the reference value for n% notations."
	DEFVAL { "20.0%" }
	::= { winA3ConfigProcGroup 22 }

winA3ConfigProcCpuCritMin OBJECT-TYPE
	SYNTAX DisplayString
	ACCESS read-write
	STATUS mandatory
	DESCRIPTION "&<caiWinA3.376>Default critical minimum threshold, in seconds, for the cpu utilization monitoring of the process watcher to add. This value represents a declining threshold and must be equal to or greater than 0.0, less than or equal to the total value (maximum capacity) of the monitored resource as specified in winA3StatusProcCpuInterval, but cannot be greater than the warning minimum threshold. A value of -1 disables the evaluation of this threshold. The threshold can be specified as either an absolute value (n) or a percentage (n%). The value of winA3StatusProcCpuInterval will be the reference value for n% notations."
	DEFVAL { "-1" }
	::= { winA3ConfigProcGroup 23 }

winA3ConfigProcCpuCritMax OBJECT-TYPE
	SYNTAX DisplayString
	ACCESS read-write
	STATUS mandatory
	DESCRIPTION "&<caiWinA3.377>Default critical maximum threshold, in seconds, for the cpu utilization monitoring of the process watcher to add. This value represents a rising threshold and must be equal to or greater than 0.0, less than or equal to the total value (maximum capacity) of the monitored resource as specified in winA3StatusProcCpuInterval, but cannot be less than the warning maximum threshold. A value of -1 disables the evaluation of this threshold. The threshold can be specified as either an absolute value (n) or a percentage (n%). The value of winA3StatusProcCpuInterval will be the reference value for n% notations."
	DEFVAL { "50.0%" }
	::= { winA3ConfigProcGroup 24 }

winA3ConfigProcCpuMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.378>Default monitor level for the cpu utilization monitoring of the process watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3ConfigProcGroup 25 }

winA3ConfigProcMiscMode OBJECT-TYPE
	SYNTAX INTEGER {
		threads(1),
		handles(2),
		children(3),
		runtime(4)
	}
	ACCESS read-write
	STATUS mandatory
	DESCRIPTION "&<caiWinA3.379>This attribute determines which value (threads, handles, children or runtime) should be calculated by this metric. The option runtime(4) is the time, in seconds, the process is running for (beginning with the process creation)."
	DEFVAL { 2 }
	::= { winA3ConfigProcGroup 26 }

winA3ConfigProcMiscMin OBJECT-TYPE
	SYNTAX DisplayString
	ACCESS read-write
	STATUS mandatory
	DESCRIPTION "&<caiWinA3.380>Default minimum threshold for the miscellaneous data monitoring of the process watcher to add. This value represents a declining threshold and must be equal to or greater than 0.0, but cannot be greater than the maximum threshold. A value of -1 disables the evaluation of this threshold."
	DEFVAL { "-1" }
	::= { winA3ConfigProcGroup 27 }

winA3ConfigProcMiscMax OBJECT-TYPE
	SYNTAX DisplayString
	ACCESS read-write
	STATUS mandatory
	DESCRIPTION "&<caiWinA3.381>Default maximum threshold for the miscellaneous data monitoring of the process watcher to add. This value represents a rising threshold and must be equal to or greater than 0.0, but cannot be less than the minimum threshold. A value of -1 disables the evaluation of this threshold."
	DEFVAL { "5000.0" }
	::= { winA3ConfigProcGroup 28 }

winA3ConfigProcMiscMonitor OBJECT-TYPE
	SYNTAX INTEGER {
		do-not-monitor(1),
		down-warning(2),
		down-critical(3)
	}
	ACCESS read-write
	STATUS mandatory
	DESCRIPTION "&<caiWinA3.382>Default monitor level for the miscellaneous data monitoring of the process watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigProcGroup 29 }

winA3ConfigProcRestartPolicy OBJECT-TYPE
	SYNTAX INTEGER {
		none-should-stop-or-start(1),
		none-should-stop(2),
		none-should-start(3),
		some-should-continue(4),
		none-should-continue(5)
	}
	ACCESS read-write
	STATUS mandatory
	DESCRIPTION "&<caiWinA3.383>Default monitor policy for the restart monitoring of the process watcher to add. The status will be set to 'down' according to the following rules: In case none-should-stop-or-start(1), if any process in the scope of the watcher did stop or start since the last poll; in case none-should-stop(2), if any process did stop; in case none-should-start(3), if any process did start; in case some-should-continue(4), if all processes did stop; and in case none-should-continue(5), if at least one process did not stop."
	DEFVAL { 1 }
	::= { winA3ConfigProcGroup 30 }

winA3ConfigProcRestartMonitor OBJECT-TYPE
	SYNTAX INTEGER {
		do-not-monitor(1),
		down-warning(2),
		down-critical(3)
	}
	ACCESS read-write
	STATUS mandatory
	DESCRIPTION "&<caiWinA3.384>Default monitor level for the restart monitoring of the process watcher to add. If set to 1 (do-not-monitor), the agent does not evaluate the actual state of the resource and sets the status to ok. If set to 2 (down-warning), the agent uses a warning severity if the resource is in bad condition. If set to 3 (down-critical), the agent uses a critical severity if the resource is in bad condition."
	DEFVAL { 1 }
	::= { winA3ConfigProcGroup 31 }

winA3ConfigProcButton OBJECT-TYPE
	SYNTAX INTEGER {
		none(1),
		add(2),
		remove(3)
	}
	ACCESS read-write
	STATUS mandatory
	DESCRIPTION "&<caiWinA3.385>This attribute is used to add or remove the process watcher specified by the current setting of the watcher name attribute(s) in this group. If set to 2 (add), the agent adds the specified watcher to the status table using the current values of the remaining attributes as defaults. If set to 3 (remove), the agent removes the specified watcher from the status table. This attribute cannot be set to 1 (none)."
	DEFVAL { 1 }
	::= { winA3ConfigProcGroup 32 }

--
-- The ConfigSrvc Group
--

winA3ConfigSrvcPollInterval OBJECT-TYPE
	SYNTAX INTEGER
	ACCESS read-write
	STATUS mandatory
	DESCRIPTION "&<caiWinA3.386>Time, in seconds, between collections of service information. Valid range: 30 seconds or greater."
	DEFVAL { 120 }
	::= { winA3ConfigSrvcGroup 1 }

winA3ConfigSrvcPollMethod OBJECT-TYPE
	SYNTAX INTEGER {
		disabled(1),
		poll-interval-only(2),
		poll-interval-and-query(3),
		query-only(4)
	}
	ACCESS read-write
	STATUS mandatory
	DESCRIPTION "&<caiWinA3.387>Specifies how and when the agent collects service information. If set to 1 (disabled), the agent does not retrieve the service information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigSrvcGroup 2 }

winA3ConfigSrvcAutoPollInterval OBJECT-TYPE
	SYNTAX INTEGER
	ACCESS read-write
	STATUS mandatory
	DESCRIPTION "&<caiWinA3.388>Time, in minutes, between the processing of the service auto watchers. Valid range: -1 (suspended), 30 minutes or greater."
	DEFVAL { 60 }
	::= { winA3ConfigSrvcGroup 3 }

winA3ConfigSrvcName OBJECT-TYPE
	SYNTAX DisplayString
	ACCESS read-write
	STATUS mandatory
	DESCRIPTION "&<caiWinA3.389>Name of the service for which to add or remove a watcher. For uniqueness, the service name must be specified as defined in the Windows registry. This name is typically different to the display name of a service, visible in the service manager console. If used as a filter element for auto discovery, this name can be a regular expression (case-insensitive). In this case, it restricts the resources to be searched for during an auto discovery run."
	::= { winA3ConfigSrvcGroup 4 }

winA3ConfigSrvcDisplayName OBJECT-TYPE
	SYNTAX DisplayString
	ACCESS read-write
	STATUS mandatory
	DESCRIPTION "&<caiWinA3.390>The display name of a service as visible in the service manager console. This attribute is only used as a filter element for auto discovery and can be a regular expression (case-insensitive). It restricts the resources to be searched for during an auto discovery run."
	DEFVAL { ".*" }
	::= { winA3ConfigSrvcGroup 5 }

winA3ConfigSrvcStartupType OBJECT-TYPE
	SYNTAX INTEGER {
		automatic(1),
		manual(2),
		disabled(3),
		any(4)
	}
	ACCESS read-write
	STATUS mandatory
	DESCRIPTION "&<caiWinA3.391>The current startup type (automatic, manual or disabled) of the service. This attribute is only used as a filter element for auto discovery. It restricts the resources to be searched for during an auto discovery run."
	DEFVAL { 4 }
	::= { winA3ConfigSrvcGroup 6 }

winA3ConfigSrvcAccount OBJECT-TYPE
	SYNTAX DisplayString
	ACCESS read-write
	STATUS mandatory
	DESCRIPTION "&<caiWinA3.392>The account, the system uses to start this service. This attribute is only used as a filter element for auto discovery and can be a regular expression (case-insensitive). It restricts the resources to be searched for during an auto discovery run."
	DEFVAL { ".*" }
	::= { winA3ConfigSrvcGroup 7 }

winA3ConfigSrvcExecutable OBJECT-TYPE
	SYNTAX DisplayString
	ACCESS read-write
	STATUS mandatory
	DESCRIPTION "&<caiWinA3.393>The executable belonging to this service. This attribute is only used as a filter element for auto discovery and can be a regular expression (case-insensitive). It restricts the resources to be searched for during an auto discovery run."
	DEFVAL { ".*" }
	::= { winA3ConfigSrvcGroup 8 }

winA3ConfigSrvcClusterType OBJECT-TYPE
	SYNTAX INTEGER {
		not-clustered(1),
		clustered-active(2),
		clustered-passive(3),
		any(4)
	}
	ACCESS read-write
	STATUS mandatory
	DESCRIPTION "&<caiWinA3.394>Cluster type of the service to be searched for during an auto discovery run. This attribute is only used when adding an auto watcher. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { winA3ConfigSrvcGroup 9 }

winA3ConfigSrvcDescription OBJECT-TYPE
	SYNTAX DisplayString
	ACCESS read-write
	STATUS mandatory
	DESCRIPTION "&<caiWinA3.395>Default description for the service watcher to add."
	::= { winA3ConfigSrvcGroup 10 }

winA3ConfigSrvcAggLag OBJECT-TYPE
	SYNTAX INTEGER
	ACCESS read-write
	STATUS mandatory
	DESCRIPTION "&<caiWinA3.396>Default aggregate lag setting for the service watcher to add. Specifies the consecutive number of times at which any status is not in the ok state, before the aggregate status changes. This value must be greater than 0."
	DEFVAL { 1 }
	::= { winA3ConfigSrvcGroup 11 }

winA3ConfigSrvcConfigMonitor OBJECT-TYPE
	SYNTAX INTEGER {
		do-not-monitor(1),
		down-warning(2),
		down-critical(3)
	}
	ACCESS read-write
	STATUS mandatory
	DESCRIPTION "&<caiWinA3.397>Default monitor level for the configuration change monitoring of the service watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigSrvcGroup 12 }

winA3ConfigSrvcActivePolicy OBJECT-TYPE
	SYNTAX INTEGER {
		should-be-active(1),
		should-not-be-active(2)
	}
	ACCESS read-write
	STATUS mandatory
	DESCRIPTION "&<caiWinA3.398>Default monitor policy for the activity monitoring of the service watcher to add."
	DEFVAL { 1 }
	::= { winA3ConfigSrvcGroup 13 }

winA3ConfigSrvcActiveMonitor OBJECT-TYPE
	SYNTAX INTEGER {
		do-not-monitor(1),
		down-warning(2),
		down-critical(3)
	}
	ACCESS read-write
	STATUS mandatory
	DESCRIPTION "&<caiWinA3.399>Default monitor level for the activity monitoring of the service watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigSrvcGroup 14 }

winA3ConfigSrvcExistPolicy OBJECT-TYPE
	SYNTAX INTEGER {
		should-exist(1),
		should-not-exist(2)
	}
	ACCESS read-write
	STATUS mandatory
	DESCRIPTION "&<caiWinA3.400>Default monitor policy for the existence monitoring of the service watcher to add. Specifies how the agent should evaluate the presence or absence of the monitored resource in order to determine whether the resource is in good condition. If set to 1 (should-exist), the resource is expected to be existent. If set to 2 (should-not-exist), the resource is expected to be nonexistent."
	DEFVAL { 1 }
	::= { winA3ConfigSrvcGroup 15 }

winA3ConfigSrvcExistMonitor OBJECT-TYPE
	SYNTAX INTEGER {
		do-not-monitor(1),
		down-warning(2),
		down-critical(3)
	}
	ACCESS read-write
	STATUS mandatory
	DESCRIPTION "&<caiWinA3.401>Default monitor level for the existence monitoring of the service watcher to add. If set to 1 (do-not-monitor), the agent does not evaluate the actual state of the resource and sets the status to ok. If set to 2 (down-warning), the agent uses a warning severity if the resource is in bad condition. If set to 3 (down-critical), the agent uses a critical severity if the resource is in bad condition."
	DEFVAL { 3 }
	::= { winA3ConfigSrvcGroup 16 }

winA3ConfigSrvcAutoTableWatcherName OBJECT-TYPE
	SYNTAX DisplayString
	ACCESS read-write
	STATUS mandatory
	DESCRIPTION "&<caiWinA3.402>Name of the service auto watcher to add or remove."
	::= { winA3ConfigSrvcGroup 17 }

winA3ConfigSrvcAutoTableWatcherMatchType OBJECT-TYPE
	SYNTAX INTEGER {
		positive(1),
		negative(2)
	}
	ACCESS read-write
	STATUS mandatory
	DESCRIPTION "&<caiWinA3.403>Default search algorithm for the service auto watcher to add. The filter is the logical AND of all attributes used to identify or otherwise narrow down resources. If set to 1 (positive), the agent searches for service resources that match the filter. If set to 2 (negative), the agent searches for service resources that do not match the filter."
	DEFVAL { 1 }
	::= { winA3ConfigSrvcGroup 18 }

winA3ConfigSrvcAutoTableWatcherLimit OBJECT-TYPE
	SYNTAX INTEGER
	ACCESS read-write
	STATUS mandatory
	DESCRIPTION "&<caiWinA3.404>Default minimum number of matches that causes a lock of the service auto watcher to add."
	DEFVAL { 100 }
	::= { winA3ConfigSrvcGroup 19 }

winA3ConfigSrvcButton OBJECT-TYPE
	SYNTAX INTEGER {
		none(1),
		add(2),
		remove(3),
		add-auto(4),
		remove-auto(5)
	}
	ACCESS read-write
	STATUS mandatory
	DESCRIPTION "&<caiWinA3.405>This attribute is used to add or remove the service watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigSrvcGroup 20 }

winA3ConfigSrvcAutoCount OBJECT-TYPE
	SYNTAX INTEGER
	ACCESS read-only
	STATUS mandatory
	DESCRIPTION "&<caiWinA3.406>Number of auto watchers in the service auto configuration table."
	::= { winA3ConfigSrvcGroup 21 }

winA3ConfigSrvcAutoLocked OBJECT-TYPE
	SYNTAX INTEGER
	ACCESS read-only
	STATUS mandatory
	DESCRIPTION "&<caiWinA3.407>Number of auto watchers in the service auto configuration table which are currently locked."
	::= { winA3ConfigSrvcGroup 22 }

winA3ConfigSrvcAutoTable OBJECT-TYPE
	SYNTAX SEQUENCE OF WinA3ConfigSrvcAutoEntry
	ACCESS not-accessible
	STATUS mandatory
	DESCRIPTION "&<caiWinA3.408>Configuration table containing a list of service auto watchers."
	::= { winA3ConfigSrvcGroup 23 }

winA3ConfigSrvcAutoEntry OBJECT-TYPE
	SYNTAX WinA3ConfigSrvcAutoEntry
	ACCESS not-accessible
	STATUS mandatory
	DESCRIPTION "&<caiWinA3.409>Entry in the service auto watcher configuration table."
	INDEX {
		winA3ConfigSrvcAutoWatcherName
	}
	::= { winA3ConfigSrvcAutoTable 1 }

WinA3ConfigSrvcAutoEntry ::= SEQUENCE {
	winA3ConfigSrvcAutoWatcherName DisplayString,
	winA3ConfigSrvcAutoName DisplayString,
	winA3ConfigSrvcAutoDisplayName DisplayString,
	winA3ConfigSrvcAutoStartupType INTEGER,
	winA3ConfigSrvcAutoAccount DisplayString,
	winA3ConfigSrvcAutoExecutable DisplayString,
	winA3ConfigSrvcAutoClusterType INTEGER,
	winA3ConfigSrvcAutoDescription DisplayString,
	winA3ConfigSrvcAutoWatcherMatchType INTEGER,
	winA3ConfigSrvcAutoWatcherLimit INTEGER,
	winA3ConfigSrvcAutoWatcherLastMatched INTEGER,
	winA3ConfigSrvcAutoAggLag INTEGER,
	winA3ConfigSrvcAutoConfigMonitor INTEGER,
	winA3ConfigSrvcAutoActivePolicy INTEGER,
	winA3ConfigSrvcAutoActiveMonitor INTEGER,
	winA3ConfigSrvcAutoExistPolicy INTEGER,
	winA3ConfigSrvcAutoExistMonitor INTEGER,
	winA3ConfigSrvcAutoButton INTEGER
}

winA3ConfigSrvcAutoWatcherName OBJECT-TYPE
	SYNTAX DisplayString
	ACCESS read-only
	STATUS mandatory
	DESCRIPTION "&<caiWinA3.410>Name of the service auto watcher."
	::= { winA3ConfigSrvcAutoEntry 1 }

winA3ConfigSrvcAutoName OBJECT-TYPE
	SYNTAX DisplayString
	ACCESS read-write
	STATUS mandatory
	DESCRIPTION "&<caiWinA3.411>Name of the service to be searched for during an auto discovery run. For uniqueness, the service name must be specified as defined in the Windows registry. This name is typically different to the display name of a service, visible in the service manager console. This name is used as a filter element for auto discovery and can be a regular expression (case-insensitive). It restricts the resources to be searched for during an auto discovery run."
	::= { winA3ConfigSrvcAutoEntry 2 }

winA3ConfigSrvcAutoDisplayName OBJECT-TYPE
	SYNTAX DisplayString
	ACCESS read-write
	STATUS mandatory
	DESCRIPTION "&<caiWinA3.412>The display name of a service as visible in the service manager console. This attribute is used as a filter element for auto discovery and can be a regular expression (case-insensitive). It restricts the resources to be searched for during an auto discovery run."
	::= { winA3ConfigSrvcAutoEntry 3 }

winA3ConfigSrvcAutoStartupType OBJECT-TYPE
	SYNTAX INTEGER {
		automatic(1),
		manual(2),
		disabled(3),
		any(4)
	}
	ACCESS read-write
	STATUS mandatory
	DESCRIPTION "&<caiWinA3.413>The current startup type (automatic, manual or disabled) of the service. This attribute is used as a filter element for auto discovery. It restricts the resources to be searched for during an auto discovery run."
	DEFVAL { 0 }
	::= { winA3ConfigSrvcAutoEntry 4 }

winA3ConfigSrvcAutoAccount OBJECT-TYPE
	SYNTAX DisplayString
	ACCESS read-write
	STATUS mandatory
	DESCRIPTION "&<caiWinA3.414>The account, the system uses to start this service. This attribute is used as a filter element for auto discovery and can be a regular expression (case-insensitive). It restricts the resources to be searched for during an auto discovery run."
	::= { winA3ConfigSrvcAutoEntry 5 }

winA3ConfigSrvcAutoExecutable OBJECT-TYPE
	SYNTAX DisplayString
	ACCESS read-write
	STATUS mandatory
	DESCRIPTION "&<caiWinA3.415>The executable belonging to this service. This attribute is used as a filter element for auto discovery and can be a regular expression (case-insensitive). It restricts the resources to be searched for during an auto discovery run."
	::= { winA3ConfigSrvcAutoEntry 6 }

winA3ConfigSrvcAutoClusterType OBJECT-TYPE
	SYNTAX INTEGER {
		not-clustered(1),
		clustered-active(2),
		clustered-passive(3),
		any(4)
	}
	ACCESS read-write
	STATUS mandatory
	DESCRIPTION "&<caiWinA3.416>Cluster type of the service to be searched for during an auto discovery run. If set to 1 (not-clustered), the search is restricted to not-clustered resources only. If set to 2 (clustered-active), the search is restricted to clustered-active resources only. If set to 3 (clustered-passive), the search is restricted to clustered-passive resources only. If set to 4 (any), the cluster type does not affect the search."
	DEFVAL { 0 }
	::= { winA3ConfigSrvcAutoEntry 7 }

winA3ConfigSrvcAutoDescription OBJECT-TYPE
	SYNTAX DisplayString
	ACCESS read-write
	STATUS mandatory
	DESCRIPTION "&<caiWinA3.417>Current description for the service auto watcher."
	::= { winA3ConfigSrvcAutoEntry 8 }

winA3ConfigSrvcAutoWatcherMatchType OBJECT-TYPE
	SYNTAX INTEGER {
		positive(1),
		negative(2)
	}
	ACCESS read-write
	STATUS mandatory
	DESCRIPTION "&<caiWinA3.418>Current search algorithm for the service auto watcher. The filter is the logical AND of all attributes used to identify or otherwise narrow down resources. If set to 1 (positive), the agent searches for service resources that match the filter. If set to 2 (negative), the agent searches for service resources that do not match the filter."
	DEFVAL { 0 }
	::= { winA3ConfigSrvcAutoEntry 9 }

winA3ConfigSrvcAutoWatcherLimit OBJECT-TYPE
	SYNTAX INTEGER
	ACCESS read-write
	STATUS mandatory
	DESCRIPTION "&<caiWinA3.419>Current minimum number of matches that causes the service auto watcher to be locked."
	::= { winA3ConfigSrvcAutoEntry 10 }

winA3ConfigSrvcAutoWatcherLastMatched OBJECT-TYPE
	SYNTAX INTEGER
	ACCESS read-only
	STATUS mandatory
	DESCRIPTION "&<caiWinA3.420>Number of matches for the last service auto discovery run."
	::= { winA3ConfigSrvcAutoEntry 11 }

winA3ConfigSrvcAutoAggLag OBJECT-TYPE
	SYNTAX INTEGER
	ACCESS read-write
	STATUS mandatory
	DESCRIPTION "&<caiWinA3.421>Current lag setting for the service auto watcher. Specifies the consecutive number of times at which any status is not in the ok state, before the aggregate status changes. This value must be greater than 0."
	::= { winA3ConfigSrvcAutoEntry 12 }

winA3ConfigSrvcAutoConfigMonitor OBJECT-TYPE
	SYNTAX INTEGER {
		do-not-monitor(1),
		down-warning(2),
		down-critical(3)
	}
	ACCESS read-write
	STATUS mandatory
	DESCRIPTION "&<caiWinA3.422>Default monitor level for the configuration change monitoring of any service watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3ConfigSrvcAutoEntry 13 }

winA3ConfigSrvcAutoActivePolicy OBJECT-TYPE
	SYNTAX INTEGER {
		should-be-active(1),
		should-not-be-active(2)
	}
	ACCESS read-write
	STATUS mandatory
	DESCRIPTION "&<caiWinA3.423>Default monitor policy for the activity monitoring of any service watcher created by the auto watcher."
	DEFVAL { 0 }
	::= { winA3ConfigSrvcAutoEntry 14 }

winA3ConfigSrvcAutoActiveMonitor OBJECT-TYPE
	SYNTAX INTEGER {
		do-not-monitor(1),
		down-warning(2),
		down-critical(3)
	}
	ACCESS read-write
	STATUS mandatory
	DESCRIPTION "&<caiWinA3.424>Default monitor level for the activity monitoring of any service watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3ConfigSrvcAutoEntry 15 }

winA3ConfigSrvcAutoExistPolicy OBJECT-TYPE
	SYNTAX INTEGER {
		should-exist(1),
		should-not-exist(2)
	}
	ACCESS read-write
	STATUS mandatory
	DESCRIPTION "&<caiWinA3.425>Default monitor policy for the existence monitoring of any service watcher created by the auto watcher. Specifies how the agent should evaluate the presence or absence of the monitored resource in order to determine whether the resource is in good condition. If set to 1 (should-exist), the resource is expected to be existent. If set to 2 (should-not-exist), the resource is expected to be nonexistent."
	DEFVAL { 0 }
	::= { winA3ConfigSrvcAutoEntry 16 }

winA3ConfigSrvcAutoExistMonitor OBJECT-TYPE
	SYNTAX INTEGER {
		do-not-monitor(1),
		down-warning(2),
		down-critical(3)
	}
	ACCESS read-write
	STATUS mandatory
	DESCRIPTION "&<caiWinA3.426>Default monitor level for the existence monitoring of any service watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3ConfigSrvcAutoEntry 17 }

winA3ConfigSrvcAutoButton OBJECT-TYPE
	SYNTAX INTEGER {
		active(1),
		remove(2),
		locked(3)
	}
	ACCESS read-write
	STATUS mandatory
	DESCRIPTION "&<caiWinA3.427>This attribute is used to enable/disable or remove the service auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigSrvcAutoEntry 18 }

--
-- The ConfigJob Group
--

winA3ConfigJobPollInterval OBJECT-TYPE
	SYNTAX INTEGER
	ACCESS read-write
	STATUS mandatory
	DESCRIPTION "&<caiWinA3.428>Time, in seconds, between collections of job information. Valid range: 30 seconds or greater."
	DEFVAL { 120 }
	::= { winA3ConfigJobGroup 1 }

winA3ConfigJobPollMethod OBJECT-TYPE
	SYNTAX INTEGER {
		disabled(1),
		poll-interval-only(2),
		poll-interval-and-query(3),
		query-only(4)
	}
	ACCESS read-write
	STATUS mandatory
	DESCRIPTION "&<caiWinA3.429>Specifies how and when the agent collects job information. If set to 1 (disabled), the agent does not retrieve the job information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigJobGroup 2 }

winA3ConfigJobAutoPollInterval OBJECT-TYPE
	SYNTAX INTEGER
	ACCESS read-write
	STATUS mandatory
	DESCRIPTION "&<caiWinA3.430>Time, in minutes, between the processing of the job auto watchers. Valid range: -1 (suspended), 30 minutes or greater."
	DEFVAL { 60 }
	::= { winA3ConfigJobGroup 3 }

winA3ConfigJobName OBJECT-TYPE
	SYNTAX DisplayString
	ACCESS read-write
	STATUS mandatory
	DESCRIPTION "&<caiWinA3.431>Name of the job for which to add or remove a watcher. A job is a set of processes that is handled as a process group. If used as a filter element for auto discovery, this name can be a regular expression (case-insensitive). In this case, it restricts the resources to be searched for during an auto discovery run."
	::= { winA3ConfigJobGroup 4 }

winA3ConfigJobDescription OBJECT-TYPE
	SYNTAX DisplayString
	ACCESS read-write
	STATUS mandatory
	DESCRIPTION "&<caiWinA3.432>Default description for the job watcher to add."
	::= { winA3ConfigJobGroup 5 }

winA3ConfigJobAggLag OBJECT-TYPE
	SYNTAX INTEGER
	ACCESS read-write
	STATUS mandatory
	DESCRIPTION "&<caiWinA3.433>Default aggregate lag setting for the job watcher to add. Specifies the consecutive number of times at which any status is not in the ok state, before the aggregate status changes. This value must be greater than 0."
	DEFVAL { 3 }
	::= { winA3ConfigJobGroup 6 }

winA3ConfigJobProcsMin OBJECT-TYPE
	SYNTAX INTEGER
	ACCESS read-write
	STATUS mandatory
	DESCRIPTION "&<caiWinA3.434>Default minimum threshold for the process count monitoring of the job watcher to add. This value represents a declining threshold and must be equal to or greater than 0, but cannot be greater than the maximum threshold. A value of -1 disables the evaluation of this threshold."
	DEFVAL { 1 }
	::= { winA3ConfigJobGroup 7 }

winA3ConfigJobProcsMax OBJECT-TYPE
	SYNTAX INTEGER
	ACCESS read-write
	STATUS mandatory
	DESCRIPTION "&<caiWinA3.435>Default maximum threshold for the process count monitoring of the job watcher to add. This value represents a rising threshold and must be equal to or greater than 0, but cannot be less than the minimum threshold. A value of -1 disables the evaluation of this threshold."
	DEFVAL { -1 }
	::= { winA3ConfigJobGroup 8 }

winA3ConfigJobProcsMonitor OBJECT-TYPE
	SYNTAX INTEGER {
		do-not-monitor(1),
		down-warning(2),
		down-critical(3)
	}
	ACCESS read-write
	STATUS mandatory
	DESCRIPTION "&<caiWinA3.436>Default monitor level for the process count monitoring of the job watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigJobGroup 9 }

winA3ConfigJobSizeWarn OBJECT-TYPE
	SYNTAX DisplayString
	ACCESS read-write
	STATUS mandatory
	DESCRIPTION "&<caiWinA3.437>Default warning threshold, in kilobytes, for the size utilization monitoring of the job watcher to add. This value represents a rising threshold and must be greater than 0.0, but cannot be greater than the critical threshold."
	DEFVAL { "100000.0" }
	::= { winA3ConfigJobGroup 10 }

winA3ConfigJobSizeCrit OBJECT-TYPE
	SYNTAX DisplayString
	ACCESS read-write
	STATUS mandatory
	DESCRIPTION "&<caiWinA3.438>Default critical threshold, in kilobytes, for the size utilization monitoring of the job watcher to add. This value represents a rising threshold and must be greater than 0.0, but cannot be less than the warning threshold."
	DEFVAL { "150000.0" }
	::= { winA3ConfigJobGroup 11 }

winA3ConfigJobSizeMonitor OBJECT-TYPE
	SYNTAX INTEGER {
		do-not-monitor(1),
		warning-only(2),
		critical-only(3),
		both(4)
	}
	ACCESS read-write
	STATUS mandatory
	DESCRIPTION "&<caiWinA3.439>Default monitor level for the size utilization monitoring of the job watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigJobGroup 12 }

winA3ConfigJobCpuInterval OBJECT-TYPE
	SYNTAX DisplayString
	ACCESS read-write
	STATUS mandatory
	DESCRIPTION "&<caiWinA3.440>Time, in seconds, defining the total value to use as base for the calculation of the cpu value. This means, the cpu usage of a job, in seconds, refers to this interval. Valid range: Greater 0 or '-1'. If set to '-1', the cpu value is calculated as the cpu usage, in seconds, used up to now by all currently active processes of the job since the start of the agent or the creation of the watcher. If the cpu interval is set to a value greater than the current poll interval and this time is not elapsed for the first time, the CPU value is extrapolated. If the cpu interval is set to a value smaller than the current poll interval, the CPU value is calculated as the appropriate fraction of the value for the last poll interval. If the cpu interval is set to a value greater than the current poll interval and this time is already elapsed, the CPU value is calculated as the sliding sum, i.e. the sum of the value for the current poll interval and the value calculated at the last poll, weighted according to it's fraction of the cpu interval. If the interval is set to '-1', any overloading (%) used for the thresholds will be ignored."
	DEFVAL { "1800.0" }
	::= { winA3ConfigJobGroup 13 }

winA3ConfigJobCpuWarn OBJECT-TYPE
	SYNTAX DisplayString
	ACCESS read-write
	STATUS mandatory
	DESCRIPTION "&<caiWinA3.441>Default warning threshold, in seconds, for the cpu utilization monitoring of the job watcher to add. The active warning threshold is derived from this value and represents a rising threshold. The derived value must be greater than 0.0, less than or equal to the total value (maximum capacity) of the monitored resource as specified in winA3StatusJobCpuInterval, but cannot be greater than the active critical threshold. These constraints will be maintained by the agent during all configuration actions. The threshold can be specified as either an absolute value (n) or a percentage (n%). The value of winA3StatusJobCpuInterval will be the reference value for n% notations."
	DEFVAL { "20.0%" }
	::= { winA3ConfigJobGroup 14 }

winA3ConfigJobCpuCrit OBJECT-TYPE
	SYNTAX DisplayString
	ACCESS read-write
	STATUS mandatory
	DESCRIPTION "&<caiWinA3.442>Default critical threshold, in seconds, for the cpu utilization monitoring of the job watcher to add. The active critical threshold is derived from this value and represents a rising threshold. The derived value must be greater than 0.0, less than or equal to the total value (maximum capacity) of the monitored resource as specified in winA3StatusJobCpuInterval, but cannot be less than the active warning threshold. These constraints will be maintained by the agent during all configuration actions. The threshold can be specified as either an absolute value (n) or a percentage (n%). The value of winA3StatusJobCpuInterval will be the reference value for n% notations."
	DEFVAL { "30.0%" }
	::= { winA3ConfigJobGroup 15 }

winA3ConfigJobCpuMonitor OBJECT-TYPE
	SYNTAX INTEGER {
		do-not-monitor(1),
		warning-only(2),
		critical-only(3),
		both(4)
	}
	ACCESS read-write
	STATUS mandatory
	DESCRIPTION "&<caiWinA3.443>Default monitor level for the cpu utilization monitoring of the job watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigJobGroup 16 }

winA3ConfigJobLossAction OBJECT-TYPE
	SYNTAX INTEGER {
		remove(1),
		up(2),
		down-warning(3),
		down-critical(4)
	}
	ACCESS read-write
	STATUS mandatory
	DESCRIPTION "&<caiWinA3.444>Default loss action for the job watcher to add. Specifies the action to take if the monitored job is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigJobGroup 17 }

winA3ConfigJobAutoTableWatcherName OBJECT-TYPE
	SYNTAX DisplayString
	ACCESS read-write
	STATUS mandatory
	DESCRIPTION "&<caiWinA3.445>Name of the job auto watcher to add or remove."
	::= { winA3ConfigJobGroup 18 }

winA3ConfigJobAutoTableWatcherMatchType OBJECT-TYPE
	SYNTAX INTEGER {
		positive(1),
		negative(2)
	}
	ACCESS read-write
	STATUS mandatory
	DESCRIPTION "&<caiWinA3.446>Default search algorithm for the job auto watcher to add. The filter is the logical AND of all attributes used to identify or otherwise narrow down resources. If set to 1 (positive), the agent searches for job resources that match the filter. If set to 2 (negative), the agent searches for job resources that do not match the filter."
	DEFVAL { 1 }
	::= { winA3ConfigJobGroup 19 }

winA3ConfigJobAutoTableWatcherLimit OBJECT-TYPE
	SYNTAX INTEGER
	ACCESS read-write
	STATUS mandatory
	DESCRIPTION "&<caiWinA3.447>Default minimum number of matches that causes a lock of the job auto watcher to add."
	DEFVAL { 100 }
	::= { winA3ConfigJobGroup 20 }

winA3ConfigJobButton OBJECT-TYPE
	SYNTAX INTEGER {
		none(1),
		add(2),
		remove(3),
		add-auto(4),
		remove-auto(5)
	}
	ACCESS read-write
	STATUS mandatory
	DESCRIPTION "&<caiWinA3.448>This attribute is used to add or remove the job watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigJobGroup 21 }

winA3ConfigJobAutoCount OBJECT-TYPE
	SYNTAX INTEGER
	ACCESS read-only
	STATUS mandatory
	DESCRIPTION "&<caiWinA3.449>Number of auto watchers in the job auto configuration table."
	::= { winA3ConfigJobGroup 22 }

winA3ConfigJobAutoLocked OBJECT-TYPE
	SYNTAX INTEGER
	ACCESS read-only
	STATUS mandatory
	DESCRIPTION "&<caiWinA3.450>Number of auto watchers in the job auto configuration table which are currently locked."
	::= { winA3ConfigJobGroup 23 }

winA3ConfigJobAutoTable OBJECT-TYPE
	SYNTAX SEQUENCE OF WinA3ConfigJobAutoEntry
	ACCESS not-accessible
	STATUS mandatory
	DESCRIPTION "&<caiWinA3.451>Configuration table containing a list of job auto watchers."
	::= { winA3ConfigJobGroup 24 }

winA3ConfigJobAutoEntry OBJECT-TYPE
	SYNTAX WinA3ConfigJobAutoEntry
	ACCESS not-accessible
	STATUS mandatory
	DESCRIPTION "&<caiWinA3.452>Entry in the job auto watcher configuration table."
	INDEX {
		winA3ConfigJobAutoWatcherName
	}
	::= { winA3ConfigJobAutoTable 1 }

WinA3ConfigJobAutoEntry ::= SEQUENCE {
	winA3ConfigJobAutoWatcherName DisplayString,
	winA3ConfigJobAutoName DisplayString,
	winA3ConfigJobAutoDescription DisplayString,
	winA3ConfigJobAutoWatcherMatchType INTEGER,
	winA3ConfigJobAutoWatcherLimit INTEGER,
	winA3ConfigJobAutoWatcherLastMatched INTEGER,
	winA3ConfigJobAutoAggLag INTEGER,
	winA3ConfigJobAutoProcsMin INTEGER,
	winA3ConfigJobAutoProcsMax INTEGER,
	winA3ConfigJobAutoProcsMonitor INTEGER,
	winA3ConfigJobAutoSizeWarn DisplayString,
	winA3ConfigJobAutoSizeCrit DisplayString,
	winA3ConfigJobAutoSizeMonitor INTEGER,
	winA3ConfigJobAutoCpuInterval DisplayString,
	winA3ConfigJobAutoCpuWarn DisplayString,
	winA3ConfigJobAutoCpuCrit DisplayString,
	winA3ConfigJobAutoCpuMonitor INTEGER,
	winA3ConfigJobAutoLossAction INTEGER,
	winA3ConfigJobAutoButton INTEGER
}

winA3ConfigJobAutoWatcherName OBJECT-TYPE
	SYNTAX DisplayString
	ACCESS read-only
	STATUS mandatory
	DESCRIPTION "&<caiWinA3.453>Name of the job auto watcher."
	::= { winA3ConfigJobAutoEntry 1 }

winA3ConfigJobAutoName OBJECT-TYPE
	SYNTAX DisplayString
	ACCESS read-write
	STATUS mandatory
	DESCRIPTION "&<caiWinA3.454>Name of the job to be searched for during an auto discovery run. A job is a set of processes that is handled as a process group. This name is used as a filter element for auto discovery and can be a regular expression (case-insensitive). It restricts the resources to be searched for during an auto discovery run."
	::= { winA3ConfigJobAutoEntry 2 }

winA3ConfigJobAutoDescription OBJECT-TYPE
	SYNTAX DisplayString
	ACCESS read-write
	STATUS mandatory
	DESCRIPTION "&<caiWinA3.455>Current description for the job auto watcher."
	::= { winA3ConfigJobAutoEntry 3 }

winA3ConfigJobAutoWatcherMatchType OBJECT-TYPE
	SYNTAX INTEGER {
		positive(1),
		negative(2)
	}
	ACCESS read-write
	STATUS mandatory
	DESCRIPTION "&<caiWinA3.456>Current search algorithm for the job auto watcher. The filter is the logical AND of all attributes used to identify or otherwise narrow down resources. If set to 1 (positive), the agent searches for job resources that match the filter. If set to 2 (negative), the agent searches for job resources that do not match the filter."
	DEFVAL { 0 }
	::= { winA3ConfigJobAutoEntry 4 }

winA3ConfigJobAutoWatcherLimit OBJECT-TYPE
	SYNTAX INTEGER
	ACCESS read-write
	STATUS mandatory
	DESCRIPTION "&<caiWinA3.457>Current minimum number of matches that causes the job auto watcher to be locked."
	::= { winA3ConfigJobAutoEntry 5 }

winA3ConfigJobAutoWatcherLastMatched OBJECT-TYPE
	SYNTAX INTEGER
	ACCESS read-only
	STATUS mandatory
	DESCRIPTION "&<caiWinA3.458>Number of matches for the last job auto discovery run."
	::= { winA3ConfigJobAutoEntry 6 }

winA3ConfigJobAutoAggLag OBJECT-TYPE
	SYNTAX INTEGER
	ACCESS read-write
	STATUS mandatory
	DESCRIPTION "&<caiWinA3.459>Current lag setting for the job auto watcher. Specifies the consecutive number of times at which any status is not in the ok state, before the aggregate status changes. This value must be greater than 0."
	::= { winA3ConfigJobAutoEntry 7 }

winA3ConfigJobAutoProcsMin OBJECT-TYPE
	SYNTAX INTEGER
	ACCESS read-write
	STATUS mandatory
	DESCRIPTION "&<caiWinA3.460>Default minimum threshold for the process count monitoring of any job watcher created by the auto watcher. This value represents a declining threshold and must be equal to or greater than 0, but cannot be greater than the maximum threshold. A value of -1 disables the evaluation of this threshold."
	DEFVAL { -2 }
	::= { winA3ConfigJobAutoEntry 8 }

winA3ConfigJobAutoProcsMax OBJECT-TYPE
	SYNTAX INTEGER
	ACCESS read-write
	STATUS mandatory
	DESCRIPTION "&<caiWinA3.461>Default maximum threshold for the process count monitoring of any job watcher created by the auto watcher. This value represents a rising threshold and must be equal to or greater than 0, but cannot be less than the minimum threshold. A value of -1 disables the evaluation of this threshold."
	DEFVAL { -2 }
	::= { winA3ConfigJobAutoEntry 9 }

winA3ConfigJobAutoProcsMonitor OBJECT-TYPE
	SYNTAX INTEGER {
		do-not-monitor(1),
		down-warning(2),
		down-critical(3)
	}
	ACCESS read-write
	STATUS mandatory
	DESCRIPTION "&<caiWinA3.462>Default monitor level for the process count monitoring of any job watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3ConfigJobAutoEntry 10 }

winA3ConfigJobAutoSizeWarn OBJECT-TYPE
	SYNTAX DisplayString
	ACCESS read-write
	STATUS mandatory
	DESCRIPTION "&<caiWinA3.463>Default warning threshold, in kilobytes, for the size utilization monitoring of any job watcher created by the auto watcher. This value represents a rising threshold and must be greater than 0.0, but cannot be greater than the critical threshold."
	::= { winA3ConfigJobAutoEntry 11 }

winA3ConfigJobAutoSizeCrit OBJECT-TYPE
	SYNTAX DisplayString
	ACCESS read-write
	STATUS mandatory
	DESCRIPTION "&<caiWinA3.464>Default critical threshold, in kilobytes, for the size utilization monitoring of any job watcher created by the auto watcher. This value represents a rising threshold and must be greater than 0.0, but cannot be less than the warning threshold."
	::= { winA3ConfigJobAutoEntry 12 }

winA3ConfigJobAutoSizeMonitor OBJECT-TYPE
	SYNTAX INTEGER {
		do-not-monitor(1),
		warning-only(2),
		critical-only(3),
		both(4)
	}
	ACCESS read-write
	STATUS mandatory
	DESCRIPTION "&<caiWinA3.465>Default monitor level for the size utilization monitoring of any job watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigJobAutoEntry 13 }

winA3ConfigJobAutoCpuInterval OBJECT-TYPE
	SYNTAX DisplayString
	ACCESS read-write
	STATUS mandatory
	DESCRIPTION "&<caiWinA3.466>Time, in seconds, defining the total value to use as base for the calculation of the cpu value. This means, the cpu usage of a job, in seconds, refers to this interval. Valid range: Greater 0 or '-1'. If set to '-1', the cpu value is calculated as the cpu usage, in seconds, used up to now by all currently active processes of the job since the start of the agent or the creation of the watcher. If the cpu interval is set to a value greater than the current poll interval and this time is not elapsed for the first time, the CPU value is extrapolated. If the cpu interval is set to a value smaller than the current poll interval, the CPU value is calculated as the appropriate fraction of the value for the last poll interval. If the cpu interval is set to a value greater than the current poll interval and this time is already elapsed, the CPU value is calculated as the sliding sum, i.e. the sum of the value for the current poll interval and the value calculated at the last poll, weighted according to it's fraction of the cpu interval. If the interval is set to '-1', any overloading (%) used for the thresholds will be ignored."
	::= { winA3ConfigJobAutoEntry 14 }

winA3ConfigJobAutoCpuWarn OBJECT-TYPE
	SYNTAX DisplayString
	ACCESS read-write
	STATUS mandatory
	DESCRIPTION "&<caiWinA3.467>Default warning threshold, in seconds, for the cpu utilization monitoring of any job watcher created by the auto watcher. The active warning threshold is derived from this value and represents a rising threshold. The derived value must be greater than 0.0, less than or equal to the total value (maximum capacity) of the monitored resource as specified in winA3StatusJobCpuInterval, but cannot be greater than the active critical threshold. These constraints will be maintained by the agent during all configuration actions. The threshold can be specified as either an absolute value (n) or a percentage (n%). The value of winA3StatusJobCpuInterval will be the reference value for n% notations."
	::= { winA3ConfigJobAutoEntry 15 }

winA3ConfigJobAutoCpuCrit OBJECT-TYPE
	SYNTAX DisplayString
	ACCESS read-write
	STATUS mandatory
	DESCRIPTION "&<caiWinA3.468>Default critical threshold, in seconds, for the cpu utilization monitoring of any job watcher created by the auto watcher. The active critical threshold is derived from this value and represents a rising threshold. The derived value must be greater than 0.0, less than or equal to the total value (maximum capacity) of the monitored resource as specified in winA3StatusJobCpuInterval, but cannot be less than the active warning threshold. These constraints will be maintained by the agent during all configuration actions. The threshold can be specified as either an absolute value (n) or a percentage (n%). The value of winA3StatusJobCpuInterval will be the reference value for n% notations."
	::= { winA3ConfigJobAutoEntry 16 }

winA3ConfigJobAutoCpuMonitor OBJECT-TYPE
	SYNTAX INTEGER {
		do-not-monitor(1),
		warning-only(2),
		critical-only(3),
		both(4)
	}
	ACCESS read-write
	STATUS mandatory
	DESCRIPTION "&<caiWinA3.469>Default monitor level for the cpu utilization monitoring of any job watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigJobAutoEntry 17 }

winA3ConfigJobAutoLossAction OBJECT-TYPE
	SYNTAX INTEGER {
		remove(1),
		up(2),
		down-warning(3),
		down-critical(4)
	}
	ACCESS read-write
	STATUS mandatory
	DESCRIPTION "&<caiWinA3.470>Default loss action for any job watcher created by the auto watcher. Specifies the action to take if the monitored job is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3ConfigJobAutoEntry 18 }

winA3ConfigJobAutoButton OBJECT-TYPE
	SYNTAX INTEGER {
		active(1),
		remove(2),
		locked(3)
	}
	ACCESS read-write
	STATUS mandatory
	DESCRIPTION "&<caiWinA3.471>This attribute is used to enable/disable or remove the job auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigJobAutoEntry 19 }

--
-- The ConfigSess Group
--

winA3ConfigSessPollInterval OBJECT-TYPE
	SYNTAX INTEGER
	ACCESS read-write
	STATUS mandatory
	DESCRIPTION "&<caiWinA3.472>Time, in seconds, between collections of terminal session information. Valid range: 30 seconds or greater."
	DEFVAL { 120 }
	::= { winA3ConfigSessGroup 1 }

winA3ConfigSessPollMethod OBJECT-TYPE
	SYNTAX INTEGER {
		disabled(1),
		poll-interval-only(2),
		poll-interval-and-query(3),
		query-only(4)
	}
	ACCESS read-write
	STATUS mandatory
	DESCRIPTION "&<caiWinA3.473>Specifies how and when the agent collects terminal session information. If set to 1 (disabled), the agent does not retrieve the terminal session information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigSessGroup 2 }

winA3ConfigSessWatcherName OBJECT-TYPE
	SYNTAX DisplayString
	ACCESS read-write
	STATUS mandatory
	DESCRIPTION "&<caiWinA3.474>An arbitrary name for the watcher. Note that monitoring of sessions is not applicable on Windows XP and on Windows 2000 Professional."
	::= { winA3ConfigSessGroup 3 }

winA3ConfigSessMatchType OBJECT-TYPE
	SYNTAX INTEGER {
		positive-regular-expression(1),
		negative-regular-expression(2),
		positive-string-compare(3),
		negative-string-compare(4)
	}
	ACCESS read-write
	STATUS mandatory
	DESCRIPTION "&<caiWinA3.475>Default search algorithm for the terminal session watcher. The filter is the logical AND of all attributes used to identify or otherwise narrow down resources. If the value of one of these attributes includes 'wildcards', then the watcher will basically behave like a one-to-many watcher, i.e. it may monitor two or more resources simultaneously. If set to 1 (positive-regular-expression), the agent searches for terminal session resources that match the filter as a regular expression (case-insensitive). If set to 2 (negative-regular-expression), the agent searches for terminal session resources that do not match the filter as a regular expression (case-insensitive). If set to 3 (positive-string-compare), the agent searches for terminal session resources that match the filter as string comparison (case-insensitive). If set to 4 (negative-string-compare), the agent searches for terminal session resources that do not match the filter as string comparison (case-insensitive)."
	DEFVAL { 3 }
	::= { winA3ConfigSessGroup 4 }

winA3ConfigSessClient OBJECT-TYPE
	SYNTAX DisplayString
	ACCESS read-write
	STATUS mandatory
	DESCRIPTION "&<caiWinA3.476>Client name of the session for which to add or remove a watcher. The client name is the name of the host, from where this session was initiated. This name is used as a filter element for one-to-many monitoring (one watcher monitors several resources simultaneously) and can be a regular expression (case-insensitive). The expression '.*' always matches any string, independent from the match type. Note that monitoring of sessions is not applicable on Windows XP and on Windows 2000 Professional."
	DEFVAL { ".*" }
	::= { winA3ConfigSessGroup 5 }

winA3ConfigSessUser OBJECT-TYPE
	SYNTAX DisplayString
	ACCESS read-write
	STATUS mandatory
	DESCRIPTION "&<caiWinA3.477>User name of the session for which to add or remove a watcher. The user name specifies the user, who logged in and is in the form 'domainName\\userName'. This name is used as a filter element for one-to-many monitoring (one watcher monitors several resources simultaneously) and can be a regular expression (case-insensitive). The expression '.*' always matches any string, independent from the match type. Note that monitoring of sessions is not applicable on Windows XP and on Windows 2000 Professional."
	DEFVAL { ".*" }
	::= { winA3ConfigSessGroup 6 }

winA3ConfigSessEvalPolicy OBJECT-TYPE
	SYNTAX INTEGER {
		individual(1),
		min(2),
		max(3),
		sum(4),
		avg(5)
	}
	ACCESS read-write
	STATUS mandatory
	DESCRIPTION "&<caiWinA3.478>Default evaluation policy for the terminal session watcher. Defines how metric values will be calculated and 'culprits' be determined if two or more terminal session resources fall into the monitoring scope of a one-to-many watcher. If set to 1 (individual), metric values will be set to the worst values (lowest and/or highest) of all terminal session instances; if the value of a metric violates the threshold condition, the respective 'culprits' list will contain all instances individually violating the most severe threshold. If set to 2 (min), metric values will be set to the lowest (minimum) values of all terminal session instances; if the value of a metric violates the threshold condition, the respective 'culprits' list will contain all instances having the same minimum value. If set to 3 (max), metric values will be set to the highest (maximum) values of all terminal session instances; if the value of a metric violates the threshold condition, the respective 'culprits' list will contain all instances having the same maximum value. If set to 4 (sum), metric values will be set to the cumulative values (sum) of all terminal session instances; if the value of a metric violates the threshold condition, the respective 'culprits' list will contain all instances. If set to 5 (avg), metric values will be set to the average values of all terminal session instances; if the value of a metric violates the threshold condition, the respective 'culprits' list will contain all instances individually violating the most severe threshold."
	DEFVAL { 1 }
	::= { winA3ConfigSessGroup 7 }

winA3ConfigSessDescription OBJECT-TYPE
	SYNTAX DisplayString
	ACCESS read-write
	STATUS mandatory
	DESCRIPTION "&<caiWinA3.479>Default description for the terminal session watcher to add."
	::= { winA3ConfigSessGroup 8 }

winA3ConfigSessAggLag OBJECT-TYPE
	SYNTAX INTEGER
	ACCESS read-write
	STATUS mandatory
	DESCRIPTION "&<caiWinA3.480>Default aggregate lag setting for the terminal session watcher to add. Specifies the consecutive number of times at which any status is not in the ok state, before the aggregate status changes. This value must be greater than 0."
	DEFVAL { 3 }
	::= { winA3ConfigSessGroup 9 }

winA3ConfigSessInstMin OBJECT-TYPE
	SYNTAX INTEGER
	ACCESS read-write
	STATUS mandatory
	DESCRIPTION "&<caiWinA3.481>Default minimum threshold for the instance count monitoring of the terminal session watcher to add. This value represents a declining threshold and must be equal to or greater than 0, but cannot be greater than the maximum threshold. A value of -1 disables the evaluation of this threshold."
	DEFVAL { -1 }
	::= { winA3ConfigSessGroup 10 }

winA3ConfigSessInstMax OBJECT-TYPE
	SYNTAX INTEGER
	ACCESS read-write
	STATUS mandatory
	DESCRIPTION "&<caiWinA3.482>Default maximum threshold for the instance count monitoring of the terminal session watcher to add. This value represents a rising threshold and must be equal to or greater than 0, but cannot be less than the minimum threshold. A value of -1 disables the evaluation of this threshold."
	DEFVAL { 100 }
	::= { winA3ConfigSessGroup 11 }

winA3ConfigSessInstMonitor OBJECT-TYPE
	SYNTAX INTEGER {
		do-not-monitor(1),
		down-warning(2),
		down-critical(3)
	}
	ACCESS read-write
	STATUS mandatory
	DESCRIPTION "&<caiWinA3.483>Default monitor level for the instance count monitoring of the terminal session watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigSessGroup 12 }

winA3ConfigSessSizeWarn OBJECT-TYPE
	SYNTAX DisplayString
	ACCESS read-write
	STATUS mandatory
	DESCRIPTION "&<caiWinA3.484>Default warning threshold, in kilobytes, for the size utilization monitoring of the terminal session watcher to add. This value represents a rising threshold and must be greater than 0.0, but cannot be greater than the critical threshold."
	DEFVAL { "100000.0" }
	::= { winA3ConfigSessGroup 13 }

winA3ConfigSessSizeCrit OBJECT-TYPE
	SYNTAX DisplayString
	ACCESS read-write
	STATUS mandatory
	DESCRIPTION "&<caiWinA3.485>Default critical threshold, in kilobytes, for the size utilization monitoring of the terminal session watcher to add. This value represents a rising threshold and must be greater than 0.0, but cannot be less than the warning threshold."
	DEFVAL { "150000.0" }
	::= { winA3ConfigSessGroup 14 }

winA3ConfigSessSizeMonitor OBJECT-TYPE
	SYNTAX INTEGER {
		do-not-monitor(1),
		warning-only(2),
		critical-only(3),
		both(4)
	}
	ACCESS read-write
	STATUS mandatory
	DESCRIPTION "&<caiWinA3.486>Default monitor level for the size utilization monitoring of the terminal session watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigSessGroup 15 }

winA3ConfigSessCpuInterval OBJECT-TYPE
	SYNTAX DisplayString
	ACCESS read-write
	STATUS mandatory
	DESCRIPTION "&<caiWinA3.487>Time, in seconds, defining the total value to use as base for the calculation of the cpu value. This means, the cpu usage of a session, in seconds, refers to this interval. Valid range: Greater 0 or '-1'. If set to '-1', the cpu value is calculated as the cpu usage, in seconds, used up to now by all currently active processes of the session since the start of the agent or the creation of the watcher. If the cpu interval is set to a value greater than the current poll interval and this time is not elapsed for the first time, the CPU value is extrapolated. If the cpu interval is set to a value smaller than the current poll interval, the CPU value is calculated as the appropriate fraction of the value for the last poll interval. If the cpu interval is set to a value greater than the current poll interval and this time is already elapsed, the CPU value is calculated as the sliding sum, i.e. the sum of the value for the current poll interval and the value calculated at the last poll, weighted according to it's fraction of the cpu interval. If the interval is set to '-1', any overloading (%) used for the thresholds will be ignored."
	DEFVAL { "1800.0" }
	::= { winA3ConfigSessGroup 16 }

winA3ConfigSessCpuWarn OBJECT-TYPE
	SYNTAX DisplayString
	ACCESS read-write
	STATUS mandatory
	DESCRIPTION "&<caiWinA3.488>Default warning threshold, in seconds, for the cpu utilization monitoring of the terminal session watcher to add. The active warning threshold is derived from this value and represents a rising threshold. The derived value must be greater than 0.0, less than or equal to the total value (maximum capacity) of the monitored resource as specified in winA3StatusSessCpuInterval, but cannot be greater than the active critical threshold. These constraints will be maintained by the agent during all configuration actions. The threshold can be specified as either an absolute value (n) or a percentage (n%). The value of winA3StatusSessCpuInterval will be the reference value for n% notations."
	DEFVAL { "20.0%" }
	::= { winA3ConfigSessGroup 17 }

winA3ConfigSessCpuCrit OBJECT-TYPE
	SYNTAX DisplayString
	ACCESS read-write
	STATUS mandatory
	DESCRIPTION "&<caiWinA3.489>Default critical threshold, in seconds, for the cpu utilization monitoring of the terminal session watcher to add. The active critical threshold is derived from this value and represents a rising threshold. The derived value must be greater than 0.0, less than or equal to the total value (maximum capacity) of the monitored resource as specified in winA3StatusSessCpuInterval, but cannot be less than the active warning threshold. These constraints will be maintained by the agent during all configuration actions. The threshold can be specified as either an absolute value (n) or a percentage (n%). The value of winA3StatusSessCpuInterval will be the reference value for n% notations."
	DEFVAL { "30.0%" }
	::= { winA3ConfigSessGroup 18 }

winA3ConfigSessCpuMonitor OBJECT-TYPE
	SYNTAX INTEGER {
		do-not-monitor(1),
		warning-only(2),
		critical-only(3),
		both(4)
	}
	ACCESS read-write
	STATUS mandatory
	DESCRIPTION "&<caiWinA3.490>Default monitor level for the cpu utilization monitoring of the terminal session watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigSessGroup 19 }

winA3ConfigSessButton OBJECT-TYPE
	SYNTAX INTEGER {
		none(1),
		add(2),
		remove(3)
	}
	ACCESS read-write
	STATUS mandatory
	DESCRIPTION "&<caiWinA3.491>This attribute is used to add or remove the terminal session watcher specified by the current setting of the watcher name attribute(s) in this group. If set to 2 (add), the agent adds the specified watcher to the status table using the current values of the remaining attributes as defaults. If set to 3 (remove), the agent removes the specified watcher from the status table. This attribute cannot be set to 1 (none)."
	DEFVAL { 1 }
	::= { winA3ConfigSessGroup 20 }

--
-- The ConfigPrn Group
--

winA3ConfigPrnPollInterval OBJECT-TYPE
	SYNTAX INTEGER
	ACCESS read-write
	STATUS mandatory
	DESCRIPTION "&<caiWinA3.492>Time, in seconds, between collections of printer information. Valid range: 30 seconds or greater."
	DEFVAL { 120 }
	::= { winA3ConfigPrnGroup 1 }

winA3ConfigPrnPollMethod OBJECT-TYPE
	SYNTAX INTEGER {
		disabled(1),
		poll-interval-only(2),
		poll-interval-and-query(3),
		query-only(4)
	}
	ACCESS read-write
	STATUS mandatory
	DESCRIPTION "&<caiWinA3.493>Specifies how and when the agent collects printer information. If set to 1 (disabled), the agent does not retrieve the printer information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigPrnGroup 2 }

winA3ConfigPrnAutoPollInterval OBJECT-TYPE
	SYNTAX INTEGER
	ACCESS read-write
	STATUS mandatory
	DESCRIPTION "&<caiWinA3.494>Time, in minutes, between the processing of the printer auto watchers. Valid range: -1 (suspended), 30 minutes or greater."
	DEFVAL { 60 }
	::= { winA3ConfigPrnGroup 3 }

winA3ConfigPrnName OBJECT-TYPE
	SYNTAX DisplayString
	ACCESS read-write
	STATUS mandatory
	DESCRIPTION "&<caiWinA3.495>Name of the printer for which to add or remove a watcher. If used as a filter element for auto discovery, this name can be a regular expression (case-insensitive). In this case, it restricts the resources to be searched for during an auto discovery run."
	::= { winA3ConfigPrnGroup 4 }

winA3ConfigPrnDescription OBJECT-TYPE
	SYNTAX DisplayString
	ACCESS read-write
	STATUS mandatory
	DESCRIPTION "&<caiWinA3.496>Default description for the printer watcher to add."
	::= { winA3ConfigPrnGroup 5 }

winA3ConfigPrnAggLag OBJECT-TYPE
	SYNTAX INTEGER
	ACCESS read-write
	STATUS mandatory
	DESCRIPTION "&<caiWinA3.497>Default aggregate lag setting for the printer watcher to add. Specifies the consecutive number of times at which any status is not in the ok state, before the aggregate status changes. This value must be greater than 0."
	DEFVAL { 3 }
	::= { winA3ConfigPrnGroup 6 }

winA3ConfigPrnEventMonitor OBJECT-TYPE
	SYNTAX INTEGER {
		do-not-monitor(1),
		down-warning(2),
		down-critical(3)
	}
	ACCESS read-write
	STATUS mandatory
	DESCRIPTION "&<caiWinA3.498>Default monitor level for the event monitoring of the printer watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigPrnGroup 7 }

winA3ConfigPrnQueueWarn OBJECT-TYPE
	SYNTAX INTEGER
	ACCESS read-write
	STATUS mandatory
	DESCRIPTION "&<caiWinA3.499>Default warning threshold for the queue size monitoring of the printer watcher to add. This value represents a rising threshold and must be greater than 0, but cannot be greater than the critical threshold."
	DEFVAL { 100 }
	::= { winA3ConfigPrnGroup 8 }

winA3ConfigPrnQueueCrit OBJECT-TYPE
	SYNTAX INTEGER
	ACCESS read-write
	STATUS mandatory
	DESCRIPTION "&<caiWinA3.500>Default critical threshold for the queue size monitoring of the printer watcher to add. This value represents a rising threshold and must be greater than 0, but cannot be less than the warning threshold."
	DEFVAL { 200 }
	::= { winA3ConfigPrnGroup 9 }

winA3ConfigPrnQueueMonitor OBJECT-TYPE
	SYNTAX INTEGER {
		do-not-monitor(1),
		warning-only(2),
		critical-only(3),
		both(4)
	}
	ACCESS read-write
	STATUS mandatory
	DESCRIPTION "&<caiWinA3.501>Default monitor level for the queue size monitoring of the printer watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigPrnGroup 10 }

winA3ConfigPrnLossAction OBJECT-TYPE
	SYNTAX INTEGER {
		remove(1),
		up(2),
		down-warning(3),
		down-critical(4)
	}
	ACCESS read-write
	STATUS mandatory
	DESCRIPTION "&<caiWinA3.502>Default loss action for the printer watcher to add. Specifies the action to take if the monitored printer is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigPrnGroup 11 }

winA3ConfigPrnAutoTableWatcherName OBJECT-TYPE
	SYNTAX DisplayString
	ACCESS read-write
	STATUS mandatory
	DESCRIPTION "&<caiWinA3.503>Name of the printer auto watcher to add or remove."
	::= { winA3ConfigPrnGroup 12 }

winA3ConfigPrnAutoTableWatcherMatchType OBJECT-TYPE
	SYNTAX INTEGER {
		positive(1),
		negative(2)
	}
	ACCESS read-write
	STATUS mandatory
	DESCRIPTION "&<caiWinA3.504>Default search algorithm for the printer auto watcher to add. The filter is the logical AND of all attributes used to identify or otherwise narrow down resources. If set to 1 (positive), the agent searches for printer resources that match the filter. If set to 2 (negative), the agent searches for printer resources that do not match the filter."
	DEFVAL { 1 }
	::= { winA3ConfigPrnGroup 13 }

winA3ConfigPrnAutoTableWatcherLimit OBJECT-TYPE
	SYNTAX INTEGER
	ACCESS read-write
	STATUS mandatory
	DESCRIPTION "&<caiWinA3.505>Default minimum number of matches that causes a lock of the printer auto watcher to add."
	DEFVAL { 100 }
	::= { winA3ConfigPrnGroup 14 }

winA3ConfigPrnButton OBJECT-TYPE
	SYNTAX INTEGER {
		none(1),
		add(2),
		remove(3),
		add-auto(4),
		remove-auto(5)
	}
	ACCESS read-write
	STATUS mandatory
	DESCRIPTION "&<caiWinA3.506>This attribute is used to add or remove the printer watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigPrnGroup 15 }

winA3ConfigPrnAutoCount OBJECT-TYPE
	SYNTAX INTEGER
	ACCESS read-only
	STATUS mandatory
	DESCRIPTION "&<caiWinA3.507>Number of auto watchers in the printer auto configuration table."
	::= { winA3ConfigPrnGroup 16 }

winA3ConfigPrnAutoLocked OBJECT-TYPE
	SYNTAX INTEGER
	ACCESS read-only
	STATUS mandatory
	DESCRIPTION "&<caiWinA3.508>Number of auto watchers in the printer auto configuration table which are currently locked."
	::= { winA3ConfigPrnGroup 17 }

winA3ConfigPrnAutoTable OBJECT-TYPE
	SYNTAX SEQUENCE OF WinA3ConfigPrnAutoEntry
	ACCESS not-accessible
	STATUS mandatory
	DESCRIPTION "&<caiWinA3.509>Configuration table containing a list of printer auto watchers."
	::= { winA3ConfigPrnGroup 18 }

winA3ConfigPrnAutoEntry OBJECT-TYPE
	SYNTAX WinA3ConfigPrnAutoEntry
	ACCESS not-accessible
	STATUS mandatory
	DESCRIPTION "&<caiWinA3.510>Entry in the printer auto watcher configuration table."
	INDEX {
		winA3ConfigPrnAutoWatcherName
	}
	::= { winA3ConfigPrnAutoTable 1 }

WinA3ConfigPrnAutoEntry ::= SEQUENCE {
	winA3ConfigPrnAutoWatcherName DisplayString,
	winA3ConfigPrnAutoName DisplayString,
	winA3ConfigPrnAutoDescription DisplayString,
	winA3ConfigPrnAutoWatcherMatchType INTEGER,
	winA3ConfigPrnAutoWatcherLimit INTEGER,
	winA3ConfigPrnAutoWatcherLastMatched INTEGER,
	winA3ConfigPrnAutoAggLag INTEGER,
	winA3ConfigPrnAutoEventMonitor INTEGER,
	winA3ConfigPrnAutoQueueWarn INTEGER,
	winA3ConfigPrnAutoQueueCrit INTEGER,
	winA3ConfigPrnAutoQueueMonitor INTEGER,
	winA3ConfigPrnAutoLossAction INTEGER,
	winA3ConfigPrnAutoButton INTEGER
}

winA3ConfigPrnAutoWatcherName OBJECT-TYPE
	SYNTAX DisplayString
	ACCESS read-only
	STATUS mandatory
	DESCRIPTION "&<caiWinA3.511>Name of the printer auto watcher."
	::= { winA3ConfigPrnAutoEntry 1 }

winA3ConfigPrnAutoName OBJECT-TYPE
	SYNTAX DisplayString
	ACCESS read-write
	STATUS mandatory
	DESCRIPTION "&<caiWinA3.512>Name of the printer to be searched for during an auto discovery run. This name is used as a filter element for auto discovery and can be a regular expression (case-insensitive). It restricts the resources to be searched for during an auto discovery run."
	::= { winA3ConfigPrnAutoEntry 2 }

winA3ConfigPrnAutoDescription OBJECT-TYPE
	SYNTAX DisplayString
	ACCESS read-write
	STATUS mandatory
	DESCRIPTION "&<caiWinA3.513>Current description for the printer auto watcher."
	::= { winA3ConfigPrnAutoEntry 3 }

winA3ConfigPrnAutoWatcherMatchType OBJECT-TYPE
	SYNTAX INTEGER {
		positive(1),
		negative(2)
	}
	ACCESS read-write
	STATUS mandatory
	DESCRIPTION "&<caiWinA3.514>Current search algorithm for the printer auto watcher. The filter is the logical AND of all attributes used to identify or otherwise narrow down resources. If set to 1 (positive), the agent searches for printer resources that match the filter. If set to 2 (negative), the agent searches for printer resources that do not match the filter."
	DEFVAL { 0 }
	::= { winA3ConfigPrnAutoEntry 4 }

winA3ConfigPrnAutoWatcherLimit OBJECT-TYPE
	SYNTAX INTEGER
	ACCESS read-write
	STATUS mandatory
	DESCRIPTION "&<caiWinA3.515>Current minimum number of matches that causes the printer auto watcher to be locked."
	::= { winA3ConfigPrnAutoEntry 5 }

winA3ConfigPrnAutoWatcherLastMatched OBJECT-TYPE
	SYNTAX INTEGER
	ACCESS read-only
	STATUS mandatory
	DESCRIPTION "&<caiWinA3.516>Number of matches for the last printer auto discovery run."
	::= { winA3ConfigPrnAutoEntry 6 }

winA3ConfigPrnAutoAggLag OBJECT-TYPE
	SYNTAX INTEGER
	ACCESS read-write
	STATUS mandatory
	DESCRIPTION "&<caiWinA3.517>Current lag setting for the printer auto watcher. Specifies the consecutive number of times at which any status is not in the ok state, before the aggregate status changes. This value must be greater than 0."
	::= { winA3ConfigPrnAutoEntry 7 }

winA3ConfigPrnAutoEventMonitor OBJECT-TYPE
	SYNTAX INTEGER {
		do-not-monitor(1),
		down-warning(2),
		down-critical(3)
	}
	ACCESS read-write
	STATUS mandatory
	DESCRIPTION "&<caiWinA3.518>Default monitor level for the event monitoring of any printer watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3ConfigPrnAutoEntry 8 }

winA3ConfigPrnAutoQueueWarn OBJECT-TYPE
	SYNTAX INTEGER
	ACCESS read-write
	STATUS mandatory
	DESCRIPTION "&<caiWinA3.519>Default warning threshold for the queue size monitoring of any printer watcher created by the auto watcher. This value represents a rising threshold and must be greater than 0, but cannot be greater than the critical threshold."
	::= { winA3ConfigPrnAutoEntry 9 }

winA3ConfigPrnAutoQueueCrit OBJECT-TYPE
	SYNTAX INTEGER
	ACCESS read-write
	STATUS mandatory
	DESCRIPTION "&<caiWinA3.520>Default critical threshold for the queue size monitoring of any printer watcher created by the auto watcher. This value represents a rising threshold and must be greater than 0, but cannot be less than the warning threshold."
	::= { winA3ConfigPrnAutoEntry 10 }

winA3ConfigPrnAutoQueueMonitor OBJECT-TYPE
	SYNTAX INTEGER {
		do-not-monitor(1),
		warning-only(2),
		critical-only(3),
		both(4)
	}
	ACCESS read-write
	STATUS mandatory
	DESCRIPTION "&<caiWinA3.521>Default monitor level for the queue size monitoring of any printer watcher created by the auto watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3ConfigPrnAutoEntry 11 }

winA3ConfigPrnAutoLossAction OBJECT-TYPE
	SYNTAX INTEGER {
		remove(1),
		up(2),
		down-warning(3),
		down-critical(4)
	}
	ACCESS read-write
	STATUS mandatory
	DESCRIPTION "&<caiWinA3.522>Default loss action for any printer watcher created by the auto watcher. Specifies the action to take if the monitored printer is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3ConfigPrnAutoEntry 12 }

winA3ConfigPrnAutoButton OBJECT-TYPE
	SYNTAX INTEGER {
		active(1),
		remove(2),
		locked(3)
	}
	ACCESS read-write
	STATUS mandatory
	DESCRIPTION "&<caiWinA3.523>This attribute is used to enable/disable or remove the printer auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigPrnAutoEntry 13 }

--
-- The ConfigNet Group
--

winA3ConfigNetPollInterval OBJECT-TYPE
	SYNTAX INTEGER
	ACCESS read-write
	STATUS mandatory
	DESCRIPTION "&<caiWinA3.524>Time, in seconds, between collections of network interface information. Valid range: 30 seconds or greater."
	DEFVAL { 60 }
	::= { winA3ConfigNetGroup 1 }

winA3ConfigNetPollMethod OBJECT-TYPE
	SYNTAX INTEGER {
		disabled(1),
		poll-interval-only(2),
		poll-interval-and-query(3),
		query-only(4)
	}
	ACCESS read-write
	STATUS mandatory
	DESCRIPTION "&<caiWinA3.525>Specifies how and when the agent collects network interface information. If set to 1 (disabled), the agent does not retrieve the network interface information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigNetGroup 2 }

winA3ConfigNetAggLag OBJECT-TYPE
	SYNTAX INTEGER
	ACCESS read-write
	STATUS mandatory
	DESCRIPTION "&<caiWinA3.526>Default aggregate lag setting for the network interface watcher to add. Specifies the consecutive number of times at which any status is not in the ok state, before the aggregate status changes. This value must be greater than 0."
	DEFVAL { 10 }
	::= { winA3ConfigNetGroup 3 }

winA3ConfigNetInterfaceMonitor OBJECT-TYPE
	SYNTAX INTEGER {
		do-not-monitor(1),
		down-warning(2),
		down-critical(3)
	}
	ACCESS read-write
	STATUS mandatory
	DESCRIPTION "&<caiWinA3.527>Default monitor level for the interface status monitoring of the network interface watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigNetGroup 4 }

winA3ConfigNetInBytesWarnMin OBJECT-TYPE
	SYNTAX DisplayString
	ACCESS read-write
	STATUS mandatory
	DESCRIPTION "&<caiWinA3.528>Default warning minimum threshold, in bytes/sec, for the received bytes monitoring of the network interface watcher to add. This value represents a declining threshold and must be equal to or greater than 0.0, equal to or greater than the critical minimum threshold, but cannot be greater than the warning maximum threshold. A value of -1 disables the evaluation of this threshold."
	DEFVAL { "-1" }
	::= { winA3ConfigNetGroup 5 }

winA3ConfigNetInBytesWarnMax OBJECT-TYPE
	SYNTAX DisplayString
	ACCESS read-write
	STATUS mandatory
	DESCRIPTION "&<caiWinA3.529>Default warning maximum threshold, in bytes/sec, for the received bytes monitoring of the network interface watcher to add. This value represents a rising threshold and must be equal to or greater than 0.0, equal to or greater than the warning minimum threshold, but cannot be greater than the critical maximum threshold. A value of -1 disables the evaluation of this threshold."
	DEFVAL { "2000000.0" }
	::= { winA3ConfigNetGroup 6 }

winA3ConfigNetInBytesCritMin OBJECT-TYPE
	SYNTAX DisplayString
	ACCESS read-write
	STATUS mandatory
	DESCRIPTION "&<caiWinA3.530>Default critical minimum threshold, in bytes/sec, for the received bytes monitoring of the network interface watcher to add. This value represents a declining threshold and must be equal to or greater than 0.0, but cannot be greater than the warning minimum threshold. A value of -1 disables the evaluation of this threshold."
	DEFVAL { "-1" }
	::= { winA3ConfigNetGroup 7 }

winA3ConfigNetInBytesCritMax OBJECT-TYPE
	SYNTAX DisplayString
	ACCESS read-write
	STATUS mandatory
	DESCRIPTION "&<caiWinA3.531>Default critical maximum threshold, in bytes/sec, for the received bytes monitoring of the network interface watcher to add. This value represents a rising threshold and must be equal to or greater than 0.0, but cannot be less than the warning maximum threshold. A value of -1 disables the evaluation of this threshold."
	DEFVAL { "4000000.0" }
	::= { winA3ConfigNetGroup 8 }

winA3ConfigNetInBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.532>Default monitor level for the received bytes monitoring of the network interface watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 1 }
	::= { winA3ConfigNetGroup 9 }

winA3ConfigNetInPktsWarn OBJECT-TYPE
	SYNTAX INTEGER
	ACCESS read-write
	STATUS mandatory
	DESCRIPTION "&<caiWinA3.533>Default warning threshold, in pkts/sec, for the received packets monitoring of the network interface watcher to add. This value represents a rising threshold and must be greater than 0, but cannot be greater than the critical threshold."
	DEFVAL { 8000 }
	::= { winA3ConfigNetGroup 10 }

winA3ConfigNetInPktsCrit OBJECT-TYPE
	SYNTAX INTEGER
	ACCESS read-write
	STATUS mandatory
	DESCRIPTION "&<caiWinA3.534>Default critical threshold, in pkts/sec, for the received packets monitoring of the network interface watcher to add. This value represents a rising threshold and must be greater than 0, but cannot be less than the warning threshold."
	DEFVAL { 15000 }
	::= { winA3ConfigNetGroup 11 }

winA3ConfigNetInPktsMonitor OBJECT-TYPE
	SYNTAX INTEGER {
		do-not-monitor(1),
		warning-only(2),
		critical-only(3),
		both(4)
	}
	ACCESS read-write
	STATUS mandatory
	DESCRIPTION "&<caiWinA3.535>Default monitor level for the received packets monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigNetGroup 12 }

winA3ConfigNetInErrorsWarn OBJECT-TYPE
	SYNTAX INTEGER
	ACCESS read-write
	STATUS mandatory
	DESCRIPTION "&<caiWinA3.536>Default warning threshold, in errors/poll, for the received errors monitoring of the network interface watcher to add. This value represents a rising threshold and must be greater than 0, but cannot be greater than the critical threshold."
	DEFVAL { 5 }
	::= { winA3ConfigNetGroup 13 }

winA3ConfigNetInErrorsCrit OBJECT-TYPE
	SYNTAX INTEGER
	ACCESS read-write
	STATUS mandatory
	DESCRIPTION "&<caiWinA3.537>Default critical threshold, in errors/poll, for the received errors monitoring of the network interface watcher to add. This value represents a rising threshold and must be greater than 0, but cannot be less than the warning threshold."
	DEFVAL { 10 }
	::= { winA3ConfigNetGroup 14 }

winA3ConfigNetInErrorsMonitor OBJECT-TYPE
	SYNTAX INTEGER {
		do-not-monitor(1),
		warning-only(2),
		critical-only(3),
		both(4)
	}
	ACCESS read-write
	STATUS mandatory
	DESCRIPTION "&<caiWinA3.538>Default monitor level for the received errors monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigNetGroup 15 }

winA3ConfigNetOutBytesWarnMin OBJECT-TYPE
	SYNTAX DisplayString
	ACCESS read-write
	STATUS mandatory
	DESCRIPTION "&<caiWinA3.539>Default warning minimum threshold, in bytes/sec, for the sent bytes monitoring of the network interface watcher to add. This value represents a declining threshold and must be equal to or greater than 0.0, equal to or greater than the critical minimum threshold, but cannot be greater than the warning maximum threshold. A value of -1 disables the evaluation of this threshold."
	DEFVAL { "-1" }
	::= { winA3ConfigNetGroup 16 }

winA3ConfigNetOutBytesWarnMax OBJECT-TYPE
	SYNTAX DisplayString
	ACCESS read-write
	STATUS mandatory
	DESCRIPTION "&<caiWinA3.540>Default warning maximum threshold, in bytes/sec, for the sent bytes monitoring of the network interface watcher to add. This value represents a rising threshold and must be equal to or greater than 0.0, equal to or greater than the warning minimum threshold, but cannot be greater than the critical maximum threshold. A value of -1 disables the evaluation of this threshold."
	DEFVAL { "6000000.0" }
	::= { winA3ConfigNetGroup 17 }

winA3ConfigNetOutBytesCritMin OBJECT-TYPE
	SYNTAX DisplayString
	ACCESS read-write
	STATUS mandatory
	DESCRIPTION "&<caiWinA3.541>Default critical minimum threshold, in bytes/sec, for the sent bytes monitoring of the network interface watcher to add. This value represents a declining threshold and must be equal to or greater than 0.0, but cannot be greater than the warning minimum threshold. A value of -1 disables the evaluation of this threshold."
	DEFVAL { "-1" }
	::= { winA3ConfigNetGroup 18 }

winA3ConfigNetOutBytesCritMax OBJECT-TYPE
	SYNTAX DisplayString
	ACCESS read-write
	STATUS mandatory
	DESCRIPTION "&<caiWinA3.542>Default critical maximum threshold, in bytes/sec, for the sent bytes monitoring of the network interface watcher to add. This value represents a rising threshold and must be equal to or greater than 0.0, but cannot be less than the warning maximum threshold. A value of -1 disables the evaluation of this threshold."
	DEFVAL { "12000000.0" }
	::= { winA3ConfigNetGroup 19 }

winA3ConfigNetOutBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.543>Default monitor level for the sent bytes monitoring of the network interface watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3ConfigNetGroup 20 }

winA3ConfigNetOutPktsWarn OBJECT-TYPE
	SYNTAX INTEGER
	ACCESS read-write
	STATUS mandatory
	DESCRIPTION "&<caiWinA3.544>Default warning threshold, in pkts/sec, for the sent packets monitoring of the network interface watcher to add. This value represents a rising threshold and must be greater than 0, but cannot be greater than the critical threshold."
	DEFVAL { 25000 }
	::= { winA3ConfigNetGroup 21 }

winA3ConfigNetOutPktsCrit OBJECT-TYPE
	SYNTAX INTEGER
	ACCESS read-write
	STATUS mandatory
	DESCRIPTION "&<caiWinA3.545>Default critical threshold, in pkts/sec, for the sent packets monitoring of the network interface watcher to add. This value represents a rising threshold and must be greater than 0, but cannot be less than the warning threshold."
	DEFVAL { 50000 }
	::= { winA3ConfigNetGroup 22 }

winA3ConfigNetOutPktsMonitor OBJECT-TYPE
	SYNTAX INTEGER {
		do-not-monitor(1),
		warning-only(2),
		critical-only(3),
		both(4)
	}
	ACCESS read-write
	STATUS mandatory
	DESCRIPTION "&<caiWinA3.546>Default monitor level for the sent packets monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigNetGroup 23 }

winA3ConfigNetOutErrorsWarn OBJECT-TYPE
	SYNTAX INTEGER
	ACCESS read-write
	STATUS mandatory
	DESCRIPTION "&<caiWinA3.547>Default warning threshold, in errors/poll, for the sent errors monitoring of the network interface watcher to add. This value represents a rising threshold and must be greater than 0, but cannot be greater than the critical threshold."
	DEFVAL { 5 }
	::= { winA3ConfigNetGroup 24 }

winA3ConfigNetOutErrorsCrit OBJECT-TYPE
	SYNTAX INTEGER
	ACCESS read-write
	STATUS mandatory
	DESCRIPTION "&<caiWinA3.548>Default critical threshold, in errors/poll, for the sent errors monitoring of the network interface watcher to add. This value represents a rising threshold and must be greater than 0, but cannot be less than the warning threshold."
	DEFVAL { 10 }
	::= { winA3ConfigNetGroup 25 }

winA3ConfigNetOutErrorsMonitor OBJECT-TYPE
	SYNTAX INTEGER {
		do-not-monitor(1),
		warning-only(2),
		critical-only(3),
		both(4)
	}
	ACCESS read-write
	STATUS mandatory
	DESCRIPTION "&<caiWinA3.549>Default monitor level for the sent errors monitoring of the network interface watcher to add. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3ConfigNetGroup 26 }

winA3ConfigNetLossAction OBJECT-TYPE
	SYNTAX INTEGER {
		remove(1),
		up(2),
		down-warning(3),
		down-critical(4)
	}
	ACCESS read-write
	STATUS mandatory
	DESCRIPTION "&<caiWinA3.550>Default loss action for the network interface watcher to add. Specifies the action to take if the monitored network interface is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigNetGroup 27 }

--
-- The ConfigReg Group
--

winA3ConfigRegPollInterval OBJECT-TYPE
	SYNTAX INTEGER
	ACCESS read-write
	STATUS mandatory
	DESCRIPTION "&<caiWinA3.551>Time, in seconds, between collections of registry entry information. Valid range: 30 seconds or greater."
	DEFVAL { 120 }
	::= { winA3ConfigRegGroup 1 }

winA3ConfigRegPollMethod OBJECT-TYPE
	SYNTAX INTEGER {
		disabled(1),
		poll-interval-only(2),
		poll-interval-and-query(3),
		query-only(4)
	}
	ACCESS read-write
	STATUS mandatory
	DESCRIPTION "&<caiWinA3.552>Specifies how and when the agent collects registry entry information. If set to 1 (disabled), the agent does not retrieve the registry entry information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigRegGroup 2 }

winA3ConfigRegWatcherName OBJECT-TYPE
	SYNTAX DisplayString
	ACCESS read-write
	STATUS mandatory
	DESCRIPTION "&<caiWinA3.553>An arbitrary name for the watcher."
	::= { winA3ConfigRegGroup 3 }

winA3ConfigRegKeyName OBJECT-TYPE
	SYNTAX DisplayString
	ACCESS read-write
	STATUS mandatory
	DESCRIPTION "&<caiWinA3.554>The key name of the registry entry for which to add or remove a watcher. The key name is the complete path starting from one of the hives down to the key itself, for example: 'HKEY_LOCAL_MACHINE\SOFTWARE\Microsoft\Internet Explorer'. To monitor just the key for existence and subtree change, the value name attribute must be empty."
	::= { winA3ConfigRegGroup 4 }

winA3ConfigRegValueName OBJECT-TYPE
	SYNTAX DisplayString
	ACCESS read-write
	STATUS mandatory
	DESCRIPTION "&<caiWinA3.555>The value name of the registry entry for which to add or remove a watcher, for example: 'Version'. Omitting the value name (giving an empty string) allows to change the behaviour of the watcher. In this case the watcher will monitor the given key for existence and subtree change. As no value data can be determined, the value type is set to 'unknown' and the status of the value metric is set to 'up'."
	::= { winA3ConfigRegGroup 5 }

winA3ConfigRegDescription OBJECT-TYPE
	SYNTAX DisplayString
	ACCESS read-write
	STATUS mandatory
	DESCRIPTION "&<caiWinA3.556>Default description for the registry entry watcher to add."
	::= { winA3ConfigRegGroup 6 }

winA3ConfigRegAggLag OBJECT-TYPE
	SYNTAX INTEGER
	ACCESS read-write
	STATUS mandatory
	DESCRIPTION "&<caiWinA3.557>Default aggregate lag setting for the registry entry watcher to add. Specifies the consecutive number of times at which any status is not in the ok state, before the aggregate status changes. This value must be greater than 0."
	DEFVAL { 1 }
	::= { winA3ConfigRegGroup 7 }

winA3ConfigRegValueRef OBJECT-TYPE
	SYNTAX DisplayString
	ACCESS read-write
	STATUS mandatory
	DESCRIPTION "&<caiWinA3.558>This attribute is used as the reference the value data is compared with. If the value policy is set to 'should-not-change(5)', the reference is set initially (when the watcher is added) to the current data of the value. Additionally, the reference value can be set to the current data by setting the status button attribute to 'reset-value'."
	DEFVAL { "0" }
	::= { winA3ConfigRegGroup 8 }

winA3ConfigRegValuePolicy OBJECT-TYPE
	SYNTAX INTEGER {
		should-be-equal(1),
		should-not-be-equal(2),
		should-be-minimal(3),
		should-be-maximal(4),
		should-not-change(5)
	}
	ACCESS read-write
	STATUS mandatory
	DESCRIPTION "&<caiWinA3.559>Default monitor policy for the registry entry value monitoring of the registry entry watcher to add. This policy specifies how to compare the current value data to the reference. The policies 'should-be-minimal(3)' and 'should-be-maximal(4)' can only be applied, if the value type is 'dword'."
	DEFVAL { 5 }
	::= { winA3ConfigRegGroup 9 }

winA3ConfigRegValueMonitor OBJECT-TYPE
	SYNTAX INTEGER {
		do-not-monitor(1),
		down-warning(2),
		down-critical(3)
	}
	ACCESS read-write
	STATUS mandatory
	DESCRIPTION "&<caiWinA3.560>Default monitor level for the registry entry value monitoring of the registry entry watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigRegGroup 10 }

winA3ConfigRegSubTreeMonitor OBJECT-TYPE
	SYNTAX INTEGER {
		do-not-monitor(1),
		down-warning(2),
		down-critical(3)
	}
	ACCESS read-write
	STATUS mandatory
	DESCRIPTION "&<caiWinA3.561>Default monitor level for the sub tree change monitoring of the registry entry watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigRegGroup 11 }

winA3ConfigRegExistPolicy OBJECT-TYPE
	SYNTAX INTEGER {
		should-exist(1),
		should-not-exist(2)
	}
	ACCESS read-write
	STATUS mandatory
	DESCRIPTION "&<caiWinA3.562>Default monitor policy for the existence monitoring of the registry entry watcher to add. Specifies how the agent should evaluate the presence or absence of the monitored resource in order to determine whether the resource is in good condition. If set to 1 (should-exist), the resource is expected to be existent. If set to 2 (should-not-exist), the resource is expected to be nonexistent."
	DEFVAL { 1 }
	::= { winA3ConfigRegGroup 12 }

winA3ConfigRegExistMonitor OBJECT-TYPE
	SYNTAX INTEGER {
		do-not-monitor(1),
		down-warning(2),
		down-critical(3)
	}
	ACCESS read-write
	STATUS mandatory
	DESCRIPTION "&<caiWinA3.563>Default monitor level for the existence monitoring of the registry entry watcher to add. If set to 1 (do-not-monitor), the agent does not evaluate the actual state of the resource and sets the status to ok. If set to 2 (down-warning), the agent uses a warning severity if the resource is in bad condition. If set to 3 (down-critical), the agent uses a critical severity if the resource is in bad condition."
	DEFVAL { 3 }
	::= { winA3ConfigRegGroup 13 }

winA3ConfigRegButton OBJECT-TYPE
	SYNTAX INTEGER {
		none(1),
		add(2),
		remove(3)
	}
	ACCESS read-write
	STATUS mandatory
	DESCRIPTION "&<caiWinA3.564>This attribute is used to add or remove the registry entry watcher specified by the current setting of the watcher name attribute(s) in this group. If set to 2 (add), the agent adds the specified watcher to the status table using the current values of the remaining attributes as defaults. If set to 3 (remove), the agent removes the specified watcher from the status table. This attribute cannot be set to 1 (none)."
	DEFVAL { 1 }
	::= { winA3ConfigRegGroup 14 }

--
-- The ConfigHardwr Group
--

winA3ConfigHardwrPollInterval OBJECT-TYPE
	SYNTAX INTEGER
	ACCESS read-write
	STATUS mandatory
	DESCRIPTION "&<caiWinA3.565>Time, in seconds, between collections of hardware resource information. Valid range: 30 seconds or greater."
	DEFVAL { 300 }
	::= { winA3ConfigHardwrGroup 1 }

winA3ConfigHardwrPollMethod OBJECT-TYPE
	SYNTAX INTEGER {
		disabled(1),
		poll-interval-only(2),
		poll-interval-and-query(3),
		query-only(4)
	}
	ACCESS read-write
	STATUS mandatory
	DESCRIPTION "&<caiWinA3.566>Specifies how and when the agent collects hardware resource information. If set to 1 (disabled), the agent does not retrieve the hardware resource information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigHardwrGroup 2 }

winA3ConfigHardwrAutoPollInterval OBJECT-TYPE
	SYNTAX INTEGER
	ACCESS read-write
	STATUS mandatory
	DESCRIPTION "&<caiWinA3.567>Time, in minutes, between the processing of the hardware resource auto watchers. Valid range: -1 (suspended), 30 minutes or greater."
	DEFVAL { 60 }
	::= { winA3ConfigHardwrGroup 3 }

winA3ConfigHardwrResName OBJECT-TYPE
	SYNTAX DisplayString
	ACCESS read-write
	STATUS mandatory
	DESCRIPTION "&<caiWinA3.568>The name of the resource for which to add or remove a watcher. This is the first index used by the agent in the different MIB tables for this resource (e.g. PowerSupply). If used as a filter element for auto discovery, this name can be a regular expression (case-insensitive). In this case, it restricts the resources to be searched for during an auto discovery run."
	::= { winA3ConfigHardwrGroup 4 }

winA3ConfigHardwrResSubName OBJECT-TYPE
	SYNTAX DisplayString
	ACCESS read-write
	STATUS mandatory
	DESCRIPTION "&<caiWinA3.569>The subname of the resource for which to add or remove a watcher. This is the second index used by the agent in the different MIB tables for this resource (e.g. Voltage). If used as a filter element for auto discovery, this name can be a regular expression (case-insensitive). In this case, it restricts the resources to be searched for during an auto discovery run."
	::= { winA3ConfigHardwrGroup 5 }

winA3ConfigHardwrInstName OBJECT-TYPE
	SYNTAX DisplayString
	ACCESS read-write
	STATUS mandatory
	DESCRIPTION "&<caiWinA3.570>If a resource supports instances, this must be the name of an instance for which to add or remove a watcher. The instance name is the third index used by the agent in the different MIB tables for this resource. If a resource does not support instances, <none> should be used as third index. If used as a filter element for auto discovery, this name can be a regular expression (case-insensitive). In this case, it restricts the resources to be searched for during an auto discovery run."
	::= { winA3ConfigHardwrGroup 6 }

winA3ConfigHardwrDescription OBJECT-TYPE
	SYNTAX DisplayString
	ACCESS read-write
	STATUS mandatory
	DESCRIPTION "&<caiWinA3.571>Default description for the hardware resource watcher to add."
	::= { winA3ConfigHardwrGroup 7 }

winA3ConfigHardwrErrorMsgPattern OBJECT-TYPE
	SYNTAX DisplayString
	ACCESS read-write
	STATUS mandatory
	DESCRIPTION "&<caiWinA3.572>A regular expression (case-insensitive). If the error message matches this pattern, the error message status changes according to the error message monitor policy."
	DEFVAL { ".*" }
	::= { winA3ConfigHardwrGroup 8 }

winA3ConfigHardwrErrorMsgMonitor OBJECT-TYPE
	SYNTAX INTEGER {
		do-not-monitor(1),
		down-warning(2),
		down-critical(3)
	}
	ACCESS read-write
	STATUS mandatory
	DESCRIPTION "&<caiWinA3.573>Default monitor level for the error message monitoring of the hardware resource watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigHardwrGroup 9 }

winA3ConfigHardwrResultLag OBJECT-TYPE
	SYNTAX INTEGER
	ACCESS read-write
	STATUS mandatory
	DESCRIPTION "&<caiWinA3.574>Default lag setting for the result monitoring of the hardware resource watcher to add. Specifies the number of consecutive threshold breaches on which the result state changes. This value must be greater than 0."
	DEFVAL { 1 }
	::= { winA3ConfigHardwrGroup 10 }

winA3ConfigHardwrResultWarnMin OBJECT-TYPE
	SYNTAX DisplayString
	ACCESS read-write
	STATUS mandatory
	DESCRIPTION "&<caiWinA3.575>Default warning minimum threshold for the result monitoring of the hardware resource watcher to add. This value represents a declining threshold and must be equal to or greater than 0.0, equal to or greater than the critical minimum threshold, but cannot be greater than the warning maximum threshold. A value of -1 disables the evaluation of this threshold."
	DEFVAL { "-1" }
	::= { winA3ConfigHardwrGroup 11 }

winA3ConfigHardwrResultWarnMax OBJECT-TYPE
	SYNTAX DisplayString
	ACCESS read-write
	STATUS mandatory
	DESCRIPTION "&<caiWinA3.576>Default warning maximum threshold for the result monitoring of the hardware resource watcher to add. This value represents a rising threshold and must be equal to or greater than 0.0, equal to or greater than the warning minimum threshold, but cannot be greater than the critical maximum threshold. A value of -1 disables the evaluation of this threshold."
	DEFVAL { "1.0" }
	::= { winA3ConfigHardwrGroup 12 }

winA3ConfigHardwrResultCritMin OBJECT-TYPE
	SYNTAX DisplayString
	ACCESS read-write
	STATUS mandatory
	DESCRIPTION "&<caiWinA3.577>Default critical minimum threshold for the result monitoring of the hardware resource watcher to add. This value represents a declining threshold and must be equal to or greater than 0.0, but cannot be greater than the warning minimum threshold. A value of -1 disables the evaluation of this threshold."
	DEFVAL { "-1" }
	::= { winA3ConfigHardwrGroup 13 }

winA3ConfigHardwrResultCritMax OBJECT-TYPE
	SYNTAX DisplayString
	ACCESS read-write
	STATUS mandatory
	DESCRIPTION "&<caiWinA3.578>Default critical maximum threshold for the result monitoring of the hardware resource watcher to add. This value represents a rising threshold and must be equal to or greater than 0.0, but cannot be less than the warning maximum threshold. A value of -1 disables the evaluation of this threshold."
	DEFVAL { "2.0" }
	::= { winA3ConfigHardwrGroup 14 }

winA3ConfigHardwrResultMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.579>Default monitor level for the result monitoring of the hardware resource watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3ConfigHardwrGroup 15 }

winA3ConfigHardwrLossAction OBJECT-TYPE
	SYNTAX INTEGER {
		remove(1),
		up(2),
		down-warning(3),
		down-critical(4)
	}
	ACCESS read-write
	STATUS mandatory
	DESCRIPTION "&<caiWinA3.580>Default loss action for the hardware resource watcher to add. Specifies the action to take if the monitored hardware resource is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigHardwrGroup 16 }

winA3ConfigHardwrAutoTableWatcherName OBJECT-TYPE
	SYNTAX DisplayString
	ACCESS read-write
	STATUS mandatory
	DESCRIPTION "&<caiWinA3.581>Name of the hardware resource auto watcher to add or remove."
	::= { winA3ConfigHardwrGroup 17 }

winA3ConfigHardwrAutoTableWatcherMatchType OBJECT-TYPE
	SYNTAX INTEGER {
		positive(1),
		negative(2)
	}
	ACCESS read-write
	STATUS mandatory
	DESCRIPTION "&<caiWinA3.582>Default search algorithm for the hardware auto watcher to add. The filter is the logical AND of all attributes used to identify or otherwise narrow down resources. If set to 1 (positive), the agent searches for hardware resources that match the filter. If set to 2 (negative), the agent searches for hardware resources that do not match the filter."
	DEFVAL { 1 }
	::= { winA3ConfigHardwrGroup 18 }

winA3ConfigHardwrAutoTableWatcherLimit OBJECT-TYPE
	SYNTAX INTEGER
	ACCESS read-write
	STATUS mandatory
	DESCRIPTION "&<caiWinA3.583>Default minimum number of matches that causes a lock of the hardware resource auto watcher to add."
	DEFVAL { 200 }
	::= { winA3ConfigHardwrGroup 19 }

winA3ConfigHardwrButton OBJECT-TYPE
	SYNTAX INTEGER {
		none(1),
		add(2),
		remove(3),
		add-auto(4),
		remove-auto(5)
	}
	ACCESS read-write
	STATUS mandatory
	DESCRIPTION "&<caiWinA3.584>This attribute is used to add or remove the hardware resource watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigHardwrGroup 20 }

winA3ConfigHardwrAutoCount OBJECT-TYPE
	SYNTAX INTEGER
	ACCESS read-only
	STATUS mandatory
	DESCRIPTION "&<caiWinA3.585>Number of auto watchers in the hardware resource auto configuration table."
	::= { winA3ConfigHardwrGroup 21 }

winA3ConfigHardwrAutoLocked OBJECT-TYPE
	SYNTAX INTEGER
	ACCESS read-only
	STATUS mandatory
	DESCRIPTION "&<caiWinA3.586>Number of auto watchers in the hardware resource auto configuration table which are currently locked."
	::= { winA3ConfigHardwrGroup 22 }

winA3ConfigHardwrAutoTable OBJECT-TYPE
	SYNTAX SEQUENCE OF WinA3ConfigHardwrAutoEntry
	ACCESS not-accessible
	STATUS mandatory
	DESCRIPTION "&<caiWinA3.587>Configuration table containing a list of hardware resource auto watchers."
	::= { winA3ConfigHardwrGroup 23 }

winA3ConfigHardwrAutoEntry OBJECT-TYPE
	SYNTAX WinA3ConfigHardwrAutoEntry
	ACCESS not-accessible
	STATUS mandatory
	DESCRIPTION "&<caiWinA3.588>Entry in the hardware resource auto watcher configuration table."
	INDEX {
		winA3ConfigHardwrAutoWatcherName
	}
	::= { winA3ConfigHardwrAutoTable 1 }

WinA3ConfigHardwrAutoEntry ::= SEQUENCE {
	winA3ConfigHardwrAutoWatcherName DisplayString,
	winA3ConfigHardwrAutoResName DisplayString,
	winA3ConfigHardwrAutoResSubName DisplayString,
	winA3ConfigHardwrAutoInstName DisplayString,
	winA3ConfigHardwrAutoDescription DisplayString,
	winA3ConfigHardwrAutoWatcherMatchType INTEGER,
	winA3ConfigHardwrAutoWatcherLimit INTEGER,
	winA3ConfigHardwrAutoWatcherLastMatched INTEGER,
	winA3ConfigHardwrAutoErrorMsgPattern DisplayString,
	winA3ConfigHardwrAutoErrorMsgMonitor INTEGER,
	winA3ConfigHardwrAutoResultLag INTEGER,
	winA3ConfigHardwrAutoResultWarnMin DisplayString,
	winA3ConfigHardwrAutoResultWarnMax DisplayString,
	winA3ConfigHardwrAutoResultCritMin DisplayString,
	winA3ConfigHardwrAutoResultCritMax DisplayString,
	winA3ConfigHardwrAutoResultMonitor INTEGER,
	winA3ConfigHardwrAutoLossAction INTEGER,
	winA3ConfigHardwrAutoButton INTEGER
}

winA3ConfigHardwrAutoWatcherName OBJECT-TYPE
	SYNTAX DisplayString
	ACCESS read-only
	STATUS mandatory
	DESCRIPTION "&<caiWinA3.589>Name of the hardware resource auto watcher."
	::= { winA3ConfigHardwrAutoEntry 1 }

winA3ConfigHardwrAutoResName OBJECT-TYPE
	SYNTAX DisplayString
	ACCESS read-write
	STATUS mandatory
	DESCRIPTION "&<caiWinA3.590>A regular expression (case-insensitive) used to filter the resource names. It restricts the resources to be searched for during an auto discovery run."
	::= { winA3ConfigHardwrAutoEntry 2 }

winA3ConfigHardwrAutoResSubName OBJECT-TYPE
	SYNTAX DisplayString
	ACCESS read-write
	STATUS mandatory
	DESCRIPTION "&<caiWinA3.591>A regular expression (case-insensitive) used to filter the resource subnames. It restricts the resources to be searched for during an auto discovery run."
	::= { winA3ConfigHardwrAutoEntry 3 }

winA3ConfigHardwrAutoInstName OBJECT-TYPE
	SYNTAX DisplayString
	ACCESS read-write
	STATUS mandatory
	DESCRIPTION "&<caiWinA3.592>A regular expression (case-insensitive) used to filter the instance names. It restricts the resources to be searched for during an auto discovery run."
	::= { winA3ConfigHardwrAutoEntry 4 }

winA3ConfigHardwrAutoDescription OBJECT-TYPE
	SYNTAX DisplayString
	ACCESS read-write
	STATUS mandatory
	DESCRIPTION "&<caiWinA3.593>Current description for the hardware resource auto watcher."
	::= { winA3ConfigHardwrAutoEntry 5 }

winA3ConfigHardwrAutoWatcherMatchType OBJECT-TYPE
	SYNTAX INTEGER {
		positive(1),
		negative(2)
	}
	ACCESS read-write
	STATUS mandatory
	DESCRIPTION "&<caiWinA3.594>Current search algorithm for the hardware auto watcher. The filter is the logical AND of all attributes used to identify or otherwise narrow down resources. If set to 1 (positive), the agent searches for hardware resources that match the filter. If set to 2 (negative), the agent searches for hardware resources that do not match the filter."
	DEFVAL { 0 }
	::= { winA3ConfigHardwrAutoEntry 6 }

winA3ConfigHardwrAutoWatcherLimit OBJECT-TYPE
	SYNTAX INTEGER
	ACCESS read-write
	STATUS mandatory
	DESCRIPTION "&<caiWinA3.595>Current minimum number of matches that causes the hardware resource auto watcher to be locked."
	::= { winA3ConfigHardwrAutoEntry 7 }

winA3ConfigHardwrAutoWatcherLastMatched OBJECT-TYPE
	SYNTAX INTEGER
	ACCESS read-only
	STATUS mandatory
	DESCRIPTION "&<caiWinA3.596>Number of matches for the last hardware resource auto discovery run."
	::= { winA3ConfigHardwrAutoEntry 8 }

winA3ConfigHardwrAutoErrorMsgPattern OBJECT-TYPE
	SYNTAX DisplayString
	ACCESS read-write
	STATUS mandatory
	DESCRIPTION "&<caiWinA3.597>A regular expression (case-insensitive). If the error message matches this pattern, the error message status changes according to the error message monitor policy."
	::= { winA3ConfigHardwrAutoEntry 9 }

winA3ConfigHardwrAutoErrorMsgMonitor OBJECT-TYPE
	SYNTAX INTEGER {
		do-not-monitor(1),
		down-warning(2),
		down-critical(3)
	}
	ACCESS read-write
	STATUS mandatory
	DESCRIPTION "&<caiWinA3.598>Default monitor level for the error message monitoring of any hardware resource watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3ConfigHardwrAutoEntry 10 }

winA3ConfigHardwrAutoResultLag OBJECT-TYPE
	SYNTAX INTEGER
	ACCESS read-write
	STATUS mandatory
	DESCRIPTION "&<caiWinA3.599>Default lag setting for the result monitoring of any hardware resource watcher created by the auto watcher. Specifies the number of consecutive threshold breaches on which the result state changes. This value must be greater than 0."
	::= { winA3ConfigHardwrAutoEntry 11 }

winA3ConfigHardwrAutoResultWarnMin OBJECT-TYPE
	SYNTAX DisplayString
	ACCESS read-write
	STATUS mandatory
	DESCRIPTION "&<caiWinA3.600>Default warning minimum threshold for the result monitoring of any hardware resource watcher created by the auto watcher. This value represents a declining threshold and must be equal to or greater than 0.0, equal to or greater than the critical minimum threshold, but cannot be greater than the warning maximum threshold. A value of -1 disables the evaluation of this threshold."
	DEFVAL { "-2" }
	::= { winA3ConfigHardwrAutoEntry 12 }

winA3ConfigHardwrAutoResultWarnMax OBJECT-TYPE
	SYNTAX DisplayString
	ACCESS read-write
	STATUS mandatory
	DESCRIPTION "&<caiWinA3.601>Default warning maximum threshold for the result monitoring of any hardware resource watcher created by the auto watcher. This value represents a rising threshold and must be equal to or greater than 0.0, equal to or greater than the warning minimum threshold, but cannot be greater than the critical maximum threshold. A value of -1 disables the evaluation of this threshold."
	DEFVAL { "-2" }
	::= { winA3ConfigHardwrAutoEntry 13 }

winA3ConfigHardwrAutoResultCritMin OBJECT-TYPE
	SYNTAX DisplayString
	ACCESS read-write
	STATUS mandatory
	DESCRIPTION "&<caiWinA3.602>Default critical minimum threshold for the result monitoring of any hardware resource watcher created by the auto watcher. This value represents a declining threshold and must be equal to or greater than 0.0, but cannot be greater than the warning minimum threshold. A value of -1 disables the evaluation of this threshold."
	DEFVAL { "-2" }
	::= { winA3ConfigHardwrAutoEntry 14 }

winA3ConfigHardwrAutoResultCritMax OBJECT-TYPE
	SYNTAX DisplayString
	ACCESS read-write
	STATUS mandatory
	DESCRIPTION "&<caiWinA3.603>Default critical maximum threshold for the result monitoring of any hardware resource watcher created by the auto watcher. This value represents a rising threshold and must be equal to or greater than 0.0, but cannot be less than the warning maximum threshold. A value of -1 disables the evaluation of this threshold."
	DEFVAL { "-2" }
	::= { winA3ConfigHardwrAutoEntry 15 }

winA3ConfigHardwrAutoResultMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.604>Default monitor level for the result monitoring of any hardware resource watcher created by the auto watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3ConfigHardwrAutoEntry 16 }

winA3ConfigHardwrAutoLossAction OBJECT-TYPE
	SYNTAX INTEGER {
		remove(1),
		up(2),
		down-warning(3),
		down-critical(4)
	}
	ACCESS read-write
	STATUS mandatory
	DESCRIPTION "&<caiWinA3.605>Default loss action for any hardware resource watcher created by the auto watcher. Specifies the action to take if the monitored hardware resource is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3ConfigHardwrAutoEntry 17 }

winA3ConfigHardwrAutoButton OBJECT-TYPE
	SYNTAX INTEGER {
		active(1),
		remove(2),
		locked(3)
	}
	ACCESS read-write
	STATUS mandatory
	DESCRIPTION "&<caiWinA3.606>This attribute is used to enable/disable or remove the hardware resource auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigHardwrAutoEntry 18 }

--
-- The ConfigProgrm Group
--

winA3ConfigProgrmPollInterval OBJECT-TYPE
	SYNTAX INTEGER
	ACCESS read-write
	STATUS mandatory
	DESCRIPTION "&<caiWinA3.607>Time, in seconds, between collections of programmable resource information. Valid range: 30 seconds or greater."
	DEFVAL { 300 }
	::= { winA3ConfigProgrmGroup 1 }

winA3ConfigProgrmPollMethod OBJECT-TYPE
	SYNTAX INTEGER {
		disabled(1),
		poll-interval-only(2),
		poll-interval-and-query(3),
		query-only(4)
	}
	ACCESS read-write
	STATUS mandatory
	DESCRIPTION "&<caiWinA3.608>Specifies how and when the agent collects programmable resource information. If set to 1 (disabled), the agent does not retrieve the programmable resource information (neither by polling nor by get request) and sets all statuses to passive or ok. If set to 2 (poll-interval-only), the agent only retrieves the information by polling, but not by get request. If set to 3 (poll-interval-and-query), the agent retrieves the information both by polling and by get request. If set to 4 (query-only), the agent retrieves the information only when a get request is made."
	DEFVAL { 2 }
	::= { winA3ConfigProgrmGroup 2 }

winA3ConfigProgrmAutoPollInterval OBJECT-TYPE
	SYNTAX INTEGER
	ACCESS read-write
	STATUS mandatory
	DESCRIPTION "&<caiWinA3.609>Time, in minutes, between the processing of the programmable resource auto watchers. Valid range: -1 (suspended), 30 minutes or greater."
	DEFVAL { 60 }
	::= { winA3ConfigProgrmGroup 3 }

winA3ConfigProgrmResName OBJECT-TYPE
	SYNTAX DisplayString
	ACCESS read-write
	STATUS mandatory
	DESCRIPTION "&<caiWinA3.610>The name of the resource for which to add or remove a watcher. This is the first index used by the agent in the different MIB tables for this resource (e.g. PowerSupply). If used as a filter element for auto discovery, this name can be a regular expression (case-insensitive). In this case, it restricts the resources to be searched for during an auto discovery run."
	::= { winA3ConfigProgrmGroup 4 }

winA3ConfigProgrmResSubName OBJECT-TYPE
	SYNTAX DisplayString
	ACCESS read-write
	STATUS mandatory
	DESCRIPTION "&<caiWinA3.611>The subname of the resource for which to add or remove a watcher. This is the second index used by the agent in the different MIB tables for this resource (e.g. Voltage). If used as a filter element for auto discovery, this name can be a regular expression (case-insensitive). In this case, it restricts the resources to be searched for during an auto discovery run."
	::= { winA3ConfigProgrmGroup 5 }

winA3ConfigProgrmInstName OBJECT-TYPE
	SYNTAX DisplayString
	ACCESS read-write
	STATUS mandatory
	DESCRIPTION "&<caiWinA3.612>If a resource supports instances, this must be the name of an instance for which to add or remove a watcher. The instance name is the third index used by the agent in the different MIB tables for this resource. If a resource does not support instances, <none> should be used as third index. If used as a filter element for auto discovery, this name can be a regular expression (case-insensitive). In this case, it restricts the resources to be searched for during an auto discovery run."
	::= { winA3ConfigProgrmGroup 6 }

winA3ConfigProgrmDescription OBJECT-TYPE
	SYNTAX DisplayString
	ACCESS read-write
	STATUS mandatory
	DESCRIPTION "&<caiWinA3.613>Default description for the programmable resource watcher to add."
	::= { winA3ConfigProgrmGroup 7 }

winA3ConfigProgrmErrorMsgPattern OBJECT-TYPE
	SYNTAX DisplayString
	ACCESS read-write
	STATUS mandatory
	DESCRIPTION "&<caiWinA3.614>A regular expression (case-insensitive). If the error message matches this pattern, the error message status changes according to the error message monitor policy."
	DEFVAL { ".*" }
	::= { winA3ConfigProgrmGroup 8 }

winA3ConfigProgrmErrorMsgMonitor OBJECT-TYPE
	SYNTAX INTEGER {
		do-not-monitor(1),
		down-warning(2),
		down-critical(3)
	}
	ACCESS read-write
	STATUS mandatory
	DESCRIPTION "&<caiWinA3.615>Default monitor level for the error message monitoring of the programmable resource watcher to add. If set to 1 (do-not-monitor), the agent does not evaluate the actual state of the resource and sets the status to ok. If set to 2 (down-warning), the agent uses a warning severity if the resource is in bad condition. If set to 3 (down-critical), the agent uses a critical severity if the resource is in bad condition."
	DEFVAL { 2 }
	::= { winA3ConfigProgrmGroup 9 }

winA3ConfigProgrmResultLag OBJECT-TYPE
	SYNTAX INTEGER
	ACCESS read-write
	STATUS mandatory
	DESCRIPTION "&<caiWinA3.616>Default lag setting for the result monitoring of the programmable resource watcher to add. Specifies the number of consecutive threshold breaches on which the result state changes. This value must be greater than 0."
	DEFVAL { 1 }
	::= { winA3ConfigProgrmGroup 10 }

winA3ConfigProgrmResultWarnMin OBJECT-TYPE
	SYNTAX DisplayString
	ACCESS read-write
	STATUS mandatory
	DESCRIPTION "&<caiWinA3.617>Default warning minimum threshold for the result monitoring of the programmable resource watcher to add. This value represents a declining threshold and must be equal to or greater than 0.0, equal to or greater than the critical minimum threshold, but cannot be greater than the warning maximum threshold. A value of -1 disables the evaluation of this threshold."
	DEFVAL { "-1" }
	::= { winA3ConfigProgrmGroup 11 }

winA3ConfigProgrmResultWarnMax OBJECT-TYPE
	SYNTAX DisplayString
	ACCESS read-write
	STATUS mandatory
	DESCRIPTION "&<caiWinA3.618>Default warning maximum threshold for the result monitoring of the programmable resource watcher to add. This value represents a rising threshold and must be equal to or greater than 0.0, equal to or greater than the warning minimum threshold, but cannot be greater than the critical maximum threshold. A value of -1 disables the evaluation of this threshold."
	DEFVAL { "1.0" }
	::= { winA3ConfigProgrmGroup 12 }

winA3ConfigProgrmResultCritMin OBJECT-TYPE
	SYNTAX DisplayString
	ACCESS read-write
	STATUS mandatory
	DESCRIPTION "&<caiWinA3.619>Default critical minimum threshold for the result monitoring of the programmable resource watcher to add. This value represents a declining threshold and must be equal to or greater than 0.0, but cannot be greater than the warning minimum threshold. A value of -1 disables the evaluation of this threshold."
	DEFVAL { "-1" }
	::= { winA3ConfigProgrmGroup 13 }

winA3ConfigProgrmResultCritMax OBJECT-TYPE
	SYNTAX DisplayString
	ACCESS read-write
	STATUS mandatory
	DESCRIPTION "&<caiWinA3.620>Default critical maximum threshold for the result monitoring of the programmable resource watcher to add. This value represents a rising threshold and must be equal to or greater than 0.0, but cannot be less than the warning maximum threshold. A value of -1 disables the evaluation of this threshold."
	DEFVAL { "2.0" }
	::= { winA3ConfigProgrmGroup 14 }

winA3ConfigProgrmResultMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.621>Default monitor level for the result monitoring of the programmable resource watcher to add. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3ConfigProgrmGroup 15 }

winA3ConfigProgrmLossAction OBJECT-TYPE
	SYNTAX INTEGER {
		remove(1),
		up(2),
		down-warning(3),
		down-critical(4)
	}
	ACCESS read-write
	STATUS mandatory
	DESCRIPTION "&<caiWinA3.622>Default loss action for the programmable resource watcher to add. Specifies the action to take if the monitored programmable resource is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 4 }
	::= { winA3ConfigProgrmGroup 16 }

winA3ConfigProgrmAutoTableWatcherName OBJECT-TYPE
	SYNTAX DisplayString
	ACCESS read-write
	STATUS mandatory
	DESCRIPTION "&<caiWinA3.623>Name of the programmable resource auto watcher to add or remove."
	::= { winA3ConfigProgrmGroup 17 }

winA3ConfigProgrmAutoTableWatcherMatchType OBJECT-TYPE
	SYNTAX INTEGER {
		positive(1),
		negative(2)
	}
	ACCESS read-write
	STATUS mandatory
	DESCRIPTION "&<caiWinA3.624>Default search algorithm for the programmable auto watcher to add. The filter is the logical AND of all attributes used to identify or otherwise narrow down resources. If set to 1 (positive), the agent searches for programmable resources that match the filter. If set to 2 (negative), the agent searches for programmable resources that do not match the filter."
	DEFVAL { 1 }
	::= { winA3ConfigProgrmGroup 18 }

winA3ConfigProgrmAutoTableWatcherLimit OBJECT-TYPE
	SYNTAX INTEGER
	ACCESS read-write
	STATUS mandatory
	DESCRIPTION "&<caiWinA3.625>Default minimum number of matches that causes a lock of the programmable resource auto watcher to add."
	DEFVAL { 200 }
	::= { winA3ConfigProgrmGroup 19 }

winA3ConfigProgrmButton OBJECT-TYPE
	SYNTAX INTEGER {
		none(1),
		add(2),
		remove(3),
		add-auto(4),
		remove-auto(5)
	}
	ACCESS read-write
	STATUS mandatory
	DESCRIPTION "&<caiWinA3.626>This attribute is used to add or remove the programmable resource watcher specified by the current setting of the watcher name attribute(s) in this group. If set to 2 (add), the agent adds the specified watcher to the status table using the current values of the remaining attributes as defaults. If set to 3 (remove), the agent removes the specified watcher from the status table. If set to 4 (add-auto), the agent adds the specified watcher to the auto configuration table using the current values of the remaining attributes as defaults. If set to 5 (remove-auto), the agent removes the specified watcher from the auto configuration table. This attribute cannot be set to 1 (none)."
	DEFVAL { 1 }
	::= { winA3ConfigProgrmGroup 20 }

winA3ConfigProgrmAutoCount OBJECT-TYPE
	SYNTAX INTEGER
	ACCESS read-only
	STATUS mandatory
	DESCRIPTION "&<caiWinA3.627>Number of auto watchers in the programmable resource auto configuration table."
	::= { winA3ConfigProgrmGroup 21 }

winA3ConfigProgrmAutoLocked OBJECT-TYPE
	SYNTAX INTEGER
	ACCESS read-only
	STATUS mandatory
	DESCRIPTION "&<caiWinA3.628>Number of auto watchers in the programmable resource auto configuration table which are currently locked."
	::= { winA3ConfigProgrmGroup 22 }

winA3ConfigProgrmAutoTable OBJECT-TYPE
	SYNTAX SEQUENCE OF WinA3ConfigProgrmAutoEntry
	ACCESS not-accessible
	STATUS mandatory
	DESCRIPTION "&<caiWinA3.629>Configuration table containing a list of programmable resource auto watchers."
	::= { winA3ConfigProgrmGroup 23 }

winA3ConfigProgrmAutoEntry OBJECT-TYPE
	SYNTAX WinA3ConfigProgrmAutoEntry
	ACCESS not-accessible
	STATUS mandatory
	DESCRIPTION "&<caiWinA3.630>Entry in the programmable resource auto watcher configuration table."
	INDEX {
		winA3ConfigProgrmAutoWatcherName
	}
	::= { winA3ConfigProgrmAutoTable 1 }

WinA3ConfigProgrmAutoEntry ::= SEQUENCE {
	winA3ConfigProgrmAutoWatcherName DisplayString,
	winA3ConfigProgrmAutoResName DisplayString,
	winA3ConfigProgrmAutoResSubName DisplayString,
	winA3ConfigProgrmAutoInstName DisplayString,
	winA3ConfigProgrmAutoDescription DisplayString,
	winA3ConfigProgrmAutoWatcherMatchType INTEGER,
	winA3ConfigProgrmAutoWatcherLimit INTEGER,
	winA3ConfigProgrmAutoWatcherLastMatched INTEGER,
	winA3ConfigProgrmAutoErrorMsgPattern DisplayString,
	winA3ConfigProgrmAutoErrorMsgMonitor INTEGER,
	winA3ConfigProgrmAutoResultLag INTEGER,
	winA3ConfigProgrmAutoResultWarnMin DisplayString,
	winA3ConfigProgrmAutoResultWarnMax DisplayString,
	winA3ConfigProgrmAutoResultCritMin DisplayString,
	winA3ConfigProgrmAutoResultCritMax DisplayString,
	winA3ConfigProgrmAutoResultMonitor INTEGER,
	winA3ConfigProgrmAutoLossAction INTEGER,
	winA3ConfigProgrmAutoButton INTEGER
}

winA3ConfigProgrmAutoWatcherName OBJECT-TYPE
	SYNTAX DisplayString
	ACCESS read-only
	STATUS mandatory
	DESCRIPTION "&<caiWinA3.631>Name of the programmable resource auto watcher."
	::= { winA3ConfigProgrmAutoEntry 1 }

winA3ConfigProgrmAutoResName OBJECT-TYPE
	SYNTAX DisplayString
	ACCESS read-write
	STATUS mandatory
	DESCRIPTION "&<caiWinA3.632>A regular expression (case-insensitive) used to filter the resource names. It restricts the resources to be searched for during an auto discovery run."
	::= { winA3ConfigProgrmAutoEntry 2 }

winA3ConfigProgrmAutoResSubName OBJECT-TYPE
	SYNTAX DisplayString
	ACCESS read-write
	STATUS mandatory
	DESCRIPTION "&<caiWinA3.633>A regular expression (case-insensitive) used to filter the resource subnames. It restricts the resources to be searched for during an auto discovery run."
	::= { winA3ConfigProgrmAutoEntry 3 }

winA3ConfigProgrmAutoInstName OBJECT-TYPE
	SYNTAX DisplayString
	ACCESS read-write
	STATUS mandatory
	DESCRIPTION "&<caiWinA3.634>A regular expression (case-insensitive) used to filter the instance names. It restricts the resources to be searched for during an auto discovery run."
	::= { winA3ConfigProgrmAutoEntry 4 }

winA3ConfigProgrmAutoDescription OBJECT-TYPE
	SYNTAX DisplayString
	ACCESS read-write
	STATUS mandatory
	DESCRIPTION "&<caiWinA3.635>Current description for the programmable resource auto watcher."
	::= { winA3ConfigProgrmAutoEntry 5 }

winA3ConfigProgrmAutoWatcherMatchType OBJECT-TYPE
	SYNTAX INTEGER {
		positive(1),
		negative(2)
	}
	ACCESS read-write
	STATUS mandatory
	DESCRIPTION "&<caiWinA3.636>Current search algorithm for the programmable auto watcher. The filter is the logical AND of all attributes used to identify or otherwise narrow down resources. If set to 1 (positive), the agent searches for programmable resources that match the filter. If set to 2 (negative), the agent searches for programmable resources that do not match the filter."
	DEFVAL { 0 }
	::= { winA3ConfigProgrmAutoEntry 6 }

winA3ConfigProgrmAutoWatcherLimit OBJECT-TYPE
	SYNTAX INTEGER
	ACCESS read-write
	STATUS mandatory
	DESCRIPTION "&<caiWinA3.637>Current minimum number of matches that causes the programmable resource auto watcher to be locked."
	::= { winA3ConfigProgrmAutoEntry 7 }

winA3ConfigProgrmAutoWatcherLastMatched OBJECT-TYPE
	SYNTAX INTEGER
	ACCESS read-only
	STATUS mandatory
	DESCRIPTION "&<caiWinA3.638>Number of matches for the last programmable resource auto discovery run."
	::= { winA3ConfigProgrmAutoEntry 8 }

winA3ConfigProgrmAutoErrorMsgPattern OBJECT-TYPE
	SYNTAX DisplayString
	ACCESS read-write
	STATUS mandatory
	DESCRIPTION "&<caiWinA3.639>A regular expression (case-insensitive). If the error message matches this pattern, the error message status changes according to the error message monitor policy."
	::= { winA3ConfigProgrmAutoEntry 9 }

winA3ConfigProgrmAutoErrorMsgMonitor OBJECT-TYPE
	SYNTAX INTEGER {
		do-not-monitor(1),
		down-warning(2),
		down-critical(3)
	}
	ACCESS read-write
	STATUS mandatory
	DESCRIPTION "&<caiWinA3.640>Default monitor level for the error message monitoring of any programmable resource watcher created by the auto watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3ConfigProgrmAutoEntry 10 }

winA3ConfigProgrmAutoResultLag OBJECT-TYPE
	SYNTAX INTEGER
	ACCESS read-write
	STATUS mandatory
	DESCRIPTION "&<caiWinA3.641>Default lag setting for the result monitoring of any programmable resource watcher created by the auto watcher. Specifies the number of consecutive threshold breaches on which the result state changes. This value must be greater than 0."
	::= { winA3ConfigProgrmAutoEntry 11 }

winA3ConfigProgrmAutoResultWarnMin OBJECT-TYPE
	SYNTAX DisplayString
	ACCESS read-write
	STATUS mandatory
	DESCRIPTION "&<caiWinA3.642>Default warning minimum threshold for the result monitoring of any programmable resource watcher created by the auto watcher. This value represents a declining threshold and must be equal to or greater than 0.0, equal to or greater than the critical minimum threshold, but cannot be greater than the warning maximum threshold. A value of -1 disables the evaluation of this threshold."
	DEFVAL { "-2" }
	::= { winA3ConfigProgrmAutoEntry 12 }

winA3ConfigProgrmAutoResultWarnMax OBJECT-TYPE
	SYNTAX DisplayString
	ACCESS read-write
	STATUS mandatory
	DESCRIPTION "&<caiWinA3.643>Default warning maximum threshold for the result monitoring of any programmable resource watcher created by the auto watcher. This value represents a rising threshold and must be equal to or greater than 0.0, equal to or greater than the warning minimum threshold, but cannot be greater than the critical maximum threshold. A value of -1 disables the evaluation of this threshold."
	DEFVAL { "-2" }
	::= { winA3ConfigProgrmAutoEntry 13 }

winA3ConfigProgrmAutoResultCritMin OBJECT-TYPE
	SYNTAX DisplayString
	ACCESS read-write
	STATUS mandatory
	DESCRIPTION "&<caiWinA3.644>Default critical minimum threshold for the result monitoring of any programmable resource watcher created by the auto watcher. This value represents a declining threshold and must be equal to or greater than 0.0, but cannot be greater than the warning minimum threshold. A value of -1 disables the evaluation of this threshold."
	DEFVAL { "-2" }
	::= { winA3ConfigProgrmAutoEntry 14 }

winA3ConfigProgrmAutoResultCritMax OBJECT-TYPE
	SYNTAX DisplayString
	ACCESS read-write
	STATUS mandatory
	DESCRIPTION "&<caiWinA3.645>Default critical maximum threshold for the result monitoring of any programmable resource watcher created by the auto watcher. This value represents a rising threshold and must be equal to or greater than 0.0, but cannot be less than the warning maximum threshold. A value of -1 disables the evaluation of this threshold."
	DEFVAL { "-2" }
	::= { winA3ConfigProgrmAutoEntry 15 }

winA3ConfigProgrmAutoResultMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.646>Default monitor level for the result monitoring of any programmable resource watcher created by the auto watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3ConfigProgrmAutoEntry 16 }

winA3ConfigProgrmAutoLossAction OBJECT-TYPE
	SYNTAX INTEGER {
		remove(1),
		up(2),
		down-warning(3),
		down-critical(4)
	}
	ACCESS read-write
	STATUS mandatory
	DESCRIPTION "&<caiWinA3.647>Default loss action for any programmable resource watcher created by the auto watcher. Specifies the action to take if the monitored programmable resource is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3ConfigProgrmAutoEntry 17 }

winA3ConfigProgrmAutoButton OBJECT-TYPE
	SYNTAX INTEGER {
		active(1),
		remove(2),
		locked(3)
	}
	ACCESS read-write
	STATUS mandatory
	DESCRIPTION "&<caiWinA3.648>This attribute is used to enable/disable or remove the programmable resource auto watcher. If set to 1 (active), the agent re-enables the watcher previously locked either explicitly or implicitly by exceeding the maximum number of allowed matches. Each set request with this value will cause the agent to process the auto watcher. If set to 3 (locked), the agent disables the auto watcher. If set to 2 (remove), the agent removes the auto watcher from the table."
	DEFVAL { 1 }
	::= { winA3ConfigProgrmAutoEntry 18 }

--
-- The StatusGeneral Group
--

winA3StatusGeneralTotalCount OBJECT-TYPE
	SYNTAX INTEGER
	ACCESS read-only
	STATUS mandatory
	DESCRIPTION "&<caiWinA3.649>Total number of resources that the agent is configured to monitor."
	::= { winA3StatusGeneralGroup 1 }

winA3StatusGeneralTotalWarn OBJECT-TYPE
	SYNTAX INTEGER
	ACCESS read-only
	STATUS mandatory
	DESCRIPTION "&<caiWinA3.650>Total number of resources that the agent is configured to monitor that are in a warning state."
	::= { winA3StatusGeneralGroup 2 }

winA3StatusGeneralTotalCrit OBJECT-TYPE
	SYNTAX INTEGER
	ACCESS read-only
	STATUS mandatory
	DESCRIPTION "&<caiWinA3.651>Total number of resources that the agent is configured to monitor that are in a critical state."
	::= { winA3StatusGeneralGroup 3 }

winA3StatusGeneralCPUCount OBJECT-TYPE
	SYNTAX INTEGER
	ACCESS read-only
	STATUS mandatory
	DESCRIPTION "&<caiWinA3.652>Total number of CPU resources that the agent is configured to monitor."
	::= { winA3StatusGeneralGroup 4 }

winA3StatusGeneralCPUWarn OBJECT-TYPE
	SYNTAX INTEGER
	ACCESS read-only
	STATUS mandatory
	DESCRIPTION "&<caiWinA3.653>Total number of CPU resources that the agent is configured to monitor that are in a warning state."
	::= { winA3StatusGeneralGroup 5 }

winA3StatusGeneralCPUCrit OBJECT-TYPE
	SYNTAX INTEGER
	ACCESS read-only
	STATUS mandatory
	DESCRIPTION "&<caiWinA3.654>Total number of CPU resources that the agent is configured to monitor that are in a critical state."
	::= { winA3StatusGeneralGroup 6 }

winA3StatusGeneralMemCount OBJECT-TYPE
	SYNTAX INTEGER
	ACCESS read-only
	STATUS mandatory
	DESCRIPTION "&<caiWinA3.655>Total number of memory resources that the agent is configured to monitor."
	::= { winA3StatusGeneralGroup 7 }

winA3StatusGeneralMemWarn OBJECT-TYPE
	SYNTAX INTEGER
	ACCESS read-only
	STATUS mandatory
	DESCRIPTION "&<caiWinA3.656>Total number of memory resources that the agent is configured to monitor that are in a warning state."
	::= { winA3StatusGeneralGroup 8 }

winA3StatusGeneralMemCrit OBJECT-TYPE
	SYNTAX INTEGER
	ACCESS read-only
	STATUS mandatory
	DESCRIPTION "&<caiWinA3.657>Total number of memory resources that the agent is configured to monitor that are in a critical state."
	::= { winA3StatusGeneralGroup 9 }

winA3StatusGeneralLVolCount OBJECT-TYPE
	SYNTAX INTEGER
	ACCESS read-only
	STATUS mandatory
	DESCRIPTION "&<caiWinA3.658>Total number of logical volume resources that the agent is configured to monitor."
	::= { winA3StatusGeneralGroup 10 }

winA3StatusGeneralLVolWarn OBJECT-TYPE
	SYNTAX INTEGER
	ACCESS read-only
	STATUS mandatory
	DESCRIPTION "&<caiWinA3.659>Total number of logical volume resources that the agent is configured to monitor that are in a warning state."
	::= { winA3StatusGeneralGroup 11 }

winA3StatusGeneralLVolCrit OBJECT-TYPE
	SYNTAX INTEGER
	ACCESS read-only
	STATUS mandatory
	DESCRIPTION "&<caiWinA3.660>Total number of logical volume resources that the agent is configured to monitor that are in a critical state."
	::= { winA3StatusGeneralGroup 12 }

winA3StatusGeneralMntCount OBJECT-TYPE
	SYNTAX INTEGER
	ACCESS read-only
	STATUS mandatory
	DESCRIPTION "&<caiWinA3.661>Total number of mount resources that the agent is configured to monitor."
	::= { winA3StatusGeneralGroup 13 }

winA3StatusGeneralMntWarn OBJECT-TYPE
	SYNTAX INTEGER
	ACCESS read-only
	STATUS mandatory
	DESCRIPTION "&<caiWinA3.662>Total number of mount resources that the agent is configured to monitor that are in a warning state."
	::= { winA3StatusGeneralGroup 14 }

winA3StatusGeneralMntCrit OBJECT-TYPE
	SYNTAX INTEGER
	ACCESS read-only
	STATUS mandatory
	DESCRIPTION "&<caiWinA3.663>Total number of mount resources that the agent is configured to monitor that are in a critical state."
	::= { winA3StatusGeneralGroup 15 }

winA3StatusGeneralDfsCount OBJECT-TYPE
	SYNTAX INTEGER
	ACCESS read-only
	STATUS mandatory
	DESCRIPTION "&<caiWinA3.664>Total number of distributed file system link resources that the agent is configured to monitor."
	::= { winA3StatusGeneralGroup 16 }

winA3StatusGeneralDfsWarn OBJECT-TYPE
	SYNTAX INTEGER
	ACCESS read-only
	STATUS mandatory
	DESCRIPTION "&<caiWinA3.665>Total number of distributed file system link resources that the agent is configured to monitor that are in a warning state."
	::= { winA3StatusGeneralGroup 17 }

winA3StatusGeneralDfsCrit OBJECT-TYPE
	SYNTAX INTEGER
	ACCESS read-only
	STATUS mandatory
	DESCRIPTION "&<caiWinA3.666>Total number of distributed file system link resources that the agent is configured to monitor that are in a critical state."
	::= { winA3StatusGeneralGroup 18 }

winA3StatusGeneralQuotaCount OBJECT-TYPE
	SYNTAX INTEGER
	ACCESS read-only
	STATUS mandatory
	DESCRIPTION "&<caiWinA3.667>Total number of quota resources that the agent is configured to monitor."
	::= { winA3StatusGeneralGroup 19 }

winA3StatusGeneralQuotaWarn OBJECT-TYPE
	SYNTAX INTEGER
	ACCESS read-only
	STATUS mandatory
	DESCRIPTION "&<caiWinA3.668>Total number of quota resources that the agent is configured to monitor that are in a warning state."
	::= { winA3StatusGeneralGroup 20 }

winA3StatusGeneralQuotaCrit OBJECT-TYPE
	SYNTAX INTEGER
	ACCESS read-only
	STATUS mandatory
	DESCRIPTION "&<caiWinA3.669>Total number of quota resources that the agent is configured to monitor that are in a critical state."
	::= { winA3StatusGeneralGroup 21 }

winA3StatusGeneralDirCount OBJECT-TYPE
	SYNTAX INTEGER
	ACCESS read-only
	STATUS mandatory
	DESCRIPTION "&<caiWinA3.670>Total number of directory resources that the agent is configured to monitor."
	::= { winA3StatusGeneralGroup 22 }

winA3StatusGeneralDirWarn OBJECT-TYPE
	SYNTAX INTEGER
	ACCESS read-only
	STATUS mandatory
	DESCRIPTION "&<caiWinA3.671>Total number of directory resources that the agent is configured to monitor that are in a warning state."
	::= { winA3StatusGeneralGroup 23 }

winA3StatusGeneralDirCrit OBJECT-TYPE
	SYNTAX INTEGER
	ACCESS read-only
	STATUS mandatory
	DESCRIPTION "&<caiWinA3.672>Total number of directory resources that the agent is configured to monitor that are in a critical state."
	::= { winA3StatusGeneralGroup 24 }

winA3StatusGeneralFileCount OBJECT-TYPE
	SYNTAX INTEGER
	ACCESS read-only
	STATUS mandatory
	DESCRIPTION "&<caiWinA3.673>Total number of file resources that the agent is configured to monitor."
	::= { winA3StatusGeneralGroup 25 }

winA3StatusGeneralFileWarn OBJECT-TYPE
	SYNTAX INTEGER
	ACCESS read-only
	STATUS mandatory
	DESCRIPTION "&<caiWinA3.674>Total number of file resources that the agent is configured to monitor that are in a warning state."
	::= { winA3StatusGeneralGroup 26 }

winA3StatusGeneralFileCrit OBJECT-TYPE
	SYNTAX INTEGER
	ACCESS read-only
	STATUS mandatory
	DESCRIPTION "&<caiWinA3.675>Total number of file resources that the agent is configured to monitor that are in a critical state."
	::= { winA3StatusGeneralGroup 27 }

winA3StatusGeneralProcCount OBJECT-TYPE
	SYNTAX INTEGER
	ACCESS read-only
	STATUS mandatory
	DESCRIPTION "&<caiWinA3.676>Total number of process resources that the agent is configured to monitor."
	::= { winA3StatusGeneralGroup 28 }

winA3StatusGeneralProcWarn OBJECT-TYPE
	SYNTAX INTEGER
	ACCESS read-only
	STATUS mandatory
	DESCRIPTION "&<caiWinA3.677>Total number of process resources that the agent is configured to monitor that are in a warning state."
	::= { winA3StatusGeneralGroup 29 }

winA3StatusGeneralProcCrit OBJECT-TYPE
	SYNTAX INTEGER
	ACCESS read-only
	STATUS mandatory
	DESCRIPTION "&<caiWinA3.678>Total number of process resources that the agent is configured to monitor that are in a critical state."
	::= { winA3StatusGeneralGroup 30 }

winA3StatusGeneralSrvcCount OBJECT-TYPE
	SYNTAX INTEGER
	ACCESS read-only
	STATUS mandatory
	DESCRIPTION "&<caiWinA3.679>Total number of service resources that the agent is configured to monitor."
	::= { winA3StatusGeneralGroup 31 }

winA3StatusGeneralSrvcWarn OBJECT-TYPE
	SYNTAX INTEGER
	ACCESS read-only
	STATUS mandatory
	DESCRIPTION "&<caiWinA3.680>Total number of service resources that the agent is configured to monitor that are in a warning state."
	::= { winA3StatusGeneralGroup 32 }

winA3StatusGeneralSrvcCrit OBJECT-TYPE
	SYNTAX INTEGER
	ACCESS read-only
	STATUS mandatory
	DESCRIPTION "&<caiWinA3.681>Total number of service resources that the agent is configured to monitor that are in a critical state."
	::= { winA3StatusGeneralGroup 33 }

winA3StatusGeneralJobCount OBJECT-TYPE
	SYNTAX INTEGER
	ACCESS read-only
	STATUS mandatory
	DESCRIPTION "&<caiWinA3.682>Total number of job resources that the agent is configured to monitor."
	::= { winA3StatusGeneralGroup 34 }

winA3StatusGeneralJobWarn OBJECT-TYPE
	SYNTAX INTEGER
	ACCESS read-only
	STATUS mandatory
	DESCRIPTION "&<caiWinA3.683>Total number of job resources that the agent is configured to monitor that are in a warning state."
	::= { winA3StatusGeneralGroup 35 }

winA3StatusGeneralJobCrit OBJECT-TYPE
	SYNTAX INTEGER
	ACCESS read-only
	STATUS mandatory
	DESCRIPTION "&<caiWinA3.684>Total number of job resources that the agent is configured to monitor that are in a critical state."
	::= { winA3StatusGeneralGroup 36 }

winA3StatusGeneralSessCount OBJECT-TYPE
	SYNTAX INTEGER
	ACCESS read-only
	STATUS mandatory
	DESCRIPTION "&<caiWinA3.685>Total number of terminal session resources that the agent is configured to monitor."
	::= { winA3StatusGeneralGroup 37 }

winA3StatusGeneralSessWarn OBJECT-TYPE
	SYNTAX INTEGER
	ACCESS read-only
	STATUS mandatory
	DESCRIPTION "&<caiWinA3.686>Total number of terminal session resources that the agent is configured to monitor that are in a warning state."
	::= { winA3StatusGeneralGroup 38 }

winA3StatusGeneralSessCrit OBJECT-TYPE
	SYNTAX INTEGER
	ACCESS read-only
	STATUS mandatory
	DESCRIPTION "&<caiWinA3.687>Total number of terminal session resources that the agent is configured to monitor that are in a critical state."
	::= { winA3StatusGeneralGroup 39 }

winA3StatusGeneralPrnCount OBJECT-TYPE
	SYNTAX INTEGER
	ACCESS read-only
	STATUS mandatory
	DESCRIPTION "&<caiWinA3.688>Total number of printer resources that the agent is configured to monitor."
	::= { winA3StatusGeneralGroup 40 }

winA3StatusGeneralPrnWarn OBJECT-TYPE
	SYNTAX INTEGER
	ACCESS read-only
	STATUS mandatory
	DESCRIPTION "&<caiWinA3.689>Total number of printer resources that the agent is configured to monitor that are in a warning state."
	::= { winA3StatusGeneralGroup 41 }

winA3StatusGeneralPrnCrit OBJECT-TYPE
	SYNTAX INTEGER
	ACCESS read-only
	STATUS mandatory
	DESCRIPTION "&<caiWinA3.690>Total number of printer resources that the agent is configured to monitor that are in a critical state."
	::= { winA3StatusGeneralGroup 42 }

winA3StatusGeneralNetCount OBJECT-TYPE
	SYNTAX INTEGER
	ACCESS read-only
	STATUS mandatory
	DESCRIPTION "&<caiWinA3.691>Total number of network interface resources that the agent is configured to monitor."
	::= { winA3StatusGeneralGroup 43 }

winA3StatusGeneralNetWarn OBJECT-TYPE
	SYNTAX INTEGER
	ACCESS read-only
	STATUS mandatory
	DESCRIPTION "&<caiWinA3.692>Total number of network interface resources that the agent is configured to monitor that are in a warning state."
	::= { winA3StatusGeneralGroup 44 }

winA3StatusGeneralNetCrit OBJECT-TYPE
	SYNTAX INTEGER
	ACCESS read-only
	STATUS mandatory
	DESCRIPTION "&<caiWinA3.693>Total number of network interface resources that the agent is configured to monitor that are in a critical state."
	::= { winA3StatusGeneralGroup 45 }

winA3StatusGeneralRegCount OBJECT-TYPE
	SYNTAX INTEGER
	ACCESS read-only
	STATUS mandatory
	DESCRIPTION "&<caiWinA3.694>Total number of registry entry resources that the agent is configured to monitor."
	::= { winA3StatusGeneralGroup 46 }

winA3StatusGeneralRegWarn OBJECT-TYPE
	SYNTAX INTEGER
	ACCESS read-only
	STATUS mandatory
	DESCRIPTION "&<caiWinA3.695>Total number of registry entry resources that the agent is configured to monitor that are in a warning state."
	::= { winA3StatusGeneralGroup 47 }

winA3StatusGeneralRegCrit OBJECT-TYPE
	SYNTAX INTEGER
	ACCESS read-only
	STATUS mandatory
	DESCRIPTION "&<caiWinA3.696>Total number of registry entry resources that the agent is configured to monitor that are in a critical state."
	::= { winA3StatusGeneralGroup 48 }

winA3StatusGeneralHardwrCount OBJECT-TYPE
	SYNTAX INTEGER
	ACCESS read-only
	STATUS mandatory
	DESCRIPTION "&<caiWinA3.697>Total number of hardware resources that the agent is configured to monitor."
	::= { winA3StatusGeneralGroup 49 }

winA3StatusGeneralHardwrWarn OBJECT-TYPE
	SYNTAX INTEGER
	ACCESS read-only
	STATUS mandatory
	DESCRIPTION "&<caiWinA3.698>Total number of hardware resources that the agent is configured to monitor that are in a warning state."
	::= { winA3StatusGeneralGroup 50 }

winA3StatusGeneralHardwrCrit OBJECT-TYPE
	SYNTAX INTEGER
	ACCESS read-only
	STATUS mandatory
	DESCRIPTION "&<caiWinA3.699>Total number of hardware resources that the agent is configured to monitor that are in a critical state."
	::= { winA3StatusGeneralGroup 51 }

winA3StatusGeneralProgrmCount OBJECT-TYPE
	SYNTAX INTEGER
	ACCESS read-only
	STATUS mandatory
	DESCRIPTION "&<caiWinA3.700>Total number of programmable resources that the agent is configured to monitor."
	::= { winA3StatusGeneralGroup 52 }

winA3StatusGeneralProgrmWarn OBJECT-TYPE
	SYNTAX INTEGER
	ACCESS read-only
	STATUS mandatory
	DESCRIPTION "&<caiWinA3.701>Total number of programmable resources that the agent is configured to monitor that are in a warning state."
	::= { winA3StatusGeneralGroup 53 }

winA3StatusGeneralProgrmCrit OBJECT-TYPE
	SYNTAX INTEGER
	ACCESS read-only
	STATUS mandatory
	DESCRIPTION "&<caiWinA3.702>Total number of programmable resources that the agent is configured to monitor that are in a critical state."
	::= { winA3StatusGeneralGroup 54 }

--
-- The StatusCPU Group
--

winA3StatusCPUTotalAggLagValue OBJECT-TYPE
	SYNTAX INTEGER
	ACCESS read-only
	STATUS mandatory
	DESCRIPTION "&<caiWinA3.703>Current aggregate lag value of the CPU watcher. Indicates the consecutive number of times at which any status was not in the ok state. The aggregate status changes from ok as soon as the aggregate lag value reaches the configured value."
	::= { winA3StatusCPUGroup 1 }

winA3StatusCPUTotalAggLag OBJECT-TYPE
	SYNTAX INTEGER
	ACCESS read-write
	STATUS mandatory
	DESCRIPTION "&<caiWinA3.704>Current aggregate lag setting for the CPU watcher. Specifies the consecutive number of times at which any status is not in the ok state, before the aggregate status changes. This value must be greater than 0."
	DEFVAL { 10 }
	::= { winA3StatusCPUGroup 2 }

winA3StatusCPUTotalAggStatus OBJECT-TYPE
	SYNTAX INTEGER {
		unknown(1),
		ok(2),
		warning(3),
		critical(4),
		passive(5)
	}
	ACCESS read-only
	STATUS mandatory
	DESCRIPTION "&<caiWinA3.705>Current aggregate status of the CPU watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusCPUGroup 3 }

winA3StatusCPUTotalLoadValue OBJECT-TYPE
	SYNTAX DisplayString
	ACCESS read-only
	STATUS mandatory
	DESCRIPTION "&<caiWinA3.706>Current value, in percent, for the total CPU utilization monitoring of the CPU watcher. This is the average of all CPUs."
	DEFVAL { "0" }
	::= { winA3StatusCPUGroup 4 }

winA3StatusCPUTotalLoadWarnMin OBJECT-TYPE
	SYNTAX DisplayString
	ACCESS read-write
	STATUS mandatory
	DESCRIPTION "&<caiWinA3.707>Current warning minimum threshold, in percent, for the total CPU utilization monitoring of the CPU watcher. This value represents a declining threshold and must be equal to or greater than 0.0, less than or equal to 100.0, equal to or greater than the critical minimum threshold, but cannot be greater than the warning maximum threshold. A value of -1 disables the evaluation of this threshold."
	DEFVAL { "-1" }
	::= { winA3StatusCPUGroup 5 }

winA3StatusCPUTotalLoadWarnMax OBJECT-TYPE
	SYNTAX DisplayString
	ACCESS read-write
	STATUS mandatory
	DESCRIPTION "&<caiWinA3.708>Current warning maximum threshold, in percent, for the total CPU utilization monitoring of the CPU watcher. This value represents a rising threshold and must be equal to or greater than 0.0, less than or equal to 100.0, equal to or greater than the warning minimum threshold, but cannot be greater than the critical maximum threshold. A value of -1 disables the evaluation of this threshold."
	DEFVAL { "70.0" }
	::= { winA3StatusCPUGroup 6 }

winA3StatusCPUTotalLoadCritMin OBJECT-TYPE
	SYNTAX DisplayString
	ACCESS read-write
	STATUS mandatory
	DESCRIPTION "&<caiWinA3.709>Current critical minimum threshold, in percent, for the total CPU utilization monitoring of the CPU watcher. This value represents a declining threshold and must be equal to or greater than 0.0, less than or equal to 100.0, but cannot be greater than the warning minimum threshold. A value of -1 disables the evaluation of this threshold."
	DEFVAL { "-1" }
	::= { winA3StatusCPUGroup 7 }

winA3StatusCPUTotalLoadCritMax OBJECT-TYPE
	SYNTAX DisplayString
	ACCESS read-write
	STATUS mandatory
	DESCRIPTION "&<caiWinA3.710>Current critical maximum threshold, in percent, for the total CPU utilization monitoring of the CPU watcher. This value represents a rising threshold and must be equal to or greater than 0.0, less than or equal to 100.0, but cannot be less than the warning maximum threshold. A value of -1 disables the evaluation of this threshold."
	DEFVAL { "90.0" }
	::= { winA3StatusCPUGroup 8 }

winA3StatusCPUTotalLoadMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.711>Current monitor level for the total CPU utilization monitoring of the CPU watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3StatusCPUGroup 9 }

winA3StatusCPUTotalLoadStatus OBJECT-TYPE
	SYNTAX INTEGER {
		unknown(1),
		up(2),
		down-warning(3),
		down-critical(4)
	}
	ACCESS read-only
	STATUS mandatory
	DESCRIPTION "&<caiWinA3.712>Current status for the total CPU utilization monitoring of the CPU watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusCPUGroup 10 }

winA3StatusCPUTotalQueueValue OBJECT-TYPE
	SYNTAX DisplayString
	ACCESS read-only
	STATUS mandatory
	DESCRIPTION "&<caiWinA3.713>Current value for the total CPU queue length monitoring of the CPU watcher. This is the sum of all CPUs."
	DEFVAL { "0" }
	::= { winA3StatusCPUGroup 11 }

winA3StatusCPUTotalQueueWarn OBJECT-TYPE
	SYNTAX DisplayString
	ACCESS read-write
	STATUS mandatory
	DESCRIPTION "&<caiWinA3.714>Current warning threshold for the total CPU queue length monitoring of the CPU watcher. This value represents a rising threshold and must be greater than 0.0, but cannot be greater than the critical threshold."
	DEFVAL { "8.0" }
	::= { winA3StatusCPUGroup 12 }

winA3StatusCPUTotalQueueCrit OBJECT-TYPE
	SYNTAX DisplayString
	ACCESS read-write
	STATUS mandatory
	DESCRIPTION "&<caiWinA3.715>Current critical threshold for the total CPU queue length monitoring of the CPU watcher. This value represents a rising threshold and must be greater than 0.0, but cannot be less than the warning threshold."
	DEFVAL { "16.0" }
	::= { winA3StatusCPUGroup 13 }

winA3StatusCPUTotalQueueMonitor OBJECT-TYPE
	SYNTAX INTEGER {
		do-not-monitor(1),
		warning-only(2),
		critical-only(3),
		both(4)
	}
	ACCESS read-write
	STATUS mandatory
	DESCRIPTION "&<caiWinA3.716>Current monitor level for the total CPU queue length monitoring of the CPU watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3StatusCPUGroup 14 }

winA3StatusCPUTotalQueueStatus OBJECT-TYPE
	SYNTAX INTEGER {
		unknown(1),
		ok(2),
		warning(3),
		critical(4)
	}
	ACCESS read-only
	STATUS mandatory
	DESCRIPTION "&<caiWinA3.717>Current status for the total CPU queue length monitoring of the CPU watcher: 1 (unknown) - An error occurred during data collection, 2 (ok) - The resource is operating within the defined limits or status evaluation is turned off and/or polling is disabled, 3 (warning) - The resource has breached the warning threshold, 4 (critical) - The resource has breached the critical threshold."
	::= { winA3StatusCPUGroup 15 }

winA3StatusCPUTotalCallBackRef OBJECT-TYPE
	SYNTAX DisplayString
	ACCESS read-only
	STATUS mandatory
	DESCRIPTION "&<caiWinA3.718>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusCPUGroup 16 }

winA3StatusCPUCount OBJECT-TYPE
	SYNTAX INTEGER
	ACCESS read-only
	STATUS mandatory
	DESCRIPTION "&<caiWinA3.719>Number of entries in the CPU status table."
	::= { winA3StatusCPUGroup 17 }

winA3StatusCPUTable OBJECT-TYPE
	SYNTAX SEQUENCE OF WinA3StatusCPUEntry
	ACCESS not-accessible
	STATUS mandatory
	DESCRIPTION "&<caiWinA3.720>The CPU status table containing details about the currently configured CPU watchers."
	::= { winA3StatusCPUGroup 18 }

winA3StatusCPUEntry OBJECT-TYPE
	SYNTAX WinA3StatusCPUEntry
	ACCESS not-accessible
	STATUS mandatory
	DESCRIPTION "&<caiWinA3.721>Entry in the CPU status table."
	INDEX {
		winA3StatusCPUName
	}
	::= { winA3StatusCPUTable 1 }

WinA3StatusCPUEntry ::= SEQUENCE {
	winA3StatusCPUName DisplayString,
	winA3StatusCPUAggLagValue INTEGER,
	winA3StatusCPUAggLag INTEGER,
	winA3StatusCPUAggStatus INTEGER,
	winA3StatusCPUType DisplayString,
	winA3StatusCPULoadValue DisplayString,
	winA3StatusCPULoadWarnMin DisplayString,
	winA3StatusCPULoadWarnMax DisplayString,
	winA3StatusCPULoadCritMin DisplayString,
	winA3StatusCPULoadCritMax DisplayString,
	winA3StatusCPULoadMonitor INTEGER,
	winA3StatusCPULoadStatus INTEGER,
	winA3StatusCPUQueueValue DisplayString,
	winA3StatusCPUQueueWarn DisplayString,
	winA3StatusCPUQueueCrit DisplayString,
	winA3StatusCPUQueueMonitor INTEGER,
	winA3StatusCPUQueueStatus INTEGER,
	winA3StatusCPULossAction INTEGER,
	winA3StatusCPULossStatus INTEGER,
	winA3StatusCPUCallBackRef DisplayString
}

winA3StatusCPUName OBJECT-TYPE
	SYNTAX DisplayString
	ACCESS read-only
	STATUS mandatory
	DESCRIPTION "&<caiWinA3.722>Name of the CPU. The CPUs are named 'CPU_N', with N being a running index starting with zero."
	::= { winA3StatusCPUEntry 1 }

winA3StatusCPUAggLagValue OBJECT-TYPE
	SYNTAX INTEGER
	ACCESS read-only
	STATUS mandatory
	DESCRIPTION "&<caiWinA3.723>Current aggregate lag value of the CPU watcher. Indicates the consecutive number of times at which any status was not in the ok state. The aggregate status changes from ok as soon as the aggregate lag value reaches the configured value."
	::= { winA3StatusCPUEntry 2 }

winA3StatusCPUAggLag OBJECT-TYPE
	SYNTAX INTEGER
	ACCESS read-write
	STATUS mandatory
	DESCRIPTION "&<caiWinA3.724>Current aggregate lag setting for the CPU watcher. Specifies the consecutive number of times at which any status is not in the ok state, before the aggregate status changes. This value must be greater than 0."
	::= { winA3StatusCPUEntry 3 }

winA3StatusCPUAggStatus OBJECT-TYPE
	SYNTAX INTEGER {
		unknown(1),
		ok(2),
		warning(3),
		critical(4),
		passive(5)
	}
	ACCESS read-only
	STATUS mandatory
	DESCRIPTION "&<caiWinA3.725>Current aggregate status of the CPU watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusCPUEntry 4 }

winA3StatusCPUType OBJECT-TYPE
	SYNTAX DisplayString
	ACCESS read-only
	STATUS mandatory
	DESCRIPTION "&<caiWinA3.726>Type of the CPU."
	::= { winA3StatusCPUEntry 5 }

winA3StatusCPULoadValue OBJECT-TYPE
	SYNTAX DisplayString
	ACCESS read-only
	STATUS mandatory
	DESCRIPTION "&<caiWinA3.727>Current value, in percent, for the CPU utilization monitoring of the CPU watcher. This is the percentage of time in the last poll interval that the processor was executing a non-idle thread."
	DEFVAL { "0" }
	::= { winA3StatusCPUEntry 6 }

winA3StatusCPULoadWarnMin OBJECT-TYPE
	SYNTAX DisplayString
	ACCESS read-write
	STATUS mandatory
	DESCRIPTION "&<caiWinA3.728>Current warning minimum threshold, in percent, for the CPU utilization monitoring of the CPU watcher. This value represents a declining threshold and must be equal to or greater than 0.0, less than or equal to 100.0, equal to or greater than the critical minimum threshold, but cannot be greater than the warning maximum threshold. A value of -1 disables the evaluation of this threshold."
	DEFVAL { "-2" }
	::= { winA3StatusCPUEntry 7 }

winA3StatusCPULoadWarnMax OBJECT-TYPE
	SYNTAX DisplayString
	ACCESS read-write
	STATUS mandatory
	DESCRIPTION "&<caiWinA3.729>Current warning maximum threshold, in percent, for the CPU utilization monitoring of the CPU watcher. This value represents a rising threshold and must be equal to or greater than 0.0, less than or equal to 100.0, equal to or greater than the warning minimum threshold, but cannot be greater than the critical maximum threshold. A value of -1 disables the evaluation of this threshold."
	DEFVAL { "-2" }
	::= { winA3StatusCPUEntry 8 }

winA3StatusCPULoadCritMin OBJECT-TYPE
	SYNTAX DisplayString
	ACCESS read-write
	STATUS mandatory
	DESCRIPTION "&<caiWinA3.730>Current critical minimum threshold, in percent, for the CPU utilization monitoring of the CPU watcher. This value represents a declining threshold and must be equal to or greater than 0.0, less than or equal to 100.0, but cannot be greater than the warning minimum threshold. A value of -1 disables the evaluation of this threshold."
	DEFVAL { "-2" }
	::= { winA3StatusCPUEntry 9 }

winA3StatusCPULoadCritMax OBJECT-TYPE
	SYNTAX DisplayString
	ACCESS read-write
	STATUS mandatory
	DESCRIPTION "&<caiWinA3.731>Current critical maximum threshold, in percent, for the CPU utilization monitoring of the CPU watcher. This value represents a rising threshold and must be equal to or greater than 0.0, less than or equal to 100.0, but cannot be less than the warning maximum threshold. A value of -1 disables the evaluation of this threshold."
	DEFVAL { "-2" }
	::= { winA3StatusCPUEntry 10 }

winA3StatusCPULoadMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.732>Current monitor level for the CPU utilization monitoring of the CPU watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusCPUEntry 11 }

winA3StatusCPULoadStatus OBJECT-TYPE
	SYNTAX INTEGER {
		unknown(1),
		up(2),
		down-warning(3),
		down-critical(4)
	}
	ACCESS read-only
	STATUS mandatory
	DESCRIPTION "&<caiWinA3.733>Current status for the CPU utilization monitoring of the CPU watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusCPUEntry 12 }

winA3StatusCPUQueueValue OBJECT-TYPE
	SYNTAX DisplayString
	ACCESS read-only
	STATUS mandatory
	DESCRIPTION "&<caiWinA3.734>Current value for the CPU queue length monitoring of the CPU watcher. This is the number of ready (i.e. waiting and not running) threads in the processor queue, observed at the last poll. This is not an average."
	DEFVAL { "0" }
	::= { winA3StatusCPUEntry 13 }

winA3StatusCPUQueueWarn OBJECT-TYPE
	SYNTAX DisplayString
	ACCESS read-write
	STATUS mandatory
	DESCRIPTION "&<caiWinA3.735>Current warning threshold for the CPU queue length monitoring of the CPU watcher. This value represents a rising threshold and must be greater than 0.0, but cannot be greater than the critical threshold."
	::= { winA3StatusCPUEntry 14 }

winA3StatusCPUQueueCrit OBJECT-TYPE
	SYNTAX DisplayString
	ACCESS read-write
	STATUS mandatory
	DESCRIPTION "&<caiWinA3.736>Current critical threshold for the CPU queue length monitoring of the CPU watcher. This value represents a rising threshold and must be greater than 0.0, but cannot be less than the warning threshold."
	::= { winA3StatusCPUEntry 15 }

winA3StatusCPUQueueMonitor OBJECT-TYPE
	SYNTAX INTEGER {
		do-not-monitor(1),
		warning-only(2),
		critical-only(3),
		both(4)
	}
	ACCESS read-write
	STATUS mandatory
	DESCRIPTION "&<caiWinA3.737>Current monitor level for the CPU queue length monitoring of the CPU watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusCPUEntry 16 }

winA3StatusCPUQueueStatus OBJECT-TYPE
	SYNTAX INTEGER {
		unknown(1),
		ok(2),
		warning(3),
		critical(4)
	}
	ACCESS read-only
	STATUS mandatory
	DESCRIPTION "&<caiWinA3.738>Current status for the CPU queue length monitoring of the CPU watcher: 1 (unknown) - An error occurred during data collection, 2 (ok) - The resource is operating within the defined limits or status evaluation is turned off and/or polling is disabled, 3 (warning) - The resource has breached the warning threshold, 4 (critical) - The resource has breached the critical threshold."
	::= { winA3StatusCPUEntry 17 }

winA3StatusCPULossAction OBJECT-TYPE
	SYNTAX INTEGER {
		remove(1),
		up(2),
		down-warning(3),
		down-critical(4)
	}
	ACCESS read-write
	STATUS mandatory
	DESCRIPTION "&<caiWinA3.739>Current loss action for the CPU watcher. Specifies the action to take if the monitored CPU is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusCPUEntry 18 }

winA3StatusCPULossStatus OBJECT-TYPE
	SYNTAX INTEGER {
		unknown(1),
		up(2),
		down-warning(3),
		down-critical(4)
	}
	ACCESS read-only
	STATUS mandatory
	DESCRIPTION "&<caiWinA3.740>Current loss status of the CPU watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusCPUEntry 19 }

winA3StatusCPUCallBackRef OBJECT-TYPE
	SYNTAX DisplayString
	ACCESS read-only
	STATUS mandatory
	DESCRIPTION "&<caiWinA3.741>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusCPUEntry 20 }

--
-- The StatusMem Group
--

winA3StatusMemVirtTotal OBJECT-TYPE
	SYNTAX DisplayString
	ACCESS read-only
	STATUS mandatory
	DESCRIPTION "&<caiWinA3.742>The total size, in kilobytes, of the virtual memory on the system that can be committed. The virtual memory comprises the physical and the paging memory."
	DEFVAL { "0" }
	::= { winA3StatusMemGroup 1 }

winA3StatusMemVirtValue OBJECT-TYPE
	SYNTAX DisplayString
	ACCESS read-only
	STATUS mandatory
	DESCRIPTION "&<caiWinA3.743>Current value, in kilobytes, for the virtual memory utilization monitoring of the memory watcher. This is the size of the currently committed virtual memory."
	DEFVAL { "0" }
	::= { winA3StatusMemGroup 2 }

winA3StatusMemVirtLagValue OBJECT-TYPE
	SYNTAX INTEGER
	ACCESS read-only
	STATUS mandatory
	DESCRIPTION "&<caiWinA3.744>Current number of consecutive threshold breaches for the virtual memory utilization monitoring of the memory watcher. The virtual memory utilization state changes from ok as soon as the lag value reaches the configured value. The state reverts back to ok if a threshold is no longer breached."
	::= { winA3StatusMemGroup 3 }

winA3StatusMemVirtLag OBJECT-TYPE
	SYNTAX INTEGER
	ACCESS read-write
	STATUS mandatory
	DESCRIPTION "&<caiWinA3.745>Current lag setting for the virtual memory utilization monitoring of the memory watcher. Specifies the number of consecutive threshold breaches on which the virtual memory utilization state changes. This value must be greater than 0."
	DEFVAL { 10 }
	::= { winA3StatusMemGroup 4 }

winA3StatusMemVirtWarnValue OBJECT-TYPE
	SYNTAX DisplayString
	ACCESS read-only
	STATUS mandatory
	DESCRIPTION "&<caiWinA3.746>Active warning threshold, in kilobytes, as derived from the configured value for the virtual memory utilization monitoring of the memory watcher. This value represents a rising threshold and must be greater than 0.0, less than or equal to the total value (maximum capacity) of the monitored resource as specified in winA3StatusMemVirtTotal, but cannot be greater than the active critical threshold. These constraints will be maintained by the agent during all configuration actions."
	::= { winA3StatusMemGroup 5 }

winA3StatusMemVirtCritValue OBJECT-TYPE
	SYNTAX DisplayString
	ACCESS read-only
	STATUS mandatory
	DESCRIPTION "&<caiWinA3.747>Active critical threshold, in kilobytes, as derived from the configured value for the virtual memory utilization monitoring of the memory watcher. This value represents a rising threshold and must be greater than 0.0, less than or equal to the total value (maximum capacity) of the monitored resource as specified in winA3StatusMemVirtTotal, but cannot be less than the active warning threshold. These constraints will be maintained by the agent during all configuration actions."
	::= { winA3StatusMemGroup 6 }

winA3StatusMemVirtWarn OBJECT-TYPE
	SYNTAX DisplayString
	ACCESS read-write
	STATUS mandatory
	DESCRIPTION "&<caiWinA3.748>Configured warning threshold from which the active warning threshold is derived for the virtual memory utilization monitoring of the memory watcher. The threshold can be specified as either an absolute value (n) or a percentage (n%). It can also be specified as the absolute value left free (nF). The value of winA3StatusMemVirtTotal will be the reference value for n% and nF notations."
	DEFVAL { "85.0%" }
	::= { winA3StatusMemGroup 7 }

winA3StatusMemVirtCrit OBJECT-TYPE
	SYNTAX DisplayString
	ACCESS read-write
	STATUS mandatory
	DESCRIPTION "&<caiWinA3.749>Configured critical threshold from which the active critical threshold is derived for the virtual memory utilization monitoring of the memory watcher. The threshold can be specified as either an absolute value (n) or a percentage (n%). It can also be specified as the absolute value left free (nF). The value of winA3StatusMemVirtTotal will be the reference value for n% and nF notations."
	DEFVAL { "95.0%" }
	::= { winA3StatusMemGroup 8 }

winA3StatusMemVirtMonitor OBJECT-TYPE
	SYNTAX INTEGER {
		do-not-monitor(1),
		warning-only(2),
		critical-only(3),
		both(4)
	}
	ACCESS read-write
	STATUS mandatory
	DESCRIPTION "&<caiWinA3.750>Current monitor level for the virtual memory utilization monitoring of the memory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3StatusMemGroup 9 }

winA3StatusMemVirtStatus OBJECT-TYPE
	SYNTAX INTEGER {
		unknown(1),
		ok(2),
		warning(3),
		critical(4),
		passive(5)
	}
	ACCESS read-only
	STATUS mandatory
	DESCRIPTION "&<caiWinA3.751>Current status for the virtual memory utilization monitoring of the memory watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { winA3StatusMemGroup 10 }

winA3StatusMemPhysTotal OBJECT-TYPE
	SYNTAX DisplayString
	ACCESS read-only
	STATUS mandatory
	DESCRIPTION "&<caiWinA3.752>The total size, in kilobytes, of the physical memory on the system."
	DEFVAL { "0" }
	::= { winA3StatusMemGroup 11 }

winA3StatusMemPhysValue OBJECT-TYPE
	SYNTAX DisplayString
	ACCESS read-only
	STATUS mandatory
	DESCRIPTION "&<caiWinA3.753>Current value, in kilobytes, for the physical memory utilization monitoring of the memory watcher."
	DEFVAL { "0" }
	::= { winA3StatusMemGroup 12 }

winA3StatusMemPhysLagValue OBJECT-TYPE
	SYNTAX INTEGER
	ACCESS read-only
	STATUS mandatory
	DESCRIPTION "&<caiWinA3.754>Current number of consecutive threshold breaches for the physical memory utilization monitoring of the memory watcher. The physical memory utilization state changes from ok as soon as the lag value reaches the configured value. The state reverts back to ok if a threshold is no longer breached."
	::= { winA3StatusMemGroup 13 }

winA3StatusMemPhysLag OBJECT-TYPE
	SYNTAX INTEGER
	ACCESS read-write
	STATUS mandatory
	DESCRIPTION "&<caiWinA3.755>Current lag setting for the physical memory utilization monitoring of the memory watcher. Specifies the number of consecutive threshold breaches on which the physical memory utilization state changes. This value must be greater than 0."
	DEFVAL { 10 }
	::= { winA3StatusMemGroup 14 }

winA3StatusMemPhysWarnValue OBJECT-TYPE
	SYNTAX DisplayString
	ACCESS read-only
	STATUS mandatory
	DESCRIPTION "&<caiWinA3.756>Active warning threshold, in kilobytes, as derived from the configured value for the physical memory utilization monitoring of the memory watcher. This value represents a rising threshold and must be greater than 0.0, less than or equal to the total value (maximum capacity) of the monitored resource as specified in winA3StatusMemPhysTotal, but cannot be greater than the active critical threshold. These constraints will be maintained by the agent during all configuration actions."
	::= { winA3StatusMemGroup 15 }

winA3StatusMemPhysCritValue OBJECT-TYPE
	SYNTAX DisplayString
	ACCESS read-only
	STATUS mandatory
	DESCRIPTION "&<caiWinA3.757>Active critical threshold, in kilobytes, as derived from the configured value for the physical memory utilization monitoring of the memory watcher. This value represents a rising threshold and must be greater than 0.0, less than or equal to the total value (maximum capacity) of the monitored resource as specified in winA3StatusMemPhysTotal, but cannot be less than the active warning threshold. These constraints will be maintained by the agent during all configuration actions."
	::= { winA3StatusMemGroup 16 }

winA3StatusMemPhysWarn OBJECT-TYPE
	SYNTAX DisplayString
	ACCESS read-write
	STATUS mandatory
	DESCRIPTION "&<caiWinA3.758>Configured warning threshold from which the active warning threshold is derived for the physical memory utilization monitoring of the memory watcher. The threshold can be specified as either an absolute value (n) or a percentage (n%). It can also be specified as the absolute value left free (nF). The value of winA3StatusMemPhysTotal will be the reference value for n% and nF notations."
	DEFVAL { "85.0%" }
	::= { winA3StatusMemGroup 17 }

winA3StatusMemPhysCrit OBJECT-TYPE
	SYNTAX DisplayString
	ACCESS read-write
	STATUS mandatory
	DESCRIPTION "&<caiWinA3.759>Configured critical threshold from which the active critical threshold is derived for the physical memory utilization monitoring of the memory watcher. The threshold can be specified as either an absolute value (n) or a percentage (n%). It can also be specified as the absolute value left free (nF). The value of winA3StatusMemPhysTotal will be the reference value for n% and nF notations."
	DEFVAL { "95.0%" }
	::= { winA3StatusMemGroup 18 }

winA3StatusMemPhysMonitor OBJECT-TYPE
	SYNTAX INTEGER {
		do-not-monitor(1),
		warning-only(2),
		critical-only(3),
		both(4)
	}
	ACCESS read-write
	STATUS mandatory
	DESCRIPTION "&<caiWinA3.760>Current monitor level for the physical memory utilization monitoring of the memory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3StatusMemGroup 19 }

winA3StatusMemPhysStatus OBJECT-TYPE
	SYNTAX INTEGER {
		unknown(1),
		ok(2),
		warning(3),
		critical(4),
		passive(5)
	}
	ACCESS read-only
	STATUS mandatory
	DESCRIPTION "&<caiWinA3.761>Current status for the physical memory utilization monitoring of the memory watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { winA3StatusMemGroup 20 }

winA3StatusMemPageTotal OBJECT-TYPE
	SYNTAX DisplayString
	ACCESS read-only
	STATUS mandatory
	DESCRIPTION "&<caiWinA3.762>The total size, in kilobytes, of the paging memory on the system."
	DEFVAL { "0" }
	::= { winA3StatusMemGroup 21 }

winA3StatusMemPageValue OBJECT-TYPE
	SYNTAX DisplayString
	ACCESS read-only
	STATUS mandatory
	DESCRIPTION "&<caiWinA3.763>Current value, in kilobytes, for the paging memory utilization monitoring of the memory watcher."
	DEFVAL { "0" }
	::= { winA3StatusMemGroup 22 }

winA3StatusMemPageLagValue OBJECT-TYPE
	SYNTAX INTEGER
	ACCESS read-only
	STATUS mandatory
	DESCRIPTION "&<caiWinA3.764>Current number of consecutive threshold breaches for the paging memory utilization monitoring of the memory watcher. The paging memory utilization state changes from ok as soon as the lag value reaches the configured value. The state reverts back to ok if a threshold is no longer breached."
	::= { winA3StatusMemGroup 23 }

winA3StatusMemPageLag OBJECT-TYPE
	SYNTAX INTEGER
	ACCESS read-write
	STATUS mandatory
	DESCRIPTION "&<caiWinA3.765>Current lag setting for the paging memory utilization monitoring of the memory watcher. Specifies the number of consecutive threshold breaches on which the paging memory utilization state changes. This value must be greater than 0."
	DEFVAL { 10 }
	::= { winA3StatusMemGroup 24 }

winA3StatusMemPageWarnValue OBJECT-TYPE
	SYNTAX DisplayString
	ACCESS read-only
	STATUS mandatory
	DESCRIPTION "&<caiWinA3.766>Active warning threshold, in kilobytes, as derived from the configured value for the paging memory utilization monitoring of the memory watcher. This value represents a rising threshold and must be greater than 0.0, less than or equal to the total value (maximum capacity) of the monitored resource as specified in winA3StatusMemPageTotal, but cannot be greater than the active critical threshold. These constraints will be maintained by the agent during all configuration actions."
	::= { winA3StatusMemGroup 25 }

winA3StatusMemPageCritValue OBJECT-TYPE
	SYNTAX DisplayString
	ACCESS read-only
	STATUS mandatory
	DESCRIPTION "&<caiWinA3.767>Active critical threshold, in kilobytes, as derived from the configured value for the paging memory utilization monitoring of the memory watcher. This value represents a rising threshold and must be greater than 0.0, less than or equal to the total value (maximum capacity) of the monitored resource as specified in winA3StatusMemPageTotal, but cannot be less than the active warning threshold. These constraints will be maintained by the agent during all configuration actions."
	::= { winA3StatusMemGroup 26 }

winA3StatusMemPageWarn OBJECT-TYPE
	SYNTAX DisplayString
	ACCESS read-write
	STATUS mandatory
	DESCRIPTION "&<caiWinA3.768>Configured warning threshold from which the active warning threshold is derived for the paging memory utilization monitoring of the memory watcher. The threshold can be specified as either an absolute value (n) or a percentage (n%). It can also be specified as the absolute value left free (nF). The value of winA3StatusMemPageTotal will be the reference value for n% and nF notations."
	DEFVAL { "85.0%" }
	::= { winA3StatusMemGroup 27 }

winA3StatusMemPageCrit OBJECT-TYPE
	SYNTAX DisplayString
	ACCESS read-write
	STATUS mandatory
	DESCRIPTION "&<caiWinA3.769>Configured critical threshold from which the active critical threshold is derived for the paging memory utilization monitoring of the memory watcher. The threshold can be specified as either an absolute value (n) or a percentage (n%). It can also be specified as the absolute value left free (nF). The value of winA3StatusMemPageTotal will be the reference value for n% and nF notations."
	DEFVAL { "95.0%" }
	::= { winA3StatusMemGroup 28 }

winA3StatusMemPageMonitor OBJECT-TYPE
	SYNTAX INTEGER {
		do-not-monitor(1),
		warning-only(2),
		critical-only(3),
		both(4)
	}
	ACCESS read-write
	STATUS mandatory
	DESCRIPTION "&<caiWinA3.770>Current monitor level for the paging memory utilization monitoring of the memory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 4 }
	::= { winA3StatusMemGroup 29 }

winA3StatusMemPageStatus OBJECT-TYPE
	SYNTAX INTEGER {
		unknown(1),
		ok(2),
		warning(3),
		critical(4),
		passive(5)
	}
	ACCESS read-only
	STATUS mandatory
	DESCRIPTION "&<caiWinA3.771>Current status for the paging memory utilization monitoring of the memory watcher: 1 (unknown) - An error occurred during data collection, 2 (ok) - The resource is operating within the defined limits or status evaluation is turned off, 3 (warning) - The resource has breached the warning threshold, 4 (critical) - The resource has breached the critical threshold, 5 (passive) - The polling is disabled for the resource and hence no data collection occurs."
	::= { winA3StatusMemGroup 30 }

winA3StatusMemCallBackRef OBJECT-TYPE
	SYNTAX DisplayString
	ACCESS read-only
	STATUS mandatory
	DESCRIPTION "&<caiWinA3.772>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusMemGroup 31 }

--
-- The StatusLVol Group
--

winA3StatusLVolCount OBJECT-TYPE
	SYNTAX INTEGER
	ACCESS read-only
	STATUS mandatory
	DESCRIPTION "&<caiWinA3.773>Number of entries in the logical volume status table."
	::= { winA3StatusLVolGroup 1 }

winA3StatusLVolTable OBJECT-TYPE
	SYNTAX SEQUENCE OF WinA3StatusLVolEntry
	ACCESS not-accessible
	STATUS mandatory
	DESCRIPTION "&<caiWinA3.774>The logical volume status table containing details about the currently configured logical volume watchers."
	::= { winA3StatusLVolGroup 2 }

winA3StatusLVolEntry OBJECT-TYPE
	SYNTAX WinA3StatusLVolEntry
	ACCESS not-accessible
	STATUS mandatory
	DESCRIPTION "&<caiWinA3.775>Entry in the logical volume status table."
	INDEX {
		winA3StatusLVolName
	}
	::= { winA3StatusLVolTable 1 }

WinA3StatusLVolEntry ::= SEQUENCE {
	winA3StatusLVolName DisplayString,
	winA3StatusLVolDescription DisplayString,
	winA3StatusLVolAutoWatcherName DisplayString,
	winA3StatusLVolAggLagValue INTEGER,
	winA3StatusLVolAggLag INTEGER,
	winA3StatusLVolAggStatus INTEGER,
	winA3StatusLVolMounts DisplayString,
	winA3StatusLVolInfo DisplayString,
	winA3StatusLVolClusterType INTEGER,
	winA3StatusLVolSizeTotal DisplayString,
	winA3StatusLVolSizeValue DisplayString,
	winA3StatusLVolSizeWarnValue DisplayString,
	winA3StatusLVolSizeCritValue DisplayString,
	winA3StatusLVolSizeWarn DisplayString,
	winA3StatusLVolSizeCrit DisplayString,
	winA3StatusLVolSizeMonitor INTEGER,
	winA3StatusLVolSizeStatus INTEGER,
	winA3StatusLVolSizeDValue DisplayString,
	winA3StatusLVolSizeDWarnValue DisplayString,
	winA3StatusLVolSizeDCritValue DisplayString,
	winA3StatusLVolSizeDWarn DisplayString,
	winA3StatusLVolSizeDCrit DisplayString,
	winA3StatusLVolSizeDMonitor INTEGER,
	winA3StatusLVolSizeDStatus INTEGER,
	winA3StatusLVolMiscMode INTEGER,
	winA3StatusLVolMiscValue DisplayString,
	winA3StatusLVolMiscWarn DisplayString,
	winA3StatusLVolMiscCrit DisplayString,
	winA3StatusLVolMiscMonitor INTEGER,
	winA3StatusLVolMiscStatus INTEGER,
	winA3StatusLVolFragmtMode INTEGER,
	winA3StatusLVolFragmtInterval INTEGER,
	winA3StatusLVolFragmtValue INTEGER,
	winA3StatusLVolFragmtWarn INTEGER,
	winA3StatusLVolFragmtCrit INTEGER,
	winA3StatusLVolFragmtMonitor INTEGER,
	winA3StatusLVolFragmtStatus INTEGER,
	winA3StatusLVolLossAction INTEGER,
	winA3StatusLVolLossStatus INTEGER,
	winA3StatusLVolCallBackRef DisplayString,
	winA3StatusLVolButton INTEGER
}

winA3StatusLVolName OBJECT-TYPE
	SYNTAX DisplayString
	ACCESS read-only
	STATUS mandatory
	DESCRIPTION "&<caiWinA3.776>Name of the logical volume. A logical volume name can be in drive letter format (e.g. C:) or in GUID format (e.g. Volume{2ab0a340-997c-11d6-9d96-00b0d09b7d72})."
	::= { winA3StatusLVolEntry 1 }

winA3StatusLVolDescription OBJECT-TYPE
	SYNTAX DisplayString
	ACCESS read-write
	STATUS mandatory
	DESCRIPTION "&<caiWinA3.777>Current description for the logical volume watcher."
	::= { winA3StatusLVolEntry 2 }

winA3StatusLVolAutoWatcherName OBJECT-TYPE
	SYNTAX DisplayString
	ACCESS read-only
	STATUS mandatory
	DESCRIPTION "&<caiWinA3.778>Name of the logical volume auto watcher which automatically created this watcher. This attribute is left blank if the watcher was added manually."
	::= { winA3StatusLVolEntry 3 }

winA3StatusLVolAggLagValue OBJECT-TYPE
	SYNTAX INTEGER
	ACCESS read-only
	STATUS mandatory
	DESCRIPTION "&<caiWinA3.779>Current aggregate lag value of the logical volume watcher. Indicates the consecutive number of times at which any status was not in the ok state. The aggregate status changes from ok as soon as the aggregate lag value reaches the configured value."
	::= { winA3StatusLVolEntry 4 }

winA3StatusLVolAggLag OBJECT-TYPE
	SYNTAX INTEGER
	ACCESS read-write
	STATUS mandatory
	DESCRIPTION "&<caiWinA3.780>Current aggregate lag setting for the logical volume watcher. Specifies the consecutive number of times at which any status is not in the ok state, before the aggregate status changes. This value must be greater than 0."
	::= { winA3StatusLVolEntry 5 }

winA3StatusLVolAggStatus OBJECT-TYPE
	SYNTAX INTEGER {
		unknown(1),
		ok(2),
		warning(3),
		critical(4),
		passive(5)
	}
	ACCESS read-only
	STATUS mandatory
	DESCRIPTION "&<caiWinA3.781>Current aggregate status of the logical volume watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { winA3StatusLVolEntry 6 }

winA3StatusLVolMounts OBJECT-TYPE
	SYNTAX DisplayString
	ACCESS read-only
	STATUS mandatory
	DESCRIPTION "&<caiWinA3.782>A list of the mount points (seperated by pipe signs), where this logical volume is mounted on."
	::= { winA3StatusLVolEntry 7 }

winA3StatusLVolInfo OBJECT-TYPE
	SYNTAX DisplayString
	ACCESS read-only
	STATUS mandatory
	DESCRIPTION "&<caiWinA3.783>Information about the label, the filesystem (e.g. NTFS) and the alternate name (e.g. used in performance monitor) of the logical volume. This string has the format 'Label (FSys) (Alternate)'. 'Label' resp. 'FSys' are set to '-', if no label is defined, if the logical volume is not formatted or if it was in a clustered-passive state since start of monitoring. 'Alternate' may be missing if not applicable (typically if the logical volume can be adressed by a drive letter)."
	::= { winA3StatusLVolEntry 8 }

winA3StatusLVolClusterType OBJECT-TYPE
	SYNTAX INTEGER {
		not-clustered(1),
		clustered-active(2),
		clustered-passive(3)
	}
	ACCESS read-only
	STATUS mandatory
	DESCRIPTION "&<caiWinA3.784>Cluster type of the logical volume: 1 (not-clustered) - Resource is not clustered, 2 (clustered-active) - Local cluster node has resource ownership, 3 (clustered-passive) - Another node in the cluster has resource ownership; the agent on the local node does not actively monitor the resource until ownership is transferred back."
	::= { winA3StatusLVolEntry 9 }

winA3StatusLVolSizeTotal OBJECT-TYPE
	SYNTAX DisplayString
	ACCESS read-only
	STATUS mandatory
	DESCRIPTION "&<caiWinA3.785>The total size, in megabytes, of the logical volume."
	DEFVAL { "0" }
	::= { winA3StatusLVolEntry 10 }

winA3StatusLVolSizeValue OBJECT-TYPE
	SYNTAX DisplayString
	ACCESS read-only
	STATUS mandatory
	DESCRIPTION "&<caiWinA3.786>Current value, in megabytes, for the logical volume utilization monitoring of the logical volume watcher."
	DEFVAL { "0" }
	::= { winA3StatusLVolEntry 11 }

winA3StatusLVolSizeWarnValue OBJECT-TYPE
	SYNTAX DisplayString
	ACCESS read-only
	STATUS mandatory
	DESCRIPTION "&<caiWinA3.787>Active warning threshold, in megabytes, as derived from the configured value for the logical volume utilization monitoring of the logical volume watcher. This value represents a rising threshold and must be greater than 0.0, less than or equal to the total value (maximum capacity) of the monitored resource as specified in winA3StatusLVolSizeTotal, but cannot be greater than the active critical threshold. These constraints will be maintained by the agent during all configuration actions."
	::= { winA3StatusLVolEntry 12 }

winA3StatusLVolSizeCritValue OBJECT-TYPE
	SYNTAX DisplayString
	ACCESS read-only
	STATUS mandatory
	DESCRIPTION "&<caiWinA3.788>Active critical threshold, in megabytes, as derived from the configured value for the logical volume utilization monitoring of the logical volume watcher. This value represents a rising threshold and must be greater than 0.0, less than or equal to the total value (maximum capacity) of the monitored resource as specified in winA3StatusLVolSizeTotal, but cannot be less than the active warning threshold. These constraints will be maintained by the agent during all configuration actions."
	::= { winA3StatusLVolEntry 13 }

winA3StatusLVolSizeWarn OBJECT-TYPE
	SYNTAX DisplayString
	ACCESS read-write
	STATUS mandatory
	DESCRIPTION "&<caiWinA3.789>Configured warning threshold from which the active warning threshold is derived for the logical volume utilization monitoring of the logical volume watcher. The threshold can be specified as either an absolute value (n) or a percentage (n%). It can also be specified as the absolute value left free (nF). The value of winA3StatusLVolSizeTotal will be the reference value for n% and nF notations."
	::= { winA3StatusLVolEntry 14 }

winA3StatusLVolSizeCrit OBJECT-TYPE
	SYNTAX DisplayString
	ACCESS read-write
	STATUS mandatory
	DESCRIPTION "&<caiWinA3.790>Configured critical threshold from which the active critical threshold is derived for the logical volume utilization monitoring of the logical volume watcher. The threshold can be specified as either an absolute value (n) or a percentage (n%). It can also be specified as the absolute value left free (nF). The value of winA3StatusLVolSizeTotal will be the reference value for n% and nF notations."
	::= { winA3StatusLVolEntry 15 }

winA3StatusLVolSizeMonitor OBJECT-TYPE
	SYNTAX INTEGER {
		do-not-monitor(1),
		warning-only(2),
		critical-only(3),
		both(4)
	}
	ACCESS read-write
	STATUS mandatory
	DESCRIPTION "&<caiWinA3.791>Current monitor level for the logical volume utilization monitoring of the logical volume watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusLVolEntry 16 }

winA3StatusLVolSizeStatus OBJECT-TYPE
	SYNTAX INTEGER {
		unknown(1),
		ok(2),
		warning(3),
		critical(4)
	}
	ACCESS read-only
	STATUS mandatory
	DESCRIPTION "&<caiWinA3.792>Current status for the logical volume utilization monitoring of the logical volume watcher: 1 (unknown) - An error occurred during data collection, 2 (ok) - The resource is operating within the defined limits or status evaluation is turned off and/or polling is disabled, 3 (warning) - The resource has breached the warning threshold, 4 (critical) - The resource has breached the critical threshold."
	::= { winA3StatusLVolEntry 17 }

winA3StatusLVolSizeDValue OBJECT-TYPE
	SYNTAX DisplayString
	ACCESS read-only
	STATUS mandatory
	DESCRIPTION "&<caiWinA3.793>Current value, in megabytes, for the delta logical volume utilization monitoring of the logical volume watcher. This is the difference of the size utilization from one poll to the next."
	DEFVAL { "0" }
	::= { winA3StatusLVolEntry 18 }

winA3StatusLVolSizeDWarnValue OBJECT-TYPE
	SYNTAX DisplayString
	ACCESS read-only
	STATUS mandatory
	DESCRIPTION "&<caiWinA3.794>Active warning threshold, in megabytes, as derived from the configured value for the delta logical volume utilization monitoring of the logical volume watcher. This value represents a rising threshold and must be greater than 0.0, less than or equal to the total value (maximum capacity) of the monitored resource as specified in winA3StatusLVolSizeTotal, but cannot be greater than the active critical threshold. These constraints will be maintained by the agent during all configuration actions."
	::= { winA3StatusLVolEntry 19 }

winA3StatusLVolSizeDCritValue OBJECT-TYPE
	SYNTAX DisplayString
	ACCESS read-only
	STATUS mandatory
	DESCRIPTION "&<caiWinA3.795>Active critical threshold, in megabytes, as derived from the configured value for the delta logical volume utilization monitoring of the logical volume watcher. This value represents a rising threshold and must be greater than 0.0, less than or equal to the total value (maximum capacity) of the monitored resource as specified in winA3StatusLVolSizeTotal, but cannot be less than the active warning threshold. These constraints will be maintained by the agent during all configuration actions."
	::= { winA3StatusLVolEntry 20 }

winA3StatusLVolSizeDWarn OBJECT-TYPE
	SYNTAX DisplayString
	ACCESS read-write
	STATUS mandatory
	DESCRIPTION "&<caiWinA3.796>Configured warning threshold from which the active warning threshold is derived for the delta logical volume utilization monitoring of the logical volume watcher. The threshold can be specified as either an absolute value or a percentage and can denote a growth, shrinkage or change in either direction: Absolute shrinkage (n-), absolute growth (n+), absolute change in either direction (n), percentage shrinkage (n%-), percentage growth (n%+), or percentage change in either direction (n%). The value of winA3StatusLVolSizeTotal will be the reference value for n% notations."
	::= { winA3StatusLVolEntry 21 }

winA3StatusLVolSizeDCrit OBJECT-TYPE
	SYNTAX DisplayString
	ACCESS read-write
	STATUS mandatory
	DESCRIPTION "&<caiWinA3.797>Configured critical threshold from which the active critical threshold is derived for the delta logical volume utilization monitoring of the logical volume watcher. The threshold can be specified as either an absolute value or a percentage and can denote a growth, shrinkage or change in either direction: Absolute shrinkage (n-), absolute growth (n+), absolute change in either direction (n), percentage shrinkage (n%-), percentage growth (n%+), or percentage change in either direction (n%). The value of winA3StatusLVolSizeTotal will be the reference value for n% notations."
	::= { winA3StatusLVolEntry 22 }

winA3StatusLVolSizeDMonitor OBJECT-TYPE
	SYNTAX INTEGER {
		do-not-monitor(1),
		warning-only(2),
		critical-only(3),
		both(4)
	}
	ACCESS read-write
	STATUS mandatory
	DESCRIPTION "&<caiWinA3.798>Current monitor level for the delta logical volume utilization monitoring of the logical volume watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusLVolEntry 23 }

winA3StatusLVolSizeDStatus OBJECT-TYPE
	SYNTAX INTEGER {
		unknown(1),
		ok(2),
		warning(3),
		critical(4)
	}
	ACCESS read-only
	STATUS mandatory
	DESCRIPTION "&<caiWinA3.799>Current status for the delta logical volume utilization monitoring of the logical volume watcher: 1 (unknown) - An error occurred during data collection, 2 (ok) - The resource is operating within the defined limits or status evaluation is turned off and/or polling is disabled, 3 (warning) - The resource has breached the warning threshold, 4 (critical) - The resource has breached the critical threshold."
	::= { winA3StatusLVolEntry 24 }

winA3StatusLVolMiscMode OBJECT-TYPE
	SYNTAX INTEGER {
		throughput(1),
		queue-length(2)
	}
	ACCESS read-write
	STATUS mandatory
	DESCRIPTION "&<caiWinA3.800>This attribute determines which value (throughput or queue-length) should be calculated by this metric. The option throughput(1) is expressed in KBytes/sec. The option queue-length(2) is expressed as an average number."
	DEFVAL { 0 }
	::= { winA3StatusLVolEntry 25 }

winA3StatusLVolMiscValue OBJECT-TYPE
	SYNTAX DisplayString
	ACCESS read-only
	STATUS mandatory
	DESCRIPTION "&<caiWinA3.801>This value dependends from the misc mode. In case throughput(1) it is the transfer rate during read and write operations on the volume expressed in KBytes/sec. In case queue-length(2) it is the average number of read and write requests that were queued for the volume during the poll interval."
	DEFVAL { "0" }
	::= { winA3StatusLVolEntry 26 }

winA3StatusLVolMiscWarn OBJECT-TYPE
	SYNTAX DisplayString
	ACCESS read-write
	STATUS mandatory
	DESCRIPTION "&<caiWinA3.802>Current warning threshold for the miscellaneous data monitoring of the logical volume watcher. This value represents a rising threshold and must be greater than 0.0, but cannot be greater than the critical threshold."
	::= { winA3StatusLVolEntry 27 }

winA3StatusLVolMiscCrit OBJECT-TYPE
	SYNTAX DisplayString
	ACCESS read-write
	STATUS mandatory
	DESCRIPTION "&<caiWinA3.803>Current critical threshold for the miscellaneous data monitoring of the logical volume watcher. This value represents a rising threshold and must be greater than 0.0, but cannot be less than the warning threshold."
	::= { winA3StatusLVolEntry 28 }

winA3StatusLVolMiscMonitor OBJECT-TYPE
	SYNTAX INTEGER {
		do-not-monitor(1),
		warning-only(2),
		critical-only(3),
		both(4)
	}
	ACCESS read-write
	STATUS mandatory
	DESCRIPTION "&<caiWinA3.804>Current monitor level for the miscellaneous data monitoring of the logical volume watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusLVolEntry 29 }

winA3StatusLVolMiscStatus OBJECT-TYPE
	SYNTAX INTEGER {
		unknown(1),
		ok(2),
		warning(3),
		critical(4)
	}
	ACCESS read-only
	STATUS mandatory
	DESCRIPTION "&<caiWinA3.805>Current status for the miscellaneous data monitoring of the logical volume watcher: 1 (unknown) - An error occurred during data collection, 2 (ok) - The resource is operating within the defined limits or status evaluation is turned off and/or polling is disabled, 3 (warning) - The resource has breached the warning threshold, 4 (critical) - The resource has breached the critical threshold."
	::= { winA3StatusLVolEntry 30 }

winA3StatusLVolFragmtMode OBJECT-TYPE
	SYNTAX INTEGER {
		file-fragmentation(1),
		total-fragmentation(2)
	}
	ACCESS read-write
	STATUS mandatory
	DESCRIPTION "&<caiWinA3.806>This attribute determines which mode of fragmentation (file or total) should be calculated. The option total-fragmentation(2) is only supported on Windows 2003/XP."
	DEFVAL { 0 }
	::= { winA3StatusLVolEntry 31 }

winA3StatusLVolFragmtInterval OBJECT-TYPE
	SYNTAX INTEGER
	ACCESS read-write
	STATUS mandatory
	DESCRIPTION "&<caiWinA3.807>Time, in hours, between collections of fragmentation information (always triggered by the next polling or a get request). The agent will not calculate the fragmentation every standard poll interval, because it is an expensive task. Valid range: 1 hour or greater, or -1 to disable the fragmentation calculation."
	::= { winA3StatusLVolEntry 32 }

winA3StatusLVolFragmtValue OBJECT-TYPE
	SYNTAX INTEGER
	ACCESS read-only
	STATUS mandatory
	DESCRIPTION "&<caiWinA3.808>Current value, in percent, for the fragmentation monitoring of the logical volume watcher."
	::= { winA3StatusLVolEntry 33 }

winA3StatusLVolFragmtWarn OBJECT-TYPE
	SYNTAX INTEGER
	ACCESS read-write
	STATUS mandatory
	DESCRIPTION "&<caiWinA3.809>Current warning threshold, in percent, for the fragmentation monitoring of the logical volume watcher. This value represents a rising threshold and must be greater than 0, less than or equal to 100, but cannot be greater than the critical threshold."
	::= { winA3StatusLVolEntry 34 }

winA3StatusLVolFragmtCrit OBJECT-TYPE
	SYNTAX INTEGER
	ACCESS read-write
	STATUS mandatory
	DESCRIPTION "&<caiWinA3.810>Current critical threshold, in percent, for the fragmentation monitoring of the logical volume watcher. This value represents a rising threshold and must be greater than 0, less than or equal to 100, but cannot be less than the warning threshold."
	::= { winA3StatusLVolEntry 35 }

winA3StatusLVolFragmtMonitor OBJECT-TYPE
	SYNTAX INTEGER {
		do-not-monitor(1),
		warning-only(2),
		critical-only(3),
		both(4)
	}
	ACCESS read-write
	STATUS mandatory
	DESCRIPTION "&<caiWinA3.811>Current monitor level for the fragmentation monitoring of the logical volume watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusLVolEntry 36 }

winA3StatusLVolFragmtStatus OBJECT-TYPE
	SYNTAX INTEGER {
		unknown(1),
		ok(2),
		warning(3),
		critical(4)
	}
	ACCESS read-only
	STATUS mandatory
	DESCRIPTION "&<caiWinA3.812>Current status for the fragmentation monitoring of the logical volume watcher: 1 (unknown) - An error occurred during data collection, 2 (ok) - The resource is operating within the defined limits or status evaluation is turned off and/or polling is disabled, 3 (warning) - The resource has breached the warning threshold, 4 (critical) - The resource has breached the critical threshold."
	::= { winA3StatusLVolEntry 37 }

winA3StatusLVolLossAction OBJECT-TYPE
	SYNTAX INTEGER {
		remove(1),
		up(2),
		down-warning(3),
		down-critical(4)
	}
	ACCESS read-write
	STATUS mandatory
	DESCRIPTION "&<caiWinA3.813>Current loss action for the logical volume watcher. Specifies the action to take if the monitored logical volume is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusLVolEntry 38 }

winA3StatusLVolLossStatus OBJECT-TYPE
	SYNTAX INTEGER {
		unknown(1),
		up(2),
		down-warning(3),
		down-critical(4)
	}
	ACCESS read-only
	STATUS mandatory
	DESCRIPTION "&<caiWinA3.814>Current loss status of the logical volume watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusLVolEntry 39 }

winA3StatusLVolCallBackRef OBJECT-TYPE
	SYNTAX DisplayString
	ACCESS read-only
	STATUS mandatory
	DESCRIPTION "&<caiWinA3.815>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusLVolEntry 40 }

winA3StatusLVolButton OBJECT-TYPE
	SYNTAX INTEGER {
		none(1),
		remove(2)
	}
	ACCESS read-write
	STATUS mandatory
	DESCRIPTION "&<caiWinA3.816>This attribute is used to remove the logical volume watcher. If set to 2 (remove), the agent removes the watcher from the table. This attribute cannot be set to 1 (none)."
	DEFVAL { 1 }
	::= { winA3StatusLVolEntry 41 }

--
-- The StatusMnt Group
--

winA3StatusMntCount OBJECT-TYPE
	SYNTAX INTEGER
	ACCESS read-only
	STATUS mandatory
	DESCRIPTION "&<caiWinA3.817>Number of entries in the mount status table."
	::= { winA3StatusMntGroup 1 }

winA3StatusMntTable OBJECT-TYPE
	SYNTAX SEQUENCE OF WinA3StatusMntEntry
	ACCESS not-accessible
	STATUS mandatory
	DESCRIPTION "&<caiWinA3.818>The mount status table containing details about the currently configured mount watchers."
	::= { winA3StatusMntGroup 2 }

winA3StatusMntEntry OBJECT-TYPE
	SYNTAX WinA3StatusMntEntry
	ACCESS not-accessible
	STATUS mandatory
	DESCRIPTION "&<caiWinA3.819>Entry in the mount status table."
	INDEX {
		winA3StatusMntName
	}
	::= { winA3StatusMntTable 1 }

WinA3StatusMntEntry ::= SEQUENCE {
	winA3StatusMntName DisplayString,
	winA3StatusMntDescription DisplayString,
	winA3StatusMntAutoWatcherName DisplayString,
	winA3StatusMntAggLagValue INTEGER,
	winA3StatusMntAggLag INTEGER,
	winA3StatusMntAggStatus INTEGER,
	winA3StatusMntTarget DisplayString,
	winA3StatusMntClusterType INTEGER,
	winA3StatusMntTargetRef DisplayString,
	winA3StatusMntTargetMonitor INTEGER,
	winA3StatusMntTargetStatus INTEGER,
	winA3StatusMntLossAction INTEGER,
	winA3StatusMntLossStatus INTEGER,
	winA3StatusMntCallBackRef DisplayString,
	winA3StatusMntButton INTEGER
}

winA3StatusMntName OBJECT-TYPE
	SYNTAX DisplayString
	ACCESS read-only
	STATUS mandatory
	DESCRIPTION "&<caiWinA3.820>Name of the mount."
	::= { winA3StatusMntEntry 1 }

winA3StatusMntDescription OBJECT-TYPE
	SYNTAX DisplayString
	ACCESS read-write
	STATUS mandatory
	DESCRIPTION "&<caiWinA3.821>Current description for the mount watcher."
	::= { winA3StatusMntEntry 2 }

winA3StatusMntAutoWatcherName OBJECT-TYPE
	SYNTAX DisplayString
	ACCESS read-only
	STATUS mandatory
	DESCRIPTION "&<caiWinA3.822>Name of the mount auto watcher which automatically created this watcher. This attribute is left blank if the watcher was added manually."
	::= { winA3StatusMntEntry 3 }

winA3StatusMntAggLagValue OBJECT-TYPE
	SYNTAX INTEGER
	ACCESS read-only
	STATUS mandatory
	DESCRIPTION "&<caiWinA3.823>Current aggregate lag value of the mount watcher. Indicates the consecutive number of times at which any status was not in the ok state. The aggregate status changes from ok as soon as the aggregate lag value reaches the configured value."
	::= { winA3StatusMntEntry 4 }

winA3StatusMntAggLag OBJECT-TYPE
	SYNTAX INTEGER
	ACCESS read-write
	STATUS mandatory
	DESCRIPTION "&<caiWinA3.824>Current aggregate lag setting for the mount watcher. Specifies the consecutive number of times at which any status is not in the ok state, before the aggregate status changes. This value must be greater than 0."
	::= { winA3StatusMntEntry 5 }

winA3StatusMntAggStatus OBJECT-TYPE
	SYNTAX INTEGER {
		unknown(1),
		ok(2),
		warning(3),
		critical(4),
		passive(5)
	}
	ACCESS read-only
	STATUS mandatory
	DESCRIPTION "&<caiWinA3.825>Current aggregate status of the mount watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { winA3StatusMntEntry 6 }

winA3StatusMntTarget OBJECT-TYPE
	SYNTAX DisplayString
	ACCESS read-only
	STATUS mandatory
	DESCRIPTION "&<caiWinA3.826>The name of the logical volume currently mounted by this mount. This value is compared to the target reference (using a 'should-not-change' policy) to derive the status."
	::= { winA3StatusMntEntry 7 }

winA3StatusMntClusterType OBJECT-TYPE
	SYNTAX INTEGER {
		not-clustered(1),
		clustered-active(2),
		clustered-passive(3)
	}
	ACCESS read-only
	STATUS mandatory
	DESCRIPTION "&<caiWinA3.827>Cluster type of the mount: 1 (not-clustered) - Resource is not clustered, 2 (clustered-active) - Local cluster node has resource ownership, 3 (clustered-passive) - Another node in the cluster has resource ownership; the agent on the local node does not actively monitor the resource until ownership is transferred back."
	::= { winA3StatusMntEntry 8 }

winA3StatusMntTargetRef OBJECT-TYPE
	SYNTAX DisplayString
	ACCESS read-only
	STATUS mandatory
	DESCRIPTION "&<caiWinA3.828>This attribute is used as the reference the target value is compared with, implicitly using a 'should-not-change' policy. It is the name of the logical volume mounted by this mount when the watcher was created or when the last time the status button attribute has been set to 'reset-target'."
	::= { winA3StatusMntEntry 9 }

winA3StatusMntTargetMonitor OBJECT-TYPE
	SYNTAX INTEGER {
		do-not-monitor(1),
		down-warning(2),
		down-critical(3)
	}
	ACCESS read-write
	STATUS mandatory
	DESCRIPTION "&<caiWinA3.829>Current monitor level for the target monitoring of the mount watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusMntEntry 10 }

winA3StatusMntTargetStatus OBJECT-TYPE
	SYNTAX INTEGER {
		unknown(1),
		up(2),
		down-warning(3),
		down-critical(4)
	}
	ACCESS read-only
	STATUS mandatory
	DESCRIPTION "&<caiWinA3.830>Current status for the target monitoring of the mount watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusMntEntry 11 }

winA3StatusMntLossAction OBJECT-TYPE
	SYNTAX INTEGER {
		remove(1),
		up(2),
		down-warning(3),
		down-critical(4)
	}
	ACCESS read-write
	STATUS mandatory
	DESCRIPTION "&<caiWinA3.831>Current loss action for the mount watcher. Specifies the action to take if the monitored mount is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusMntEntry 12 }

winA3StatusMntLossStatus OBJECT-TYPE
	SYNTAX INTEGER {
		unknown(1),
		up(2),
		down-warning(3),
		down-critical(4)
	}
	ACCESS read-only
	STATUS mandatory
	DESCRIPTION "&<caiWinA3.832>Current loss status of the mount watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusMntEntry 13 }

winA3StatusMntCallBackRef OBJECT-TYPE
	SYNTAX DisplayString
	ACCESS read-only
	STATUS mandatory
	DESCRIPTION "&<caiWinA3.833>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusMntEntry 14 }

winA3StatusMntButton OBJECT-TYPE
	SYNTAX INTEGER {
		none(1),
		remove(2),
		reset-target(3)
	}
	ACCESS read-write
	STATUS mandatory
	DESCRIPTION "&<caiWinA3.834>This attribute is used to remove the mount watcher. Additionally, if set to 3 (reset-target), the target reference is set to the current target value and the status of the target metric is set to 'up'. If set to 2 (remove), the agent removes the watcher from the table. This attribute cannot be set to 1 (none)."
	DEFVAL { 1 }
	::= { winA3StatusMntEntry 15 }

--
-- The StatusDfs Group
--

winA3StatusDfsCount OBJECT-TYPE
	SYNTAX INTEGER
	ACCESS read-only
	STATUS mandatory
	DESCRIPTION "&<caiWinA3.835>Number of entries in the distributed file system link status table."
	::= { winA3StatusDfsGroup 1 }

winA3StatusDfsTable OBJECT-TYPE
	SYNTAX SEQUENCE OF WinA3StatusDfsEntry
	ACCESS not-accessible
	STATUS mandatory
	DESCRIPTION "&<caiWinA3.836>The distributed file system link status table containing details about the currently configured distributed file system link watchers."
	::= { winA3StatusDfsGroup 2 }

winA3StatusDfsEntry OBJECT-TYPE
	SYNTAX WinA3StatusDfsEntry
	ACCESS not-accessible
	STATUS mandatory
	DESCRIPTION "&<caiWinA3.837>Entry in the distributed file system link status table."
	INDEX {
		winA3StatusDfsName
	}
	::= { winA3StatusDfsTable 1 }

WinA3StatusDfsEntry ::= SEQUENCE {
	winA3StatusDfsName DisplayString,
	winA3StatusDfsDescription DisplayString,
	winA3StatusDfsAutoWatcherName DisplayString,
	winA3StatusDfsAggLagValue INTEGER,
	winA3StatusDfsAggLag INTEGER,
	winA3StatusDfsAggStatus INTEGER,
	winA3StatusDfsTargetsList DisplayString,
	winA3StatusDfsTargetsTotal INTEGER,
	winA3StatusDfsTargetsValue INTEGER,
	winA3StatusDfsTargetsWarn INTEGER,
	winA3StatusDfsTargetsCrit INTEGER,
	winA3StatusDfsTargetsMonitor INTEGER,
	winA3StatusDfsTargetsStatus INTEGER,
	winA3StatusDfsTargetsIds DisplayString,
	winA3StatusDfsLossAction INTEGER,
	winA3StatusDfsLossStatus INTEGER,
	winA3StatusDfsCallBackRef DisplayString,
	winA3StatusDfsButton INTEGER
}

winA3StatusDfsName OBJECT-TYPE
	SYNTAX DisplayString
	ACCESS read-only
	STATUS mandatory
	DESCRIPTION "&<caiWinA3.838>Name of the distributed file system link. A fully qualified Dfs name consists of the Dfs root name followed by the Dfs link name. These two names are concatenated by a back-slash. A single Dfs root name can also be used, allowing to monitor all Dfs links of this Dfs root. In that case the values are calculated as the sum of all DFS links of this DFS root and no loss action will be triggered if no Dfs link exists for this DFS root. Note that monitoring of DFS links is not applicable on Windows XP and on Windows 2000 Professional."
	::= { winA3StatusDfsEntry 1 }

winA3StatusDfsDescription OBJECT-TYPE
	SYNTAX DisplayString
	ACCESS read-write
	STATUS mandatory
	DESCRIPTION "&<caiWinA3.839>Current description for the distributed file system link watcher."
	::= { winA3StatusDfsEntry 2 }

winA3StatusDfsAutoWatcherName OBJECT-TYPE
	SYNTAX DisplayString
	ACCESS read-only
	STATUS mandatory
	DESCRIPTION "&<caiWinA3.840>Name of the distributed file system link auto watcher which automatically created this watcher. This attribute is left blank if the watcher was added manually."
	::= { winA3StatusDfsEntry 3 }

winA3StatusDfsAggLagValue OBJECT-TYPE
	SYNTAX INTEGER
	ACCESS read-only
	STATUS mandatory
	DESCRIPTION "&<caiWinA3.841>Current aggregate lag value of the distributed file system link watcher. Indicates the consecutive number of times at which any status was not in the ok state. The aggregate status changes from ok as soon as the aggregate lag value reaches the configured value."
	::= { winA3StatusDfsEntry 4 }

winA3StatusDfsAggLag OBJECT-TYPE
	SYNTAX INTEGER
	ACCESS read-write
	STATUS mandatory
	DESCRIPTION "&<caiWinA3.842>Current aggregate lag setting for the distributed file system link watcher. Specifies the consecutive number of times at which any status is not in the ok state, before the aggregate status changes. This value must be greater than 0."
	::= { winA3StatusDfsEntry 5 }

winA3StatusDfsAggStatus OBJECT-TYPE
	SYNTAX INTEGER {
		unknown(1),
		ok(2),
		warning(3),
		critical(4),
		passive(5)
	}
	ACCESS read-only
	STATUS mandatory
	DESCRIPTION "&<caiWinA3.843>Current aggregate status of the distributed file system link watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusDfsEntry 6 }

winA3StatusDfsTargetsList OBJECT-TYPE
	SYNTAX DisplayString
	ACCESS read-only
	STATUS mandatory
	DESCRIPTION "&<caiWinA3.844>A list of the targets (seperated by pipe signs), currently configured for this Dfs link."
	::= { winA3StatusDfsEntry 7 }

winA3StatusDfsTargetsTotal OBJECT-TYPE
	SYNTAX INTEGER
	ACCESS read-only
	STATUS mandatory
	DESCRIPTION "&<caiWinA3.845>The total number of targets, currently configured for this Dfs link."
	::= { winA3StatusDfsEntry 8 }

winA3StatusDfsTargetsValue OBJECT-TYPE
	SYNTAX INTEGER
	ACCESS read-only
	STATUS mandatory
	DESCRIPTION "&<caiWinA3.846>This is the number of targets configured for this Dfs link, that are currently not accessible. Note that the agent typically can only monitor the availability of network shares and not of subfolders on network shares."
	::= { winA3StatusDfsEntry 9 }

winA3StatusDfsTargetsWarn OBJECT-TYPE
	SYNTAX INTEGER
	ACCESS read-write
	STATUS mandatory
	DESCRIPTION "&<caiWinA3.847>Current warning threshold for the target monitoring of the distributed file system link watcher. This value represents a rising threshold and must be greater than 0, less than or equal to the total value (maximum capacity) of the monitored resource as specified in winA3StatusDfsTargetsTotal, but cannot be greater than the critical threshold."
	::= { winA3StatusDfsEntry 10 }

winA3StatusDfsTargetsCrit OBJECT-TYPE
	SYNTAX INTEGER
	ACCESS read-write
	STATUS mandatory
	DESCRIPTION "&<caiWinA3.848>Current critical threshold for the target monitoring of the distributed file system link watcher. This value represents a rising threshold and must be greater than 0, less than or equal to the total value (maximum capacity) of the monitored resource as specified in winA3StatusDfsTargetsTotal, but cannot be less than the warning threshold."
	::= { winA3StatusDfsEntry 11 }

winA3StatusDfsTargetsMonitor OBJECT-TYPE
	SYNTAX INTEGER {
		do-not-monitor(1),
		warning-only(2),
		critical-only(3),
		both(4)
	}
	ACCESS read-write
	STATUS mandatory
	DESCRIPTION "&<caiWinA3.849>Current monitor level for the target monitoring of the distributed file system link watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusDfsEntry 12 }

winA3StatusDfsTargetsStatus OBJECT-TYPE
	SYNTAX INTEGER {
		unknown(1),
		ok(2),
		warning(3),
		critical(4)
	}
	ACCESS read-only
	STATUS mandatory
	DESCRIPTION "&<caiWinA3.850>Current status for the target monitoring of the distributed file system link watcher: 1 (unknown) - An error occurred during data collection, 2 (ok) - The resource is operating within the defined limits or status evaluation is turned off and/or polling is disabled, 3 (warning) - The resource has breached the warning threshold, 4 (critical) - The resource has breached the critical threshold."
	::= { winA3StatusDfsEntry 13 }

winA3StatusDfsTargetsIds OBJECT-TYPE
	SYNTAX DisplayString
	ACCESS read-only
	STATUS mandatory
	DESCRIPTION "&<caiWinA3.851>A pipe sign separated list of those targets of this Dfs link, that are unavailable. Note that the agent typically can only monitor the availability of network shares and not of subfolders on network shares."
	::= { winA3StatusDfsEntry 14 }

winA3StatusDfsLossAction OBJECT-TYPE
	SYNTAX INTEGER {
		remove(1),
		up(2),
		down-warning(3),
		down-critical(4)
	}
	ACCESS read-write
	STATUS mandatory
	DESCRIPTION "&<caiWinA3.852>Current loss action for the distributed file system link watcher. Specifies the action to take if the monitored distributed file system link is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusDfsEntry 15 }

winA3StatusDfsLossStatus OBJECT-TYPE
	SYNTAX INTEGER {
		unknown(1),
		up(2),
		down-warning(3),
		down-critical(4)
	}
	ACCESS read-only
	STATUS mandatory
	DESCRIPTION "&<caiWinA3.853>Current loss status of the distributed file system link watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusDfsEntry 16 }

winA3StatusDfsCallBackRef OBJECT-TYPE
	SYNTAX DisplayString
	ACCESS read-only
	STATUS mandatory
	DESCRIPTION "&<caiWinA3.854>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusDfsEntry 17 }

winA3StatusDfsButton OBJECT-TYPE
	SYNTAX INTEGER {
		none(1),
		remove(2)
	}
	ACCESS read-write
	STATUS mandatory
	DESCRIPTION "&<caiWinA3.855>This attribute is used to remove the distributed file system link watcher. If set to 2 (remove), the agent removes the watcher from the table. This attribute cannot be set to 1 (none)."
	DEFVAL { 1 }
	::= { winA3StatusDfsEntry 18 }

--
-- The StatusQuota Group
--

winA3StatusQuotaCount OBJECT-TYPE
	SYNTAX INTEGER
	ACCESS read-only
	STATUS mandatory
	DESCRIPTION "&<caiWinA3.856>Number of entries in the quota status table."
	::= { winA3StatusQuotaGroup 1 }

winA3StatusQuotaTable OBJECT-TYPE
	SYNTAX SEQUENCE OF WinA3StatusQuotaEntry
	ACCESS not-accessible
	STATUS mandatory
	DESCRIPTION "&<caiWinA3.857>The quota status table containing details about the currently configured quota watchers."
	::= { winA3StatusQuotaGroup 2 }

winA3StatusQuotaEntry OBJECT-TYPE
	SYNTAX WinA3StatusQuotaEntry
	ACCESS not-accessible
	STATUS mandatory
	DESCRIPTION "&<caiWinA3.858>Entry in the quota status table."
	INDEX {
		winA3StatusQuotaLVolName,
		winA3StatusQuotaUserName
	}
	::= { winA3StatusQuotaTable 1 }

WinA3StatusQuotaEntry ::= SEQUENCE {
	winA3StatusQuotaLVolName DisplayString,
	winA3StatusQuotaUserName DisplayString,
	winA3StatusQuotaDescription DisplayString,
	winA3StatusQuotaAutoWatcherName DisplayString,
	winA3StatusQuotaAggLagValue INTEGER,
	winA3StatusQuotaAggLag INTEGER,
	winA3StatusQuotaAggStatus INTEGER,
	winA3StatusQuotaWarnLevel DisplayString,
	winA3StatusQuotaLimit DisplayString,
	winA3StatusQuotaSizeTotal DisplayString,
	winA3StatusQuotaSizeValue DisplayString,
	winA3StatusQuotaSizeWarnValue DisplayString,
	winA3StatusQuotaSizeCritValue DisplayString,
	winA3StatusQuotaSizeWarn DisplayString,
	winA3StatusQuotaSizeCrit DisplayString,
	winA3StatusQuotaSizeMonitor INTEGER,
	winA3StatusQuotaSizeStatus INTEGER,
	winA3StatusQuotaLossAction INTEGER,
	winA3StatusQuotaLossStatus INTEGER,
	winA3StatusQuotaCallBackRef DisplayString,
	winA3StatusQuotaButton INTEGER
}

winA3StatusQuotaLVolName OBJECT-TYPE
	SYNTAX DisplayString
	ACCESS read-only
	STATUS mandatory
	DESCRIPTION "&<caiWinA3.859>LVol name part of the quota, specifying the logical volume on which this quota exists."
	::= { winA3StatusQuotaEntry 1 }

winA3StatusQuotaUserName OBJECT-TYPE
	SYNTAX DisplayString
	ACCESS read-only
	STATUS mandatory
	DESCRIPTION "&<caiWinA3.860>User name part of the quota, specifying the user for whom this quota exists. This name must be in the correct form ('domainName\\userName' or 'userName@domainName')."
	::= { winA3StatusQuotaEntry 2 }

winA3StatusQuotaDescription OBJECT-TYPE
	SYNTAX DisplayString
	ACCESS read-write
	STATUS mandatory
	DESCRIPTION "&<caiWinA3.861>Current description for the quota watcher."
	::= { winA3StatusQuotaEntry 3 }

winA3StatusQuotaAutoWatcherName OBJECT-TYPE
	SYNTAX DisplayString
	ACCESS read-only
	STATUS mandatory
	DESCRIPTION "&<caiWinA3.862>Name of the quota auto watcher which automatically created this watcher. This attribute is left blank if the watcher was added manually."
	::= { winA3StatusQuotaEntry 4 }

winA3StatusQuotaAggLagValue OBJECT-TYPE
	SYNTAX INTEGER
	ACCESS read-only
	STATUS mandatory
	DESCRIPTION "&<caiWinA3.863>Current aggregate lag value of the quota watcher. Indicates the consecutive number of times at which any status was not in the ok state. The aggregate status changes from ok as soon as the aggregate lag value reaches the configured value."
	::= { winA3StatusQuotaEntry 5 }

winA3StatusQuotaAggLag OBJECT-TYPE
	SYNTAX INTEGER
	ACCESS read-write
	STATUS mandatory
	DESCRIPTION "&<caiWinA3.864>Current aggregate lag setting for the quota watcher. Specifies the consecutive number of times at which any status is not in the ok state, before the aggregate status changes. This value must be greater than 0."
	::= { winA3StatusQuotaEntry 6 }

winA3StatusQuotaAggStatus OBJECT-TYPE
	SYNTAX INTEGER {
		unknown(1),
		ok(2),
		warning(3),
		critical(4),
		passive(5)
	}
	ACCESS read-only
	STATUS mandatory
	DESCRIPTION "&<caiWinA3.865>Current aggregate status of the quota watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { winA3StatusQuotaEntry 7 }

winA3StatusQuotaWarnLevel OBJECT-TYPE
	SYNTAX DisplayString
	ACCESS read-only
	STATUS mandatory
	DESCRIPTION "&<caiWinA3.866>The warning level, in kilobytes, for this quota, as defined in the Windows quota management. A value of zero means 'No Limit'. If adding a watcher, this value can be used as default warning threshold."
	DEFVAL { "0" }
	::= { winA3StatusQuotaEntry 8 }

winA3StatusQuotaLimit OBJECT-TYPE
	SYNTAX DisplayString
	ACCESS read-only
	STATUS mandatory
	DESCRIPTION "&<caiWinA3.867>The limit, in kilobytes, for this quota, as defined in the Windows quota management. A value of zero means 'No Limit'. If adding a watcher, this value can be used as default critical threshold."
	DEFVAL { "0" }
	::= { winA3StatusQuotaEntry 9 }

winA3StatusQuotaSizeTotal OBJECT-TYPE
	SYNTAX DisplayString
	ACCESS read-only
	STATUS mandatory
	DESCRIPTION "&<caiWinA3.868>The total size, in kilobytes, of the logical volume on which this quota exists."
	DEFVAL { "0" }
	::= { winA3StatusQuotaEntry 10 }

winA3StatusQuotaSizeValue OBJECT-TYPE
	SYNTAX DisplayString
	ACCESS read-only
	STATUS mandatory
	DESCRIPTION "&<caiWinA3.869>Current value, in kilobytes, for the quota size utilization monitoring of the quota watcher."
	DEFVAL { "0" }
	::= { winA3StatusQuotaEntry 11 }

winA3StatusQuotaSizeWarnValue OBJECT-TYPE
	SYNTAX DisplayString
	ACCESS read-only
	STATUS mandatory
	DESCRIPTION "&<caiWinA3.870>Active warning threshold, in kilobytes, as derived from the configured value for the quota size utilization monitoring of the quota watcher. This value represents a rising threshold and must be greater than 0.0, less than or equal to the total value (maximum capacity) of the monitored resource as specified in winA3StatusQuotaSizeTotal, but cannot be greater than the active critical threshold. These constraints will be maintained by the agent during all configuration actions."
	::= { winA3StatusQuotaEntry 12 }

winA3StatusQuotaSizeCritValue OBJECT-TYPE
	SYNTAX DisplayString
	ACCESS read-only
	STATUS mandatory
	DESCRIPTION "&<caiWinA3.871>Active critical threshold, in kilobytes, as derived from the configured value for the quota size utilization monitoring of the quota watcher. This value represents a rising threshold and must be greater than 0.0, less than or equal to the total value (maximum capacity) of the monitored resource as specified in winA3StatusQuotaSizeTotal, but cannot be less than the active warning threshold. These constraints will be maintained by the agent during all configuration actions."
	::= { winA3StatusQuotaEntry 13 }

winA3StatusQuotaSizeWarn OBJECT-TYPE
	SYNTAX DisplayString
	ACCESS read-write
	STATUS mandatory
	DESCRIPTION "&<caiWinA3.872>Configured warning threshold from which the active warning threshold is derived for the quota size utilization monitoring of the quota watcher. The threshold can be specified as either an absolute value (n) or a percentage (n%). The value of winA3StatusQuotaSizeTotal will be the reference value for n% notations."
	::= { winA3StatusQuotaEntry 14 }

winA3StatusQuotaSizeCrit OBJECT-TYPE
	SYNTAX DisplayString
	ACCESS read-write
	STATUS mandatory
	DESCRIPTION "&<caiWinA3.873>Configured critical threshold from which the active critical threshold is derived for the quota size utilization monitoring of the quota watcher. The threshold can be specified as either an absolute value (n) or a percentage (n%). The value of winA3StatusQuotaSizeTotal will be the reference value for n% notations."
	::= { winA3StatusQuotaEntry 15 }

winA3StatusQuotaSizeMonitor OBJECT-TYPE
	SYNTAX INTEGER {
		do-not-monitor(1),
		warning-only(2),
		critical-only(3),
		both(4)
	}
	ACCESS read-write
	STATUS mandatory
	DESCRIPTION "&<caiWinA3.874>Current monitor level for the quota size utilization monitoring of the quota watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusQuotaEntry 16 }

winA3StatusQuotaSizeStatus OBJECT-TYPE
	SYNTAX INTEGER {
		unknown(1),
		ok(2),
		warning(3),
		critical(4)
	}
	ACCESS read-only
	STATUS mandatory
	DESCRIPTION "&<caiWinA3.875>Current status for the quota size utilization monitoring of the quota watcher: 1 (unknown) - An error occurred during data collection, 2 (ok) - The resource is operating within the defined limits or status evaluation is turned off and/or polling is disabled, 3 (warning) - The resource has breached the warning threshold, 4 (critical) - The resource has breached the critical threshold."
	::= { winA3StatusQuotaEntry 17 }

winA3StatusQuotaLossAction OBJECT-TYPE
	SYNTAX INTEGER {
		remove(1),
		up(2),
		down-warning(3),
		down-critical(4)
	}
	ACCESS read-write
	STATUS mandatory
	DESCRIPTION "&<caiWinA3.876>Current loss action for the quota watcher. Specifies the action to take if the monitored quota is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusQuotaEntry 18 }

winA3StatusQuotaLossStatus OBJECT-TYPE
	SYNTAX INTEGER {
		unknown(1),
		up(2),
		down-warning(3),
		down-critical(4)
	}
	ACCESS read-only
	STATUS mandatory
	DESCRIPTION "&<caiWinA3.877>Current loss status of the quota watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusQuotaEntry 19 }

winA3StatusQuotaCallBackRef OBJECT-TYPE
	SYNTAX DisplayString
	ACCESS read-only
	STATUS mandatory
	DESCRIPTION "&<caiWinA3.878>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusQuotaEntry 20 }

winA3StatusQuotaButton OBJECT-TYPE
	SYNTAX INTEGER {
		none(1),
		remove(2)
	}
	ACCESS read-write
	STATUS mandatory
	DESCRIPTION "&<caiWinA3.879>This attribute is used to remove the quota watcher. If set to 2 (remove), the agent removes the watcher from the table. This attribute cannot be set to 1 (none)."
	DEFVAL { 1 }
	::= { winA3StatusQuotaEntry 21 }

--
-- The StatusDir Group
--

winA3StatusDirCount OBJECT-TYPE
	SYNTAX INTEGER
	ACCESS read-only
	STATUS mandatory
	DESCRIPTION "&<caiWinA3.880>Number of entries in the directory status table."
	::= { winA3StatusDirGroup 1 }

winA3StatusDirTable OBJECT-TYPE
	SYNTAX SEQUENCE OF WinA3StatusDirEntry
	ACCESS not-accessible
	STATUS mandatory
	DESCRIPTION "&<caiWinA3.881>The directory status table containing details about the currently configured directory watchers."
	::= { winA3StatusDirGroup 2 }

winA3StatusDirEntry OBJECT-TYPE
	SYNTAX WinA3StatusDirEntry
	ACCESS not-accessible
	STATUS mandatory
	DESCRIPTION "&<caiWinA3.882>Entry in the directory status table."
	INDEX {
		winA3StatusDirWatcherName
	}
	::= { winA3StatusDirTable 1 }

WinA3StatusDirEntry ::= SEQUENCE {
	winA3StatusDirWatcherName DisplayString,
	winA3StatusDirName DisplayString,
	winA3StatusDirRecursivePolicy INTEGER,
	winA3StatusDirDescription DisplayString,
	winA3StatusDirAggLagValue INTEGER,
	winA3StatusDirAggLag INTEGER,
	winA3StatusDirAggStatus INTEGER,
	winA3StatusDirSizeTotal DisplayString,
	winA3StatusDirSizeValue DisplayString,
	winA3StatusDirSizeWarnMin DisplayString,
	winA3StatusDirSizeWarnMax DisplayString,
	winA3StatusDirSizeCritMin DisplayString,
	winA3StatusDirSizeCritMax DisplayString,
	winA3StatusDirSizeMonitor INTEGER,
	winA3StatusDirSizeStatus INTEGER,
	winA3StatusDirSizeDValue DisplayString,
	winA3StatusDirSizeDWarnValue DisplayString,
	winA3StatusDirSizeDCritValue DisplayString,
	winA3StatusDirSizeDWarn DisplayString,
	winA3StatusDirSizeDCrit DisplayString,
	winA3StatusDirSizeDMonitor INTEGER,
	winA3StatusDirSizeDStatus INTEGER,
	winA3StatusDirEntriesValue DisplayString,
	winA3StatusDirEntriesWarnMin DisplayString,
	winA3StatusDirEntriesWarnMax DisplayString,
	winA3StatusDirEntriesCritMin DisplayString,
	winA3StatusDirEntriesCritMax DisplayString,
	winA3StatusDirEntriesMonitor INTEGER,
	winA3StatusDirEntriesStatus INTEGER,
	winA3StatusDirTimeMode INTEGER,
	winA3StatusDirTimeInterval INTEGER,
	winA3StatusDirTimeValue DisplayString,
	winA3StatusDirTimeRef DisplayString,
	winA3StatusDirTimePolicy INTEGER,
	winA3StatusDirTimeMonitor INTEGER,
	winA3StatusDirTimeStatus INTEGER,
	winA3StatusDirExistPolicy INTEGER,
	winA3StatusDirExistMonitor INTEGER,
	winA3StatusDirExistStatus INTEGER,
	winA3StatusDirCallBackRef DisplayString,
	winA3StatusDirButton INTEGER
}

winA3StatusDirWatcherName OBJECT-TYPE
	SYNTAX DisplayString
	ACCESS read-only
	STATUS mandatory
	DESCRIPTION "&<caiWinA3.883>An arbitrary name for the watcher."
	::= { winA3StatusDirEntry 1 }

winA3StatusDirName OBJECT-TYPE
	SYNTAX DisplayString
	ACCESS read-write
	STATUS mandatory
	DESCRIPTION "&<caiWinA3.884>Name of the directory. This must be a fully qualified name that may contain environment variables."
	::= { winA3StatusDirEntry 2 }

winA3StatusDirRecursivePolicy OBJECT-TYPE
	SYNTAX INTEGER {
		no(1),
		yes(2)
	}
	ACCESS read-write
	STATUS mandatory
	DESCRIPTION "&<caiWinA3.885>If set to yes(2), the scope of th watcher, to calculate the values from, is the complete subtree of the given directory. If set to no(1), the scope is just the (flat) directory."
	DEFVAL { 0 }
	::= { winA3StatusDirEntry 3 }

winA3StatusDirDescription OBJECT-TYPE
	SYNTAX DisplayString
	ACCESS read-write
	STATUS mandatory
	DESCRIPTION "&<caiWinA3.886>Current description for the directory watcher."
	::= { winA3StatusDirEntry 4 }

winA3StatusDirAggLagValue OBJECT-TYPE
	SYNTAX INTEGER
	ACCESS read-only
	STATUS mandatory
	DESCRIPTION "&<caiWinA3.887>Current aggregate lag value of the directory watcher. Indicates the consecutive number of times at which any status was not in the ok state. The aggregate status changes from ok as soon as the aggregate lag value reaches the configured value."
	::= { winA3StatusDirEntry 5 }

winA3StatusDirAggLag OBJECT-TYPE
	SYNTAX INTEGER
	ACCESS read-write
	STATUS mandatory
	DESCRIPTION "&<caiWinA3.888>Current aggregate lag setting for the directory watcher. Specifies the consecutive number of times at which any status is not in the ok state, before the aggregate status changes. This value must be greater than 0."
	::= { winA3StatusDirEntry 6 }

winA3StatusDirAggStatus OBJECT-TYPE
	SYNTAX INTEGER {
		unknown(1),
		ok(2),
		warning(3),
		critical(4),
		passive(5)
	}
	ACCESS read-only
	STATUS mandatory
	DESCRIPTION "&<caiWinA3.889>Current aggregate status of the directory watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { winA3StatusDirEntry 7 }

winA3StatusDirSizeTotal OBJECT-TYPE
	SYNTAX DisplayString
	ACCESS read-only
	STATUS mandatory
	DESCRIPTION "&<caiWinA3.890>The total size, in kilobytes, of the directory at the time when this watcher was created or when the last time the status button attribute has been set to 'reinit'."
	DEFVAL { "0" }
	::= { winA3StatusDirEntry 8 }

winA3StatusDirSizeValue OBJECT-TYPE
	SYNTAX DisplayString
	ACCESS read-only
	STATUS mandatory
	DESCRIPTION "&<caiWinA3.891>Current value, in kilobytes, for the size utilization monitoring of the directory watcher."
	DEFVAL { "0" }
	::= { winA3StatusDirEntry 9 }

winA3StatusDirSizeWarnMin OBJECT-TYPE
	SYNTAX DisplayString
	ACCESS read-write
	STATUS mandatory
	DESCRIPTION "&<caiWinA3.892>Current warning minimum threshold, in kilobytes, for the size utilization monitoring of the directory watcher. This value represents a declining threshold and must be equal to or greater than 0.0, equal to or greater than the critical minimum threshold, but cannot be greater than the warning maximum threshold. A value of -1 disables the evaluation of this threshold. The threshold can be specified as either an absolute value (n) or a percentage (n%). The value of winA3StatusDirSizeTotal will be the reference value for n% notations."
	DEFVAL { "-2" }
	::= { winA3StatusDirEntry 10 }

winA3StatusDirSizeWarnMax OBJECT-TYPE
	SYNTAX DisplayString
	ACCESS read-write
	STATUS mandatory
	DESCRIPTION "&<caiWinA3.893>Current warning maximum threshold, in kilobytes, for the size utilization monitoring of the directory watcher. This value represents a rising threshold and must be equal to or greater than 0.0, equal to or greater than the warning minimum threshold, but cannot be greater than the critical maximum threshold. A value of -1 disables the evaluation of this threshold. The threshold can be specified as either an absolute value (n) or a percentage (n%). The value of winA3StatusDirSizeTotal will be the reference value for n% notations."
	DEFVAL { "-2" }
	::= { winA3StatusDirEntry 11 }

winA3StatusDirSizeCritMin OBJECT-TYPE
	SYNTAX DisplayString
	ACCESS read-write
	STATUS mandatory
	DESCRIPTION "&<caiWinA3.894>Current critical minimum threshold, in kilobytes, for the size utilization monitoring of the directory watcher. This value represents a declining threshold and must be equal to or greater than 0.0, but cannot be greater than the warning minimum threshold. A value of -1 disables the evaluation of this threshold. The threshold can be specified as either an absolute value (n) or a percentage (n%). The value of winA3StatusDirSizeTotal will be the reference value for n% notations."
	DEFVAL { "-2" }
	::= { winA3StatusDirEntry 12 }

winA3StatusDirSizeCritMax OBJECT-TYPE
	SYNTAX DisplayString
	ACCESS read-write
	STATUS mandatory
	DESCRIPTION "&<caiWinA3.895>Current critical maximum threshold, in kilobytes, for the size utilization monitoring of the directory watcher. This value represents a rising threshold and must be equal to or greater than 0.0, but cannot be less than the warning maximum threshold. A value of -1 disables the evaluation of this threshold. The threshold can be specified as either an absolute value (n) or a percentage (n%). The value of winA3StatusDirSizeTotal will be the reference value for n% notations."
	DEFVAL { "-2" }
	::= { winA3StatusDirEntry 13 }

winA3StatusDirSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.896>Current monitor level for the size utilization monitoring of the directory watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusDirEntry 14 }

winA3StatusDirSizeStatus OBJECT-TYPE
	SYNTAX INTEGER {
		unknown(1),
		up(2),
		down-warning(3),
		down-critical(4)
	}
	ACCESS read-only
	STATUS mandatory
	DESCRIPTION "&<caiWinA3.897>Current status for the size utilization monitoring of the directory watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusDirEntry 15 }

winA3StatusDirSizeDValue OBJECT-TYPE
	SYNTAX DisplayString
	ACCESS read-only
	STATUS mandatory
	DESCRIPTION "&<caiWinA3.898>Current value, in kilobytes, for the delta size utilization monitoring of the directory watcher. This is the difference of the size utilization from one poll to the next."
	DEFVAL { "0" }
	::= { winA3StatusDirEntry 16 }

winA3StatusDirSizeDWarnValue OBJECT-TYPE
	SYNTAX DisplayString
	ACCESS read-only
	STATUS mandatory
	DESCRIPTION "&<caiWinA3.899>Active warning threshold, in kilobytes, as derived from the configured value for the delta size utilization monitoring of the directory watcher. This value represents a rising threshold and must be greater than 0.0, but cannot be greater than the active critical threshold. These constraints will be maintained by the agent during all configuration actions."
	::= { winA3StatusDirEntry 17 }

winA3StatusDirSizeDCritValue OBJECT-TYPE
	SYNTAX DisplayString
	ACCESS read-only
	STATUS mandatory
	DESCRIPTION "&<caiWinA3.900>Active critical threshold, in kilobytes, as derived from the configured value for the delta size utilization monitoring of the directory watcher. This value represents a rising threshold and must be greater than 0.0, but cannot be less than the active warning threshold. These constraints will be maintained by the agent during all configuration actions."
	::= { winA3StatusDirEntry 18 }

winA3StatusDirSizeDWarn OBJECT-TYPE
	SYNTAX DisplayString
	ACCESS read-write
	STATUS mandatory
	DESCRIPTION "&<caiWinA3.901>Configured warning threshold from which the active warning threshold is derived for the delta size utilization monitoring of the directory watcher. The threshold can be specified as either an absolute value or a percentage and can denote a growth, shrinkage or change in either direction: Absolute shrinkage (n-), absolute growth (n+), absolute change in either direction (n), percentage shrinkage (n%-), percentage growth (n%+), or percentage change in either direction (n%). The value of winA3StatusDirSizeTotal will be the reference value for n% notations."
	::= { winA3StatusDirEntry 19 }

winA3StatusDirSizeDCrit OBJECT-TYPE
	SYNTAX DisplayString
	ACCESS read-write
	STATUS mandatory
	DESCRIPTION "&<caiWinA3.902>Configured critical threshold from which the active critical threshold is derived for the delta size utilization monitoring of the directory watcher. The threshold can be specified as either an absolute value or a percentage and can denote a growth, shrinkage or change in either direction: Absolute shrinkage (n-), absolute growth (n+), absolute change in either direction (n), percentage shrinkage (n%-), percentage growth (n%+), or percentage change in either direction (n%). The value of winA3StatusDirSizeTotal will be the reference value for n% notations."
	::= { winA3StatusDirEntry 20 }

winA3StatusDirSizeDMonitor OBJECT-TYPE
	SYNTAX INTEGER {
		do-not-monitor(1),
		warning-only(2),
		critical-only(3),
		both(4)
	}
	ACCESS read-write
	STATUS mandatory
	DESCRIPTION "&<caiWinA3.903>Current monitor level for the delta size utilization monitoring of the directory watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusDirEntry 21 }

winA3StatusDirSizeDStatus OBJECT-TYPE
	SYNTAX INTEGER {
		unknown(1),
		ok(2),
		warning(3),
		critical(4)
	}
	ACCESS read-only
	STATUS mandatory
	DESCRIPTION "&<caiWinA3.904>Current status for the delta size utilization monitoring of the directory watcher: 1 (unknown) - An error occurred during data collection, 2 (ok) - The resource is operating within the defined limits or status evaluation is turned off and/or polling is disabled, 3 (warning) - The resource has breached the warning threshold, 4 (critical) - The resource has breached the critical threshold."
	::= { winA3StatusDirEntry 22 }

winA3StatusDirEntriesValue OBJECT-TYPE
	SYNTAX DisplayString
	ACCESS read-only
	STATUS mandatory
	DESCRIPTION "&<caiWinA3.905>Current value for the number of file and/or directory entries monitoring of the directory watcher."
	DEFVAL { "0" }
	::= { winA3StatusDirEntry 23 }

winA3StatusDirEntriesWarnMin OBJECT-TYPE
	SYNTAX DisplayString
	ACCESS read-write
	STATUS mandatory
	DESCRIPTION "&<caiWinA3.906>Current warning minimum threshold for the number of file and/or directory entries monitoring of the directory watcher. This value represents a declining threshold and must be equal to or greater than 0.0, equal to or greater than the critical minimum threshold, but cannot be greater than the warning maximum threshold. A value of -1 disables the evaluation of this threshold."
	DEFVAL { "-2" }
	::= { winA3StatusDirEntry 24 }

winA3StatusDirEntriesWarnMax OBJECT-TYPE
	SYNTAX DisplayString
	ACCESS read-write
	STATUS mandatory
	DESCRIPTION "&<caiWinA3.907>Current warning maximum threshold for the number of file and/or directory entries monitoring of the directory watcher. This value represents a rising threshold and must be equal to or greater than 0.0, equal to or greater than the warning minimum threshold, but cannot be greater than the critical maximum threshold. A value of -1 disables the evaluation of this threshold."
	DEFVAL { "-2" }
	::= { winA3StatusDirEntry 25 }

winA3StatusDirEntriesCritMin OBJECT-TYPE
	SYNTAX DisplayString
	ACCESS read-write
	STATUS mandatory
	DESCRIPTION "&<caiWinA3.908>Current critical minimum threshold for the number of file and/or directory entries monitoring of the directory watcher. This value represents a declining threshold and must be equal to or greater than 0.0, but cannot be greater than the warning minimum threshold. A value of -1 disables the evaluation of this threshold."
	DEFVAL { "-2" }
	::= { winA3StatusDirEntry 26 }

winA3StatusDirEntriesCritMax OBJECT-TYPE
	SYNTAX DisplayString
	ACCESS read-write
	STATUS mandatory
	DESCRIPTION "&<caiWinA3.909>Current critical maximum threshold for the number of file and/or directory entries monitoring of the directory watcher. This value represents a rising threshold and must be equal to or greater than 0.0, but cannot be less than the warning maximum threshold. A value of -1 disables the evaluation of this threshold."
	DEFVAL { "-2" }
	::= { winA3StatusDirEntry 27 }

winA3StatusDirEntriesMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.910>Current monitor level for the number of file and/or directory entries monitoring of the directory watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusDirEntry 28 }

winA3StatusDirEntriesStatus OBJECT-TYPE
	SYNTAX INTEGER {
		unknown(1),
		up(2),
		down-warning(3),
		down-critical(4)
	}
	ACCESS read-only
	STATUS mandatory
	DESCRIPTION "&<caiWinA3.911>Current status for the number of file and/or directory entries monitoring of the directory watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusDirEntry 29 }

winA3StatusDirTimeMode OBJECT-TYPE
	SYNTAX INTEGER {
		modification-time(1),
		access-time(2),
		creation-time(3)
	}
	ACCESS read-write
	STATUS mandatory
	DESCRIPTION "&<caiWinA3.912>This attribute determines which mode of time (modification, access or creation) should be used for the time monitoring."
	DEFVAL { 0 }
	::= { winA3StatusDirEntry 30 }

winA3StatusDirTimeInterval OBJECT-TYPE
	SYNTAX INTEGER
	ACCESS read-write
	STATUS mandatory
	DESCRIPTION "&<caiWinA3.913>Time, in seconds, defining the time frame during which the time monitoring is performed. Dependend from the policy, the status is set to 'down' if the time interval is elapsed and the time value changed or changed not. A value of zero stands for an infinite interval."
	::= { winA3StatusDirEntry 31 }

winA3StatusDirTimeValue OBJECT-TYPE
	SYNTAX DisplayString
	ACCESS read-only
	STATUS mandatory
	DESCRIPTION "&<caiWinA3.914>The current value of the time monitoring. This is the time of the latest change. If the directory does not exist, the time value is set to '-'."
	::= { winA3StatusDirEntry 32 }

winA3StatusDirTimeRef OBJECT-TYPE
	SYNTAX DisplayString
	ACCESS read-only
	STATUS mandatory
	DESCRIPTION "&<caiWinA3.915>This attribute is used as the reference to determine the status of the time metric, dependend from the policy. The reference always reflects the start point of the current time interval. The reference is set initially when the agent starts up or when a watcher is created. Additionally it is reset if the user sets the status button attribute to 'reset-time'. Furthermore, under certain circumstances, the agent resets the time reference internally."
	::= { winA3StatusDirEntry 33 }

winA3StatusDirTimePolicy OBJECT-TYPE
	SYNTAX INTEGER {
		should-not-change(1),
		should-change(2)
	}
	ACCESS read-write
	STATUS mandatory
	DESCRIPTION "&<caiWinA3.916>Current monitor policy for the time monitoring of the directory watcher. The policy indicates the expected behaviour of the time value during the given time interval."
	DEFVAL { 0 }
	::= { winA3StatusDirEntry 34 }

winA3StatusDirTimeMonitor OBJECT-TYPE
	SYNTAX INTEGER {
		do-not-monitor(1),
		down-warning(2),
		down-critical(3)
	}
	ACCESS read-write
	STATUS mandatory
	DESCRIPTION "&<caiWinA3.917>Current monitor level for the time monitoring of the directory watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusDirEntry 35 }

winA3StatusDirTimeStatus OBJECT-TYPE
	SYNTAX INTEGER {
		unknown(1),
		up(2),
		down-warning(3),
		down-critical(4)
	}
	ACCESS read-only
	STATUS mandatory
	DESCRIPTION "&<caiWinA3.918>Current status for the time monitoring of the directory watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusDirEntry 36 }

winA3StatusDirExistPolicy OBJECT-TYPE
	SYNTAX INTEGER {
		should-exist(1),
		should-not-exist(2)
	}
	ACCESS read-write
	STATUS mandatory
	DESCRIPTION "&<caiWinA3.919>Current monitor policy for the existence monitoring of the directory watcher. Specifies how the agent should evaluate the presence or absence of the monitored resource in order to determine whether the resource is in good condition. If set to 1 (should-exist), the resource is expected to be existent. If set to 2 (should-not-exist), the resource is expected to be nonexistent."
	DEFVAL { 0 }
	::= { winA3StatusDirEntry 37 }

winA3StatusDirExistMonitor OBJECT-TYPE
	SYNTAX INTEGER {
		do-not-monitor(1),
		down-warning(2),
		down-critical(3)
	}
	ACCESS read-write
	STATUS mandatory
	DESCRIPTION "&<caiWinA3.920>Current monitor level for the existence monitoring of the directory watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusDirEntry 38 }

winA3StatusDirExistStatus OBJECT-TYPE
	SYNTAX INTEGER {
		unknown(1),
		up(2),
		down-warning(3),
		down-critical(4)
	}
	ACCESS read-only
	STATUS mandatory
	DESCRIPTION "&<caiWinA3.921>Current status for the existence monitoring of the directory watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusDirEntry 39 }

winA3StatusDirCallBackRef OBJECT-TYPE
	SYNTAX DisplayString
	ACCESS read-only
	STATUS mandatory
	DESCRIPTION "&<caiWinA3.922>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusDirEntry 40 }

winA3StatusDirButton OBJECT-TYPE
	SYNTAX INTEGER {
		none(1),
		remove(2),
		reinit(3),
		reset-time(4)
	}
	ACCESS read-write
	STATUS mandatory
	DESCRIPTION "&<caiWinA3.923>This attribute is used to remove the directory watcher. Additionally, if set to 3 (reinit), the watcher is completely new evaluated. If set to 4 (reset-time), the time reference is set to the actual current time and the status of the time metric is set to 'up'. If set to 2 (remove), the agent removes the watcher from the table. This attribute cannot be set to 1 (none)."
	DEFVAL { 1 }
	::= { winA3StatusDirEntry 41 }

--
-- The StatusFile Group
--

winA3StatusFileCount OBJECT-TYPE
	SYNTAX INTEGER
	ACCESS read-only
	STATUS mandatory
	DESCRIPTION "&<caiWinA3.924>Number of entries in the file status table."
	::= { winA3StatusFileGroup 1 }

winA3StatusFileTable OBJECT-TYPE
	SYNTAX SEQUENCE OF WinA3StatusFileEntry
	ACCESS not-accessible
	STATUS mandatory
	DESCRIPTION "&<caiWinA3.925>The file status table containing details about the currently configured file watchers."
	::= { winA3StatusFileGroup 2 }

winA3StatusFileEntry OBJECT-TYPE
	SYNTAX WinA3StatusFileEntry
	ACCESS not-accessible
	STATUS mandatory
	DESCRIPTION "&<caiWinA3.926>Entry in the file status table."
	INDEX {
		winA3StatusFileWatcherName
	}
	::= { winA3StatusFileTable 1 }

WinA3StatusFileEntry ::= SEQUENCE {
	winA3StatusFileWatcherName DisplayString,
	winA3StatusFileMatchType INTEGER,
	winA3StatusFileName DisplayString,
	winA3StatusFileEvalPolicy INTEGER,
	winA3StatusFileDescription DisplayString,
	winA3StatusFileAggLagValue INTEGER,
	winA3StatusFileAggLag INTEGER,
	winA3StatusFileAggStatus INTEGER,
	winA3StatusFileInstValue INTEGER,
	winA3StatusFileInstMin INTEGER,
	winA3StatusFileInstMax INTEGER,
	winA3StatusFileInstMonitor INTEGER,
	winA3StatusFileInstStatus INTEGER,
	winA3StatusFileInstIds DisplayString,
	winA3StatusFileSizeTotal DisplayString,
	winA3StatusFileSizeMinValue DisplayString,
	winA3StatusFileSizeMaxValue DisplayString,
	winA3StatusFileSizeWarnMin DisplayString,
	winA3StatusFileSizeWarnMax DisplayString,
	winA3StatusFileSizeCritMin DisplayString,
	winA3StatusFileSizeCritMax DisplayString,
	winA3StatusFileSizeMonitor INTEGER,
	winA3StatusFileSizeStatus INTEGER,
	winA3StatusFileSizeIds DisplayString,
	winA3StatusFileSizeDValue DisplayString,
	winA3StatusFileSizeDWarnValue DisplayString,
	winA3StatusFileSizeDCritValue DisplayString,
	winA3StatusFileSizeDWarn DisplayString,
	winA3StatusFileSizeDCrit DisplayString,
	winA3StatusFileSizeDMonitor INTEGER,
	winA3StatusFileSizeDStatus INTEGER,
	winA3StatusFileSizeDIds DisplayString,
	winA3StatusFileTimeMode INTEGER,
	winA3StatusFileTimeInterval INTEGER,
	winA3StatusFileTimeValue DisplayString,
	winA3StatusFileTimeRef DisplayString,
	winA3StatusFileTimePolicy INTEGER,
	winA3StatusFileTimeMonitor INTEGER,
	winA3StatusFileTimeStatus INTEGER,
	winA3StatusFileTimeIds DisplayString,
	winA3StatusFileCallBackRef DisplayString,
	winA3StatusFileButton INTEGER
}

winA3StatusFileWatcherName OBJECT-TYPE
	SYNTAX DisplayString
	ACCESS read-only
	STATUS mandatory
	DESCRIPTION "&<caiWinA3.927>An arbitrary name for the watcher."
	::= { winA3StatusFileEntry 1 }

winA3StatusFileMatchType OBJECT-TYPE
	SYNTAX INTEGER {
		positive-regular-expression(1),
		negative-regular-expression(2),
		positive-string-compare(3),
		negative-string-compare(4)
	}
	ACCESS read-write
	STATUS mandatory
	DESCRIPTION "&<caiWinA3.928>Current search algorithm for the file watcher. The filter is the logical AND of all attributes used to identify or otherwise narrow down resources. If the value of one of these attributes includes 'wildcards', then the watcher will basically behave like a one-to-many watcher, i.e. it may monitor two or more resources simultaneously. If set to 1 (positive-regular-expression), the agent searches for file resources that match the filter as a regular expression (case-insensitive). If set to 2 (negative-regular-expression), the agent searches for file resources that do not match the filter as a regular expression (case-insensitive). If set to 3 (positive-string-compare), the agent searches for file resources that match the filter as string comparison (case-insensitive). If set to 4 (negative-string-compare), the agent searches for file resources that do not match the filter as string comparison (case-insensitive)."
	DEFVAL { 0 }
	::= { winA3StatusFileEntry 2 }

winA3StatusFileName OBJECT-TYPE
	SYNTAX DisplayString
	ACCESS read-write
	STATUS mandatory
	DESCRIPTION "&<caiWinA3.929>Name of the file. This name may contain environment variables. This name is used as a filter element for one-to-many monitoring (one watcher monitors several resources simultaneously). The file name (not the path) can be a regular expression (case-insensitive). The expression '.*' always matches any string, independent from the match type."
	::= { winA3StatusFileEntry 3 }

winA3StatusFileEvalPolicy OBJECT-TYPE
	SYNTAX INTEGER {
		individual(1),
		min(2),
		max(3),
		sum(4),
		avg(5)
	}
	ACCESS read-write
	STATUS mandatory
	DESCRIPTION "&<caiWinA3.930>Current evaluation policy for the file watcher. Defines how metric values will be calculated and 'culprits' be determined if two or more file resources fall into the monitoring scope of a one-to-many watcher. If set to 1 (individual), metric values will be set to the worst values (lowest and/or highest) of all file instances; if the value of a metric violates the threshold condition, the respective 'culprits' list will contain all instances individually violating the most severe threshold. If set to 2 (min), metric values will be set to the lowest (minimum) values of all file instances; if the value of a metric violates the threshold condition, the respective 'culprits' list will contain all instances having the same minimum value. If set to 3 (max), metric values will be set to the highest (maximum) values of all file instances; if the value of a metric violates the threshold condition, the respective 'culprits' list will contain all instances having the same maximum value. If set to 4 (sum), metric values will be set to the cumulative values (sum) of all file instances; if the value of a metric violates the threshold condition, the respective 'culprits' list will contain all instances. If set to 5 (avg), metric values will be set to the average values of all file instances; if the value of a metric violates the threshold condition, the respective 'culprits' list will contain all instances individually violating the most severe threshold."
	DEFVAL { 0 }
	::= { winA3StatusFileEntry 4 }

winA3StatusFileDescription OBJECT-TYPE
	SYNTAX DisplayString
	ACCESS read-write
	STATUS mandatory
	DESCRIPTION "&<caiWinA3.931>Current description for the file watcher."
	::= { winA3StatusFileEntry 5 }

winA3StatusFileAggLagValue OBJECT-TYPE
	SYNTAX INTEGER
	ACCESS read-only
	STATUS mandatory
	DESCRIPTION "&<caiWinA3.932>Current aggregate lag value of the file watcher. Indicates the consecutive number of times at which any status was not in the ok state. The aggregate status changes from ok as soon as the aggregate lag value reaches the configured value."
	::= { winA3StatusFileEntry 6 }

winA3StatusFileAggLag OBJECT-TYPE
	SYNTAX INTEGER
	ACCESS read-write
	STATUS mandatory
	DESCRIPTION "&<caiWinA3.933>Current aggregate lag setting for the file watcher. Specifies the consecutive number of times at which any status is not in the ok state, before the aggregate status changes. This value must be greater than 0."
	::= { winA3StatusFileEntry 7 }

winA3StatusFileAggStatus OBJECT-TYPE
	SYNTAX INTEGER {
		unknown(1),
		ok(2),
		warning(3),
		critical(4),
		passive(5)
	}
	ACCESS read-only
	STATUS mandatory
	DESCRIPTION "&<caiWinA3.934>Current aggregate status of the file watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { winA3StatusFileEntry 8 }

winA3StatusFileInstValue OBJECT-TYPE
	SYNTAX INTEGER
	ACCESS read-only
	STATUS mandatory
	DESCRIPTION "&<caiWinA3.935>Current value for the instance count monitoring of the file watcher. This is the number of files that fall in the scope of this watcher, i.e. that match the filter conditions and hence are monitored simultaneously by this watcher."
	::= { winA3StatusFileEntry 9 }

winA3StatusFileInstMin OBJECT-TYPE
	SYNTAX INTEGER
	ACCESS read-write
	STATUS mandatory
	DESCRIPTION "&<caiWinA3.936>Current minimum threshold for the instance count monitoring of the file watcher. This value represents a declining threshold and must be equal to or greater than 0, but cannot be greater than the maximum threshold. A value of -1 disables the evaluation of this threshold."
	DEFVAL { -2 }
	::= { winA3StatusFileEntry 10 }

winA3StatusFileInstMax OBJECT-TYPE
	SYNTAX INTEGER
	ACCESS read-write
	STATUS mandatory
	DESCRIPTION "&<caiWinA3.937>Current maximum threshold for the instance count monitoring of the file watcher. This value represents a rising threshold and must be equal to or greater than 0, but cannot be less than the minimum threshold. A value of -1 disables the evaluation of this threshold."
	DEFVAL { -2 }
	::= { winA3StatusFileEntry 11 }

winA3StatusFileInstMonitor OBJECT-TYPE
	SYNTAX INTEGER {
		do-not-monitor(1),
		down-warning(2),
		down-critical(3)
	}
	ACCESS read-write
	STATUS mandatory
	DESCRIPTION "&<caiWinA3.938>Current monitor level for the instance count monitoring of the file watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusFileEntry 12 }

winA3StatusFileInstStatus OBJECT-TYPE
	SYNTAX INTEGER {
		unknown(1),
		up(2),
		down-warning(3),
		down-critical(4)
	}
	ACCESS read-only
	STATUS mandatory
	DESCRIPTION "&<caiWinA3.939>Current status for the instance count monitoring of the file watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusFileEntry 13 }

winA3StatusFileInstIds OBJECT-TYPE
	SYNTAX DisplayString
	ACCESS read-only
	STATUS mandatory
	DESCRIPTION "&<caiWinA3.940>A pipe sign separated list of those files that caused a violation of the instance metric thresholds."
	::= { winA3StatusFileEntry 14 }

winA3StatusFileSizeTotal OBJECT-TYPE
	SYNTAX DisplayString
	ACCESS read-only
	STATUS mandatory
	DESCRIPTION "&<caiWinA3.941>The total size, in kilobytes, of the file at the time when this watcher was created or when the last time the status button attribute has been set to 'reinit'. If more than one file fall in the scope of this watcher, the total size is calculated according to the evaluation policy."
	DEFVAL { "0" }
	::= { winA3StatusFileEntry 15 }

winA3StatusFileSizeMinValue OBJECT-TYPE
	SYNTAX DisplayString
	ACCESS read-only
	STATUS mandatory
	DESCRIPTION "&<caiWinA3.942>Current minimum value, in kilobytes, for the size utilization monitoring of the file watcher. If more than one file fall in the scope of this watcher, this value is the minimum of all instances."
	DEFVAL { "0" }
	::= { winA3StatusFileEntry 16 }

winA3StatusFileSizeMaxValue OBJECT-TYPE
	SYNTAX DisplayString
	ACCESS read-only
	STATUS mandatory
	DESCRIPTION "&<caiWinA3.943>Current maximum value, in kilobytes, for the size utilization monitoring of the file watcher. If more than one file fall in the scope of this watcher, this value is the maximum of all instances."
	DEFVAL { "0" }
	::= { winA3StatusFileEntry 17 }

winA3StatusFileSizeWarnMin OBJECT-TYPE
	SYNTAX DisplayString
	ACCESS read-write
	STATUS mandatory
	DESCRIPTION "&<caiWinA3.944>Current warning minimum threshold, in kilobytes, for the size utilization monitoring of the file watcher. This value represents a declining threshold and must be equal to or greater than 0.0, equal to or greater than the critical minimum threshold, but cannot be greater than the warning maximum threshold. A value of -1 disables the evaluation of this threshold. The threshold can be specified as either an absolute value (n) or a percentage (n%). The value of winA3StatusFileSizeTotal will be the reference value for n% notations."
	DEFVAL { "-2" }
	::= { winA3StatusFileEntry 18 }

winA3StatusFileSizeWarnMax OBJECT-TYPE
	SYNTAX DisplayString
	ACCESS read-write
	STATUS mandatory
	DESCRIPTION "&<caiWinA3.945>Current warning maximum threshold, in kilobytes, for the size utilization monitoring of the file watcher. This value represents a rising threshold and must be equal to or greater than 0.0, equal to or greater than the warning minimum threshold, but cannot be greater than the critical maximum threshold. A value of -1 disables the evaluation of this threshold. The threshold can be specified as either an absolute value (n) or a percentage (n%). The value of winA3StatusFileSizeTotal will be the reference value for n% notations."
	DEFVAL { "-2" }
	::= { winA3StatusFileEntry 19 }

winA3StatusFileSizeCritMin OBJECT-TYPE
	SYNTAX DisplayString
	ACCESS read-write
	STATUS mandatory
	DESCRIPTION "&<caiWinA3.946>Current critical minimum threshold, in kilobytes, for the size utilization monitoring of the file watcher. This value represents a declining threshold and must be equal to or greater than 0.0, but cannot be greater than the warning minimum threshold. A value of -1 disables the evaluation of this threshold. The threshold can be specified as either an absolute value (n) or a percentage (n%). The value of winA3StatusFileSizeTotal will be the reference value for n% notations."
	DEFVAL { "-2" }
	::= { winA3StatusFileEntry 20 }

winA3StatusFileSizeCritMax OBJECT-TYPE
	SYNTAX DisplayString
	ACCESS read-write
	STATUS mandatory
	DESCRIPTION "&<caiWinA3.947>Current critical maximum threshold, in kilobytes, for the size utilization monitoring of the file watcher. This value represents a rising threshold and must be equal to or greater than 0.0, but cannot be less than the warning maximum threshold. A value of -1 disables the evaluation of this threshold. The threshold can be specified as either an absolute value (n) or a percentage (n%). The value of winA3StatusFileSizeTotal will be the reference value for n% notations."
	DEFVAL { "-2" }
	::= { winA3StatusFileEntry 21 }

winA3StatusFileSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.948>Current monitor level for the size utilization monitoring of the file watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusFileEntry 22 }

winA3StatusFileSizeStatus OBJECT-TYPE
	SYNTAX INTEGER {
		unknown(1),
		up(2),
		down-warning(3),
		down-critical(4)
	}
	ACCESS read-only
	STATUS mandatory
	DESCRIPTION "&<caiWinA3.949>Current status for the size utilization monitoring of the file watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusFileEntry 23 }

winA3StatusFileSizeIds OBJECT-TYPE
	SYNTAX DisplayString
	ACCESS read-only
	STATUS mandatory
	DESCRIPTION "&<caiWinA3.950>A pipe sign separated list of those files that caused a violation of the size metric thresholds. This list also contains the size value for each instance (appended as ':value' after each name) and it is sorted according to the severity of the violation."
	::= { winA3StatusFileEntry 24 }

winA3StatusFileSizeDValue OBJECT-TYPE
	SYNTAX DisplayString
	ACCESS read-only
	STATUS mandatory
	DESCRIPTION "&<caiWinA3.951>Current value, in kilobytes, for the delta size utilization monitoring of the file watcher. This is the difference of the size utilization from one poll to the next. If more than one file fall into the scope of the watcher, the delta value is calculated from the individual deltas of each file. Deltas of zero are disregarded if the evaluation policy is minimum."
	DEFVAL { "0" }
	::= { winA3StatusFileEntry 25 }

winA3StatusFileSizeDWarnValue OBJECT-TYPE
	SYNTAX DisplayString
	ACCESS read-only
	STATUS mandatory
	DESCRIPTION "&<caiWinA3.952>Active warning threshold, in kilobytes, as derived from the configured value for the delta size utilization monitoring of the file watcher. This value represents a rising threshold and must be greater than 0.0, but cannot be greater than the active critical threshold. These constraints will be maintained by the agent during all configuration actions."
	::= { winA3StatusFileEntry 26 }

winA3StatusFileSizeDCritValue OBJECT-TYPE
	SYNTAX DisplayString
	ACCESS read-only
	STATUS mandatory
	DESCRIPTION "&<caiWinA3.953>Active critical threshold, in kilobytes, as derived from the configured value for the delta size utilization monitoring of the file watcher. This value represents a rising threshold and must be greater than 0.0, but cannot be less than the active warning threshold. These constraints will be maintained by the agent during all configuration actions."
	::= { winA3StatusFileEntry 27 }

winA3StatusFileSizeDWarn OBJECT-TYPE
	SYNTAX DisplayString
	ACCESS read-write
	STATUS mandatory
	DESCRIPTION "&<caiWinA3.954>Configured warning threshold from which the active warning threshold is derived for the delta size utilization monitoring of the file watcher. The threshold can be specified as either an absolute value or a percentage and can denote a growth, shrinkage or change in either direction: Absolute shrinkage (n-), absolute growth (n+), absolute change in either direction (n), percentage shrinkage (n%-), percentage growth (n%+), or percentage change in either direction (n%). The value of winA3StatusFileSizeTotal will be the reference value for n% notations."
	::= { winA3StatusFileEntry 28 }

winA3StatusFileSizeDCrit OBJECT-TYPE
	SYNTAX DisplayString
	ACCESS read-write
	STATUS mandatory
	DESCRIPTION "&<caiWinA3.955>Configured critical threshold from which the active critical threshold is derived for the delta size utilization monitoring of the file watcher. The threshold can be specified as either an absolute value or a percentage and can denote a growth, shrinkage or change in either direction: Absolute shrinkage (n-), absolute growth (n+), absolute change in either direction (n), percentage shrinkage (n%-), percentage growth (n%+), or percentage change in either direction (n%). The value of winA3StatusFileSizeTotal will be the reference value for n% notations."
	::= { winA3StatusFileEntry 29 }

winA3StatusFileSizeDMonitor OBJECT-TYPE
	SYNTAX INTEGER {
		do-not-monitor(1),
		warning-only(2),
		critical-only(3),
		both(4)
	}
	ACCESS read-write
	STATUS mandatory
	DESCRIPTION "&<caiWinA3.956>Current monitor level for the delta size utilization monitoring of the file watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusFileEntry 30 }

winA3StatusFileSizeDStatus OBJECT-TYPE
	SYNTAX INTEGER {
		unknown(1),
		ok(2),
		warning(3),
		critical(4)
	}
	ACCESS read-only
	STATUS mandatory
	DESCRIPTION "&<caiWinA3.957>Current status for the delta size utilization monitoring of the file watcher: 1 (unknown) - An error occurred during data collection, 2 (ok) - The resource is operating within the defined limits or status evaluation is turned off and/or polling is disabled, 3 (warning) - The resource has breached the warning threshold, 4 (critical) - The resource has breached the critical threshold."
	::= { winA3StatusFileEntry 31 }

winA3StatusFileSizeDIds OBJECT-TYPE
	SYNTAX DisplayString
	ACCESS read-only
	STATUS mandatory
	DESCRIPTION "&<caiWinA3.958>A pipe sign separated list of those files that caused a violation of the delta size metric thresholds. This list also contains the delta size value for each instance (appended as ':value' after each name) and it is sorted according to the severity of the violation."
	::= { winA3StatusFileEntry 32 }

winA3StatusFileTimeMode OBJECT-TYPE
	SYNTAX INTEGER {
		modification-time(1),
		access-time(2),
		creation-time(3)
	}
	ACCESS read-write
	STATUS mandatory
	DESCRIPTION "&<caiWinA3.959>This attribute determines which mode of time (modification, access or creation) should be used for the time monitoring."
	DEFVAL { 0 }
	::= { winA3StatusFileEntry 33 }

winA3StatusFileTimeInterval OBJECT-TYPE
	SYNTAX INTEGER
	ACCESS read-write
	STATUS mandatory
	DESCRIPTION "&<caiWinA3.960>Time, in seconds, defining the time frame during which the time monitoring is performed. Dependend from the policy, the status is set to 'down' if the time interval is elapsed and the time value changed or changed not. A value of zero stands for an infinite interval."
	::= { winA3StatusFileEntry 34 }

winA3StatusFileTimeValue OBJECT-TYPE
	SYNTAX DisplayString
	ACCESS read-only
	STATUS mandatory
	DESCRIPTION "&<caiWinA3.961>The current value of the time monitoring. This is the time of the latest change. If the file does not exist, the time value is set to '-'."
	::= { winA3StatusFileEntry 35 }

winA3StatusFileTimeRef OBJECT-TYPE
	SYNTAX DisplayString
	ACCESS read-only
	STATUS mandatory
	DESCRIPTION "&<caiWinA3.962>This attribute is used as the reference to determine the status of the time metric, dependend from the policy. The reference always reflects the start point of the current time interval. The reference is set initially when the agent starts up or when a watcher is created. Additionally it is reset if the user sets the status button attribute to 'reset-time'. Furthermore, under certain circumstances, the agent resets the time reference internally."
	::= { winA3StatusFileEntry 36 }

winA3StatusFileTimePolicy OBJECT-TYPE
	SYNTAX INTEGER {
		should-not-change(1),
		should-change(2)
	}
	ACCESS read-write
	STATUS mandatory
	DESCRIPTION "&<caiWinA3.963>Current monitor policy for the time monitoring of the file watcher. The policy indicates the expected behaviour of the time value during the given time interval."
	DEFVAL { 0 }
	::= { winA3StatusFileEntry 37 }

winA3StatusFileTimeMonitor OBJECT-TYPE
	SYNTAX INTEGER {
		do-not-monitor(1),
		down-warning(2),
		down-critical(3)
	}
	ACCESS read-write
	STATUS mandatory
	DESCRIPTION "&<caiWinA3.964>Current monitor level for the time monitoring of the file watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusFileEntry 38 }

winA3StatusFileTimeStatus OBJECT-TYPE
	SYNTAX INTEGER {
		unknown(1),
		up(2),
		down-warning(3),
		down-critical(4)
	}
	ACCESS read-only
	STATUS mandatory
	DESCRIPTION "&<caiWinA3.965>Current status for the time monitoring of the file watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusFileEntry 39 }

winA3StatusFileTimeIds OBJECT-TYPE
	SYNTAX DisplayString
	ACCESS read-only
	STATUS mandatory
	DESCRIPTION "&<caiWinA3.966>A pipe sign separated list of those files that caused a violation of the time metric policy."
	::= { winA3StatusFileEntry 40 }

winA3StatusFileCallBackRef OBJECT-TYPE
	SYNTAX DisplayString
	ACCESS read-only
	STATUS mandatory
	DESCRIPTION "&<caiWinA3.967>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusFileEntry 41 }

winA3StatusFileButton OBJECT-TYPE
	SYNTAX INTEGER {
		none(1),
		remove(2),
		reinit(3),
		reset-time(4)
	}
	ACCESS read-write
	STATUS mandatory
	DESCRIPTION "&<caiWinA3.968>This attribute is used to remove the file watcher. Additionally, if set to 3 (reinit), the watcher is completely new evaluated. If set to 4 (reset-time), the time reference is set to the actual current time and the status of the time metric is set to 'up'. If set to 2 (remove), the agent removes the watcher from the table. This attribute cannot be set to 1 (none)."
	DEFVAL { 1 }
	::= { winA3StatusFileEntry 42 }

--
-- The StatusProc Group
--

winA3StatusProcCount OBJECT-TYPE
	SYNTAX INTEGER
	ACCESS read-only
	STATUS mandatory
	DESCRIPTION "&<caiWinA3.969>Number of entries in the process status table."
	::= { winA3StatusProcGroup 1 }

winA3StatusProcTable OBJECT-TYPE
	SYNTAX SEQUENCE OF WinA3StatusProcEntry
	ACCESS not-accessible
	STATUS mandatory
	DESCRIPTION "&<caiWinA3.970>The process status table containing details about the currently configured process watchers."
	::= { winA3StatusProcGroup 2 }

winA3StatusProcEntry OBJECT-TYPE
	SYNTAX WinA3StatusProcEntry
	ACCESS not-accessible
	STATUS mandatory
	DESCRIPTION "&<caiWinA3.971>Entry in the process status table."
	INDEX {
		winA3StatusProcWatcherName
	}
	::= { winA3StatusProcTable 1 }

WinA3StatusProcEntry ::= SEQUENCE {
	winA3StatusProcWatcherName DisplayString,
	winA3StatusProcMatchType INTEGER,
	winA3StatusProcName DisplayString,
	winA3StatusProcPath DisplayString,
	winA3StatusProcUser DisplayString,
	winA3StatusProcClusterResGroup DisplayString,
	winA3StatusProcEvalPolicy INTEGER,
	winA3StatusProcDescription DisplayString,
	winA3StatusProcAggLagValue INTEGER,
	winA3StatusProcAggLag INTEGER,
	winA3StatusProcAggStatus INTEGER,
	winA3StatusProcClusterType INTEGER,
	winA3StatusProcInstValue INTEGER,
	winA3StatusProcInstMin INTEGER,
	winA3StatusProcInstMax INTEGER,
	winA3StatusProcInstMonitor INTEGER,
	winA3StatusProcInstStatus INTEGER,
	winA3StatusProcInstIds DisplayString,
	winA3StatusProcSizeMinValue DisplayString,
	winA3StatusProcSizeMaxValue DisplayString,
	winA3StatusProcSizeWarnMin DisplayString,
	winA3StatusProcSizeWarnMax DisplayString,
	winA3StatusProcSizeCritMin DisplayString,
	winA3StatusProcSizeCritMax DisplayString,
	winA3StatusProcSizeMonitor INTEGER,
	winA3StatusProcSizeStatus INTEGER,
	winA3StatusProcSizeIds DisplayString,
	winA3StatusProcCpuInterval DisplayString,
	winA3StatusProcCpuMinValue DisplayString,
	winA3StatusProcCpuMaxValue DisplayString,
	winA3StatusProcCpuWarnMin DisplayString,
	winA3StatusProcCpuWarnMax DisplayString,
	winA3StatusProcCpuCritMin DisplayString,
	winA3StatusProcCpuCritMax DisplayString,
	winA3StatusProcCpuMonitor INTEGER,
	winA3StatusProcCpuStatus INTEGER,
	winA3StatusProcCpuIds DisplayString,
	winA3StatusProcMiscMode INTEGER,
	winA3StatusProcMiscMinValue DisplayString,
	winA3StatusProcMiscMaxValue DisplayString,
	winA3StatusProcMiscMin DisplayString,
	winA3StatusProcMiscMax DisplayString,
	winA3StatusProcMiscMonitor INTEGER,
	winA3StatusProcMiscStatus INTEGER,
	winA3StatusProcMiscIds DisplayString,
	winA3StatusProcRestartPolicy INTEGER,
	winA3StatusProcRestartMonitor INTEGER,
	winA3StatusProcRestartStatus INTEGER,
	winA3StatusProcRestartIds DisplayString,
	winA3StatusProcCallBackRef DisplayString,
	winA3StatusProcButton INTEGER
}

winA3StatusProcWatcherName OBJECT-TYPE
	SYNTAX DisplayString
	ACCESS read-only
	STATUS mandatory
	DESCRIPTION "&<caiWinA3.972>An arbitrary name for the watcher."
	::= { winA3StatusProcEntry 1 }

winA3StatusProcMatchType OBJECT-TYPE
	SYNTAX INTEGER {
		positive-regular-expression(1),
		negative-regular-expression(2),
		positive-string-compare(3),
		negative-string-compare(4)
	}
	ACCESS read-write
	STATUS mandatory
	DESCRIPTION "&<caiWinA3.973>Current search algorithm for the process watcher. The filter is the logical AND of all attributes used to identify or otherwise narrow down resources. If the value of one of these attributes includes 'wildcards', then the watcher will basically behave like a one-to-many watcher, i.e. it may monitor two or more resources simultaneously. If set to 1 (positive-regular-expression), the agent searches for process resources that match the filter as a regular expression (case-insensitive). If set to 2 (negative-regular-expression), the agent searches for process resources that do not match the filter as a regular expression (case-insensitive). If set to 3 (positive-string-compare), the agent searches for process resources that match the filter as string comparison (case-insensitive). If set to 4 (negative-string-compare), the agent searches for process resources that do not match the filter as string comparison (case-insensitive)."
	DEFVAL { 0 }
	::= { winA3StatusProcEntry 2 }

winA3StatusProcName OBJECT-TYPE
	SYNTAX DisplayString
	ACCESS read-write
	STATUS mandatory
	DESCRIPTION "&<caiWinA3.974>Name of the process. This name is used as a filter element for one-to-many monitoring (one watcher monitors several resources simultaneously) and can be a regular expression (case-insensitive). The expression '.*' always matches any string, independent from the match type."
	::= { winA3StatusProcEntry 3 }

winA3StatusProcPath OBJECT-TYPE
	SYNTAX DisplayString
	ACCESS read-write
	STATUS mandatory
	DESCRIPTION "&<caiWinA3.975>Path name of the process. This name is used as a filter element for one-to-many monitoring (one watcher monitors several resources simultaneously) and can be a regular expression (case-insensitive). The expression '.*' always matches any string, independent from the match type."
	::= { winA3StatusProcEntry 4 }

winA3StatusProcUser OBJECT-TYPE
	SYNTAX DisplayString
	ACCESS read-write
	STATUS mandatory
	DESCRIPTION "&<caiWinA3.976>User name of the process. This name is used as a filter element for one-to-many monitoring (one watcher monitors several resources simultaneously) and can be a regular expression (case-insensitive). The expression '.*' always matches any string, independent from the match type."
	::= { winA3StatusProcEntry 5 }

winA3StatusProcClusterResGroup OBJECT-TYPE
	SYNTAX DisplayString
	ACCESS read-write
	STATUS mandatory
	DESCRIPTION "&<caiWinA3.977>Name of the cluster resource group of the process. For an unclustered process this attribute is set to '-'. For a clustered process, set this attribute to '-' to disable retrieval of the cluster type."
	::= { winA3StatusProcEntry 6 }

winA3StatusProcEvalPolicy OBJECT-TYPE
	SYNTAX INTEGER {
		individual(1),
		min(2),
		max(3),
		sum(4),
		avg(5)
	}
	ACCESS read-write
	STATUS mandatory
	DESCRIPTION "&<caiWinA3.978>Current evaluation policy for the process watcher. Defines how metric values will be calculated and 'culprits' be determined if two or more process resources fall into the monitoring scope of a one-to-many watcher. If set to 1 (individual), metric values will be set to the worst values (lowest and/or highest) of all process instances; if the value of a metric violates the threshold condition, the respective 'culprits' list will contain all instances individually violating the most severe threshold. If set to 2 (min), metric values will be set to the lowest (minimum) values of all process instances; if the value of a metric violates the threshold condition, the respective 'culprits' list will contain all instances having the same minimum value. If set to 3 (max), metric values will be set to the highest (maximum) values of all process instances; if the value of a metric violates the threshold condition, the respective 'culprits' list will contain all instances having the same maximum value. If set to 4 (sum), metric values will be set to the cumulative values (sum) of all process instances; if the value of a metric violates the threshold condition, the respective 'culprits' list will contain all instances. If set to 5 (avg), metric values will be set to the average values of all process instances; if the value of a metric violates the threshold condition, the respective 'culprits' list will contain all instances individually violating the most severe threshold."
	DEFVAL { 0 }
	::= { winA3StatusProcEntry 7 }

winA3StatusProcDescription OBJECT-TYPE
	SYNTAX DisplayString
	ACCESS read-write
	STATUS mandatory
	DESCRIPTION "&<caiWinA3.979>Current description for the process watcher."
	::= { winA3StatusProcEntry 8 }

winA3StatusProcAggLagValue OBJECT-TYPE
	SYNTAX INTEGER
	ACCESS read-only
	STATUS mandatory
	DESCRIPTION "&<caiWinA3.980>Current aggregate lag value of the process watcher. Indicates the consecutive number of times at which any status was not in the ok state. The aggregate status changes from ok as soon as the aggregate lag value reaches the configured value."
	::= { winA3StatusProcEntry 9 }

winA3StatusProcAggLag OBJECT-TYPE
	SYNTAX INTEGER
	ACCESS read-write
	STATUS mandatory
	DESCRIPTION "&<caiWinA3.981>Current aggregate lag setting for the process watcher. Specifies the consecutive number of times at which any status is not in the ok state, before the aggregate status changes. This value must be greater than 0."
	::= { winA3StatusProcEntry 10 }

winA3StatusProcAggStatus OBJECT-TYPE
	SYNTAX INTEGER {
		unknown(1),
		ok(2),
		warning(3),
		critical(4),
		passive(5)
	}
	ACCESS read-only
	STATUS mandatory
	DESCRIPTION "&<caiWinA3.982>Current aggregate status of the process watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { winA3StatusProcEntry 11 }

winA3StatusProcClusterType OBJECT-TYPE
	SYNTAX INTEGER {
		not-clustered(1),
		clustered-active(2),
		clustered-passive(3),
		clustered-mixed(4)
	}
	ACCESS read-only
	STATUS mandatory
	DESCRIPTION "&<caiWinA3.983>Cluster type of the process: 1 (not-clustered) - Resource is not clustered, 2 (clustered-active) - Local cluster node has resource ownership, 3 (clustered-passive) - Another node in the cluster has resource ownership; the agent on the local node does not actively monitor the resource until ownership is transferred back, 4 (clustered-mixed) - The resource instances monitored by the watcher have different cluster types."
	::= { winA3StatusProcEntry 12 }

winA3StatusProcInstValue OBJECT-TYPE
	SYNTAX INTEGER
	ACCESS read-only
	STATUS mandatory
	DESCRIPTION "&<caiWinA3.984>Current value for the instance count monitoring of the process watcher. This is the number of processes that fall in the scope of this watcher, i.e. that match the filter conditions and hence are monitored simultaneously by this watcher."
	::= { winA3StatusProcEntry 13 }

winA3StatusProcInstMin OBJECT-TYPE
	SYNTAX INTEGER
	ACCESS read-write
	STATUS mandatory
	DESCRIPTION "&<caiWinA3.985>Current minimum threshold for the instance count monitoring of the process watcher. This value represents a declining threshold and must be equal to or greater than 0, but cannot be greater than the maximum threshold. A value of -1 disables the evaluation of this threshold."
	DEFVAL { -2 }
	::= { winA3StatusProcEntry 14 }

winA3StatusProcInstMax OBJECT-TYPE
	SYNTAX INTEGER
	ACCESS read-write
	STATUS mandatory
	DESCRIPTION "&<caiWinA3.986>Current maximum threshold for the instance count monitoring of the process watcher. This value represents a rising threshold and must be equal to or greater than 0, but cannot be less than the minimum threshold. A value of -1 disables the evaluation of this threshold."
	DEFVAL { -2 }
	::= { winA3StatusProcEntry 15 }

winA3StatusProcInstMonitor OBJECT-TYPE
	SYNTAX INTEGER {
		do-not-monitor(1),
		down-warning(2),
		down-critical(3)
	}
	ACCESS read-write
	STATUS mandatory
	DESCRIPTION "&<caiWinA3.987>Current monitor level for the instance count monitoring of the process watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusProcEntry 16 }

winA3StatusProcInstStatus OBJECT-TYPE
	SYNTAX INTEGER {
		unknown(1),
		up(2),
		down-warning(3),
		down-critical(4)
	}
	ACCESS read-only
	STATUS mandatory
	DESCRIPTION "&<caiWinA3.988>Current status for the instance count monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusProcEntry 17 }

winA3StatusProcInstIds OBJECT-TYPE
	SYNTAX DisplayString
	ACCESS read-only
	STATUS mandatory
	DESCRIPTION "&<caiWinA3.989>A pipe sign separated list of those process IDs that caused a violation of the instance metric thresholds."
	::= { winA3StatusProcEntry 18 }

winA3StatusProcSizeMinValue OBJECT-TYPE
	SYNTAX DisplayString
	ACCESS read-only
	STATUS mandatory
	DESCRIPTION "&<caiWinA3.990>Current minimum value, in kilobytes, for the size utilization monitoring of the process watcher. This is the sum of real memory size (size of working set in physical memory) and virtual memory size (size of committed pages in the paging file). If more than one process fall in the scope of this watcher, this value is the minimum of all instances."
	DEFVAL { "0" }
	::= { winA3StatusProcEntry 19 }

winA3StatusProcSizeMaxValue OBJECT-TYPE
	SYNTAX DisplayString
	ACCESS read-only
	STATUS mandatory
	DESCRIPTION "&<caiWinA3.991>Current maximum value, in kilobytes, for the size utilization monitoring of the process watcher. This is the sum of real memory size (size of working set in physical memory) and virtual memory size (size of committed pages in the paging file). If more than one process fall in the scope of this watcher, this value is the maximum of all instances."
	DEFVAL { "0" }
	::= { winA3StatusProcEntry 20 }

winA3StatusProcSizeWarnMin OBJECT-TYPE
	SYNTAX DisplayString
	ACCESS read-write
	STATUS mandatory
	DESCRIPTION "&<caiWinA3.992>Current warning minimum threshold, in kilobytes, for the size utilization monitoring of the process watcher. This value represents a declining threshold and must be equal to or greater than 0.0, equal to or greater than the critical minimum threshold, but cannot be greater than the warning maximum threshold. A value of -1 disables the evaluation of this threshold."
	DEFVAL { "-2" }
	::= { winA3StatusProcEntry 21 }

winA3StatusProcSizeWarnMax OBJECT-TYPE
	SYNTAX DisplayString
	ACCESS read-write
	STATUS mandatory
	DESCRIPTION "&<caiWinA3.993>Current warning maximum threshold, in kilobytes, for the size utilization monitoring of the process watcher. This value represents a rising threshold and must be equal to or greater than 0.0, equal to or greater than the warning minimum threshold, but cannot be greater than the critical maximum threshold. A value of -1 disables the evaluation of this threshold."
	DEFVAL { "-2" }
	::= { winA3StatusProcEntry 22 }

winA3StatusProcSizeCritMin OBJECT-TYPE
	SYNTAX DisplayString
	ACCESS read-write
	STATUS mandatory
	DESCRIPTION "&<caiWinA3.994>Current critical minimum threshold, in kilobytes, for the size utilization monitoring of the process watcher. This value represents a declining threshold and must be equal to or greater than 0.0, but cannot be greater than the warning minimum threshold. A value of -1 disables the evaluation of this threshold."
	DEFVAL { "-2" }
	::= { winA3StatusProcEntry 23 }

winA3StatusProcSizeCritMax OBJECT-TYPE
	SYNTAX DisplayString
	ACCESS read-write
	STATUS mandatory
	DESCRIPTION "&<caiWinA3.995>Current critical maximum threshold, in kilobytes, for the size utilization monitoring of the process watcher. This value represents a rising threshold and must be equal to or greater than 0.0, but cannot be less than the warning maximum threshold. A value of -1 disables the evaluation of this threshold."
	DEFVAL { "-2" }
	::= { winA3StatusProcEntry 24 }

winA3StatusProcSizeMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.996>Current monitor level for the size utilization monitoring of the process watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusProcEntry 25 }

winA3StatusProcSizeStatus OBJECT-TYPE
	SYNTAX INTEGER {
		unknown(1),
		up(2),
		down-warning(3),
		down-critical(4)
	}
	ACCESS read-only
	STATUS mandatory
	DESCRIPTION "&<caiWinA3.997>Current status for the size utilization monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusProcEntry 26 }

winA3StatusProcSizeIds OBJECT-TYPE
	SYNTAX DisplayString
	ACCESS read-only
	STATUS mandatory
	DESCRIPTION "&<caiWinA3.998>A pipe sign separated list of those process IDs that caused a violation of the size metric thresholds. This list also contains the size value for each instance (appended as ':value' after each ID) and it is sorted according to the severity of the violation."
	::= { winA3StatusProcEntry 27 }

winA3StatusProcCpuInterval OBJECT-TYPE
	SYNTAX DisplayString
	ACCESS read-write
	STATUS mandatory
	DESCRIPTION "&<caiWinA3.999>Time, in seconds, defining the total value to use as base for the calculation of the cpu value. This means, the cpu usage of a process, in seconds, refers to this interval. Valid range: Greater 0 or '-1'. If set to '-1', the cpu value is calculated as the cpu usage, in seconds, used up to now since the start of the agent or the creation of the watcher. If the cpu interval is set to a value greater than the current poll interval and this time is not elapsed for the first time, the CPU value is extrapolated. If the cpu interval is set to a value smaller than the current poll interval, the CPU value is calculated as the appropriate fraction of the value for the last poll interval. If the cpu interval is set to a value greater than the current poll interval and this time is already elapsed, the CPU value is calculated as the sliding sum, i.e. the sum of the value for the current poll interval and the value calculated at the last poll, weighted according to it's fraction of the cpu interval. If the interval is set to '-1', any overloading (%) used for the thresholds will be ignored."
	::= { winA3StatusProcEntry 28 }

winA3StatusProcCpuMinValue OBJECT-TYPE
	SYNTAX DisplayString
	ACCESS read-only
	STATUS mandatory
	DESCRIPTION "&<caiWinA3.1000>Current minimum value, in seconds, for the cpu utilization monitoring of the process watcher. This is the cpu utilization the process takes in the given CPU interval. If more than one process fall in the scope of this watcher, this value is the minimum of all instances."
	DEFVAL { "0" }
	::= { winA3StatusProcEntry 29 }

winA3StatusProcCpuMaxValue OBJECT-TYPE
	SYNTAX DisplayString
	ACCESS read-only
	STATUS mandatory
	DESCRIPTION "&<caiWinA3.1001>Current maximum value, in seconds, for the cpu utilization monitoring of the process watcher. This is the cpu utilization the process takes in the given CPU interval. If more than one process fall in the scope of this watcher, this value is the maximum of all instances."
	DEFVAL { "0" }
	::= { winA3StatusProcEntry 30 }

winA3StatusProcCpuWarnMin OBJECT-TYPE
	SYNTAX DisplayString
	ACCESS read-write
	STATUS mandatory
	DESCRIPTION "&<caiWinA3.1002>Current warning minimum threshold, in seconds, for the cpu utilization monitoring of the process watcher. This value represents a declining threshold and must be equal to or greater than 0.0, less than or equal to the total value (maximum capacity) of the monitored resource as specified in winA3StatusProcCpuInterval, equal to or greater than the critical minimum threshold, but cannot be greater than the warning maximum threshold. A value of -1 disables the evaluation of this threshold. The threshold can be specified as either an absolute value (n) or a percentage (n%). The value of winA3StatusProcCpuInterval will be the reference value for n% notations."
	DEFVAL { "-2" }
	::= { winA3StatusProcEntry 31 }

winA3StatusProcCpuWarnMax OBJECT-TYPE
	SYNTAX DisplayString
	ACCESS read-write
	STATUS mandatory
	DESCRIPTION "&<caiWinA3.1003>Current warning maximum threshold, in seconds, for the cpu utilization monitoring of the process watcher. This value represents a rising threshold and must be equal to or greater than 0.0, less than or equal to the total value (maximum capacity) of the monitored resource as specified in winA3StatusProcCpuInterval, equal to or greater than the warning minimum threshold, but cannot be greater than the critical maximum threshold. A value of -1 disables the evaluation of this threshold. The threshold can be specified as either an absolute value (n) or a percentage (n%). The value of winA3StatusProcCpuInterval will be the reference value for n% notations."
	DEFVAL { "-2" }
	::= { winA3StatusProcEntry 32 }

winA3StatusProcCpuCritMin OBJECT-TYPE
	SYNTAX DisplayString
	ACCESS read-write
	STATUS mandatory
	DESCRIPTION "&<caiWinA3.1004>Current critical minimum threshold, in seconds, for the cpu utilization monitoring of the process watcher. This value represents a declining threshold and must be equal to or greater than 0.0, less than or equal to the total value (maximum capacity) of the monitored resource as specified in winA3StatusProcCpuInterval, but cannot be greater than the warning minimum threshold. A value of -1 disables the evaluation of this threshold. The threshold can be specified as either an absolute value (n) or a percentage (n%). The value of winA3StatusProcCpuInterval will be the reference value for n% notations."
	DEFVAL { "-2" }
	::= { winA3StatusProcEntry 33 }

winA3StatusProcCpuCritMax OBJECT-TYPE
	SYNTAX DisplayString
	ACCESS read-write
	STATUS mandatory
	DESCRIPTION "&<caiWinA3.1005>Current critical maximum threshold, in seconds, for the cpu utilization monitoring of the process watcher. This value represents a rising threshold and must be equal to or greater than 0.0, less than or equal to the total value (maximum capacity) of the monitored resource as specified in winA3StatusProcCpuInterval, but cannot be less than the warning maximum threshold. A value of -1 disables the evaluation of this threshold. The threshold can be specified as either an absolute value (n) or a percentage (n%). The value of winA3StatusProcCpuInterval will be the reference value for n% notations."
	DEFVAL { "-2" }
	::= { winA3StatusProcEntry 34 }

winA3StatusProcCpuMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.1006>Current monitor level for the cpu utilization monitoring of the process watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusProcEntry 35 }

winA3StatusProcCpuStatus OBJECT-TYPE
	SYNTAX INTEGER {
		unknown(1),
		up(2),
		down-warning(3),
		down-critical(4)
	}
	ACCESS read-only
	STATUS mandatory
	DESCRIPTION "&<caiWinA3.1007>Current status for the cpu utilization monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusProcEntry 36 }

winA3StatusProcCpuIds OBJECT-TYPE
	SYNTAX DisplayString
	ACCESS read-only
	STATUS mandatory
	DESCRIPTION "&<caiWinA3.1008>A pipe sign separated list of those process IDs that caused a violation of the cpu metric thresholds. This list also contains the cpu value for each instance (appended as ':value' after each ID) and it is sorted according to the severity of the violation."
	::= { winA3StatusProcEntry 37 }

winA3StatusProcMiscMode OBJECT-TYPE
	SYNTAX INTEGER {
		threads(1),
		handles(2),
		children(3),
		runtime(4)
	}
	ACCESS read-write
	STATUS mandatory
	DESCRIPTION "&<caiWinA3.1009>This attribute determines which value (threads, handles, children or runtime) should be calculated by this metric. The option runtime(4) is the time, in seconds, the process is running for (beginning with the process creation)."
	DEFVAL { 0 }
	::= { winA3StatusProcEntry 38 }

winA3StatusProcMiscMinValue OBJECT-TYPE
	SYNTAX DisplayString
	ACCESS read-only
	STATUS mandatory
	DESCRIPTION "&<caiWinA3.1010>Current minimum value, dependend from the misc mode, for the misc monitoring of the process watcher. If more than one process fall in the scope of this watcher, this value is the minimum of all instances."
	DEFVAL { "0" }
	::= { winA3StatusProcEntry 39 }

winA3StatusProcMiscMaxValue OBJECT-TYPE
	SYNTAX DisplayString
	ACCESS read-only
	STATUS mandatory
	DESCRIPTION "&<caiWinA3.1011>Current maximum value, dependend from the misc mode, for the misc monitoring of the process watcher. If more than one process fall in the scope of this watcher, this value is the maximum of all instances."
	DEFVAL { "0" }
	::= { winA3StatusProcEntry 40 }

winA3StatusProcMiscMin OBJECT-TYPE
	SYNTAX DisplayString
	ACCESS read-write
	STATUS mandatory
	DESCRIPTION "&<caiWinA3.1012>Current minimum threshold for the miscellaneous data monitoring of the process watcher. This value represents a declining threshold and must be equal to or greater than 0.0, but cannot be greater than the maximum threshold. A value of -1 disables the evaluation of this threshold."
	DEFVAL { "-2" }
	::= { winA3StatusProcEntry 41 }

winA3StatusProcMiscMax OBJECT-TYPE
	SYNTAX DisplayString
	ACCESS read-write
	STATUS mandatory
	DESCRIPTION "&<caiWinA3.1013>Current maximum threshold for the miscellaneous data monitoring of the process watcher. This value represents a rising threshold and must be equal to or greater than 0.0, but cannot be less than the minimum threshold. A value of -1 disables the evaluation of this threshold."
	DEFVAL { "-2" }
	::= { winA3StatusProcEntry 42 }

winA3StatusProcMiscMonitor OBJECT-TYPE
	SYNTAX INTEGER {
		do-not-monitor(1),
		down-warning(2),
		down-critical(3)
	}
	ACCESS read-write
	STATUS mandatory
	DESCRIPTION "&<caiWinA3.1014>Current monitor level for the miscellaneous data monitoring of the process watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusProcEntry 43 }

winA3StatusProcMiscStatus OBJECT-TYPE
	SYNTAX INTEGER {
		unknown(1),
		up(2),
		down-warning(3),
		down-critical(4)
	}
	ACCESS read-only
	STATUS mandatory
	DESCRIPTION "&<caiWinA3.1015>Current status for the miscellaneous data monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusProcEntry 44 }

winA3StatusProcMiscIds OBJECT-TYPE
	SYNTAX DisplayString
	ACCESS read-only
	STATUS mandatory
	DESCRIPTION "&<caiWinA3.1016>A pipe sign separated list of those process IDs that caused a violation of the misc metric thresholds. This list also contains the misc value for each instance (appended as ':value' after each ID) and it is sorted according to the severity of the violation."
	::= { winA3StatusProcEntry 45 }

winA3StatusProcRestartPolicy OBJECT-TYPE
	SYNTAX INTEGER {
		none-should-stop-or-start(1),
		none-should-stop(2),
		none-should-start(3),
		some-should-continue(4),
		none-should-continue(5)
	}
	ACCESS read-write
	STATUS mandatory
	DESCRIPTION "&<caiWinA3.1017>Current monitor policy for the restart monitoring of the process watcher. The status will be set to 'down' according to the following rules: In case none-should-stop-or-start(1), if any process in the scope of the watcher did stop or start since the last poll; in case none-should-stop(2), if any process did stop; in case none-should-start(3), if any process did start; in case some-should-continue(4), if all processes did stop; and in case none-should-continue(5), if at least one process did not stop."
	DEFVAL { 0 }
	::= { winA3StatusProcEntry 46 }

winA3StatusProcRestartMonitor OBJECT-TYPE
	SYNTAX INTEGER {
		do-not-monitor(1),
		down-warning(2),
		down-critical(3)
	}
	ACCESS read-write
	STATUS mandatory
	DESCRIPTION "&<caiWinA3.1018>Current monitor level for the restart monitoring of the process watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusProcEntry 47 }

winA3StatusProcRestartStatus OBJECT-TYPE
	SYNTAX INTEGER {
		unknown(1),
		up(2),
		down-warning(3),
		down-critical(4)
	}
	ACCESS read-only
	STATUS mandatory
	DESCRIPTION "&<caiWinA3.1019>Current status for the restart monitoring of the process watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusProcEntry 48 }

winA3StatusProcRestartIds OBJECT-TYPE
	SYNTAX DisplayString
	ACCESS read-only
	STATUS mandatory
	DESCRIPTION "&<caiWinA3.1020>A pipe sign separated list of those process IDs that caused a violation of the restart policy. This list also contains information whether a process was started (+ID), stopped (-ID) or continued (ID)."
	::= { winA3StatusProcEntry 49 }

winA3StatusProcCallBackRef OBJECT-TYPE
	SYNTAX DisplayString
	ACCESS read-only
	STATUS mandatory
	DESCRIPTION "&<caiWinA3.1021>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusProcEntry 50 }

winA3StatusProcButton OBJECT-TYPE
	SYNTAX INTEGER {
		none(1),
		remove(2),
		reinit(3),
		reset-restart(4)
	}
	ACCESS read-write
	STATUS mandatory
	DESCRIPTION "&<caiWinA3.1022>This attribute is used to remove the process watcher. Additionally, if set to 3 (reinit), the watcher is completely new evaluated. If set to 4 (reset-restart), the status of the restart metric is set to 'up'. If set to 2 (remove), the agent removes the watcher from the table. This attribute cannot be set to 1 (none)."
	DEFVAL { 1 }
	::= { winA3StatusProcEntry 51 }

--
-- The StatusSrvc Group
--

winA3StatusSrvcCount OBJECT-TYPE
	SYNTAX INTEGER
	ACCESS read-only
	STATUS mandatory
	DESCRIPTION "&<caiWinA3.1023>Number of entries in the service status table."
	::= { winA3StatusSrvcGroup 1 }

winA3StatusSrvcTable OBJECT-TYPE
	SYNTAX SEQUENCE OF WinA3StatusSrvcEntry
	ACCESS not-accessible
	STATUS mandatory
	DESCRIPTION "&<caiWinA3.1024>The service status table containing details about the currently configured service watchers."
	::= { winA3StatusSrvcGroup 2 }

winA3StatusSrvcEntry OBJECT-TYPE
	SYNTAX WinA3StatusSrvcEntry
	ACCESS not-accessible
	STATUS mandatory
	DESCRIPTION "&<caiWinA3.1025>Entry in the service status table."
	INDEX {
		winA3StatusSrvcName
	}
	::= { winA3StatusSrvcTable 1 }

WinA3StatusSrvcEntry ::= SEQUENCE {
	winA3StatusSrvcName DisplayString,
	winA3StatusSrvcDescription DisplayString,
	winA3StatusSrvcAutoWatcherName DisplayString,
	winA3StatusSrvcAggLagValue INTEGER,
	winA3StatusSrvcAggLag INTEGER,
	winA3StatusSrvcAggStatus INTEGER,
	winA3StatusSrvcDisplayName DisplayString,
	winA3StatusSrvcStartupType INTEGER,
	winA3StatusSrvcAccount DisplayString,
	winA3StatusSrvcExecutable DisplayString,
	winA3StatusSrvcClusterType INTEGER,
	winA3StatusSrvcConfigValue DisplayString,
	winA3StatusSrvcConfigRef DisplayString,
	winA3StatusSrvcConfigMonitor INTEGER,
	winA3StatusSrvcConfigStatus INTEGER,
	winA3StatusSrvcActiveValue INTEGER,
	winA3StatusSrvcActivePolicy INTEGER,
	winA3StatusSrvcActiveMonitor INTEGER,
	winA3StatusSrvcActiveStatus INTEGER,
	winA3StatusSrvcExistPolicy INTEGER,
	winA3StatusSrvcExistMonitor INTEGER,
	winA3StatusSrvcExistStatus INTEGER,
	winA3StatusSrvcCallBackRef DisplayString,
	winA3StatusSrvcButton INTEGER
}

winA3StatusSrvcName OBJECT-TYPE
	SYNTAX DisplayString
	ACCESS read-only
	STATUS mandatory
	DESCRIPTION "&<caiWinA3.1026>Name of the service. For uniqueness, the service name must be specified as defined in the Windows registry. This name is typically different to the display name of a service, visible in the service manager console."
	::= { winA3StatusSrvcEntry 1 }

winA3StatusSrvcDescription OBJECT-TYPE
	SYNTAX DisplayString
	ACCESS read-write
	STATUS mandatory
	DESCRIPTION "&<caiWinA3.1027>Current description for the service watcher."
	::= { winA3StatusSrvcEntry 2 }

winA3StatusSrvcAutoWatcherName OBJECT-TYPE
	SYNTAX DisplayString
	ACCESS read-only
	STATUS mandatory
	DESCRIPTION "&<caiWinA3.1028>Name of the service auto watcher which automatically created this watcher. This attribute is left blank if the watcher was added manually."
	::= { winA3StatusSrvcEntry 3 }

winA3StatusSrvcAggLagValue OBJECT-TYPE
	SYNTAX INTEGER
	ACCESS read-only
	STATUS mandatory
	DESCRIPTION "&<caiWinA3.1029>Current aggregate lag value of the service watcher. Indicates the consecutive number of times at which any status was not in the ok state. The aggregate status changes from ok as soon as the aggregate lag value reaches the configured value."
	::= { winA3StatusSrvcEntry 4 }

winA3StatusSrvcAggLag OBJECT-TYPE
	SYNTAX INTEGER
	ACCESS read-write
	STATUS mandatory
	DESCRIPTION "&<caiWinA3.1030>Current aggregate lag setting for the service watcher. Specifies the consecutive number of times at which any status is not in the ok state, before the aggregate status changes. This value must be greater than 0."
	::= { winA3StatusSrvcEntry 5 }

winA3StatusSrvcAggStatus OBJECT-TYPE
	SYNTAX INTEGER {
		unknown(1),
		ok(2),
		warning(3),
		critical(4),
		passive(5)
	}
	ACCESS read-only
	STATUS mandatory
	DESCRIPTION "&<caiWinA3.1031>Current aggregate status of the service watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs, or another node in the cluster has resource ownership, in which case the agent on the local node does not actively monitor the resource until ownership is transferred back."
	::= { winA3StatusSrvcEntry 6 }

winA3StatusSrvcDisplayName OBJECT-TYPE
	SYNTAX DisplayString
	ACCESS read-only
	STATUS mandatory
	DESCRIPTION "&<caiWinA3.1032>The display name of a service as visible in the service manager console."
	::= { winA3StatusSrvcEntry 7 }

winA3StatusSrvcStartupType OBJECT-TYPE
	SYNTAX INTEGER {
		automatic(1),
		manual(2),
		disabled(3)
	}
	ACCESS read-only
	STATUS mandatory
	DESCRIPTION "&<caiWinA3.1033>The current startup type (automatic, manual or disabled) of the service."
	::= { winA3StatusSrvcEntry 8 }

winA3StatusSrvcAccount OBJECT-TYPE
	SYNTAX DisplayString
	ACCESS read-only
	STATUS mandatory
	DESCRIPTION "&<caiWinA3.1034>The account, the system uses to start this service."
	::= { winA3StatusSrvcEntry 9 }

winA3StatusSrvcExecutable OBJECT-TYPE
	SYNTAX DisplayString
	ACCESS read-only
	STATUS mandatory
	DESCRIPTION "&<caiWinA3.1035>The executable belonging to this service."
	::= { winA3StatusSrvcEntry 10 }

winA3StatusSrvcClusterType OBJECT-TYPE
	SYNTAX INTEGER {
		not-clustered(1),
		clustered-active(2),
		clustered-passive(3)
	}
	ACCESS read-only
	STATUS mandatory
	DESCRIPTION "&<caiWinA3.1036>Cluster type of the service: 1 (not-clustered) - Resource is not clustered, 2 (clustered-active) - Local cluster node has resource ownership, 3 (clustered-passive) - Another node in the cluster has resource ownership; the agent on the local node does not actively monitor the resource until ownership is transferred back."
	::= { winA3StatusSrvcEntry 11 }

winA3StatusSrvcConfigValue OBJECT-TYPE
	SYNTAX DisplayString
	ACCESS read-only
	STATUS mandatory
	DESCRIPTION "&<caiWinA3.1037>A pipe sign seperated concatenation of the startup type, the account and the executable of the service. This value is compared to the config reference (using a 'should-not-change' policy) to derive the status."
	::= { winA3StatusSrvcEntry 12 }

winA3StatusSrvcConfigRef OBJECT-TYPE
	SYNTAX DisplayString
	ACCESS read-only
	STATUS mandatory
	DESCRIPTION "&<caiWinA3.1038>This attribute is used as the reference the config value is compared with, implicitly using a 'should-not-change' policy. It is a pipe sign seperated concatenation of the startup type, the account and the executable of the service when the watcher was created or when the last time the status button attribute has been set to 'reset-config'."
	::= { winA3StatusSrvcEntry 13 }

winA3StatusSrvcConfigMonitor OBJECT-TYPE
	SYNTAX INTEGER {
		do-not-monitor(1),
		down-warning(2),
		down-critical(3)
	}
	ACCESS read-write
	STATUS mandatory
	DESCRIPTION "&<caiWinA3.1039>Current monitor level for the configuration change monitoring of the service watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusSrvcEntry 14 }

winA3StatusSrvcConfigStatus OBJECT-TYPE
	SYNTAX INTEGER {
		unknown(1),
		up(2),
		down-warning(3),
		down-critical(4)
	}
	ACCESS read-only
	STATUS mandatory
	DESCRIPTION "&<caiWinA3.1040>Current status for the configuration change monitoring of the service watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusSrvcEntry 15 }

winA3StatusSrvcActiveValue OBJECT-TYPE
	SYNTAX INTEGER {
		unknown(1),
		active-running(2),
		active-pausePending(3),
		active-stopPending(4),
		notActive-stopped(5),
		notActive-paused(6),
		notActive-continuePending(7),
		notActive-startPending(8)
	}
	ACCESS read-only
	STATUS mandatory
	DESCRIPTION "&<caiWinA3.1041>The current value of the activity monitoring. This value groups different pending states to one group of 'active' and one group of 'not-active' states."
	::= { winA3StatusSrvcEntry 16 }

winA3StatusSrvcActivePolicy OBJECT-TYPE
	SYNTAX INTEGER {
		should-be-active(1),
		should-not-be-active(2)
	}
	ACCESS read-write
	STATUS mandatory
	DESCRIPTION "&<caiWinA3.1042>Current monitor policy for the activity monitoring of the service watcher."
	DEFVAL { 0 }
	::= { winA3StatusSrvcEntry 17 }

winA3StatusSrvcActiveMonitor OBJECT-TYPE
	SYNTAX INTEGER {
		do-not-monitor(1),
		down-warning(2),
		down-critical(3)
	}
	ACCESS read-write
	STATUS mandatory
	DESCRIPTION "&<caiWinA3.1043>Current monitor level for the activity monitoring of the service watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusSrvcEntry 18 }

winA3StatusSrvcActiveStatus OBJECT-TYPE
	SYNTAX INTEGER {
		unknown(1),
		up(2),
		down-warning(3),
		down-critical(4)
	}
	ACCESS read-only
	STATUS mandatory
	DESCRIPTION "&<caiWinA3.1044>Current status for the activity monitoring of the service watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusSrvcEntry 19 }

winA3StatusSrvcExistPolicy OBJECT-TYPE
	SYNTAX INTEGER {
		should-exist(1),
		should-not-exist(2)
	}
	ACCESS read-write
	STATUS mandatory
	DESCRIPTION "&<caiWinA3.1045>Current monitor policy for the existence monitoring of the service watcher. Specifies how the agent should evaluate the presence or absence of the monitored resource in order to determine whether the resource is in good condition. If set to 1 (should-exist), the resource is expected to be existent. If set to 2 (should-not-exist), the resource is expected to be nonexistent."
	DEFVAL { 0 }
	::= { winA3StatusSrvcEntry 20 }

winA3StatusSrvcExistMonitor OBJECT-TYPE
	SYNTAX INTEGER {
		do-not-monitor(1),
		down-warning(2),
		down-critical(3)
	}
	ACCESS read-write
	STATUS mandatory
	DESCRIPTION "&<caiWinA3.1046>Current monitor level for the existence monitoring of the service watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusSrvcEntry 21 }

winA3StatusSrvcExistStatus OBJECT-TYPE
	SYNTAX INTEGER {
		unknown(1),
		up(2),
		down-warning(3),
		down-critical(4)
	}
	ACCESS read-only
	STATUS mandatory
	DESCRIPTION "&<caiWinA3.1047>Current status for the existence monitoring of the service watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusSrvcEntry 22 }

winA3StatusSrvcCallBackRef OBJECT-TYPE
	SYNTAX DisplayString
	ACCESS read-only
	STATUS mandatory
	DESCRIPTION "&<caiWinA3.1048>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusSrvcEntry 23 }

winA3StatusSrvcButton OBJECT-TYPE
	SYNTAX INTEGER {
		none(1),
		remove(2),
		reset-config(3)
	}
	ACCESS read-write
	STATUS mandatory
	DESCRIPTION "&<caiWinA3.1049>This attribute is used to remove the service watcher. Additionally, if set to 3 (reset-config), the config reference is set to the current config value and the status of the config metric is set to 'up'. If set to 2 (remove), the agent removes the watcher from the table. This attribute cannot be set to 1 (none)."
	DEFVAL { 1 }
	::= { winA3StatusSrvcEntry 24 }

--
-- The StatusJob Group
--

winA3StatusJobCount OBJECT-TYPE
	SYNTAX INTEGER
	ACCESS read-only
	STATUS mandatory
	DESCRIPTION "&<caiWinA3.1050>Number of entries in the job status table."
	::= { winA3StatusJobGroup 1 }

winA3StatusJobTable OBJECT-TYPE
	SYNTAX SEQUENCE OF WinA3StatusJobEntry
	ACCESS not-accessible
	STATUS mandatory
	DESCRIPTION "&<caiWinA3.1051>The job status table containing details about the currently configured job watchers."
	::= { winA3StatusJobGroup 2 }

winA3StatusJobEntry OBJECT-TYPE
	SYNTAX WinA3StatusJobEntry
	ACCESS not-accessible
	STATUS mandatory
	DESCRIPTION "&<caiWinA3.1052>Entry in the job status table."
	INDEX {
		winA3StatusJobName
	}
	::= { winA3StatusJobTable 1 }

WinA3StatusJobEntry ::= SEQUENCE {
	winA3StatusJobName DisplayString,
	winA3StatusJobDescription DisplayString,
	winA3StatusJobAutoWatcherName DisplayString,
	winA3StatusJobAggLagValue INTEGER,
	winA3StatusJobAggLag INTEGER,
	winA3StatusJobAggStatus INTEGER,
	winA3StatusJobProcsValue INTEGER,
	winA3StatusJobProcsMin INTEGER,
	winA3StatusJobProcsMax INTEGER,
	winA3StatusJobProcsMonitor INTEGER,
	winA3StatusJobProcsStatus INTEGER,
	winA3StatusJobSizeValue DisplayString,
	winA3StatusJobSizeWarn DisplayString,
	winA3StatusJobSizeCrit DisplayString,
	winA3StatusJobSizeMonitor INTEGER,
	winA3StatusJobSizeStatus INTEGER,
	winA3StatusJobCpuInterval DisplayString,
	winA3StatusJobCpuValue DisplayString,
	winA3StatusJobCpuWarnValue DisplayString,
	winA3StatusJobCpuCritValue DisplayString,
	winA3StatusJobCpuWarn DisplayString,
	winA3StatusJobCpuCrit DisplayString,
	winA3StatusJobCpuMonitor INTEGER,
	winA3StatusJobCpuStatus INTEGER,
	winA3StatusJobLossAction INTEGER,
	winA3StatusJobLossStatus INTEGER,
	winA3StatusJobCallBackRef DisplayString,
	winA3StatusJobButton INTEGER
}

winA3StatusJobName OBJECT-TYPE
	SYNTAX DisplayString
	ACCESS read-only
	STATUS mandatory
	DESCRIPTION "&<caiWinA3.1053>Name of the job. A job is a set of processes that is handled as a process group."
	::= { winA3StatusJobEntry 1 }

winA3StatusJobDescription OBJECT-TYPE
	SYNTAX DisplayString
	ACCESS read-write
	STATUS mandatory
	DESCRIPTION "&<caiWinA3.1054>Current description for the job watcher."
	::= { winA3StatusJobEntry 2 }

winA3StatusJobAutoWatcherName OBJECT-TYPE
	SYNTAX DisplayString
	ACCESS read-only
	STATUS mandatory
	DESCRIPTION "&<caiWinA3.1055>Name of the job auto watcher which automatically created this watcher. This attribute is left blank if the watcher was added manually."
	::= { winA3StatusJobEntry 3 }

winA3StatusJobAggLagValue OBJECT-TYPE
	SYNTAX INTEGER
	ACCESS read-only
	STATUS mandatory
	DESCRIPTION "&<caiWinA3.1056>Current aggregate lag value of the job watcher. Indicates the consecutive number of times at which any status was not in the ok state. The aggregate status changes from ok as soon as the aggregate lag value reaches the configured value."
	::= { winA3StatusJobEntry 4 }

winA3StatusJobAggLag OBJECT-TYPE
	SYNTAX INTEGER
	ACCESS read-write
	STATUS mandatory
	DESCRIPTION "&<caiWinA3.1057>Current aggregate lag setting for the job watcher. Specifies the consecutive number of times at which any status is not in the ok state, before the aggregate status changes. This value must be greater than 0."
	::= { winA3StatusJobEntry 5 }

winA3StatusJobAggStatus OBJECT-TYPE
	SYNTAX INTEGER {
		unknown(1),
		ok(2),
		warning(3),
		critical(4),
		passive(5)
	}
	ACCESS read-only
	STATUS mandatory
	DESCRIPTION "&<caiWinA3.1058>Current aggregate status of the job watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusJobEntry 6 }

winA3StatusJobProcsValue OBJECT-TYPE
	SYNTAX INTEGER
	ACCESS read-only
	STATUS mandatory
	DESCRIPTION "&<caiWinA3.1059>Current value for the process count monitoring of the job watcher. This is the number of active processes currently belonging to this job."
	::= { winA3StatusJobEntry 7 }

winA3StatusJobProcsMin OBJECT-TYPE
	SYNTAX INTEGER
	ACCESS read-write
	STATUS mandatory
	DESCRIPTION "&<caiWinA3.1060>Current minimum threshold for the process count monitoring of the job watcher. This value represents a declining threshold and must be equal to or greater than 0, but cannot be greater than the maximum threshold. A value of -1 disables the evaluation of this threshold."
	DEFVAL { -2 }
	::= { winA3StatusJobEntry 8 }

winA3StatusJobProcsMax OBJECT-TYPE
	SYNTAX INTEGER
	ACCESS read-write
	STATUS mandatory
	DESCRIPTION "&<caiWinA3.1061>Current maximum threshold for the process count monitoring of the job watcher. This value represents a rising threshold and must be equal to or greater than 0, but cannot be less than the minimum threshold. A value of -1 disables the evaluation of this threshold."
	DEFVAL { -2 }
	::= { winA3StatusJobEntry 9 }

winA3StatusJobProcsMonitor OBJECT-TYPE
	SYNTAX INTEGER {
		do-not-monitor(1),
		down-warning(2),
		down-critical(3)
	}
	ACCESS read-write
	STATUS mandatory
	DESCRIPTION "&<caiWinA3.1062>Current monitor level for the process count monitoring of the job watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusJobEntry 10 }

winA3StatusJobProcsStatus OBJECT-TYPE
	SYNTAX INTEGER {
		unknown(1),
		up(2),
		down-warning(3),
		down-critical(4)
	}
	ACCESS read-only
	STATUS mandatory
	DESCRIPTION "&<caiWinA3.1063>Current status for the process count monitoring of the job watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusJobEntry 11 }

winA3StatusJobSizeValue OBJECT-TYPE
	SYNTAX DisplayString
	ACCESS read-only
	STATUS mandatory
	DESCRIPTION "&<caiWinA3.1064>Current value, in kilobytes, for the size utilization monitoring of the job watcher. This is the size utilization of all active processes currently belonging to this job. It is the sum of real memory size (size of working set in physical memory) and virtual memory size (size of committed pages in the paging file)."
	DEFVAL { "0" }
	::= { winA3StatusJobEntry 12 }

winA3StatusJobSizeWarn OBJECT-TYPE
	SYNTAX DisplayString
	ACCESS read-write
	STATUS mandatory
	DESCRIPTION "&<caiWinA3.1065>Current warning threshold, in kilobytes, for the size utilization monitoring of the job watcher. This value represents a rising threshold and must be greater than 0.0, but cannot be greater than the critical threshold."
	::= { winA3StatusJobEntry 13 }

winA3StatusJobSizeCrit OBJECT-TYPE
	SYNTAX DisplayString
	ACCESS read-write
	STATUS mandatory
	DESCRIPTION "&<caiWinA3.1066>Current critical threshold, in kilobytes, for the size utilization monitoring of the job watcher. This value represents a rising threshold and must be greater than 0.0, but cannot be less than the warning threshold."
	::= { winA3StatusJobEntry 14 }

winA3StatusJobSizeMonitor OBJECT-TYPE
	SYNTAX INTEGER {
		do-not-monitor(1),
		warning-only(2),
		critical-only(3),
		both(4)
	}
	ACCESS read-write
	STATUS mandatory
	DESCRIPTION "&<caiWinA3.1067>Current monitor level for the size utilization monitoring of the job watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusJobEntry 15 }

winA3StatusJobSizeStatus OBJECT-TYPE
	SYNTAX INTEGER {
		unknown(1),
		ok(2),
		warning(3),
		critical(4)
	}
	ACCESS read-only
	STATUS mandatory
	DESCRIPTION "&<caiWinA3.1068>Current status for the size utilization monitoring of the job watcher: 1 (unknown) - An error occurred during data collection, 2 (ok) - The resource is operating within the defined limits or status evaluation is turned off and/or polling is disabled, 3 (warning) - The resource has breached the warning threshold, 4 (critical) - The resource has breached the critical threshold."
	::= { winA3StatusJobEntry 16 }

winA3StatusJobCpuInterval OBJECT-TYPE
	SYNTAX DisplayString
	ACCESS read-write
	STATUS mandatory
	DESCRIPTION "&<caiWinA3.1069>Time, in seconds, defining the total value to use as base for the calculation of the cpu value. This means, the cpu usage of a job, in seconds, refers to this interval. Valid range: Greater 0 or '-1'. If set to '-1', the cpu value is calculated as the cpu usage, in seconds, used up to now by all currently active processes of the job since the start of the agent or the creation of the watcher. If the cpu interval is set to a value greater than the current poll interval and this time is not elapsed for the first time, the CPU value is extrapolated. If the cpu interval is set to a value smaller than the current poll interval, the CPU value is calculated as the appropriate fraction of the value for the last poll interval. If the cpu interval is set to a value greater than the current poll interval and this time is already elapsed, the CPU value is calculated as the sliding sum, i.e. the sum of the value for the current poll interval and the value calculated at the last poll, weighted according to it's fraction of the cpu interval. If the interval is set to '-1', any overloading (%) used for the thresholds will be ignored."
	::= { winA3StatusJobEntry 17 }

winA3StatusJobCpuValue OBJECT-TYPE
	SYNTAX DisplayString
	ACCESS read-only
	STATUS mandatory
	DESCRIPTION "&<caiWinA3.1070>Current value, in seconds, for the cpu utilization monitoring of the job watcher. This is the cpu utilization all active processes currently belonging to this job take in the given CPU interval."
	DEFVAL { "0" }
	::= { winA3StatusJobEntry 18 }

winA3StatusJobCpuWarnValue OBJECT-TYPE
	SYNTAX DisplayString
	ACCESS read-only
	STATUS mandatory
	DESCRIPTION "&<caiWinA3.1071>Active warning threshold, in seconds, as derived from the configured value for the cpu utilization monitoring of the job watcher. This value represents a rising threshold and must be greater than 0.0, less than or equal to the total value (maximum capacity) of the monitored resource as specified in winA3StatusJobCpuInterval, but cannot be greater than the active critical threshold. These constraints will be maintained by the agent during all configuration actions."
	::= { winA3StatusJobEntry 19 }

winA3StatusJobCpuCritValue OBJECT-TYPE
	SYNTAX DisplayString
	ACCESS read-only
	STATUS mandatory
	DESCRIPTION "&<caiWinA3.1072>Active critical threshold, in seconds, as derived from the configured value for the cpu utilization monitoring of the job watcher. This value represents a rising threshold and must be greater than 0.0, less than or equal to the total value (maximum capacity) of the monitored resource as specified in winA3StatusJobCpuInterval, but cannot be less than the active warning threshold. These constraints will be maintained by the agent during all configuration actions."
	::= { winA3StatusJobEntry 20 }

winA3StatusJobCpuWarn OBJECT-TYPE
	SYNTAX DisplayString
	ACCESS read-write
	STATUS mandatory
	DESCRIPTION "&<caiWinA3.1073>Configured warning threshold from which the active warning threshold is derived for the cpu utilization monitoring of the job watcher. The threshold can be specified as either an absolute value (n) or a percentage (n%). The value of winA3StatusJobCpuInterval will be the reference value for n% notations."
	::= { winA3StatusJobEntry 21 }

winA3StatusJobCpuCrit OBJECT-TYPE
	SYNTAX DisplayString
	ACCESS read-write
	STATUS mandatory
	DESCRIPTION "&<caiWinA3.1074>Configured critical threshold from which the active critical threshold is derived for the cpu utilization monitoring of the job watcher. The threshold can be specified as either an absolute value (n) or a percentage (n%). The value of winA3StatusJobCpuInterval will be the reference value for n% notations."
	::= { winA3StatusJobEntry 22 }

winA3StatusJobCpuMonitor OBJECT-TYPE
	SYNTAX INTEGER {
		do-not-monitor(1),
		warning-only(2),
		critical-only(3),
		both(4)
	}
	ACCESS read-write
	STATUS mandatory
	DESCRIPTION "&<caiWinA3.1075>Current monitor level for the cpu utilization monitoring of the job watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusJobEntry 23 }

winA3StatusJobCpuStatus OBJECT-TYPE
	SYNTAX INTEGER {
		unknown(1),
		ok(2),
		warning(3),
		critical(4)
	}
	ACCESS read-only
	STATUS mandatory
	DESCRIPTION "&<caiWinA3.1076>Current status for the cpu utilization monitoring of the job watcher: 1 (unknown) - An error occurred during data collection, 2 (ok) - The resource is operating within the defined limits or status evaluation is turned off and/or polling is disabled, 3 (warning) - The resource has breached the warning threshold, 4 (critical) - The resource has breached the critical threshold."
	::= { winA3StatusJobEntry 24 }

winA3StatusJobLossAction OBJECT-TYPE
	SYNTAX INTEGER {
		remove(1),
		up(2),
		down-warning(3),
		down-critical(4)
	}
	ACCESS read-write
	STATUS mandatory
	DESCRIPTION "&<caiWinA3.1077>Current loss action for the job watcher. Specifies the action to take if the monitored job is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusJobEntry 25 }

winA3StatusJobLossStatus OBJECT-TYPE
	SYNTAX INTEGER {
		unknown(1),
		up(2),
		down-warning(3),
		down-critical(4)
	}
	ACCESS read-only
	STATUS mandatory
	DESCRIPTION "&<caiWinA3.1078>Current loss status of the job watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusJobEntry 26 }

winA3StatusJobCallBackRef OBJECT-TYPE
	SYNTAX DisplayString
	ACCESS read-only
	STATUS mandatory
	DESCRIPTION "&<caiWinA3.1079>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusJobEntry 27 }

winA3StatusJobButton OBJECT-TYPE
	SYNTAX INTEGER {
		none(1),
		remove(2)
	}
	ACCESS read-write
	STATUS mandatory
	DESCRIPTION "&<caiWinA3.1080>This attribute is used to remove the job watcher. If set to 2 (remove), the agent removes the watcher from the table. This attribute cannot be set to 1 (none)."
	DEFVAL { 1 }
	::= { winA3StatusJobEntry 28 }

--
-- The StatusSess Group
--

winA3StatusSessCount OBJECT-TYPE
	SYNTAX INTEGER
	ACCESS read-only
	STATUS mandatory
	DESCRIPTION "&<caiWinA3.1081>Number of entries in the terminal session status table."
	::= { winA3StatusSessGroup 1 }

winA3StatusSessTable OBJECT-TYPE
	SYNTAX SEQUENCE OF WinA3StatusSessEntry
	ACCESS not-accessible
	STATUS mandatory
	DESCRIPTION "&<caiWinA3.1082>The terminal session status table containing details about the currently configured terminal session watchers."
	::= { winA3StatusSessGroup 2 }

winA3StatusSessEntry OBJECT-TYPE
	SYNTAX WinA3StatusSessEntry
	ACCESS not-accessible
	STATUS mandatory
	DESCRIPTION "&<caiWinA3.1083>Entry in the terminal session status table."
	INDEX {
		winA3StatusSessWatcherName
	}
	::= { winA3StatusSessTable 1 }

WinA3StatusSessEntry ::= SEQUENCE {
	winA3StatusSessWatcherName DisplayString,
	winA3StatusSessMatchType INTEGER,
	winA3StatusSessClient DisplayString,
	winA3StatusSessUser DisplayString,
	winA3StatusSessEvalPolicy INTEGER,
	winA3StatusSessDescription DisplayString,
	winA3StatusSessAggLagValue INTEGER,
	winA3StatusSessAggLag INTEGER,
	winA3StatusSessAggStatus INTEGER,
	winA3StatusSessInstValue INTEGER,
	winA3StatusSessInstMin INTEGER,
	winA3StatusSessInstMax INTEGER,
	winA3StatusSessInstMonitor INTEGER,
	winA3StatusSessInstStatus INTEGER,
	winA3StatusSessInstIds DisplayString,
	winA3StatusSessSizeValue DisplayString,
	winA3StatusSessSizeWarn DisplayString,
	winA3StatusSessSizeCrit DisplayString,
	winA3StatusSessSizeMonitor INTEGER,
	winA3StatusSessSizeStatus INTEGER,
	winA3StatusSessSizeIds DisplayString,
	winA3StatusSessCpuInterval DisplayString,
	winA3StatusSessCpuValue DisplayString,
	winA3StatusSessCpuWarnValue DisplayString,
	winA3StatusSessCpuCritValue DisplayString,
	winA3StatusSessCpuWarn DisplayString,
	winA3StatusSessCpuCrit DisplayString,
	winA3StatusSessCpuMonitor INTEGER,
	winA3StatusSessCpuStatus INTEGER,
	winA3StatusSessCpuIds DisplayString,
	winA3StatusSessCallBackRef DisplayString,
	winA3StatusSessButton INTEGER
}

winA3StatusSessWatcherName OBJECT-TYPE
	SYNTAX DisplayString
	ACCESS read-only
	STATUS mandatory
	DESCRIPTION "&<caiWinA3.1084>An arbitrary name for the watcher. Note that monitoring of sessions is not applicable on Windows XP and on Windows 2000 Professional."
	::= { winA3StatusSessEntry 1 }

winA3StatusSessMatchType OBJECT-TYPE
	SYNTAX INTEGER {
		positive-regular-expression(1),
		negative-regular-expression(2),
		positive-string-compare(3),
		negative-string-compare(4)
	}
	ACCESS read-write
	STATUS mandatory
	DESCRIPTION "&<caiWinA3.1085>Current search algorithm for the terminal session watcher. The filter is the logical AND of all attributes used to identify or otherwise narrow down resources. If the value of one of these attributes includes 'wildcards', then the watcher will basically behave like a one-to-many watcher, i.e. it may monitor two or more resources simultaneously. If set to 1 (positive-regular-expression), the agent searches for terminal session resources that match the filter as a regular expression (case-insensitive). If set to 2 (negative-regular-expression), the agent searches for terminal session resources that do not match the filter as a regular expression (case-insensitive). If set to 3 (positive-string-compare), the agent searches for terminal session resources that match the filter as string comparison (case-insensitive). If set to 4 (negative-string-compare), the agent searches for terminal session resources that do not match the filter as string comparison (case-insensitive)."
	DEFVAL { 0 }
	::= { winA3StatusSessEntry 2 }

winA3StatusSessClient OBJECT-TYPE
	SYNTAX DisplayString
	ACCESS read-write
	STATUS mandatory
	DESCRIPTION "&<caiWinA3.1086>Client name of the session. The client name is the name of the host, from where this session was initiated. This name is used as a filter element for one-to-many monitoring (one watcher monitors several resources simultaneously) and can be a regular expression (case-insensitive). The expression '.*' always matches any string, independent from the match type. Note that monitoring of sessions is not applicable on Windows XP and on Windows 2000 Professional."
	::= { winA3StatusSessEntry 3 }

winA3StatusSessUser OBJECT-TYPE
	SYNTAX DisplayString
	ACCESS read-write
	STATUS mandatory
	DESCRIPTION "&<caiWinA3.1087>User name of the session. The user name specifies the user, who logged in and is in the form 'domainName\\userName'. This name is used as a filter element for one-to-many monitoring (one watcher monitors several resources simultaneously) and can be a regular expression (case-insensitive). The expression '.*' always matches any string, independent from the match type. Note that monitoring of sessions is not applicable on Windows XP and on Windows 2000 Professional."
	::= { winA3StatusSessEntry 4 }

winA3StatusSessEvalPolicy OBJECT-TYPE
	SYNTAX INTEGER {
		individual(1),
		min(2),
		max(3),
		sum(4),
		avg(5)
	}
	ACCESS read-write
	STATUS mandatory
	DESCRIPTION "&<caiWinA3.1088>Current evaluation policy for the terminal session watcher. Defines how metric values will be calculated and 'culprits' be determined if two or more terminal session resources fall into the monitoring scope of a one-to-many watcher. If set to 1 (individual), metric values will be set to the worst values (lowest and/or highest) of all terminal session instances; if the value of a metric violates the threshold condition, the respective 'culprits' list will contain all instances individually violating the most severe threshold. If set to 2 (min), metric values will be set to the lowest (minimum) values of all terminal session instances; if the value of a metric violates the threshold condition, the respective 'culprits' list will contain all instances having the same minimum value. If set to 3 (max), metric values will be set to the highest (maximum) values of all terminal session instances; if the value of a metric violates the threshold condition, the respective 'culprits' list will contain all instances having the same maximum value. If set to 4 (sum), metric values will be set to the cumulative values (sum) of all terminal session instances; if the value of a metric violates the threshold condition, the respective 'culprits' list will contain all instances. If set to 5 (avg), metric values will be set to the average values of all terminal session instances; if the value of a metric violates the threshold condition, the respective 'culprits' list will contain all instances individually violating the most severe threshold."
	DEFVAL { 0 }
	::= { winA3StatusSessEntry 5 }

winA3StatusSessDescription OBJECT-TYPE
	SYNTAX DisplayString
	ACCESS read-write
	STATUS mandatory
	DESCRIPTION "&<caiWinA3.1089>Current description for the terminal session watcher."
	::= { winA3StatusSessEntry 6 }

winA3StatusSessAggLagValue OBJECT-TYPE
	SYNTAX INTEGER
	ACCESS read-only
	STATUS mandatory
	DESCRIPTION "&<caiWinA3.1090>Current aggregate lag value of the terminal session watcher. Indicates the consecutive number of times at which any status was not in the ok state. The aggregate status changes from ok as soon as the aggregate lag value reaches the configured value."
	::= { winA3StatusSessEntry 7 }

winA3StatusSessAggLag OBJECT-TYPE
	SYNTAX INTEGER
	ACCESS read-write
	STATUS mandatory
	DESCRIPTION "&<caiWinA3.1091>Current aggregate lag setting for the terminal session watcher. Specifies the consecutive number of times at which any status is not in the ok state, before the aggregate status changes. This value must be greater than 0."
	::= { winA3StatusSessEntry 8 }

winA3StatusSessAggStatus OBJECT-TYPE
	SYNTAX INTEGER {
		unknown(1),
		ok(2),
		warning(3),
		critical(4),
		passive(5)
	}
	ACCESS read-only
	STATUS mandatory
	DESCRIPTION "&<caiWinA3.1092>Current aggregate status of the terminal session watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusSessEntry 9 }

winA3StatusSessInstValue OBJECT-TYPE
	SYNTAX INTEGER
	ACCESS read-only
	STATUS mandatory
	DESCRIPTION "&<caiWinA3.1093>Current value for the instance count monitoring of the terminal session watcher. This is the number of sessions that fall in the scope of this watcher, i.e. that match the filter conditions and hence are monitored simultaneously by this watcher."
	::= { winA3StatusSessEntry 10 }

winA3StatusSessInstMin OBJECT-TYPE
	SYNTAX INTEGER
	ACCESS read-write
	STATUS mandatory
	DESCRIPTION "&<caiWinA3.1094>Current minimum threshold for the instance count monitoring of the terminal session watcher. This value represents a declining threshold and must be equal to or greater than 0, but cannot be greater than the maximum threshold. A value of -1 disables the evaluation of this threshold."
	DEFVAL { -2 }
	::= { winA3StatusSessEntry 11 }

winA3StatusSessInstMax OBJECT-TYPE
	SYNTAX INTEGER
	ACCESS read-write
	STATUS mandatory
	DESCRIPTION "&<caiWinA3.1095>Current maximum threshold for the instance count monitoring of the terminal session watcher. This value represents a rising threshold and must be equal to or greater than 0, but cannot be less than the minimum threshold. A value of -1 disables the evaluation of this threshold."
	DEFVAL { -2 }
	::= { winA3StatusSessEntry 12 }

winA3StatusSessInstMonitor OBJECT-TYPE
	SYNTAX INTEGER {
		do-not-monitor(1),
		down-warning(2),
		down-critical(3)
	}
	ACCESS read-write
	STATUS mandatory
	DESCRIPTION "&<caiWinA3.1096>Current monitor level for the instance count monitoring of the terminal session watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusSessEntry 13 }

winA3StatusSessInstStatus OBJECT-TYPE
	SYNTAX INTEGER {
		unknown(1),
		up(2),
		down-warning(3),
		down-critical(4)
	}
	ACCESS read-only
	STATUS mandatory
	DESCRIPTION "&<caiWinA3.1097>Current status for the instance count monitoring of the terminal session watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusSessEntry 14 }

winA3StatusSessInstIds OBJECT-TYPE
	SYNTAX DisplayString
	ACCESS read-only
	STATUS mandatory
	DESCRIPTION "&<caiWinA3.1098>A pipe sign separated list of those session IDs that caused a violation of the instance metric thresholds."
	::= { winA3StatusSessEntry 15 }

winA3StatusSessSizeValue OBJECT-TYPE
	SYNTAX DisplayString
	ACCESS read-only
	STATUS mandatory
	DESCRIPTION "&<caiWinA3.1099>Current value, in kilobytes, for the size utilization monitoring of the terminal session watcher. This is the size utilization of all active processes currently belonging to this session.It is the sum of real memory size (size of working set in physical memory) and virtual memory size (size of committed pages in the paging file)."
	DEFVAL { "0" }
	::= { winA3StatusSessEntry 16 }

winA3StatusSessSizeWarn OBJECT-TYPE
	SYNTAX DisplayString
	ACCESS read-write
	STATUS mandatory
	DESCRIPTION "&<caiWinA3.1100>Current warning threshold, in kilobytes, for the size utilization monitoring of the terminal session watcher. This value represents a rising threshold and must be greater than 0.0, but cannot be greater than the critical threshold."
	::= { winA3StatusSessEntry 17 }

winA3StatusSessSizeCrit OBJECT-TYPE
	SYNTAX DisplayString
	ACCESS read-write
	STATUS mandatory
	DESCRIPTION "&<caiWinA3.1101>Current critical threshold, in kilobytes, for the size utilization monitoring of the terminal session watcher. This value represents a rising threshold and must be greater than 0.0, but cannot be less than the warning threshold."
	::= { winA3StatusSessEntry 18 }

winA3StatusSessSizeMonitor OBJECT-TYPE
	SYNTAX INTEGER {
		do-not-monitor(1),
		warning-only(2),
		critical-only(3),
		both(4)
	}
	ACCESS read-write
	STATUS mandatory
	DESCRIPTION "&<caiWinA3.1102>Current monitor level for the size utilization monitoring of the terminal session watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusSessEntry 19 }

winA3StatusSessSizeStatus OBJECT-TYPE
	SYNTAX INTEGER {
		unknown(1),
		ok(2),
		warning(3),
		critical(4)
	}
	ACCESS read-only
	STATUS mandatory
	DESCRIPTION "&<caiWinA3.1103>Current status for the size utilization monitoring of the terminal session watcher: 1 (unknown) - An error occurred during data collection, 2 (ok) - The resource is operating within the defined limits or status evaluation is turned off and/or polling is disabled, 3 (warning) - The resource has breached the warning threshold, 4 (critical) - The resource has breached the critical threshold."
	::= { winA3StatusSessEntry 20 }

winA3StatusSessSizeIds OBJECT-TYPE
	SYNTAX DisplayString
	ACCESS read-only
	STATUS mandatory
	DESCRIPTION "&<caiWinA3.1104>A pipe sign separated list of those session IDs that caused a violation of the size metric thresholds. This list also contains the size value for each instance (appended as ':value' after each ID) and it is sorted according to the severity of the violation."
	::= { winA3StatusSessEntry 21 }

winA3StatusSessCpuInterval OBJECT-TYPE
	SYNTAX DisplayString
	ACCESS read-write
	STATUS mandatory
	DESCRIPTION "&<caiWinA3.1105>Time, in seconds, defining the total value to use as base for the calculation of the cpu value. This means, the cpu usage of a session, in seconds, refers to this interval. Valid range: Greater 0 or '-1'. If set to '-1', the cpu value is calculated as the cpu usage, in seconds, used up to now by all currently active processes of the session since the start of the agent or the creation of the watcher. If the cpu interval is set to a value greater than the current poll interval and this time is not elapsed for the first time, the CPU value is extrapolated. If the cpu interval is set to a value smaller than the current poll interval, the CPU value is calculated as the appropriate fraction of the value for the last poll interval. If the cpu interval is set to a value greater than the current poll interval and this time is already elapsed, the CPU value is calculated as the sliding sum, i.e. the sum of the value for the current poll interval and the value calculated at the last poll, weighted according to it's fraction of the cpu interval. If the interval is set to '-1', any overloading (%) used for the thresholds will be ignored."
	::= { winA3StatusSessEntry 22 }

winA3StatusSessCpuValue OBJECT-TYPE
	SYNTAX DisplayString
	ACCESS read-only
	STATUS mandatory
	DESCRIPTION "&<caiWinA3.1106>Current value, in seconds, for the cpu utilization monitoring of the terminal session watcher. This is the cpu utilization all active processes currently belonging to this session take in the given CPU interval."
	DEFVAL { "0" }
	::= { winA3StatusSessEntry 23 }

winA3StatusSessCpuWarnValue OBJECT-TYPE
	SYNTAX DisplayString
	ACCESS read-only
	STATUS mandatory
	DESCRIPTION "&<caiWinA3.1107>Active warning threshold, in seconds, as derived from the configured value for the cpu utilization monitoring of the terminal session watcher. This value represents a rising threshold and must be greater than 0.0, less than or equal to the total value (maximum capacity) of the monitored resource as specified in winA3StatusSessCpuInterval, but cannot be greater than the active critical threshold. These constraints will be maintained by the agent during all configuration actions."
	::= { winA3StatusSessEntry 24 }

winA3StatusSessCpuCritValue OBJECT-TYPE
	SYNTAX DisplayString
	ACCESS read-only
	STATUS mandatory
	DESCRIPTION "&<caiWinA3.1108>Active critical threshold, in seconds, as derived from the configured value for the cpu utilization monitoring of the terminal session watcher. This value represents a rising threshold and must be greater than 0.0, less than or equal to the total value (maximum capacity) of the monitored resource as specified in winA3StatusSessCpuInterval, but cannot be less than the active warning threshold. These constraints will be maintained by the agent during all configuration actions."
	::= { winA3StatusSessEntry 25 }

winA3StatusSessCpuWarn OBJECT-TYPE
	SYNTAX DisplayString
	ACCESS read-write
	STATUS mandatory
	DESCRIPTION "&<caiWinA3.1109>Configured warning threshold from which the active warning threshold is derived for the cpu utilization monitoring of the terminal session watcher. The threshold can be specified as either an absolute value (n) or a percentage (n%). The value of winA3StatusSessCpuInterval will be the reference value for n% notations."
	::= { winA3StatusSessEntry 26 }

winA3StatusSessCpuCrit OBJECT-TYPE
	SYNTAX DisplayString
	ACCESS read-write
	STATUS mandatory
	DESCRIPTION "&<caiWinA3.1110>Configured critical threshold from which the active critical threshold is derived for the cpu utilization monitoring of the terminal session watcher. The threshold can be specified as either an absolute value (n) or a percentage (n%). The value of winA3StatusSessCpuInterval will be the reference value for n% notations."
	::= { winA3StatusSessEntry 27 }

winA3StatusSessCpuMonitor OBJECT-TYPE
	SYNTAX INTEGER {
		do-not-monitor(1),
		warning-only(2),
		critical-only(3),
		both(4)
	}
	ACCESS read-write
	STATUS mandatory
	DESCRIPTION "&<caiWinA3.1111>Current monitor level for the cpu utilization monitoring of the terminal session watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusSessEntry 28 }

winA3StatusSessCpuStatus OBJECT-TYPE
	SYNTAX INTEGER {
		unknown(1),
		ok(2),
		warning(3),
		critical(4)
	}
	ACCESS read-only
	STATUS mandatory
	DESCRIPTION "&<caiWinA3.1112>Current status for the cpu utilization monitoring of the terminal session watcher: 1 (unknown) - An error occurred during data collection, 2 (ok) - The resource is operating within the defined limits or status evaluation is turned off and/or polling is disabled, 3 (warning) - The resource has breached the warning threshold, 4 (critical) - The resource has breached the critical threshold."
	::= { winA3StatusSessEntry 29 }

winA3StatusSessCpuIds OBJECT-TYPE
	SYNTAX DisplayString
	ACCESS read-only
	STATUS mandatory
	DESCRIPTION "&<caiWinA3.1113>A pipe sign separated list of those session IDs that caused a violation of the cpu metric thresholds. This list also contains the cpu value for each instance (appended as ':value' after each ID) and it is sorted according to the severity of the violation."
	::= { winA3StatusSessEntry 30 }

winA3StatusSessCallBackRef OBJECT-TYPE
	SYNTAX DisplayString
	ACCESS read-only
	STATUS mandatory
	DESCRIPTION "&<caiWinA3.1114>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusSessEntry 31 }

winA3StatusSessButton OBJECT-TYPE
	SYNTAX INTEGER {
		none(1),
		remove(2),
		reinit(3)
	}
	ACCESS read-write
	STATUS mandatory
	DESCRIPTION "&<caiWinA3.1115>This attribute is used to remove the terminal session watcher. Additionally, if set to 3 (reinit), the watcher is completely new evaluated. If set to 2 (remove), the agent removes the watcher from the table. This attribute cannot be set to 1 (none)."
	DEFVAL { 1 }
	::= { winA3StatusSessEntry 32 }

--
-- The StatusPrn Group
--

winA3StatusPrnCount OBJECT-TYPE
	SYNTAX INTEGER
	ACCESS read-only
	STATUS mandatory
	DESCRIPTION "&<caiWinA3.1116>Number of entries in the printer status table."
	::= { winA3StatusPrnGroup 1 }

winA3StatusPrnTable OBJECT-TYPE
	SYNTAX SEQUENCE OF WinA3StatusPrnEntry
	ACCESS not-accessible
	STATUS mandatory
	DESCRIPTION "&<caiWinA3.1117>The printer status table containing details about the currently configured printer watchers."
	::= { winA3StatusPrnGroup 2 }

winA3StatusPrnEntry OBJECT-TYPE
	SYNTAX WinA3StatusPrnEntry
	ACCESS not-accessible
	STATUS mandatory
	DESCRIPTION "&<caiWinA3.1118>Entry in the printer status table."
	INDEX {
		winA3StatusPrnName
	}
	::= { winA3StatusPrnTable 1 }

WinA3StatusPrnEntry ::= SEQUENCE {
	winA3StatusPrnName DisplayString,
	winA3StatusPrnDescription DisplayString,
	winA3StatusPrnAutoWatcherName DisplayString,
	winA3StatusPrnAggLagValue INTEGER,
	winA3StatusPrnAggLag INTEGER,
	winA3StatusPrnAggStatus INTEGER,
	winA3StatusPrnEventValue INTEGER,
	winA3StatusPrnEventMonitor INTEGER,
	winA3StatusPrnEventStatus INTEGER,
	winA3StatusPrnQueueValue INTEGER,
	winA3StatusPrnQueueWarn INTEGER,
	winA3StatusPrnQueueCrit INTEGER,
	winA3StatusPrnQueueMonitor INTEGER,
	winA3StatusPrnQueueStatus INTEGER,
	winA3StatusPrnLossAction INTEGER,
	winA3StatusPrnLossStatus INTEGER,
	winA3StatusPrnCallBackRef DisplayString,
	winA3StatusPrnButton INTEGER
}

winA3StatusPrnName OBJECT-TYPE
	SYNTAX DisplayString
	ACCESS read-only
	STATUS mandatory
	DESCRIPTION "&<caiWinA3.1119>Name of the printer."
	::= { winA3StatusPrnEntry 1 }

winA3StatusPrnDescription OBJECT-TYPE
	SYNTAX DisplayString
	ACCESS read-write
	STATUS mandatory
	DESCRIPTION "&<caiWinA3.1120>Current description for the printer watcher."
	::= { winA3StatusPrnEntry 2 }

winA3StatusPrnAutoWatcherName OBJECT-TYPE
	SYNTAX DisplayString
	ACCESS read-only
	STATUS mandatory
	DESCRIPTION "&<caiWinA3.1121>Name of the printer auto watcher which automatically created this watcher. This attribute is left blank if the watcher was added manually."
	::= { winA3StatusPrnEntry 3 }

winA3StatusPrnAggLagValue OBJECT-TYPE
	SYNTAX INTEGER
	ACCESS read-only
	STATUS mandatory
	DESCRIPTION "&<caiWinA3.1122>Current aggregate lag value of the printer watcher. Indicates the consecutive number of times at which any status was not in the ok state. The aggregate status changes from ok as soon as the aggregate lag value reaches the configured value."
	::= { winA3StatusPrnEntry 4 }

winA3StatusPrnAggLag OBJECT-TYPE
	SYNTAX INTEGER
	ACCESS read-write
	STATUS mandatory
	DESCRIPTION "&<caiWinA3.1123>Current aggregate lag setting for the printer watcher. Specifies the consecutive number of times at which any status is not in the ok state, before the aggregate status changes. This value must be greater than 0."
	::= { winA3StatusPrnEntry 5 }

winA3StatusPrnAggStatus OBJECT-TYPE
	SYNTAX INTEGER {
		unknown(1),
		ok(2),
		warning(3),
		critical(4),
		passive(5)
	}
	ACCESS read-only
	STATUS mandatory
	DESCRIPTION "&<caiWinA3.1124>Current aggregate status of the printer watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusPrnEntry 6 }

winA3StatusPrnEventValue OBJECT-TYPE
	SYNTAX INTEGER {
		unknown-no-print-jobs(1),
		printing(2),
		paper-error(3),
		toner-error(4),
		manual(5),
		offline(6),
		paused(7),
		software-error(8),
		general-error(9)
	}
	ACCESS read-only
	STATUS mandatory
	DESCRIPTION "&<caiWinA3.1125>The value of the last printer event. The system can only determine printer events if there is a printing job in the print queue."
	::= { winA3StatusPrnEntry 7 }

winA3StatusPrnEventMonitor OBJECT-TYPE
	SYNTAX INTEGER {
		do-not-monitor(1),
		down-warning(2),
		down-critical(3)
	}
	ACCESS read-write
	STATUS mandatory
	DESCRIPTION "&<caiWinA3.1126>Current monitor level for the event monitoring of the printer watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusPrnEntry 8 }

winA3StatusPrnEventStatus OBJECT-TYPE
	SYNTAX INTEGER {
		unknown(1),
		up(2),
		down-warning(3),
		down-critical(4)
	}
	ACCESS read-only
	STATUS mandatory
	DESCRIPTION "&<caiWinA3.1127>Current status for the event monitoring of the printer watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusPrnEntry 9 }

winA3StatusPrnQueueValue OBJECT-TYPE
	SYNTAX INTEGER
	ACCESS read-only
	STATUS mandatory
	DESCRIPTION "&<caiWinA3.1128>Current value for the queue size monitoring of the printer watcher. This is the current number of print jobs in the print queue."
	::= { winA3StatusPrnEntry 10 }

winA3StatusPrnQueueWarn OBJECT-TYPE
	SYNTAX INTEGER
	ACCESS read-write
	STATUS mandatory
	DESCRIPTION "&<caiWinA3.1129>Current warning threshold for the queue size monitoring of the printer watcher. This value represents a rising threshold and must be greater than 0, but cannot be greater than the critical threshold."
	::= { winA3StatusPrnEntry 11 }

winA3StatusPrnQueueCrit OBJECT-TYPE
	SYNTAX INTEGER
	ACCESS read-write
	STATUS mandatory
	DESCRIPTION "&<caiWinA3.1130>Current critical threshold for the queue size monitoring of the printer watcher. This value represents a rising threshold and must be greater than 0, but cannot be less than the warning threshold."
	::= { winA3StatusPrnEntry 12 }

winA3StatusPrnQueueMonitor OBJECT-TYPE
	SYNTAX INTEGER {
		do-not-monitor(1),
		warning-only(2),
		critical-only(3),
		both(4)
	}
	ACCESS read-write
	STATUS mandatory
	DESCRIPTION "&<caiWinA3.1131>Current monitor level for the queue size monitoring of the printer watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusPrnEntry 13 }

winA3StatusPrnQueueStatus OBJECT-TYPE
	SYNTAX INTEGER {
		unknown(1),
		ok(2),
		warning(3),
		critical(4)
	}
	ACCESS read-only
	STATUS mandatory
	DESCRIPTION "&<caiWinA3.1132>Current status for the queue size monitoring of the printer watcher: 1 (unknown) - An error occurred during data collection, 2 (ok) - The resource is operating within the defined limits or status evaluation is turned off and/or polling is disabled, 3 (warning) - The resource has breached the warning threshold, 4 (critical) - The resource has breached the critical threshold."
	::= { winA3StatusPrnEntry 14 }

winA3StatusPrnLossAction OBJECT-TYPE
	SYNTAX INTEGER {
		remove(1),
		up(2),
		down-warning(3),
		down-critical(4)
	}
	ACCESS read-write
	STATUS mandatory
	DESCRIPTION "&<caiWinA3.1133>Current loss action for the printer watcher. Specifies the action to take if the monitored printer is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusPrnEntry 15 }

winA3StatusPrnLossStatus OBJECT-TYPE
	SYNTAX INTEGER {
		unknown(1),
		up(2),
		down-warning(3),
		down-critical(4)
	}
	ACCESS read-only
	STATUS mandatory
	DESCRIPTION "&<caiWinA3.1134>Current loss status of the printer watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusPrnEntry 16 }

winA3StatusPrnCallBackRef OBJECT-TYPE
	SYNTAX DisplayString
	ACCESS read-only
	STATUS mandatory
	DESCRIPTION "&<caiWinA3.1135>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusPrnEntry 17 }

winA3StatusPrnButton OBJECT-TYPE
	SYNTAX INTEGER {
		none(1),
		remove(2)
	}
	ACCESS read-write
	STATUS mandatory
	DESCRIPTION "&<caiWinA3.1136>This attribute is used to remove the printer watcher. If set to 2 (remove), the agent removes the watcher from the table. This attribute cannot be set to 1 (none)."
	DEFVAL { 1 }
	::= { winA3StatusPrnEntry 18 }

--
-- The StatusNet Group
--

winA3StatusNetTotalAggLagValue OBJECT-TYPE
	SYNTAX INTEGER
	ACCESS read-only
	STATUS mandatory
	DESCRIPTION "&<caiWinA3.1137>Current aggregate lag value of the network interface watcher. Indicates the consecutive number of times at which any status was not in the ok state. The aggregate status changes from ok as soon as the aggregate lag value reaches the configured value."
	::= { winA3StatusNetGroup 1 }

winA3StatusNetTotalAggLag OBJECT-TYPE
	SYNTAX INTEGER
	ACCESS read-write
	STATUS mandatory
	DESCRIPTION "&<caiWinA3.1138>Current aggregate lag setting for the network interface watcher. Specifies the consecutive number of times at which any status is not in the ok state, before the aggregate status changes. This value must be greater than 0."
	DEFVAL { 10 }
	::= { winA3StatusNetGroup 2 }

winA3StatusNetTotalAggStatus OBJECT-TYPE
	SYNTAX INTEGER {
		unknown(1),
		ok(2),
		warning(3),
		critical(4),
		passive(5)
	}
	ACCESS read-only
	STATUS mandatory
	DESCRIPTION "&<caiWinA3.1139>Current aggregate status of the network interface watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusNetGroup 3 }

winA3StatusNetTotalInBytesValue OBJECT-TYPE
	SYNTAX DisplayString
	ACCESS read-only
	STATUS mandatory
	DESCRIPTION "&<caiWinA3.1140>Current value, in bytes/sec, for the total received bytes monitoring of the network interface watcher. This is the sum of all network interfaces."
	DEFVAL { "0" }
	::= { winA3StatusNetGroup 4 }

winA3StatusNetTotalInBytesWarnMin OBJECT-TYPE
	SYNTAX DisplayString
	ACCESS read-write
	STATUS mandatory
	DESCRIPTION "&<caiWinA3.1141>Current warning minimum threshold, in bytes/sec, for the total received bytes monitoring of the network interface watcher. This value represents a declining threshold and must be equal to or greater than 0.0, equal to or greater than the critical minimum threshold, but cannot be greater than the warning maximum threshold. A value of -1 disables the evaluation of this threshold."
	DEFVAL { "-1" }
	::= { winA3StatusNetGroup 5 }

winA3StatusNetTotalInBytesWarnMax OBJECT-TYPE
	SYNTAX DisplayString
	ACCESS read-write
	STATUS mandatory
	DESCRIPTION "&<caiWinA3.1142>Current warning maximum threshold, in bytes/sec, for the total received bytes monitoring of the network interface watcher. This value represents a rising threshold and must be equal to or greater than 0.0, equal to or greater than the warning minimum threshold, but cannot be greater than the critical maximum threshold. A value of -1 disables the evaluation of this threshold."
	DEFVAL { "2000000.0" }
	::= { winA3StatusNetGroup 6 }

winA3StatusNetTotalInBytesCritMin OBJECT-TYPE
	SYNTAX DisplayString
	ACCESS read-write
	STATUS mandatory
	DESCRIPTION "&<caiWinA3.1143>Current critical minimum threshold, in bytes/sec, for the total received bytes monitoring of the network interface watcher. This value represents a declining threshold and must be equal to or greater than 0.0, but cannot be greater than the warning minimum threshold. A value of -1 disables the evaluation of this threshold."
	DEFVAL { "-1" }
	::= { winA3StatusNetGroup 7 }

winA3StatusNetTotalInBytesCritMax OBJECT-TYPE
	SYNTAX DisplayString
	ACCESS read-write
	STATUS mandatory
	DESCRIPTION "&<caiWinA3.1144>Current critical maximum threshold, in bytes/sec, for the total received bytes monitoring of the network interface watcher. This value represents a rising threshold and must be equal to or greater than 0.0, but cannot be less than the warning maximum threshold. A value of -1 disables the evaluation of this threshold."
	DEFVAL { "4000000.0" }
	::= { winA3StatusNetGroup 8 }

winA3StatusNetTotalInBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.1145>Current monitor level for the total received bytes monitoring of the network interface watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 6 }
	::= { winA3StatusNetGroup 9 }

winA3StatusNetTotalInBytesStatus OBJECT-TYPE
	SYNTAX INTEGER {
		unknown(1),
		up(2),
		down-warning(3),
		down-critical(4)
	}
	ACCESS read-only
	STATUS mandatory
	DESCRIPTION "&<caiWinA3.1146>Current status for the total received bytes monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusNetGroup 10 }

winA3StatusNetTotalInPktsValue OBJECT-TYPE
	SYNTAX INTEGER
	ACCESS read-only
	STATUS mandatory
	DESCRIPTION "&<caiWinA3.1147>Current value, in pkts/sec, for the total received packets monitoring of the network interface watcher. This is the sum of all network interfaces."
	::= { winA3StatusNetGroup 11 }

winA3StatusNetTotalInPktsWarn OBJECT-TYPE
	SYNTAX INTEGER
	ACCESS read-write
	STATUS mandatory
	DESCRIPTION "&<caiWinA3.1148>Current warning threshold, in pkts/sec, for the total received packets monitoring of the network interface watcher. This value represents a rising threshold and must be greater than 0, but cannot be greater than the critical threshold."
	DEFVAL { 8000 }
	::= { winA3StatusNetGroup 12 }

winA3StatusNetTotalInPktsCrit OBJECT-TYPE
	SYNTAX INTEGER
	ACCESS read-write
	STATUS mandatory
	DESCRIPTION "&<caiWinA3.1149>Current critical threshold, in pkts/sec, for the total received packets monitoring of the network interface watcher. This value represents a rising threshold and must be greater than 0, but cannot be less than the warning threshold."
	DEFVAL { 15000 }
	::= { winA3StatusNetGroup 13 }

winA3StatusNetTotalInPktsMonitor OBJECT-TYPE
	SYNTAX INTEGER {
		do-not-monitor(1),
		warning-only(2),
		critical-only(3),
		both(4)
	}
	ACCESS read-write
	STATUS mandatory
	DESCRIPTION "&<caiWinA3.1150>Current monitor level for the total received packets monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { winA3StatusNetGroup 14 }

winA3StatusNetTotalInPktsStatus OBJECT-TYPE
	SYNTAX INTEGER {
		unknown(1),
		ok(2),
		warning(3),
		critical(4)
	}
	ACCESS read-only
	STATUS mandatory
	DESCRIPTION "&<caiWinA3.1151>Current status for the total received packets monitoring of the network interface watcher: 1 (unknown) - An error occurred during data collection, 2 (ok) - The resource is operating within the defined limits or status evaluation is turned off and/or polling is disabled, 3 (warning) - The resource has breached the warning threshold, 4 (critical) - The resource has breached the critical threshold."
	::= { winA3StatusNetGroup 15 }

winA3StatusNetTotalInErrorsValue OBJECT-TYPE
	SYNTAX INTEGER
	ACCESS read-only
	STATUS mandatory
	DESCRIPTION "&<caiWinA3.1152>Current value, in errors/poll, for the total received errors monitoring of the network interface watcher. This is the sum of all network interfaces."
	::= { winA3StatusNetGroup 16 }

winA3StatusNetTotalInErrorsWarn OBJECT-TYPE
	SYNTAX INTEGER
	ACCESS read-write
	STATUS mandatory
	DESCRIPTION "&<caiWinA3.1153>Current warning threshold, in errors/poll, for the total received errors monitoring of the network interface watcher. This value represents a rising threshold and must be greater than 0, but cannot be greater than the critical threshold."
	DEFVAL { 5 }
	::= { winA3StatusNetGroup 17 }

winA3StatusNetTotalInErrorsCrit OBJECT-TYPE
	SYNTAX INTEGER
	ACCESS read-write
	STATUS mandatory
	DESCRIPTION "&<caiWinA3.1154>Current critical threshold, in errors/poll, for the total received errors monitoring of the network interface watcher. This value represents a rising threshold and must be greater than 0, but cannot be less than the warning threshold."
	DEFVAL { 10 }
	::= { winA3StatusNetGroup 18 }

winA3StatusNetTotalInErrorsMonitor OBJECT-TYPE
	SYNTAX INTEGER {
		do-not-monitor(1),
		warning-only(2),
		critical-only(3),
		both(4)
	}
	ACCESS read-write
	STATUS mandatory
	DESCRIPTION "&<caiWinA3.1155>Current monitor level for the total received errors monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { winA3StatusNetGroup 19 }

winA3StatusNetTotalInErrorsStatus OBJECT-TYPE
	SYNTAX INTEGER {
		unknown(1),
		ok(2),
		warning(3),
		critical(4)
	}
	ACCESS read-only
	STATUS mandatory
	DESCRIPTION "&<caiWinA3.1156>Current status for the total received errors monitoring of the network interface watcher: 1 (unknown) - An error occurred during data collection, 2 (ok) - The resource is operating within the defined limits or status evaluation is turned off and/or polling is disabled, 3 (warning) - The resource has breached the warning threshold, 4 (critical) - The resource has breached the critical threshold."
	::= { winA3StatusNetGroup 20 }

winA3StatusNetTotalOutBytesValue OBJECT-TYPE
	SYNTAX DisplayString
	ACCESS read-only
	STATUS mandatory
	DESCRIPTION "&<caiWinA3.1157>Current value, in bytes/sec, for the total sent bytes monitoring of the network interface watcher. This is the sum of all network interfaces."
	DEFVAL { "0" }
	::= { winA3StatusNetGroup 21 }

winA3StatusNetTotalOutBytesWarnMin OBJECT-TYPE
	SYNTAX DisplayString
	ACCESS read-write
	STATUS mandatory
	DESCRIPTION "&<caiWinA3.1158>Current warning minimum threshold, in bytes/sec, for the total sent bytes monitoring of the network interface watcher. This value represents a declining threshold and must be equal to or greater than 0.0, equal to or greater than the critical minimum threshold, but cannot be greater than the warning maximum threshold. A value of -1 disables the evaluation of this threshold."
	DEFVAL { "-1" }
	::= { winA3StatusNetGroup 22 }

winA3StatusNetTotalOutBytesWarnMax OBJECT-TYPE
	SYNTAX DisplayString
	ACCESS read-write
	STATUS mandatory
	DESCRIPTION "&<caiWinA3.1159>Current warning maximum threshold, in bytes/sec, for the total sent bytes monitoring of the network interface watcher. This value represents a rising threshold and must be equal to or greater than 0.0, equal to or greater than the warning minimum threshold, but cannot be greater than the critical maximum threshold. A value of -1 disables the evaluation of this threshold."
	DEFVAL { "6000000.0" }
	::= { winA3StatusNetGroup 23 }

winA3StatusNetTotalOutBytesCritMin OBJECT-TYPE
	SYNTAX DisplayString
	ACCESS read-write
	STATUS mandatory
	DESCRIPTION "&<caiWinA3.1160>Current critical minimum threshold, in bytes/sec, for the total sent bytes monitoring of the network interface watcher. This value represents a declining threshold and must be equal to or greater than 0.0, but cannot be greater than the warning minimum threshold. A value of -1 disables the evaluation of this threshold."
	DEFVAL { "-1" }
	::= { winA3StatusNetGroup 24 }

winA3StatusNetTotalOutBytesCritMax OBJECT-TYPE
	SYNTAX DisplayString
	ACCESS read-write
	STATUS mandatory
	DESCRIPTION "&<caiWinA3.1161>Current critical maximum threshold, in bytes/sec, for the total sent bytes monitoring of the network interface watcher. This value represents a rising threshold and must be equal to or greater than 0.0, but cannot be less than the warning maximum threshold. A value of -1 disables the evaluation of this threshold."
	DEFVAL { "12000000.0" }
	::= { winA3StatusNetGroup 25 }

winA3StatusNetTotalOutBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.1162>Current monitor level for the total sent bytes monitoring of the network interface watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 1 }
	::= { winA3StatusNetGroup 26 }

winA3StatusNetTotalOutBytesStatus OBJECT-TYPE
	SYNTAX INTEGER {
		unknown(1),
		up(2),
		down-warning(3),
		down-critical(4)
	}
	ACCESS read-only
	STATUS mandatory
	DESCRIPTION "&<caiWinA3.1163>Current status for the total sent bytes monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusNetGroup 27 }

winA3StatusNetTotalOutPktsValue OBJECT-TYPE
	SYNTAX INTEGER
	ACCESS read-only
	STATUS mandatory
	DESCRIPTION "&<caiWinA3.1164>Current value, in pkts/sec, for the total sent packets monitoring of the network interface watcher. This is the sum of all network interfaces."
	::= { winA3StatusNetGroup 28 }

winA3StatusNetTotalOutPktsWarn OBJECT-TYPE
	SYNTAX INTEGER
	ACCESS read-write
	STATUS mandatory
	DESCRIPTION "&<caiWinA3.1165>Current warning threshold, in pkts/sec, for the total sent packets monitoring of the network interface watcher. This value represents a rising threshold and must be greater than 0, but cannot be greater than the critical threshold."
	DEFVAL { 25000 }
	::= { winA3StatusNetGroup 29 }

winA3StatusNetTotalOutPktsCrit OBJECT-TYPE
	SYNTAX INTEGER
	ACCESS read-write
	STATUS mandatory
	DESCRIPTION "&<caiWinA3.1166>Current critical threshold, in pkts/sec, for the total sent packets monitoring of the network interface watcher. This value represents a rising threshold and must be greater than 0, but cannot be less than the warning threshold."
	DEFVAL { 50000 }
	::= { winA3StatusNetGroup 30 }

winA3StatusNetTotalOutPktsMonitor OBJECT-TYPE
	SYNTAX INTEGER {
		do-not-monitor(1),
		warning-only(2),
		critical-only(3),
		both(4)
	}
	ACCESS read-write
	STATUS mandatory
	DESCRIPTION "&<caiWinA3.1167>Current monitor level for the total sent packets monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { winA3StatusNetGroup 31 }

winA3StatusNetTotalOutPktsStatus OBJECT-TYPE
	SYNTAX INTEGER {
		unknown(1),
		ok(2),
		warning(3),
		critical(4)
	}
	ACCESS read-only
	STATUS mandatory
	DESCRIPTION "&<caiWinA3.1168>Current status for the total sent packets monitoring of the network interface watcher: 1 (unknown) - An error occurred during data collection, 2 (ok) - The resource is operating within the defined limits or status evaluation is turned off and/or polling is disabled, 3 (warning) - The resource has breached the warning threshold, 4 (critical) - The resource has breached the critical threshold."
	::= { winA3StatusNetGroup 32 }

winA3StatusNetTotalOutErrorsValue OBJECT-TYPE
	SYNTAX INTEGER
	ACCESS read-only
	STATUS mandatory
	DESCRIPTION "&<caiWinA3.1169>Current value, in errors/poll, for the total sent errors monitoring of the network interface watcher. This is the sum of all network interfaces."
	::= { winA3StatusNetGroup 33 }

winA3StatusNetTotalOutErrorsWarn OBJECT-TYPE
	SYNTAX INTEGER
	ACCESS read-write
	STATUS mandatory
	DESCRIPTION "&<caiWinA3.1170>Current warning threshold, in errors/poll, for the total sent errors monitoring of the network interface watcher. This value represents a rising threshold and must be greater than 0, but cannot be greater than the critical threshold."
	DEFVAL { 5 }
	::= { winA3StatusNetGroup 34 }

winA3StatusNetTotalOutErrorsCrit OBJECT-TYPE
	SYNTAX INTEGER
	ACCESS read-write
	STATUS mandatory
	DESCRIPTION "&<caiWinA3.1171>Current critical threshold, in errors/poll, for the total sent errors monitoring of the network interface watcher. This value represents a rising threshold and must be greater than 0, but cannot be less than the warning threshold."
	DEFVAL { 10 }
	::= { winA3StatusNetGroup 35 }

winA3StatusNetTotalOutErrorsMonitor OBJECT-TYPE
	SYNTAX INTEGER {
		do-not-monitor(1),
		warning-only(2),
		critical-only(3),
		both(4)
	}
	ACCESS read-write
	STATUS mandatory
	DESCRIPTION "&<caiWinA3.1172>Current monitor level for the total sent errors monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 1 }
	::= { winA3StatusNetGroup 36 }

winA3StatusNetTotalOutErrorsStatus OBJECT-TYPE
	SYNTAX INTEGER {
		unknown(1),
		ok(2),
		warning(3),
		critical(4)
	}
	ACCESS read-only
	STATUS mandatory
	DESCRIPTION "&<caiWinA3.1173>Current status for the total sent errors monitoring of the network interface watcher: 1 (unknown) - An error occurred during data collection, 2 (ok) - The resource is operating within the defined limits or status evaluation is turned off and/or polling is disabled, 3 (warning) - The resource has breached the warning threshold, 4 (critical) - The resource has breached the critical threshold."
	::= { winA3StatusNetGroup 37 }

winA3StatusNetTotalCallBackRef OBJECT-TYPE
	SYNTAX DisplayString
	ACCESS read-only
	STATUS mandatory
	DESCRIPTION "&<caiWinA3.1174>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusNetGroup 38 }

winA3StatusNetCount OBJECT-TYPE
	SYNTAX INTEGER
	ACCESS read-only
	STATUS mandatory
	DESCRIPTION "&<caiWinA3.1175>Number of entries in the network interface status table."
	::= { winA3StatusNetGroup 39 }

winA3StatusNetTable OBJECT-TYPE
	SYNTAX SEQUENCE OF WinA3StatusNetEntry
	ACCESS not-accessible
	STATUS mandatory
	DESCRIPTION "&<caiWinA3.1176>The network interface status table containing details about the currently configured network interface watchers."
	::= { winA3StatusNetGroup 40 }

winA3StatusNetEntry OBJECT-TYPE
	SYNTAX WinA3StatusNetEntry
	ACCESS not-accessible
	STATUS mandatory
	DESCRIPTION "&<caiWinA3.1177>Entry in the network interface status table."
	INDEX {
		winA3StatusNetName
	}
	::= { winA3StatusNetTable 1 }

WinA3StatusNetEntry ::= SEQUENCE {
	winA3StatusNetName DisplayString,
	winA3StatusNetAggLagValue INTEGER,
	winA3StatusNetAggLag INTEGER,
	winA3StatusNetAggStatus INTEGER,
	winA3StatusNetInterfaceValue INTEGER,
	winA3StatusNetInterfaceMonitor INTEGER,
	winA3StatusNetInterfaceStatus INTEGER,
	winA3StatusNetInBytesValue DisplayString,
	winA3StatusNetInBytesWarnMin DisplayString,
	winA3StatusNetInBytesWarnMax DisplayString,
	winA3StatusNetInBytesCritMin DisplayString,
	winA3StatusNetInBytesCritMax DisplayString,
	winA3StatusNetInBytesMonitor INTEGER,
	winA3StatusNetInBytesStatus INTEGER,
	winA3StatusNetInPktsValue INTEGER,
	winA3StatusNetInPktsWarn INTEGER,
	winA3StatusNetInPktsCrit INTEGER,
	winA3StatusNetInPktsMonitor INTEGER,
	winA3StatusNetInPktsStatus INTEGER,
	winA3StatusNetInErrorsValue INTEGER,
	winA3StatusNetInErrorsWarn INTEGER,
	winA3StatusNetInErrorsCrit INTEGER,
	winA3StatusNetInErrorsMonitor INTEGER,
	winA3StatusNetInErrorsStatus INTEGER,
	winA3StatusNetOutBytesValue DisplayString,
	winA3StatusNetOutBytesWarnMin DisplayString,
	winA3StatusNetOutBytesWarnMax DisplayString,
	winA3StatusNetOutBytesCritMin DisplayString,
	winA3StatusNetOutBytesCritMax DisplayString,
	winA3StatusNetOutBytesMonitor INTEGER,
	winA3StatusNetOutBytesStatus INTEGER,
	winA3StatusNetOutPktsValue INTEGER,
	winA3StatusNetOutPktsWarn INTEGER,
	winA3StatusNetOutPktsCrit INTEGER,
	winA3StatusNetOutPktsMonitor INTEGER,
	winA3StatusNetOutPktsStatus INTEGER,
	winA3StatusNetOutErrorsValue INTEGER,
	winA3StatusNetOutErrorsWarn INTEGER,
	winA3StatusNetOutErrorsCrit INTEGER,
	winA3StatusNetOutErrorsMonitor INTEGER,
	winA3StatusNetOutErrorsStatus INTEGER,
	winA3StatusNetLossAction INTEGER,
	winA3StatusNetLossStatus INTEGER,
	winA3StatusNetCallBackRef DisplayString
}

winA3StatusNetName OBJECT-TYPE
	SYNTAX DisplayString
	ACCESS read-only
	STATUS mandatory
	DESCRIPTION "&<caiWinA3.1178>Name of the network interface. The network interfaces are named using their MIB2 interface description. If two interfaces have the same description, a suffix '#N#' is appended to the description, with N being a running index starting with one for the second interface."
	::= { winA3StatusNetEntry 1 }

winA3StatusNetAggLagValue OBJECT-TYPE
	SYNTAX INTEGER
	ACCESS read-only
	STATUS mandatory
	DESCRIPTION "&<caiWinA3.1179>Current aggregate lag value of the network interface watcher. Indicates the consecutive number of times at which any status was not in the ok state. The aggregate status changes from ok as soon as the aggregate lag value reaches the configured value."
	::= { winA3StatusNetEntry 2 }

winA3StatusNetAggLag OBJECT-TYPE
	SYNTAX INTEGER
	ACCESS read-write
	STATUS mandatory
	DESCRIPTION "&<caiWinA3.1180>Current aggregate lag setting for the network interface watcher. Specifies the consecutive number of times at which any status is not in the ok state, before the aggregate status changes. This value must be greater than 0."
	::= { winA3StatusNetEntry 3 }

winA3StatusNetAggStatus OBJECT-TYPE
	SYNTAX INTEGER {
		unknown(1),
		ok(2),
		warning(3),
		critical(4),
		passive(5)
	}
	ACCESS read-only
	STATUS mandatory
	DESCRIPTION "&<caiWinA3.1181>Current aggregate status of the network interface watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusNetEntry 4 }

winA3StatusNetInterfaceValue OBJECT-TYPE
	SYNTAX INTEGER {
		unknown(1),
		operational(2),
		non-operational(3)
	}
	ACCESS read-only
	STATUS mandatory
	DESCRIPTION "&<caiWinA3.1182>The operational status of the network interface. A typical reason for an interface being non-operational is a disconnected network cable. The value is set to 'unknown', if the interface could not be found in the Windows IP helper interface table."
	::= { winA3StatusNetEntry 5 }

winA3StatusNetInterfaceMonitor OBJECT-TYPE
	SYNTAX INTEGER {
		do-not-monitor(1),
		down-warning(2),
		down-critical(3)
	}
	ACCESS read-write
	STATUS mandatory
	DESCRIPTION "&<caiWinA3.1183>Current monitor level for the interface status monitoring of the network interface watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusNetEntry 6 }

winA3StatusNetInterfaceStatus OBJECT-TYPE
	SYNTAX INTEGER {
		unknown(1),
		up(2),
		down-warning(3),
		down-critical(4)
	}
	ACCESS read-only
	STATUS mandatory
	DESCRIPTION "&<caiWinA3.1184>Current status for the interface status monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusNetEntry 7 }

winA3StatusNetInBytesValue OBJECT-TYPE
	SYNTAX DisplayString
	ACCESS read-only
	STATUS mandatory
	DESCRIPTION "&<caiWinA3.1185>Current value, in bytes/sec, for the received bytes monitoring of the network interface watcher."
	DEFVAL { "0" }
	::= { winA3StatusNetEntry 8 }

winA3StatusNetInBytesWarnMin OBJECT-TYPE
	SYNTAX DisplayString
	ACCESS read-write
	STATUS mandatory
	DESCRIPTION "&<caiWinA3.1186>Current warning minimum threshold, in bytes/sec, for the received bytes monitoring of the network interface watcher. This value represents a declining threshold and must be equal to or greater than 0.0, equal to or greater than the critical minimum threshold, but cannot be greater than the warning maximum threshold. A value of -1 disables the evaluation of this threshold."
	DEFVAL { "-2" }
	::= { winA3StatusNetEntry 9 }

winA3StatusNetInBytesWarnMax OBJECT-TYPE
	SYNTAX DisplayString
	ACCESS read-write
	STATUS mandatory
	DESCRIPTION "&<caiWinA3.1187>Current warning maximum threshold, in bytes/sec, for the received bytes monitoring of the network interface watcher. This value represents a rising threshold and must be equal to or greater than 0.0, equal to or greater than the warning minimum threshold, but cannot be greater than the critical maximum threshold. A value of -1 disables the evaluation of this threshold."
	DEFVAL { "-2" }
	::= { winA3StatusNetEntry 10 }

winA3StatusNetInBytesCritMin OBJECT-TYPE
	SYNTAX DisplayString
	ACCESS read-write
	STATUS mandatory
	DESCRIPTION "&<caiWinA3.1188>Current critical minimum threshold, in bytes/sec, for the received bytes monitoring of the network interface watcher. This value represents a declining threshold and must be equal to or greater than 0.0, but cannot be greater than the warning minimum threshold. A value of -1 disables the evaluation of this threshold."
	DEFVAL { "-2" }
	::= { winA3StatusNetEntry 11 }

winA3StatusNetInBytesCritMax OBJECT-TYPE
	SYNTAX DisplayString
	ACCESS read-write
	STATUS mandatory
	DESCRIPTION "&<caiWinA3.1189>Current critical maximum threshold, in bytes/sec, for the received bytes monitoring of the network interface watcher. This value represents a rising threshold and must be equal to or greater than 0.0, but cannot be less than the warning maximum threshold. A value of -1 disables the evaluation of this threshold."
	DEFVAL { "-2" }
	::= { winA3StatusNetEntry 12 }

winA3StatusNetInBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.1190>Current monitor level for the received bytes monitoring of the network interface watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusNetEntry 13 }

winA3StatusNetInBytesStatus OBJECT-TYPE
	SYNTAX INTEGER {
		unknown(1),
		up(2),
		down-warning(3),
		down-critical(4)
	}
	ACCESS read-only
	STATUS mandatory
	DESCRIPTION "&<caiWinA3.1191>Current status for the received bytes monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusNetEntry 14 }

winA3StatusNetInPktsValue OBJECT-TYPE
	SYNTAX INTEGER
	ACCESS read-only
	STATUS mandatory
	DESCRIPTION "&<caiWinA3.1192>Current value, in pkts/sec, for the received packets monitoring of the network interface watcher."
	::= { winA3StatusNetEntry 15 }

winA3StatusNetInPktsWarn OBJECT-TYPE
	SYNTAX INTEGER
	ACCESS read-write
	STATUS mandatory
	DESCRIPTION "&<caiWinA3.1193>Current warning threshold, in pkts/sec, for the received packets monitoring of the network interface watcher. This value represents a rising threshold and must be greater than 0, but cannot be greater than the critical threshold."
	::= { winA3StatusNetEntry 16 }

winA3StatusNetInPktsCrit OBJECT-TYPE
	SYNTAX INTEGER
	ACCESS read-write
	STATUS mandatory
	DESCRIPTION "&<caiWinA3.1194>Current critical threshold, in pkts/sec, for the received packets monitoring of the network interface watcher. This value represents a rising threshold and must be greater than 0, but cannot be less than the warning threshold."
	::= { winA3StatusNetEntry 17 }

winA3StatusNetInPktsMonitor OBJECT-TYPE
	SYNTAX INTEGER {
		do-not-monitor(1),
		warning-only(2),
		critical-only(3),
		both(4)
	}
	ACCESS read-write
	STATUS mandatory
	DESCRIPTION "&<caiWinA3.1195>Current monitor level for the received packets monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusNetEntry 18 }

winA3StatusNetInPktsStatus OBJECT-TYPE
	SYNTAX INTEGER {
		unknown(1),
		ok(2),
		warning(3),
		critical(4)
	}
	ACCESS read-only
	STATUS mandatory
	DESCRIPTION "&<caiWinA3.1196>Current status for the received packets monitoring of the network interface watcher: 1 (unknown) - An error occurred during data collection, 2 (ok) - The resource is operating within the defined limits or status evaluation is turned off and/or polling is disabled, 3 (warning) - The resource has breached the warning threshold, 4 (critical) - The resource has breached the critical threshold."
	::= { winA3StatusNetEntry 19 }

winA3StatusNetInErrorsValue OBJECT-TYPE
	SYNTAX INTEGER
	ACCESS read-only
	STATUS mandatory
	DESCRIPTION "&<caiWinA3.1197>Current value, in errors/poll, for the received errors monitoring of the network interface watcher."
	::= { winA3StatusNetEntry 20 }

winA3StatusNetInErrorsWarn OBJECT-TYPE
	SYNTAX INTEGER
	ACCESS read-write
	STATUS mandatory
	DESCRIPTION "&<caiWinA3.1198>Current warning threshold, in errors/poll, for the received errors monitoring of the network interface watcher. This value represents a rising threshold and must be greater than 0, but cannot be greater than the critical threshold."
	::= { winA3StatusNetEntry 21 }

winA3StatusNetInErrorsCrit OBJECT-TYPE
	SYNTAX INTEGER
	ACCESS read-write
	STATUS mandatory
	DESCRIPTION "&<caiWinA3.1199>Current critical threshold, in errors/poll, for the received errors monitoring of the network interface watcher. This value represents a rising threshold and must be greater than 0, but cannot be less than the warning threshold."
	::= { winA3StatusNetEntry 22 }

winA3StatusNetInErrorsMonitor OBJECT-TYPE
	SYNTAX INTEGER {
		do-not-monitor(1),
		warning-only(2),
		critical-only(3),
		both(4)
	}
	ACCESS read-write
	STATUS mandatory
	DESCRIPTION "&<caiWinA3.1200>Current monitor level for the received errors monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusNetEntry 23 }

winA3StatusNetInErrorsStatus OBJECT-TYPE
	SYNTAX INTEGER {
		unknown(1),
		ok(2),
		warning(3),
		critical(4)
	}
	ACCESS read-only
	STATUS mandatory
	DESCRIPTION "&<caiWinA3.1201>Current status for the received errors monitoring of the network interface watcher: 1 (unknown) - An error occurred during data collection, 2 (ok) - The resource is operating within the defined limits or status evaluation is turned off and/or polling is disabled, 3 (warning) - The resource has breached the warning threshold, 4 (critical) - The resource has breached the critical threshold."
	::= { winA3StatusNetEntry 24 }

winA3StatusNetOutBytesValue OBJECT-TYPE
	SYNTAX DisplayString
	ACCESS read-only
	STATUS mandatory
	DESCRIPTION "&<caiWinA3.1202>Current value, in bytes/sec, for the sent bytes monitoring of the network interface watcher."
	DEFVAL { "0" }
	::= { winA3StatusNetEntry 25 }

winA3StatusNetOutBytesWarnMin OBJECT-TYPE
	SYNTAX DisplayString
	ACCESS read-write
	STATUS mandatory
	DESCRIPTION "&<caiWinA3.1203>Current warning minimum threshold, in bytes/sec, for the sent bytes monitoring of the network interface watcher. This value represents a declining threshold and must be equal to or greater than 0.0, equal to or greater than the critical minimum threshold, but cannot be greater than the warning maximum threshold. A value of -1 disables the evaluation of this threshold."
	DEFVAL { "-2" }
	::= { winA3StatusNetEntry 26 }

winA3StatusNetOutBytesWarnMax OBJECT-TYPE
	SYNTAX DisplayString
	ACCESS read-write
	STATUS mandatory
	DESCRIPTION "&<caiWinA3.1204>Current warning maximum threshold, in bytes/sec, for the sent bytes monitoring of the network interface watcher. This value represents a rising threshold and must be equal to or greater than 0.0, equal to or greater than the warning minimum threshold, but cannot be greater than the critical maximum threshold. A value of -1 disables the evaluation of this threshold."
	DEFVAL { "-2" }
	::= { winA3StatusNetEntry 27 }

winA3StatusNetOutBytesCritMin OBJECT-TYPE
	SYNTAX DisplayString
	ACCESS read-write
	STATUS mandatory
	DESCRIPTION "&<caiWinA3.1205>Current critical minimum threshold, in bytes/sec, for the sent bytes monitoring of the network interface watcher. This value represents a declining threshold and must be equal to or greater than 0.0, but cannot be greater than the warning minimum threshold. A value of -1 disables the evaluation of this threshold."
	DEFVAL { "-2" }
	::= { winA3StatusNetEntry 28 }

winA3StatusNetOutBytesCritMax OBJECT-TYPE
	SYNTAX DisplayString
	ACCESS read-write
	STATUS mandatory
	DESCRIPTION "&<caiWinA3.1206>Current critical maximum threshold, in bytes/sec, for the sent bytes monitoring of the network interface watcher. This value represents a rising threshold and must be equal to or greater than 0.0, but cannot be less than the warning maximum threshold. A value of -1 disables the evaluation of this threshold."
	DEFVAL { "-2" }
	::= { winA3StatusNetEntry 29 }

winA3StatusNetOutBytesMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.1207>Current monitor level for the sent bytes monitoring of the network interface watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusNetEntry 30 }

winA3StatusNetOutBytesStatus OBJECT-TYPE
	SYNTAX INTEGER {
		unknown(1),
		up(2),
		down-warning(3),
		down-critical(4)
	}
	ACCESS read-only
	STATUS mandatory
	DESCRIPTION "&<caiWinA3.1208>Current status for the sent bytes monitoring of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusNetEntry 31 }

winA3StatusNetOutPktsValue OBJECT-TYPE
	SYNTAX INTEGER
	ACCESS read-only
	STATUS mandatory
	DESCRIPTION "&<caiWinA3.1209>Current value, in pkts/sec, for the sent packets monitoring of the network interface watcher."
	::= { winA3StatusNetEntry 32 }

winA3StatusNetOutPktsWarn OBJECT-TYPE
	SYNTAX INTEGER
	ACCESS read-write
	STATUS mandatory
	DESCRIPTION "&<caiWinA3.1210>Current warning threshold, in pkts/sec, for the sent packets monitoring of the network interface watcher. This value represents a rising threshold and must be greater than 0, but cannot be greater than the critical threshold."
	::= { winA3StatusNetEntry 33 }

winA3StatusNetOutPktsCrit OBJECT-TYPE
	SYNTAX INTEGER
	ACCESS read-write
	STATUS mandatory
	DESCRIPTION "&<caiWinA3.1211>Current critical threshold, in pkts/sec, for the sent packets monitoring of the network interface watcher. This value represents a rising threshold and must be greater than 0, but cannot be less than the warning threshold."
	::= { winA3StatusNetEntry 34 }

winA3StatusNetOutPktsMonitor OBJECT-TYPE
	SYNTAX INTEGER {
		do-not-monitor(1),
		warning-only(2),
		critical-only(3),
		both(4)
	}
	ACCESS read-write
	STATUS mandatory
	DESCRIPTION "&<caiWinA3.1212>Current monitor level for the sent packets monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusNetEntry 35 }

winA3StatusNetOutPktsStatus OBJECT-TYPE
	SYNTAX INTEGER {
		unknown(1),
		ok(2),
		warning(3),
		critical(4)
	}
	ACCESS read-only
	STATUS mandatory
	DESCRIPTION "&<caiWinA3.1213>Current status for the sent packets monitoring of the network interface watcher: 1 (unknown) - An error occurred during data collection, 2 (ok) - The resource is operating within the defined limits or status evaluation is turned off and/or polling is disabled, 3 (warning) - The resource has breached the warning threshold, 4 (critical) - The resource has breached the critical threshold."
	::= { winA3StatusNetEntry 36 }

winA3StatusNetOutErrorsValue OBJECT-TYPE
	SYNTAX INTEGER
	ACCESS read-only
	STATUS mandatory
	DESCRIPTION "&<caiWinA3.1214>Current value, in errors/poll, for the sent errors monitoring of the network interface watcher."
	::= { winA3StatusNetEntry 37 }

winA3StatusNetOutErrorsWarn OBJECT-TYPE
	SYNTAX INTEGER
	ACCESS read-write
	STATUS mandatory
	DESCRIPTION "&<caiWinA3.1215>Current warning threshold, in errors/poll, for the sent errors monitoring of the network interface watcher. This value represents a rising threshold and must be greater than 0, but cannot be greater than the critical threshold."
	::= { winA3StatusNetEntry 38 }

winA3StatusNetOutErrorsCrit OBJECT-TYPE
	SYNTAX INTEGER
	ACCESS read-write
	STATUS mandatory
	DESCRIPTION "&<caiWinA3.1216>Current critical threshold, in errors/poll, for the sent errors monitoring of the network interface watcher. This value represents a rising threshold and must be greater than 0, but cannot be less than the warning threshold."
	::= { winA3StatusNetEntry 39 }

winA3StatusNetOutErrorsMonitor OBJECT-TYPE
	SYNTAX INTEGER {
		do-not-monitor(1),
		warning-only(2),
		critical-only(3),
		both(4)
	}
	ACCESS read-write
	STATUS mandatory
	DESCRIPTION "&<caiWinA3.1217>Current monitor level for the sent errors monitoring of the network interface watcher. If set to 1 (do-not-monitor), the agent disregards all thresholds and sets the status to ok. If set to 2 (warning-only), the agent evaluates only the warning threshold to determine the status of the resource. If set to 3 (critical-only), the agent evaluates only the critical threshold to determine the status of the resource. If set to 4 (both), the agent evaluates both the warning and critical thresholds to determine the status of the resource. The critical threshold comes into effect if the warning threshold is set to the same value."
	DEFVAL { 0 }
	::= { winA3StatusNetEntry 40 }

winA3StatusNetOutErrorsStatus OBJECT-TYPE
	SYNTAX INTEGER {
		unknown(1),
		ok(2),
		warning(3),
		critical(4)
	}
	ACCESS read-only
	STATUS mandatory
	DESCRIPTION "&<caiWinA3.1218>Current status for the sent errors monitoring of the network interface watcher: 1 (unknown) - An error occurred during data collection, 2 (ok) - The resource is operating within the defined limits or status evaluation is turned off and/or polling is disabled, 3 (warning) - The resource has breached the warning threshold, 4 (critical) - The resource has breached the critical threshold."
	::= { winA3StatusNetEntry 41 }

winA3StatusNetLossAction OBJECT-TYPE
	SYNTAX INTEGER {
		remove(1),
		up(2),
		down-warning(3),
		down-critical(4)
	}
	ACCESS read-write
	STATUS mandatory
	DESCRIPTION "&<caiWinA3.1219>Current loss action for the network interface watcher. Specifies the action to take if the monitored network interface is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusNetEntry 42 }

winA3StatusNetLossStatus OBJECT-TYPE
	SYNTAX INTEGER {
		unknown(1),
		up(2),
		down-warning(3),
		down-critical(4)
	}
	ACCESS read-only
	STATUS mandatory
	DESCRIPTION "&<caiWinA3.1220>Current loss status of the network interface watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusNetEntry 43 }

winA3StatusNetCallBackRef OBJECT-TYPE
	SYNTAX DisplayString
	ACCESS read-only
	STATUS mandatory
	DESCRIPTION "&<caiWinA3.1221>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusNetEntry 44 }

--
-- The StatusReg Group
--

winA3StatusRegCount OBJECT-TYPE
	SYNTAX INTEGER
	ACCESS read-only
	STATUS mandatory
	DESCRIPTION "&<caiWinA3.1222>Number of entries in the registry entry status table."
	::= { winA3StatusRegGroup 1 }

winA3StatusRegTable OBJECT-TYPE
	SYNTAX SEQUENCE OF WinA3StatusRegEntry
	ACCESS not-accessible
	STATUS mandatory
	DESCRIPTION "&<caiWinA3.1223>The registry entry status table containing details about the currently configured registry entry watchers."
	::= { winA3StatusRegGroup 2 }

winA3StatusRegEntry OBJECT-TYPE
	SYNTAX WinA3StatusRegEntry
	ACCESS not-accessible
	STATUS mandatory
	DESCRIPTION "&<caiWinA3.1224>Entry in the registry entry status table."
	INDEX {
		winA3StatusRegWatcherName
	}
	::= { winA3StatusRegTable 1 }

WinA3StatusRegEntry ::= SEQUENCE {
	winA3StatusRegWatcherName DisplayString,
	winA3StatusRegKeyName DisplayString,
	winA3StatusRegValueName DisplayString,
	winA3StatusRegDescription DisplayString,
	winA3StatusRegAggLagValue INTEGER,
	winA3StatusRegAggLag INTEGER,
	winA3StatusRegAggStatus INTEGER,
	winA3StatusRegValueData DisplayString,
	winA3StatusRegValueType INTEGER,
	winA3StatusRegValueRef DisplayString,
	winA3StatusRegValuePolicy INTEGER,
	winA3StatusRegValueMonitor INTEGER,
	winA3StatusRegValueStatus INTEGER,
	winA3StatusRegSubTreeMonitor INTEGER,
	winA3StatusRegSubTreeStatus INTEGER,
	winA3StatusRegExistPolicy INTEGER,
	winA3StatusRegExistMonitor INTEGER,
	winA3StatusRegExistStatus INTEGER,
	winA3StatusRegCallBackRef DisplayString,
	winA3StatusRegButton INTEGER
}

winA3StatusRegWatcherName OBJECT-TYPE
	SYNTAX DisplayString
	ACCESS read-only
	STATUS mandatory
	DESCRIPTION "&<caiWinA3.1225>An arbitrary name for the watcher."
	::= { winA3StatusRegEntry 1 }

winA3StatusRegKeyName OBJECT-TYPE
	SYNTAX DisplayString
	ACCESS read-write
	STATUS mandatory
	DESCRIPTION "&<caiWinA3.1226>The key name of the registry entry. The key name is the complete path starting from one of the hives down to the key itself, for example: 'HKEY_LOCAL_MACHINE\SOFTWARE\Microsoft\Internet Explorer'. To monitor just the key for existence and subtree change, the value name attribute must be empty."
	::= { winA3StatusRegEntry 2 }

winA3StatusRegValueName OBJECT-TYPE
	SYNTAX DisplayString
	ACCESS read-write
	STATUS mandatory
	DESCRIPTION "&<caiWinA3.1227>The value name of the registry entry, for example: 'Version'. Omitting the value name (giving as empty string) allows to change the behaviour of the watcher. In this case the watcher will monitor the given key for existence and subtree change. As no value data can be determined, the value type is set to 'unknown' and the status of the value metric is set to 'up'."
	::= { winA3StatusRegEntry 3 }

winA3StatusRegDescription OBJECT-TYPE
	SYNTAX DisplayString
	ACCESS read-write
	STATUS mandatory
	DESCRIPTION "&<caiWinA3.1228>Current description for the registry entry watcher."
	::= { winA3StatusRegEntry 4 }

winA3StatusRegAggLagValue OBJECT-TYPE
	SYNTAX INTEGER
	ACCESS read-only
	STATUS mandatory
	DESCRIPTION "&<caiWinA3.1229>Current aggregate lag value of the registry entry watcher. Indicates the consecutive number of times at which any status was not in the ok state. The aggregate status changes from ok as soon as the aggregate lag value reaches the configured value."
	::= { winA3StatusRegEntry 5 }

winA3StatusRegAggLag OBJECT-TYPE
	SYNTAX INTEGER
	ACCESS read-write
	STATUS mandatory
	DESCRIPTION "&<caiWinA3.1230>Current aggregate lag setting for the registry entry watcher. Specifies the consecutive number of times at which any status is not in the ok state, before the aggregate status changes. This value must be greater than 0."
	::= { winA3StatusRegEntry 6 }

winA3StatusRegAggStatus OBJECT-TYPE
	SYNTAX INTEGER {
		unknown(1),
		ok(2),
		warning(3),
		critical(4),
		passive(5)
	}
	ACCESS read-only
	STATUS mandatory
	DESCRIPTION "&<caiWinA3.1231>Current aggregate status of the registry entry watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusRegEntry 7 }

winA3StatusRegValueData OBJECT-TYPE
	SYNTAX DisplayString
	ACCESS read-only
	STATUS mandatory
	DESCRIPTION "&<caiWinA3.1232>The current data of the value. If the value has type 'dword', the data is displayed in the format '0x000000FF (255)'. If the value has type 'string' and the string is a multi-string, the data is displayed in the format 'string1|string2|string3'. If the value has type 'binary', the data is displayed in the format '66 73 78 65 82 89'."
	::= { winA3StatusRegEntry 8 }

winA3StatusRegValueType OBJECT-TYPE
	SYNTAX INTEGER {
		unknown(1),
		dword(2),
		string(3),
		binary(4)
	}
	ACCESS read-only
	STATUS mandatory
	DESCRIPTION "&<caiWinA3.1233>The current type of the value. The type is set to 'unknown', if no value is given or if an unexpected type is detected."
	::= { winA3StatusRegEntry 9 }

winA3StatusRegValueRef OBJECT-TYPE
	SYNTAX DisplayString
	ACCESS read-write
	STATUS mandatory
	DESCRIPTION "&<caiWinA3.1234>This attribute is used as the reference the value data is compared with. If the value policy is set to 'should-not-change(5)', the reference is set initially (when the watcher is added) to the current data of the value. Additionally, the reference value can be set to the current data by setting the status button attribute to 'reset-value'."
	::= { winA3StatusRegEntry 10 }

winA3StatusRegValuePolicy OBJECT-TYPE
	SYNTAX INTEGER {
		should-be-equal(1),
		should-not-be-equal(2),
		should-be-minimal(3),
		should-be-maximal(4),
		should-not-change(5)
	}
	ACCESS read-write
	STATUS mandatory
	DESCRIPTION "&<caiWinA3.1235>Current monitor policy for the registry entry value monitoring of the registry entry watcher. This policy specifies how to compare the current value data to the reference. The policies 'should-be-minimal(3)' and 'should-be-maximal(4)' can only be applied, if the value type is 'dword'."
	DEFVAL { 0 }
	::= { winA3StatusRegEntry 11 }

winA3StatusRegValueMonitor OBJECT-TYPE
	SYNTAX INTEGER {
		do-not-monitor(1),
		down-warning(2),
		down-critical(3)
	}
	ACCESS read-write
	STATUS mandatory
	DESCRIPTION "&<caiWinA3.1236>Current monitor level for the registry entry value monitoring of the registry entry watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusRegEntry 12 }

winA3StatusRegValueStatus OBJECT-TYPE
	SYNTAX INTEGER {
		unknown(1),
		up(2),
		down-warning(3),
		down-critical(4)
	}
	ACCESS read-only
	STATUS mandatory
	DESCRIPTION "&<caiWinA3.1237>Current status for the registry entry value monitoring of the registry entry watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusRegEntry 13 }

winA3StatusRegSubTreeMonitor OBJECT-TYPE
	SYNTAX INTEGER {
		do-not-monitor(1),
		down-warning(2),
		down-critical(3)
	}
	ACCESS read-write
	STATUS mandatory
	DESCRIPTION "&<caiWinA3.1238>Current monitor level for the sub tree change monitoring of the registry entry watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusRegEntry 14 }

winA3StatusRegSubTreeStatus OBJECT-TYPE
	SYNTAX INTEGER {
		unknown(1),
		up(2),
		down-warning(3),
		down-critical(4)
	}
	ACCESS read-only
	STATUS mandatory
	DESCRIPTION "&<caiWinA3.1239>Current status for the sub tree change monitoring of the registry entry watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusRegEntry 15 }

winA3StatusRegExistPolicy OBJECT-TYPE
	SYNTAX INTEGER {
		should-exist(1),
		should-not-exist(2)
	}
	ACCESS read-write
	STATUS mandatory
	DESCRIPTION "&<caiWinA3.1240>Current monitor policy for the existence monitoring of the registry entry watcher. Specifies how the agent should evaluate the presence or absence of the monitored resource in order to determine whether the resource is in good condition. If set to 1 (should-exist), the resource is expected to be existent. If set to 2 (should-not-exist), the resource is expected to be nonexistent."
	DEFVAL { 0 }
	::= { winA3StatusRegEntry 16 }

winA3StatusRegExistMonitor OBJECT-TYPE
	SYNTAX INTEGER {
		do-not-monitor(1),
		down-warning(2),
		down-critical(3)
	}
	ACCESS read-write
	STATUS mandatory
	DESCRIPTION "&<caiWinA3.1241>Current monitor level for the existence monitoring of the registry entry watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusRegEntry 17 }

winA3StatusRegExistStatus OBJECT-TYPE
	SYNTAX INTEGER {
		unknown(1),
		up(2),
		down-warning(3),
		down-critical(4)
	}
	ACCESS read-only
	STATUS mandatory
	DESCRIPTION "&<caiWinA3.1242>Current status for the existence monitoring of the registry entry watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusRegEntry 18 }

winA3StatusRegCallBackRef OBJECT-TYPE
	SYNTAX DisplayString
	ACCESS read-only
	STATUS mandatory
	DESCRIPTION "&<caiWinA3.1243>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusRegEntry 19 }

winA3StatusRegButton OBJECT-TYPE
	SYNTAX INTEGER {
		none(1),
		remove(2),
		reinit(3),
		reset-value(4),
		reset-subtree(5)
	}
	ACCESS read-write
	STATUS mandatory
	DESCRIPTION "&<caiWinA3.1244>This attribute is used to remove the registry entry watcher. Additionally, if set to 3 (reinit), the watcher is completely new evaluated. If set to 4 (reset-value), the value reference is set to the current value and the status of the value metric is set to 'up' (except the case the policy is set to 'should-not-be-equal'). If set to 5 (reset-subtree), the status of the subtree metric is set to 'up'. If set to 2 (remove), the agent removes the watcher from the table. This attribute cannot be set to 1 (none)."
	DEFVAL { 1 }
	::= { winA3StatusRegEntry 20 }

--
-- The StatusHardwr Group
--

winA3StatusHardwrCount OBJECT-TYPE
	SYNTAX INTEGER
	ACCESS read-only
	STATUS mandatory
	DESCRIPTION "&<caiWinA3.1245>Number of entries in the hardware resource status table."
	::= { winA3StatusHardwrGroup 1 }

winA3StatusHardwrTable OBJECT-TYPE
	SYNTAX SEQUENCE OF WinA3StatusHardwrEntry
	ACCESS not-accessible
	STATUS mandatory
	DESCRIPTION "&<caiWinA3.1246>The hardware resource status table containing details about the currently configured hardware resource watchers."
	::= { winA3StatusHardwrGroup 2 }

winA3StatusHardwrEntry OBJECT-TYPE
	SYNTAX WinA3StatusHardwrEntry
	ACCESS not-accessible
	STATUS mandatory
	DESCRIPTION "&<caiWinA3.1247>Entry in the hardware resource status table."
	INDEX {
		winA3StatusHardwrResName,
		winA3StatusHardwrResSubName,
		winA3StatusHardwrInstName
	}
	::= { winA3StatusHardwrTable 1 }

WinA3StatusHardwrEntry ::= SEQUENCE {
	winA3StatusHardwrResName DisplayString,
	winA3StatusHardwrResSubName DisplayString,
	winA3StatusHardwrInstName DisplayString,
	winA3StatusHardwrDescription DisplayString,
	winA3StatusHardwrAutoWatcherName DisplayString,
	winA3StatusHardwrAggStatus INTEGER,
	winA3StatusHardwrCollectScript DisplayString,
	winA3StatusHardwrCollectArgs DisplayString,
	winA3StatusHardwrUserName DisplayString,
	winA3StatusHardwrSkipCount INTEGER,
	winA3StatusHardwrInfoMsg DisplayString,
	winA3StatusHardwrErrorMsg DisplayString,
	winA3StatusHardwrErrorMsgPattern DisplayString,
	winA3StatusHardwrErrorMsgMonitor INTEGER,
	winA3StatusHardwrErrorMsgStatus INTEGER,
	winA3StatusHardwrResultValue DisplayString,
	winA3StatusHardwrResultLagValue INTEGER,
	winA3StatusHardwrResultLag INTEGER,
	winA3StatusHardwrResultWarnMin DisplayString,
	winA3StatusHardwrResultWarnMax DisplayString,
	winA3StatusHardwrResultCritMin DisplayString,
	winA3StatusHardwrResultCritMax DisplayString,
	winA3StatusHardwrResultMonitor INTEGER,
	winA3StatusHardwrResultStatus INTEGER,
	winA3StatusHardwrLossAction INTEGER,
	winA3StatusHardwrLossStatus INTEGER,
	winA3StatusHardwrCallBackRef DisplayString,
	winA3StatusHardwrButton INTEGER
}

winA3StatusHardwrResName OBJECT-TYPE
	SYNTAX DisplayString
	ACCESS read-only
	STATUS mandatory
	DESCRIPTION "&<caiWinA3.1248>The name of the resource. This is the first index used by the agent in the different MIB tables for this resource (e.g. PowerSupply)."
	::= { winA3StatusHardwrEntry 1 }

winA3StatusHardwrResSubName OBJECT-TYPE
	SYNTAX DisplayString
	ACCESS read-only
	STATUS mandatory
	DESCRIPTION "&<caiWinA3.1249>The subname of the resource. This is the second index used by the agent in the different MIB tables for this resource (e.g. Voltage)."
	::= { winA3StatusHardwrEntry 2 }

winA3StatusHardwrInstName OBJECT-TYPE
	SYNTAX DisplayString
	ACCESS read-only
	STATUS mandatory
	DESCRIPTION "&<caiWinA3.1250>If a resource supports instances, this must be the name of an instance. The instance name is the third index used by the agent in the different MIB tables for this resource. If a resource does not support instances, <none> should be used as third index."
	::= { winA3StatusHardwrEntry 3 }

winA3StatusHardwrDescription OBJECT-TYPE
	SYNTAX DisplayString
	ACCESS read-write
	STATUS mandatory
	DESCRIPTION "&<caiWinA3.1251>Current description for the hardware resource watcher."
	::= { winA3StatusHardwrEntry 4 }

winA3StatusHardwrAutoWatcherName OBJECT-TYPE
	SYNTAX DisplayString
	ACCESS read-only
	STATUS mandatory
	DESCRIPTION "&<caiWinA3.1252>Name of the hardware resource auto watcher which automatically created this watcher. This attribute is left blank if the watcher was added manually."
	::= { winA3StatusHardwrEntry 5 }

winA3StatusHardwrAggStatus OBJECT-TYPE
	SYNTAX INTEGER {
		unknown(1),
		ok(2),
		warning(3),
		critical(4),
		passive(5)
	}
	ACCESS read-only
	STATUS mandatory
	DESCRIPTION "&<caiWinA3.1253>Current aggregate status of the hardware resource watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusHardwrEntry 6 }

winA3StatusHardwrCollectScript OBJECT-TYPE
	SYNTAX DisplayString
	ACCESS read-only
	STATUS mandatory
	DESCRIPTION "&<caiWinA3.1254>This attribute can only be configured in the 'Generic.ini' file. Script to be called to retrieve the value for a resource. If a resource supports instances, the script needs to gather the values for all required instances in one call. The script must be in a dedicated directory (agents\config\caiWinA3). Any path element will be ignored."
	::= { winA3StatusHardwrEntry 7 }

winA3StatusHardwrCollectArgs OBJECT-TYPE
	SYNTAX DisplayString
	ACCESS read-only
	STATUS mandatory
	DESCRIPTION "&<caiWinA3.1255>This attribute can only be configured in the 'Generic.ini' file. Arguments passed to the collect script. If a resource supports instances, the names of all monitored instances are always appended and passed as last parameters."
	::= { winA3StatusHardwrEntry 8 }

winA3StatusHardwrUserName OBJECT-TYPE
	SYNTAX DisplayString
	ACCESS read-only
	STATUS mandatory
	DESCRIPTION "&<caiWinA3.1256>This attribute can only be configured in the 'Generic.ini' file. Specifies the user ID and the password (Syntax: user,passwd) to be used for the execution of any script."
	::= { winA3StatusHardwrEntry 9 }

winA3StatusHardwrSkipCount OBJECT-TYPE
	SYNTAX INTEGER
	ACCESS read-only
	STATUS mandatory
	DESCRIPTION "&<caiWinA3.1257>This attribute can only be configured in the 'Generic.ini' file. Current skip count for the hardware resource watcher. Specifies the number of consecutive poll intervals that should be passed without evaluating the watcher. This value must be equal to or greater than 0."
	::= { winA3StatusHardwrEntry 10 }

winA3StatusHardwrInfoMsg OBJECT-TYPE
	SYNTAX DisplayString
	ACCESS read-only
	STATUS mandatory
	DESCRIPTION "&<caiWinA3.1258>The info message string the agent collected from the script. The agent uses ...<PENDING>... as value for the info message as long as the corresponding collect script of this resource is still runnng."
	::= { winA3StatusHardwrEntry 11 }

winA3StatusHardwrErrorMsg OBJECT-TYPE
	SYNTAX DisplayString
	ACCESS read-only
	STATUS mandatory
	DESCRIPTION "&<caiWinA3.1259>The error message string the agent collected from the script. If the script did not finish and has been killed by the agent, the agent uses ...<TIMEOUT>... as value for the error message. Similar, if the script could not be started, the agent uses ...<ERROR>... as value for the error message."
	::= { winA3StatusHardwrEntry 12 }

winA3StatusHardwrErrorMsgPattern OBJECT-TYPE
	SYNTAX DisplayString
	ACCESS read-write
	STATUS mandatory
	DESCRIPTION "&<caiWinA3.1260>A regular expression (case-insensitive). If the error message matches this pattern, the error message status changes according to the error message monitor policy."
	::= { winA3StatusHardwrEntry 13 }

winA3StatusHardwrErrorMsgMonitor OBJECT-TYPE
	SYNTAX INTEGER {
		do-not-monitor(1),
		down-warning(2),
		down-critical(3)
	}
	ACCESS read-write
	STATUS mandatory
	DESCRIPTION "&<caiWinA3.1261>Current monitor level for the error message monitoring of the hardware resource watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusHardwrEntry 14 }

winA3StatusHardwrErrorMsgStatus OBJECT-TYPE
	SYNTAX INTEGER {
		unknown(1),
		up(2),
		down-warning(3),
		down-critical(4)
	}
	ACCESS read-only
	STATUS mandatory
	DESCRIPTION "&<caiWinA3.1262>Current status for the error message monitoring of the hardware resource watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusHardwrEntry 15 }

winA3StatusHardwrResultValue OBJECT-TYPE
	SYNTAX DisplayString
	ACCESS read-only
	STATUS mandatory
	DESCRIPTION "&<caiWinA3.1263>Current value for the result monitoring of the hardware resource watcher."
	DEFVAL { "0" }
	::= { winA3StatusHardwrEntry 16 }

winA3StatusHardwrResultLagValue OBJECT-TYPE
	SYNTAX INTEGER
	ACCESS read-only
	STATUS mandatory
	DESCRIPTION "&<caiWinA3.1264>Current number of consecutive threshold breaches for the result monitoring of the hardware resource watcher. The result state changes from ok as soon as the lag value reaches the configured value. The state reverts back to ok if a threshold is no longer breached."
	::= { winA3StatusHardwrEntry 17 }

winA3StatusHardwrResultLag OBJECT-TYPE
	SYNTAX INTEGER
	ACCESS read-write
	STATUS mandatory
	DESCRIPTION "&<caiWinA3.1265>Current lag setting for the result monitoring of the hardware resource watcher. Specifies the number of consecutive threshold breaches on which the result state changes. This value must be greater than 0."
	::= { winA3StatusHardwrEntry 18 }

winA3StatusHardwrResultWarnMin OBJECT-TYPE
	SYNTAX DisplayString
	ACCESS read-write
	STATUS mandatory
	DESCRIPTION "&<caiWinA3.1266>Current warning minimum threshold for the result monitoring of the hardware resource watcher. This value represents a declining threshold and must be equal to or greater than 0.0, equal to or greater than the critical minimum threshold, but cannot be greater than the warning maximum threshold. A value of -1 disables the evaluation of this threshold."
	DEFVAL { "-2" }
	::= { winA3StatusHardwrEntry 19 }

winA3StatusHardwrResultWarnMax OBJECT-TYPE
	SYNTAX DisplayString
	ACCESS read-write
	STATUS mandatory
	DESCRIPTION "&<caiWinA3.1267>Current warning maximum threshold for the result monitoring of the hardware resource watcher. This value represents a rising threshold and must be equal to or greater than 0.0, equal to or greater than the warning minimum threshold, but cannot be greater than the critical maximum threshold. A value of -1 disables the evaluation of this threshold."
	DEFVAL { "-2" }
	::= { winA3StatusHardwrEntry 20 }

winA3StatusHardwrResultCritMin OBJECT-TYPE
	SYNTAX DisplayString
	ACCESS read-write
	STATUS mandatory
	DESCRIPTION "&<caiWinA3.1268>Current critical minimum threshold for the result monitoring of the hardware resource watcher. This value represents a declining threshold and must be equal to or greater than 0.0, but cannot be greater than the warning minimum threshold. A value of -1 disables the evaluation of this threshold."
	DEFVAL { "-2" }
	::= { winA3StatusHardwrEntry 21 }

winA3StatusHardwrResultCritMax OBJECT-TYPE
	SYNTAX DisplayString
	ACCESS read-write
	STATUS mandatory
	DESCRIPTION "&<caiWinA3.1269>Current critical maximum threshold for the result monitoring of the hardware resource watcher. This value represents a rising threshold and must be equal to or greater than 0.0, but cannot be less than the warning maximum threshold. A value of -1 disables the evaluation of this threshold."
	DEFVAL { "-2" }
	::= { winA3StatusHardwrEntry 22 }

winA3StatusHardwrResultMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.1270>Current monitor level for the result monitoring of the hardware resource watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusHardwrEntry 23 }

winA3StatusHardwrResultStatus OBJECT-TYPE
	SYNTAX INTEGER {
		unknown(1),
		up(2),
		down-warning(3),
		down-critical(4)
	}
	ACCESS read-only
	STATUS mandatory
	DESCRIPTION "&<caiWinA3.1271>Current status for the result monitoring of the hardware resource watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusHardwrEntry 24 }

winA3StatusHardwrLossAction OBJECT-TYPE
	SYNTAX INTEGER {
		remove(1),
		up(2),
		down-warning(3),
		down-critical(4)
	}
	ACCESS read-write
	STATUS mandatory
	DESCRIPTION "&<caiWinA3.1272>Current loss action for the hardware resource watcher. Specifies the action to take if the monitored hardware resource is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusHardwrEntry 25 }

winA3StatusHardwrLossStatus OBJECT-TYPE
	SYNTAX INTEGER {
		unknown(1),
		up(2),
		down-warning(3),
		down-critical(4)
	}
	ACCESS read-only
	STATUS mandatory
	DESCRIPTION "&<caiWinA3.1273>Current loss status of the hardware resource watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusHardwrEntry 26 }

winA3StatusHardwrCallBackRef OBJECT-TYPE
	SYNTAX DisplayString
	ACCESS read-only
	STATUS mandatory
	DESCRIPTION "&<caiWinA3.1274>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusHardwrEntry 27 }

winA3StatusHardwrButton OBJECT-TYPE
	SYNTAX INTEGER {
		none(1),
		remove(2),
		reset(3)
	}
	ACCESS read-write
	STATUS mandatory
	DESCRIPTION "&<caiWinA3.1275>This attribute is used to remove the hardware resource watcher. Additionally, if set to 3 (reset), the status of the watcher is set to OK and the error message string is set to the default value (a hyphen). If set to 2 (remove), the agent removes the watcher from the table. This attribute cannot be set to 1 (none)."
	DEFVAL { 1 }
	::= { winA3StatusHardwrEntry 28 }

--
-- The StatusProgrm Group
--

winA3StatusProgrmCount OBJECT-TYPE
	SYNTAX INTEGER
	ACCESS read-only
	STATUS mandatory
	DESCRIPTION "&<caiWinA3.1276>Number of entries in the programmable resource status table."
	::= { winA3StatusProgrmGroup 1 }

winA3StatusProgrmTable OBJECT-TYPE
	SYNTAX SEQUENCE OF WinA3StatusProgrmEntry
	ACCESS not-accessible
	STATUS mandatory
	DESCRIPTION "&<caiWinA3.1277>The programmable resource status table containing details about the currently configured programmable resource watchers."
	::= { winA3StatusProgrmGroup 2 }

winA3StatusProgrmEntry OBJECT-TYPE
	SYNTAX WinA3StatusProgrmEntry
	ACCESS not-accessible
	STATUS mandatory
	DESCRIPTION "&<caiWinA3.1278>Entry in the programmable resource status table."
	INDEX {
		winA3StatusProgrmResName,
		winA3StatusProgrmResSubName,
		winA3StatusProgrmInstName
	}
	::= { winA3StatusProgrmTable 1 }

WinA3StatusProgrmEntry ::= SEQUENCE {
	winA3StatusProgrmResName DisplayString,
	winA3StatusProgrmResSubName DisplayString,
	winA3StatusProgrmInstName DisplayString,
	winA3StatusProgrmDescription DisplayString,
	winA3StatusProgrmAutoWatcherName DisplayString,
	winA3StatusProgrmAggStatus INTEGER,
	winA3StatusProgrmCollectScript DisplayString,
	winA3StatusProgrmCollectArgs DisplayString,
	winA3StatusProgrmUserName DisplayString,
	winA3StatusProgrmSkipCount INTEGER,
	winA3StatusProgrmInfoMsg DisplayString,
	winA3StatusProgrmErrorMsg DisplayString,
	winA3StatusProgrmErrorMsgPattern DisplayString,
	winA3StatusProgrmErrorMsgMonitor INTEGER,
	winA3StatusProgrmErrorMsgStatus INTEGER,
	winA3StatusProgrmResultValue DisplayString,
	winA3StatusProgrmResultLagValue INTEGER,
	winA3StatusProgrmResultLag INTEGER,
	winA3StatusProgrmResultWarnMin DisplayString,
	winA3StatusProgrmResultWarnMax DisplayString,
	winA3StatusProgrmResultCritMin DisplayString,
	winA3StatusProgrmResultCritMax DisplayString,
	winA3StatusProgrmResultMonitor INTEGER,
	winA3StatusProgrmResultStatus INTEGER,
	winA3StatusProgrmLossAction INTEGER,
	winA3StatusProgrmLossStatus INTEGER,
	winA3StatusProgrmCallBackRef DisplayString,
	winA3StatusProgrmButton INTEGER
}

winA3StatusProgrmResName OBJECT-TYPE
	SYNTAX DisplayString
	ACCESS read-only
	STATUS mandatory
	DESCRIPTION "&<caiWinA3.1279>The name of the resource. This is the first index used by the agent in the different MIB tables for this resource (e.g. PowerSupply)."
	::= { winA3StatusProgrmEntry 1 }

winA3StatusProgrmResSubName OBJECT-TYPE
	SYNTAX DisplayString
	ACCESS read-only
	STATUS mandatory
	DESCRIPTION "&<caiWinA3.1280>The subname of the resource. This is the second index used by the agent in the different MIB tables for this resource (e.g. Voltage)."
	::= { winA3StatusProgrmEntry 2 }

winA3StatusProgrmInstName OBJECT-TYPE
	SYNTAX DisplayString
	ACCESS read-only
	STATUS mandatory
	DESCRIPTION "&<caiWinA3.1281>If a resource supports instances, this must be the name of an instance. The instance name is the third index used by the agent in the different MIB tables for this resource. If a resource does not support instances, <none> should be used as third index."
	::= { winA3StatusProgrmEntry 3 }

winA3StatusProgrmDescription OBJECT-TYPE
	SYNTAX DisplayString
	ACCESS read-write
	STATUS mandatory
	DESCRIPTION "&<caiWinA3.1282>Current description for the programmable resource watcher."
	::= { winA3StatusProgrmEntry 4 }

winA3StatusProgrmAutoWatcherName OBJECT-TYPE
	SYNTAX DisplayString
	ACCESS read-only
	STATUS mandatory
	DESCRIPTION "&<caiWinA3.1283>Name of the programmable resource auto watcher which automatically created this watcher. This attribute is left blank if the watcher was added manually."
	::= { winA3StatusProgrmEntry 5 }

winA3StatusProgrmAggStatus OBJECT-TYPE
	SYNTAX INTEGER {
		unknown(1),
		ok(2),
		warning(3),
		critical(4),
		passive(5)
	}
	ACCESS read-only
	STATUS mandatory
	DESCRIPTION "&<caiWinA3.1284>Current aggregate status of the programmable resource watcher. Represents the worst case aggregate of all its sub-states: 1 (unknown) - An error occurred during data collection, 2 (ok) - All sub-states are in good condition, 3 (warning) - One or more sub-states are in a warning condition, 4 (critical) - One or more sub-states are in a critical condition, 5 (passive) - The polling is disabled for the resource and hence no data collection occurs."
	::= { winA3StatusProgrmEntry 6 }

winA3StatusProgrmCollectScript OBJECT-TYPE
	SYNTAX DisplayString
	ACCESS read-only
	STATUS mandatory
	DESCRIPTION "&<caiWinA3.1285>This attribute can only be configured in the 'Generic.ini' file. Script to be called to retrieve the value for a resource. If a resource supports instances, the script needs to gather the values for all required instances in one call. The script must be in a dedicated directory (agents\config\caiWinA3). Any path element will be ignored."
	::= { winA3StatusProgrmEntry 7 }

winA3StatusProgrmCollectArgs OBJECT-TYPE
	SYNTAX DisplayString
	ACCESS read-only
	STATUS mandatory
	DESCRIPTION "&<caiWinA3.1286>This attribute can only be configured in the 'Generic.ini' file. Arguments passed to the collect script. If a resource supports instances, the names of all monitored instances are always appended and passed as last parameters."
	::= { winA3StatusProgrmEntry 8 }

winA3StatusProgrmUserName OBJECT-TYPE
	SYNTAX DisplayString
	ACCESS read-only
	STATUS mandatory
	DESCRIPTION "&<caiWinA3.1287>This attribute can only be configured in the 'Generic.ini' file. Specifies the user ID and the password (Syntax: user,passwd) to be used for the execution of any script."
	::= { winA3StatusProgrmEntry 9 }

winA3StatusProgrmSkipCount OBJECT-TYPE
	SYNTAX INTEGER
	ACCESS read-only
	STATUS mandatory
	DESCRIPTION "&<caiWinA3.1288>This attribute can only be configured in the 'Generic.ini' file. Current skip count for the programmable resource watcher. Specifies the number of consecutive poll intervals that should be passed without evaluating the watcher. This value must be equal to or greater than 0."
	::= { winA3StatusProgrmEntry 10 }

winA3StatusProgrmInfoMsg OBJECT-TYPE
	SYNTAX DisplayString
	ACCESS read-only
	STATUS mandatory
	DESCRIPTION "&<caiWinA3.1289>The info message string the agent collected from the script. The agent uses ...<PENDING>... as value for the info message as long as the corresponding collect script of this resource is still runnng."
	::= { winA3StatusProgrmEntry 11 }

winA3StatusProgrmErrorMsg OBJECT-TYPE
	SYNTAX DisplayString
	ACCESS read-only
	STATUS mandatory
	DESCRIPTION "&<caiWinA3.1290>The error message string the agent collected from the script. If the script did not finish and has been killed by the agent, the agent uses ...<TIMEOUT>... as value for the error message. Similar, if the script could not be started, the agent uses ...<ERROR>... as value for the error message."
	::= { winA3StatusProgrmEntry 12 }

winA3StatusProgrmErrorMsgPattern OBJECT-TYPE
	SYNTAX DisplayString
	ACCESS read-write
	STATUS mandatory
	DESCRIPTION "&<caiWinA3.1291>A regular expression (case-insensitive). If the error message matches this pattern, the error message status changes according to the error message monitor policy."
	::= { winA3StatusProgrmEntry 13 }

winA3StatusProgrmErrorMsgMonitor OBJECT-TYPE
	SYNTAX INTEGER {
		do-not-monitor(1),
		down-warning(2),
		down-critical(3)
	}
	ACCESS read-write
	STATUS mandatory
	DESCRIPTION "&<caiWinA3.1292>Current monitor level for the error message monitoring of the programmable resource watcher. If set to 1 (do-not-monitor), the agent does not evaluate the actual state of the resource and sets the status to ok. If set to 2 (down-warning), the agent uses a warning severity if the resource is in bad condition. If set to 3 (down-critical), the agent uses a critical severity if the resource is in bad condition."
	DEFVAL { 0 }
	::= { winA3StatusProgrmEntry 14 }

winA3StatusProgrmErrorMsgStatus OBJECT-TYPE
	SYNTAX INTEGER {
		unknown(1),
		up(2),
		down-warning(3),
		down-critical(4)
	}
	ACCESS read-only
	STATUS mandatory
	DESCRIPTION "&<caiWinA3.1293>Current status for the error message monitoring of the programmable resource watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusProgrmEntry 15 }

winA3StatusProgrmResultValue OBJECT-TYPE
	SYNTAX DisplayString
	ACCESS read-only
	STATUS mandatory
	DESCRIPTION "&<caiWinA3.1294>Current value for the result monitoring of the programmable resource watcher."
	DEFVAL { "0" }
	::= { winA3StatusProgrmEntry 16 }

winA3StatusProgrmResultLagValue OBJECT-TYPE
	SYNTAX INTEGER
	ACCESS read-only
	STATUS mandatory
	DESCRIPTION "&<caiWinA3.1295>Current number of consecutive threshold breaches for the result monitoring of the programmable resource watcher. The result state changes from ok as soon as the lag value reaches the configured value. The state reverts back to ok if a threshold is no longer breached."
	::= { winA3StatusProgrmEntry 17 }

winA3StatusProgrmResultLag OBJECT-TYPE
	SYNTAX INTEGER
	ACCESS read-write
	STATUS mandatory
	DESCRIPTION "&<caiWinA3.1296>Current lag setting for the result monitoring of the programmable resource watcher. Specifies the number of consecutive threshold breaches on which the result state changes. This value must be greater than 0."
	::= { winA3StatusProgrmEntry 18 }

winA3StatusProgrmResultWarnMin OBJECT-TYPE
	SYNTAX DisplayString
	ACCESS read-write
	STATUS mandatory
	DESCRIPTION "&<caiWinA3.1297>Current warning minimum threshold for the result monitoring of the programmable resource watcher. This value represents a declining threshold and must be equal to or greater than 0.0, equal to or greater than the critical minimum threshold, but cannot be greater than the warning maximum threshold. A value of -1 disables the evaluation of this threshold."
	DEFVAL { "-2" }
	::= { winA3StatusProgrmEntry 19 }

winA3StatusProgrmResultWarnMax OBJECT-TYPE
	SYNTAX DisplayString
	ACCESS read-write
	STATUS mandatory
	DESCRIPTION "&<caiWinA3.1298>Current warning maximum threshold for the result monitoring of the programmable resource watcher. This value represents a rising threshold and must be equal to or greater than 0.0, equal to or greater than the warning minimum threshold, but cannot be greater than the critical maximum threshold. A value of -1 disables the evaluation of this threshold."
	DEFVAL { "-2" }
	::= { winA3StatusProgrmEntry 20 }

winA3StatusProgrmResultCritMin OBJECT-TYPE
	SYNTAX DisplayString
	ACCESS read-write
	STATUS mandatory
	DESCRIPTION "&<caiWinA3.1299>Current critical minimum threshold for the result monitoring of the programmable resource watcher. This value represents a declining threshold and must be equal to or greater than 0.0, but cannot be greater than the warning minimum threshold. A value of -1 disables the evaluation of this threshold."
	DEFVAL { "-2" }
	::= { winA3StatusProgrmEntry 21 }

winA3StatusProgrmResultCritMax OBJECT-TYPE
	SYNTAX DisplayString
	ACCESS read-write
	STATUS mandatory
	DESCRIPTION "&<caiWinA3.1300>Current critical maximum threshold for the result monitoring of the programmable resource watcher. This value represents a rising threshold and must be equal to or greater than 0.0, but cannot be less than the warning maximum threshold. A value of -1 disables the evaluation of this threshold."
	DEFVAL { "-2" }
	::= { winA3StatusProgrmEntry 22 }

winA3StatusProgrmResultMonitor OBJECT-TYPE
	SYNTAX INTEGER {
		do-not-monitor(1),
		warning-only(2),
		critical-only(3),
		minimum-only(4),
		maximum-only(5),
		all(6)
	}
	ACCESS read-write
	STATUS mandatory
	DESCRIPTION "&<caiWinA3.1301>Current monitor level for the result monitoring of the programmable resource watcher. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
	DEFVAL { 0 }
	::= { winA3StatusProgrmEntry 23 }

winA3StatusProgrmResultStatus OBJECT-TYPE
	SYNTAX INTEGER {
		unknown(1),
		up(2),
		down-warning(3),
		down-critical(4)
	}
	ACCESS read-only
	STATUS mandatory
	DESCRIPTION "&<caiWinA3.1302>Current status for the result monitoring of the programmable resource watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusProgrmEntry 24 }

winA3StatusProgrmLossAction OBJECT-TYPE
	SYNTAX INTEGER {
		remove(1),
		up(2),
		down-warning(3),
		down-critical(4)
	}
	ACCESS read-write
	STATUS mandatory
	DESCRIPTION "&<caiWinA3.1303>Current loss action for the programmable resource watcher. Specifies the action to take if the monitored programmable resource is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
	DEFVAL { 0 }
	::= { winA3StatusProgrmEntry 25 }

winA3StatusProgrmLossStatus OBJECT-TYPE
	SYNTAX INTEGER {
		unknown(1),
		up(2),
		down-warning(3),
		down-critical(4)
	}
	ACCESS read-only
	STATUS mandatory
	DESCRIPTION "&<caiWinA3.1304>Current loss status of the programmable resource watcher: 1 (unknown) - An error occurred during data collection, 2 (up) - The resource is in good condition or status evaluation is turned off and/or polling is disabled, 3 (down-warning) - The resource is in bad condition and has been given a warning severity, 4 (down-critical) - The resource is in bad condition and has been given a critical severity."
	::= { winA3StatusProgrmEntry 26 }

winA3StatusProgrmCallBackRef OBJECT-TYPE
	SYNTAX DisplayString
	ACCESS read-only
	STATUS mandatory
	DESCRIPTION "&<caiWinA3.1305>This attribute specifies the name of a call-back reference if a user supplied script or application should be invoked in case of a status change. The configuration details of the call-back reference are located in the agent's call-back configuration file. This file contains an entry for each call-back reference detailing the path and name of the script/application to run, the arguments being passed to the script/application, the system account being used to execute the script/application, and whether the call-back should be invoked prior to a status change. A value for this attribute can only be supplied by a definition in a configuration set."
	::= { winA3StatusProgrmEntry 27 }

winA3StatusProgrmButton OBJECT-TYPE
	SYNTAX INTEGER {
		none(1),
		remove(2),
		reset(3)
	}
	ACCESS read-write
	STATUS mandatory
	DESCRIPTION "&<caiWinA3.1306>This attribute is used to remove the programmable resource watcher. Additionally, if set to 3 (reset), the status of the watcher is set to OK and the error message string is set to the default value (a hyphen). If set to 2 (remove), the agent removes the watcher from the table. This attribute cannot be set to 1 (none)."
	DEFVAL { 1 }
	::= { winA3StatusProgrmEntry 28 }

--
-- The AvailLVol Group
--

winA3AvailLVolNameFilter OBJECT-TYPE
	SYNTAX DisplayString
	ACCESS read-write
	STATUS mandatory
	DESCRIPTION "&<caiWinA3.1307>Name of the logical volume to be searched for when checking the Windows System for a list of available resources. A fully qualified logical volume name can be in drive letter format (e.g. C:) or in GUID format (e.g. Volume{2ab0a340-997c-11d6-9d96-00b0d09b7d72}). This name is used as a filter element and can be a regular expression (case-insensitive). It restricts the list of resources displayed in the available table."
	DEFVAL { ".*" }
	::= { winA3AvailLVolGroup 1 }

winA3AvailLVolMountsFilter OBJECT-TYPE
	SYNTAX DisplayString
	ACCESS read-write
	STATUS mandatory
	DESCRIPTION "&<caiWinA3.1308>A list of the mount points (seperated by pipe signs), where this logical volume is mounted on. This attribute is used as a filter element and can be a regular expression (case-insensitive). It restricts the list of resources displayed in the available table."
	DEFVAL { ".*" }
	::= { winA3AvailLVolGroup 2 }

winA3AvailLVolInfoFilter OBJECT-TYPE
	SYNTAX DisplayString
	ACCESS read-write
	STATUS mandatory
	DESCRIPTION "&<caiWinA3.1309>Information about the label, the filesystem (e.g. NTFS) and the alternate name (e.g. used in performance monitor) of the logical volume. This string has the format 'Label (FSys) (Alternate)'. 'Label' resp. 'FSys' are set to '-', if no label is defined, if the logical volume is not formatted or if it currently is in a clustered-passive state. 'Alternate' may be missing if not applicable (typically if the logical volume can be adressed by a drive letter). This attribute is used as a filter element and can be a regular expression (case-insensitive). It restricts the list of resources displayed in the available table."
	DEFVAL { ".*" }
	::= { winA3AvailLVolGroup 3 }

winA3AvailLVolClusterTypeFilter OBJECT-TYPE
	SYNTAX INTEGER {
		not-clustered(1),
		clustered-active(2),
		clustered-passive(3),
		any(4)
	}
	ACCESS read-write
	STATUS mandatory
	DESCRIPTION "&<caiWinA3.1310>Cluster type associated with the logical volume to be searched for when checking the Windows System for a list of available resources. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { winA3AvailLVolGroup 4 }

winA3AvailLVolMatchType OBJECT-TYPE
	SYNTAX INTEGER {
		positive(1),
		negative(2)
	}
	ACCESS read-write
	STATUS mandatory
	DESCRIPTION "&<caiWinA3.1311>Search algorithm the agent will apply when checking the Windows System for available logical volume resources. The filter is the logical AND of all attributes used to identify or otherwise narrow down resources. If set to 1 (positive), the agent searches for logical volume resources that match the filter. If set to 2 (negative), the agent searches for logical volume resources that do not match the filter."
	DEFVAL { 1 }
	::= { winA3AvailLVolGroup 5 }

winA3AvailLVolViewWindow OBJECT-TYPE
	SYNTAX DisplayString
	ACCESS read-only
	STATUS mandatory
	DESCRIPTION "&<caiWinA3.1312>This attribute indicates the number of the currently displayed buffer and the total number of buffers constituting the list of logical volume resources that are currently known to the agent and are available for monitoring."
	::= { winA3AvailLVolGroup 6 }

winA3AvailLVolButton OBJECT-TYPE
	SYNTAX INTEGER {
		none(1),
		next(2),
		previous(3),
		refresh(4)
	}
	ACCESS read-write
	STATUS mandatory
	DESCRIPTION "&<caiWinA3.1313>This attribute is used to update the list of logical volume resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailLVolGroup 7 }

winA3AvailLVolCount OBJECT-TYPE
	SYNTAX INTEGER
	ACCESS read-only
	STATUS mandatory
	DESCRIPTION "&<caiWinA3.1314>Number of logical volume resources that are currently known to the agent and are available for monitoring."
	::= { winA3AvailLVolGroup 8 }

--winA3AvailLVolTable OBJECT-TYPE
--	SYNTAX SEQUENCE OF WinA3AvailLVolEntry
--	ACCESS not-accessible
--	STATUS mandatory
--	DESCRIPTION "&<caiWinA3.1315>Table containing a list of logical volume resources that are currently known to the agent and are available for monitoring."
--	::= { winA3AvailLVolGroup 9 }

--winA3AvailLVolEntry OBJECT-TYPE
--	SYNTAX WinA3AvailLVolEntry
--	ACCESS not-accessible
--	STATUS mandatory
--	DESCRIPTION "&<caiWinA3.1316>Entry in the table of available logical volume resources."
--	::= { winA3AvailLVolTable 1 }

--WinA3AvailLVolEntry ::= SEQUENCE {
--	winA3AvailLVolName DisplayString,
--	winA3AvailLVolMounts DisplayString,
--	winA3AvailLVolInfo DisplayString,
--	winA3AvailLVolClusterType INTEGER
--}

--winA3AvailLVolName OBJECT-TYPE
--	SYNTAX DisplayString
--	ACCESS read-only
--	STATUS mandatory
--	DESCRIPTION "&<caiWinA3.1317>Name of the logical volume. A logical volume name can be in drive letter format (e.g. C:) or in GUID format (e.g. Volume{2ab0a340-997c-11d6-9d96-00b0d09b7d72})."
--	::= { winA3AvailLVolEntry 1 }

--winA3AvailLVolMounts OBJECT-TYPE
--	SYNTAX DisplayString
--	ACCESS read-only
--	STATUS mandatory
--	DESCRIPTION "&<caiWinA3.1318>A list of the mount points (seperated by pipe signs), where this logical volume is mounted on."
--	::= { winA3AvailLVolEntry 2 }

--winA3AvailLVolInfo OBJECT-TYPE
--	SYNTAX DisplayString
--	ACCESS read-only
--	STATUS mandatory
--	DESCRIPTION "&<caiWinA3.1319>Information about the label, the filesystem (e.g. NTFS) and the alternate name (e.g. used in performance monitor) of the logical volume. This string has the format 'Label (FSys) (Alternate)'. 'Label' resp. 'FSys' are set to '-', if no label is defined, if the logical volume is not formatted or if it currently is in a clustered-passive state. 'Alternate' may be missing if not applicable (typically if the logical volume can be adressed by a drive letter)."
--	::= { winA3AvailLVolEntry 3 }

--winA3AvailLVolClusterType OBJECT-TYPE
--	SYNTAX INTEGER {
--		not-clustered(1),
--		clustered-active(2),
--		clustered-passive(3)
--	}
--	ACCESS read-only
--	STATUS mandatory
--	DESCRIPTION "&<caiWinA3.1320>Cluster type of the logical volume: 1 (not-clustered) - Resource is not clustered, 2 (clustered-active) - Local cluster node has resource ownership, 3 (clustered-passive) - Another node in the cluster has resource ownership; the agent on the local node does not actively monitor the resource until ownership is transferred back."
--	::= { winA3AvailLVolEntry 4 }

--
-- The AvailMnt Group
--

winA3AvailMntNameFilter OBJECT-TYPE
	SYNTAX DisplayString
	ACCESS read-write
	STATUS mandatory
	DESCRIPTION "&<caiWinA3.1321>Name of the mount to be searched for when checking the Windows System for a list of available resources. This name is used as a filter element and can be a regular expression (case-insensitive). It restricts the list of resources displayed in the available table."
	DEFVAL { ".*" }
	::= { winA3AvailMntGroup 1 }

winA3AvailMntTargetFilter OBJECT-TYPE
	SYNTAX DisplayString
	ACCESS read-write
	STATUS mandatory
	DESCRIPTION "&<caiWinA3.1322>The name of the logical volume currently mounted by this mount. This attribute is used as a filter element and can be a regular expression (case-insensitive). It restricts the list of resources displayed in the available table."
	DEFVAL { ".*" }
	::= { winA3AvailMntGroup 2 }

winA3AvailMntClusterTypeFilter OBJECT-TYPE
	SYNTAX INTEGER {
		not-clustered(1),
		clustered-active(2),
		clustered-passive(3),
		any(4)
	}
	ACCESS read-write
	STATUS mandatory
	DESCRIPTION "&<caiWinA3.1323>Cluster type associated with the mount to be searched for when checking the Windows System for a list of available resources. Mounts that have become clustered-passive are no more displayed in the available table after a restart of the agent. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { winA3AvailMntGroup 3 }

winA3AvailMntMatchType OBJECT-TYPE
	SYNTAX INTEGER {
		positive(1),
		negative(2)
	}
	ACCESS read-write
	STATUS mandatory
	DESCRIPTION "&<caiWinA3.1324>Search algorithm the agent will apply when checking the Windows System for available mount resources. The filter is the logical AND of all attributes used to identify or otherwise narrow down resources. If set to 1 (positive), the agent searches for mount resources that match the filter. If set to 2 (negative), the agent searches for mount resources that do not match the filter."
	DEFVAL { 1 }
	::= { winA3AvailMntGroup 4 }

winA3AvailMntViewWindow OBJECT-TYPE
	SYNTAX DisplayString
	ACCESS read-only
	STATUS mandatory
	DESCRIPTION "&<caiWinA3.1325>This attribute indicates the number of the currently displayed buffer and the total number of buffers constituting the list of mount resources that are currently known to the agent and are available for monitoring."
	::= { winA3AvailMntGroup 5 }

winA3AvailMntButton OBJECT-TYPE
	SYNTAX INTEGER {
		none(1),
		next(2),
		previous(3),
		refresh(4)
	}
	ACCESS read-write
	STATUS mandatory
	DESCRIPTION "&<caiWinA3.1326>This attribute is used to update the list of mount resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailMntGroup 6 }

winA3AvailMntCount OBJECT-TYPE
	SYNTAX INTEGER
	ACCESS read-only
	STATUS mandatory
	DESCRIPTION "&<caiWinA3.1327>Number of mount resources that are currently known to the agent and are available for monitoring."
	::= { winA3AvailMntGroup 7 }

--winA3AvailMntTable OBJECT-TYPE
--	SYNTAX SEQUENCE OF WinA3AvailMntEntry
--	ACCESS not-accessible
--	STATUS mandatory
--	DESCRIPTION "&<caiWinA3.1328>Table containing a list of mount resources that are currently known to the agent and are available for monitoring."
--	::= { winA3AvailMntGroup 8 }

--winA3AvailMntEntry OBJECT-TYPE
--	SYNTAX WinA3AvailMntEntry
--	ACCESS not-accessible
--	STATUS mandatory
--	DESCRIPTION "&<caiWinA3.1329>Entry in the table of available mount resources."
--	::= { winA3AvailMntTable 1 }

--WinA3AvailMntEntry ::= SEQUENCE {
--	winA3AvailMntName DisplayString,
--	winA3AvailMntTarget DisplayString,
--	winA3AvailMntClusterType INTEGER
--}

--winA3AvailMntName OBJECT-TYPE
--	SYNTAX DisplayString
--	ACCESS read-only
--	STATUS mandatory
--	DESCRIPTION "&<caiWinA3.1330>Name of the mount."
--	::= { winA3AvailMntEntry 1 }

--winA3AvailMntTarget OBJECT-TYPE
--	SYNTAX DisplayString
--	ACCESS read-only
--	STATUS mandatory
--	DESCRIPTION "&<caiWinA3.1331>The name of the logical volume currently mounted by this mount."
--	::= { winA3AvailMntEntry 2 }

--winA3AvailMntClusterType OBJECT-TYPE
--	SYNTAX INTEGER {
--		not-clustered(1),
--		clustered-active(2),
--		clustered-passive(3)
--	}
--	ACCESS read-only
--	STATUS mandatory
--	DESCRIPTION "&<caiWinA3.1332>Cluster type of the mount: Mounts that have become clustered-passive are no more displayed in the available table after a restart of the agent. 1 (not-clustered) - Resource is not clustered, 2 (clustered-active) - Local cluster node has resource ownership, 3 (clustered-passive) - Another node in the cluster has resource ownership; the agent on the local node does not actively monitor the resource until ownership is transferred back."
--	::= { winA3AvailMntEntry 3 }

--
-- The AvailDfs Group
--

winA3AvailDfsNameFilter OBJECT-TYPE
	SYNTAX DisplayString
	ACCESS read-write
	STATUS mandatory
	DESCRIPTION "&<caiWinA3.1333>Name of the distributed file system link to be searched for when checking the Windows System for a list of available resources. A fully qualified Dfs name consists of the Dfs root name followed by the Dfs link name. These two names are concatenated by a back-slash. This name is used as a filter element and can be a regular expression (case-insensitive). It restricts the list of resources displayed in the available table."
	DEFVAL { ".*" }
	::= { winA3AvailDfsGroup 1 }

winA3AvailDfsTargetsListFilter OBJECT-TYPE
	SYNTAX DisplayString
	ACCESS read-write
	STATUS mandatory
	DESCRIPTION "&<caiWinA3.1334>A list of the targets (seperated by pipe signs), currently configured for this Dfs link. This attribute is used as a filter element and can be a regular expression (case-insensitive). It restricts the list of resources displayed in the available table."
	DEFVAL { ".*" }
	::= { winA3AvailDfsGroup 2 }

winA3AvailDfsMatchType OBJECT-TYPE
	SYNTAX INTEGER {
		positive(1),
		negative(2)
	}
	ACCESS read-write
	STATUS mandatory
	DESCRIPTION "&<caiWinA3.1335>Search algorithm the agent will apply when checking the Windows System for available distributed file system link resources. The filter is the logical AND of all attributes used to identify or otherwise narrow down resources. If set to 1 (positive), the agent searches for distributed file system link resources that match the filter. If set to 2 (negative), the agent searches for distributed file system link resources that do not match the filter."
	DEFVAL { 1 }
	::= { winA3AvailDfsGroup 3 }

winA3AvailDfsViewWindow OBJECT-TYPE
	SYNTAX DisplayString
	ACCESS read-only
	STATUS mandatory
	DESCRIPTION "&<caiWinA3.1336>This attribute indicates the number of the currently displayed buffer and the total number of buffers constituting the list of distributed file system link resources that are currently known to the agent and are available for monitoring."
	::= { winA3AvailDfsGroup 4 }

winA3AvailDfsButton OBJECT-TYPE
	SYNTAX INTEGER {
		none(1),
		next(2),
		previous(3),
		refresh(4)
	}
	ACCESS read-write
	STATUS mandatory
	DESCRIPTION "&<caiWinA3.1337>This attribute is used to update the list of distributed file system link resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailDfsGroup 5 }

winA3AvailDfsCount OBJECT-TYPE
	SYNTAX INTEGER
	ACCESS read-only
	STATUS mandatory
	DESCRIPTION "&<caiWinA3.1338>Number of distributed file system link resources that are currently known to the agent and are available for monitoring."
	::= { winA3AvailDfsGroup 6 }

--winA3AvailDfsTable OBJECT-TYPE
--	SYNTAX SEQUENCE OF WinA3AvailDfsEntry
--	ACCESS not-accessible
--	STATUS mandatory
--	DESCRIPTION "&<caiWinA3.1339>Table containing a list of distributed file system link resources that are currently known to the agent and are available for monitoring."
--	::= { winA3AvailDfsGroup 7 }

--winA3AvailDfsEntry OBJECT-TYPE
--	SYNTAX WinA3AvailDfsEntry
--	ACCESS not-accessible
--	STATUS mandatory
--	DESCRIPTION "&<caiWinA3.1340>Entry in the table of available distributed file system link resources."
--	::= { winA3AvailDfsTable 1 }

--WinA3AvailDfsEntry ::= SEQUENCE {
--	winA3AvailDfsName DisplayString,
--	winA3AvailDfsTargetsList DisplayString
--}

--winA3AvailDfsName OBJECT-TYPE
--	SYNTAX DisplayString
--	ACCESS read-only
--	STATUS mandatory
--	DESCRIPTION "&<caiWinA3.1341>Name of the distributed file system link. A fully qualified Dfs name consists of the Dfs root name followed by the Dfs link name. These two names are concatenated by a back-slash. Note that monitoring of DFS links is not applicable on Windows XP and on Windows 2000 Professional."
--	::= { winA3AvailDfsEntry 1 }

--winA3AvailDfsTargetsList OBJECT-TYPE
--	SYNTAX DisplayString
--	ACCESS read-only
--	STATUS mandatory
--	DESCRIPTION "&<caiWinA3.1342>A list of the targets (seperated by pipe signs), currently configured for this Dfs link."
--	::= { winA3AvailDfsEntry 2 }

--
-- The AvailQuota Group
--

winA3AvailQuotaLVolNameFilter OBJECT-TYPE
	SYNTAX DisplayString
	ACCESS read-write
	STATUS mandatory
	DESCRIPTION "&<caiWinA3.1343>LVol name part of the quota. A fully qualified name specifies the logical volume on which this quota exists. This name is used as a filter element and can be a regular expression (case-insensitive). It restricts the list of resources displayed in the available table."
	DEFVAL { ".*" }
	::= { winA3AvailQuotaGroup 1 }

winA3AvailQuotaUserNameFilter OBJECT-TYPE
	SYNTAX DisplayString
	ACCESS read-write
	STATUS mandatory
	DESCRIPTION "&<caiWinA3.1344>User name part of the quota. A fully qualified name specifies the user for whom this quota exists and is in the form 'domainName\\userName' or 'userName@domainName'. This name is used as a filter element and can be a regular expression (case-insensitive). It restricts the list of resources displayed in the available table."
	DEFVAL { ".*" }
	::= { winA3AvailQuotaGroup 2 }

winA3AvailQuotaWarnLevelFilter OBJECT-TYPE
	SYNTAX DisplayString
	ACCESS read-write
	STATUS mandatory
	DESCRIPTION "&<caiWinA3.1345>The warning level, in kilobytes, for this quota, as defined in the Windows quota management. A value of zero means 'No Limit'. This attribute is used as a filter element and can be greater or equal to 0, filtering out all values being greater or equal. It restricts the list of resources displayed in the available table."
	DEFVAL { "0.0" }
	::= { winA3AvailQuotaGroup 3 }

winA3AvailQuotaLimitFilter OBJECT-TYPE
	SYNTAX DisplayString
	ACCESS read-write
	STATUS mandatory
	DESCRIPTION "&<caiWinA3.1346>The limit, in kilobytes, for this quota, as defined in the Windows quota management. A value of zero means 'No Limit'. This attribute is used as a filter element and can be greater or equal to 0, filtering out all values being greater or equal. It restricts the list of resources displayed in the available table."
	DEFVAL { "0.0" }
	::= { winA3AvailQuotaGroup 4 }

winA3AvailQuotaMatchType OBJECT-TYPE
	SYNTAX INTEGER {
		positive(1),
		negative(2)
	}
	ACCESS read-write
	STATUS mandatory
	DESCRIPTION "&<caiWinA3.1347>Search algorithm the agent will apply when checking the Windows System for available quota resources. The filter is the logical AND of all attributes used to identify or otherwise narrow down resources. If set to 1 (positive), the agent searches for quota resources that match the filter. If set to 2 (negative), the agent searches for quota resources that do not match the filter."
	DEFVAL { 1 }
	::= { winA3AvailQuotaGroup 5 }

winA3AvailQuotaViewWindow OBJECT-TYPE
	SYNTAX DisplayString
	ACCESS read-only
	STATUS mandatory
	DESCRIPTION "&<caiWinA3.1348>This attribute indicates the number of the currently displayed buffer and the total number of buffers constituting the list of quota resources that are currently known to the agent and are available for monitoring."
	::= { winA3AvailQuotaGroup 6 }

winA3AvailQuotaButton OBJECT-TYPE
	SYNTAX INTEGER {
		none(1),
		next(2),
		previous(3),
		refresh(4)
	}
	ACCESS read-write
	STATUS mandatory
	DESCRIPTION "&<caiWinA3.1349>This attribute is used to update the list of quota resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailQuotaGroup 7 }

winA3AvailQuotaCount OBJECT-TYPE
	SYNTAX INTEGER
	ACCESS read-only
	STATUS mandatory
	DESCRIPTION "&<caiWinA3.1350>Number of quota resources that are currently known to the agent and are available for monitoring."
	::= { winA3AvailQuotaGroup 8 }

--winA3AvailQuotaTable OBJECT-TYPE
--	SYNTAX SEQUENCE OF WinA3AvailQuotaEntry
--	ACCESS not-accessible
--	STATUS mandatory
--	DESCRIPTION "&<caiWinA3.1351>Table containing a list of quota resources that are currently known to the agent and are available for monitoring."
--	::= { winA3AvailQuotaGroup 9 }

--winA3AvailQuotaEntry OBJECT-TYPE
--	SYNTAX WinA3AvailQuotaEntry
--	ACCESS not-accessible
--	STATUS mandatory
--	DESCRIPTION "&<caiWinA3.1352>Entry in the table of available quota resources."
--	::= { winA3AvailQuotaTable 1 }

--WinA3AvailQuotaEntry ::= SEQUENCE {
--	winA3AvailQuotaLVolName DisplayString,
--	winA3AvailQuotaUserName DisplayString,
--	winA3AvailQuotaWarnLevel DisplayString,
--	winA3AvailQuotaLimit DisplayString
--}

--winA3AvailQuotaLVolName OBJECT-TYPE
--	SYNTAX DisplayString
--	ACCESS read-only
--	STATUS mandatory
--	DESCRIPTION "&<caiWinA3.1353>LVol name part of the quota, specifying the logical volume on which this quota exists."
--	::= { winA3AvailQuotaEntry 1 }

--winA3AvailQuotaUserName OBJECT-TYPE
--	SYNTAX DisplayString
--	ACCESS read-only
--	STATUS mandatory
--	DESCRIPTION "&<caiWinA3.1354>User name part of the quota, specifying the user for whom this quota exists. This name can be in the form 'domainName\\userName' or 'userName@domainName'."
--	::= { winA3AvailQuotaEntry 2 }

--winA3AvailQuotaWarnLevel OBJECT-TYPE
--	SYNTAX DisplayString
--	ACCESS read-only
--	STATUS mandatory
--	DESCRIPTION "&<caiWinA3.1355>The warning level, in kilobytes, for this quota, as defined in the Windows quota management. A value of zero means 'No Limit'. If adding a watcher, this value can be used as default warning threshold."
--	::= { winA3AvailQuotaEntry 3 }

--winA3AvailQuotaLimit OBJECT-TYPE
--	SYNTAX DisplayString
--	ACCESS read-only
--	STATUS mandatory
--	DESCRIPTION "&<caiWinA3.1356>The limit, in kilobytes, for this quota, as defined in the Windows quota management. A value of zero means 'No Limit'. If adding a watcher, this value can be used as default critical threshold."
--	::= { winA3AvailQuotaEntry 4 }

--
-- The AvailProc Group
--

winA3AvailProcNameFilter OBJECT-TYPE
	SYNTAX DisplayString
	ACCESS read-write
	STATUS mandatory
	DESCRIPTION "&<caiWinA3.1357>Name of the process to be searched for when checking the Windows System for a list of available resources. This name is used as a filter element and can be a regular expression (case-insensitive). It restricts the list of resources displayed in the available table."
	DEFVAL { ".*" }
	::= { winA3AvailProcGroup 1 }

winA3AvailProcPathFilter OBJECT-TYPE
	SYNTAX DisplayString
	ACCESS read-write
	STATUS mandatory
	DESCRIPTION "&<caiWinA3.1358>Path name of the process. This name is used as a filter element and can be a regular expression (case-insensitive). It restricts the list of resources displayed in the available table."
	DEFVAL { ".*" }
	::= { winA3AvailProcGroup 2 }

winA3AvailProcUserFilter OBJECT-TYPE
	SYNTAX DisplayString
	ACCESS read-write
	STATUS mandatory
	DESCRIPTION "&<caiWinA3.1359>User name of the process. This name is used as a filter element and can be a regular expression (case-insensitive). It restricts the list of resources displayed in the available table."
	DEFVAL { ".*" }
	::= { winA3AvailProcGroup 3 }

winA3AvailProcClusterTypeFilter OBJECT-TYPE
	SYNTAX INTEGER {
		not-clustered(1),
		clustered-active(2),
		clustered-passive(3),
		any(4)
	}
	ACCESS read-write
	STATUS mandatory
	DESCRIPTION "&<caiWinA3.1360>Reserved for future use."
	DEFVAL { 4 }
	::= { winA3AvailProcGroup 4 }

winA3AvailProcMatchType OBJECT-TYPE
	SYNTAX INTEGER {
		positive(1),
		negative(2)
	}
	ACCESS read-write
	STATUS mandatory
	DESCRIPTION "&<caiWinA3.1361>Search algorithm the agent will apply when checking the Windows System for available process resources. The filter is the logical AND of all attributes used to identify or otherwise narrow down resources. If set to 1 (positive), the agent searches for process resources that match the filter. If set to 2 (negative), the agent searches for process resources that do not match the filter."
	DEFVAL { 1 }
	::= { winA3AvailProcGroup 5 }

winA3AvailProcViewWindow OBJECT-TYPE
	SYNTAX DisplayString
	ACCESS read-only
	STATUS mandatory
	DESCRIPTION "&<caiWinA3.1362>This attribute indicates the number of the currently displayed buffer and the total number of buffers constituting the list of process resources that are currently known to the agent and are available for monitoring."
	::= { winA3AvailProcGroup 6 }

winA3AvailProcButton OBJECT-TYPE
	SYNTAX INTEGER {
		none(1),
		next(2),
		previous(3),
		refresh(4)
	}
	ACCESS read-write
	STATUS mandatory
	DESCRIPTION "&<caiWinA3.1363>This attribute is used to update the list of process resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailProcGroup 7 }

winA3AvailProcCount OBJECT-TYPE
	SYNTAX INTEGER
	ACCESS read-only
	STATUS mandatory
	DESCRIPTION "&<caiWinA3.1364>Number of process resources that are currently known to the agent and are available for monitoring."
	::= { winA3AvailProcGroup 8 }

--winA3AvailProcTable OBJECT-TYPE
--	SYNTAX SEQUENCE OF WinA3AvailProcEntry
--	ACCESS not-accessible
--	STATUS mandatory
--	DESCRIPTION "&<caiWinA3.1365>Table containing a list of process resources that are currently known to the agent and are available for monitoring."
--	::= { winA3AvailProcGroup 9 }

--winA3AvailProcEntry OBJECT-TYPE
--	SYNTAX WinA3AvailProcEntry
--	ACCESS not-accessible
--	STATUS mandatory
--	DESCRIPTION "&<caiWinA3.1366>Entry in the table of available process resources."
--	::= { winA3AvailProcTable 1 }

--WinA3AvailProcEntry ::= SEQUENCE {
--	winA3AvailProcPid INTEGER,
--	winA3AvailProcName DisplayString,
--	winA3AvailProcPath DisplayString,
--	winA3AvailProcUser DisplayString,
--	winA3AvailProcClusterType INTEGER
--}

--winA3AvailProcPid OBJECT-TYPE
--	SYNTAX INTEGER
--	ACCESS read-only
--	STATUS mandatory
--	DESCRIPTION "&<caiWinA3.1367>The process ID of the process."
--	::= { winA3AvailProcEntry 1 }

--winA3AvailProcName OBJECT-TYPE
--	SYNTAX DisplayString
--	ACCESS read-only
--	STATUS mandatory
--	DESCRIPTION "&<caiWinA3.1368>Name of the process."
--	::= { winA3AvailProcEntry 2 }

--winA3AvailProcPath OBJECT-TYPE
--	SYNTAX DisplayString
--	ACCESS read-only
--	STATUS mandatory
--	DESCRIPTION "&<caiWinA3.1369>Path name of the process."
--	::= { winA3AvailProcEntry 3 }

--winA3AvailProcUser OBJECT-TYPE
--	SYNTAX DisplayString
--	ACCESS read-only
--	STATUS mandatory
--	DESCRIPTION "&<caiWinA3.1370>User name of the process."
--	::= { winA3AvailProcEntry 4 }

--winA3AvailProcClusterType OBJECT-TYPE
--	SYNTAX INTEGER {
--		not-clustered(1),
--		clustered-active(2),
--		clustered-passive(3)
--	}
--	ACCESS read-only
--	STATUS mandatory
--	DESCRIPTION "&<caiWinA3.1371>Reserved for future use."
--	::= { winA3AvailProcEntry 5 }

--
-- The AvailSrvc Group
--

winA3AvailSrvcNameFilter OBJECT-TYPE
	SYNTAX DisplayString
	ACCESS read-write
	STATUS mandatory
	DESCRIPTION "&<caiWinA3.1372>Name of the service to be searched for when checking the Windows System for a list of available resources. For uniqueness, the service name must be specified as defined in the Windows registry. This name is typically different to the display name of a service, visible in the service manager console. This name is used as a filter element and can be a regular expression (case-insensitive). It restricts the list of resources displayed in the available table."
	DEFVAL { ".*" }
	::= { winA3AvailSrvcGroup 1 }

winA3AvailSrvcDisplayNameFilter OBJECT-TYPE
	SYNTAX DisplayString
	ACCESS read-write
	STATUS mandatory
	DESCRIPTION "&<caiWinA3.1373>The display name of a service as visible in the service manager console. This attribute is used as a filter element and can be a regular expression (case-insensitive). It restricts the list of resources displayed in the available table."
	DEFVAL { ".*" }
	::= { winA3AvailSrvcGroup 2 }

winA3AvailSrvcStartupTypeFilter OBJECT-TYPE
	SYNTAX INTEGER {
		automatic(1),
		manual(2),
		disabled(3),
		any(4)
	}
	ACCESS read-write
	STATUS mandatory
	DESCRIPTION "&<caiWinA3.1374>The current startup type (automatic, manual or disabled) of the service. This attribute is used as a filter element. It restricts the list of resources displayed in the available table."
	DEFVAL { 4 }
	::= { winA3AvailSrvcGroup 3 }

winA3AvailSrvcAccountFilter OBJECT-TYPE
	SYNTAX DisplayString
	ACCESS read-write
	STATUS mandatory
	DESCRIPTION "&<caiWinA3.1375>The account, the system uses to start this service. This attribute is used as a filter element and can be a regular expression (case-insensitive). It restricts the list of resources displayed in the available table."
	DEFVAL { ".*" }
	::= { winA3AvailSrvcGroup 4 }

winA3AvailSrvcExecutableFilter OBJECT-TYPE
	SYNTAX DisplayString
	ACCESS read-write
	STATUS mandatory
	DESCRIPTION "&<caiWinA3.1376>The executable belonging to this service. This attribute is used as a filter element and can be a regular expression (case-insensitive). It restricts the list of resources displayed in the available table."
	DEFVAL { ".*" }
	::= { winA3AvailSrvcGroup 5 }

winA3AvailSrvcClusterTypeFilter OBJECT-TYPE
	SYNTAX INTEGER {
		not-clustered(1),
		clustered-active(2),
		clustered-passive(3),
		any(4)
	}
	ACCESS read-write
	STATUS mandatory
	DESCRIPTION "&<caiWinA3.1377>Cluster type associated with the service to be searched for when checking the Windows System for a list of available resources. If set to 1 (not-clustered), the search is restricted to not-clustered resources only. If set to 2 (clustered-active), the search is restricted to clustered-active resources only. If set to 3 (clustered-passive), the search is restricted to clustered-passive resources only. If set to 4 (any), the cluster type does not affect the search."
	DEFVAL { 4 }
	::= { winA3AvailSrvcGroup 6 }

winA3AvailSrvcMatchType OBJECT-TYPE
	SYNTAX INTEGER {
		positive(1),
		negative(2)
	}
	ACCESS read-write
	STATUS mandatory
	DESCRIPTION "&<caiWinA3.1378>Search algorithm the agent will apply when checking the Windows System for available service resources. The filter is the logical AND of all attributes used to identify or otherwise narrow down resources. If set to 1 (positive), the agent searches for service resources that match the filter. If set to 2 (negative), the agent searches for service resources that do not match the filter."
	DEFVAL { 1 }
	::= { winA3AvailSrvcGroup 7 }

winA3AvailSrvcViewWindow OBJECT-TYPE
	SYNTAX DisplayString
	ACCESS read-only
	STATUS mandatory
	DESCRIPTION "&<caiWinA3.1379>This attribute indicates the number of the currently displayed buffer and the total number of buffers constituting the list of service resources that are currently known to the agent and are available for monitoring."
	::= { winA3AvailSrvcGroup 8 }

winA3AvailSrvcButton OBJECT-TYPE
	SYNTAX INTEGER {
		none(1),
		next(2),
		previous(3),
		refresh(4)
	}
	ACCESS read-write
	STATUS mandatory
	DESCRIPTION "&<caiWinA3.1380>This attribute is used to update the list of service resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailSrvcGroup 9 }

winA3AvailSrvcCount OBJECT-TYPE
	SYNTAX INTEGER
	ACCESS read-only
	STATUS mandatory
	DESCRIPTION "&<caiWinA3.1381>Number of service resources that are currently known to the agent and are available for monitoring."
	::= { winA3AvailSrvcGroup 10 }

--winA3AvailSrvcTable OBJECT-TYPE
--	SYNTAX SEQUENCE OF WinA3AvailSrvcEntry
--	ACCESS not-accessible
--	STATUS mandatory
--	DESCRIPTION "&<caiWinA3.1382>Table containing a list of service resources that are currently known to the agent and are available for monitoring."
--	::= { winA3AvailSrvcGroup 11 }

--winA3AvailSrvcEntry OBJECT-TYPE
--	SYNTAX WinA3AvailSrvcEntry
--	ACCESS not-accessible
--	STATUS mandatory
--	DESCRIPTION "&<caiWinA3.1383>Entry in the table of available service resources."
--	::= { winA3AvailSrvcTable 1 }

--WinA3AvailSrvcEntry ::= SEQUENCE {
--	winA3AvailSrvcName DisplayString,
--	winA3AvailSrvcDisplayName DisplayString,
--	winA3AvailSrvcStartupType INTEGER,
--	winA3AvailSrvcAccount DisplayString,
--	winA3AvailSrvcExecutable DisplayString,
--	winA3AvailSrvcClusterType INTEGER
--}

--winA3AvailSrvcName OBJECT-TYPE
--	SYNTAX DisplayString
--	ACCESS read-only
--	STATUS mandatory
--	DESCRIPTION "&<caiWinA3.1384>Name of the service. For uniqueness, the service name is given as defined in the Windows registry. This name is typically different to the display name of a service, visible in the service manager console."
--	::= { winA3AvailSrvcEntry 1 }

--winA3AvailSrvcDisplayName OBJECT-TYPE
--	SYNTAX DisplayString
--	ACCESS read-only
--	STATUS mandatory
--	DESCRIPTION "&<caiWinA3.1385>The display name of a service as visible in the service manager console."
--	::= { winA3AvailSrvcEntry 2 }

--winA3AvailSrvcStartupType OBJECT-TYPE
--	SYNTAX INTEGER {
--		automatic(1),
--		manual(2),
--		disabled(3)
--	}
--	ACCESS read-only
--	STATUS mandatory
--	DESCRIPTION "&<caiWinA3.1386>The current startup type (automatic, manual or disabled) of the service."
--	::= { winA3AvailSrvcEntry 3 }

--winA3AvailSrvcAccount OBJECT-TYPE
--	SYNTAX DisplayString
--	ACCESS read-only
--	STATUS mandatory
--	DESCRIPTION "&<caiWinA3.1387>The account, the system uses to start this service."
--	::= { winA3AvailSrvcEntry 4 }

--winA3AvailSrvcExecutable OBJECT-TYPE
--	SYNTAX DisplayString
--	ACCESS read-only
--	STATUS mandatory
--	DESCRIPTION "&<caiWinA3.1388>The executable belonging to this service."
--	::= { winA3AvailSrvcEntry 5 }

--winA3AvailSrvcClusterType OBJECT-TYPE
--	SYNTAX INTEGER {
--		not-clustered(1),
--		clustered-active(2),
--		clustered-passive(3)
--	}
--	ACCESS read-only
--	STATUS mandatory
--	DESCRIPTION "&<caiWinA3.1389>Cluster type of the service: 1 (not-clustered) - Resource is not clustered, 2 (clustered-active) - Local cluster node has resource ownership, 3 (clustered-passive) - Another node in the cluster has resource ownership; the agent on the local node does not actively monitor the resource until ownership is transferred back."
--	::= { winA3AvailSrvcEntry 6 }

--
-- The AvailJob Group
--

winA3AvailJobNameFilter OBJECT-TYPE
	SYNTAX DisplayString
	ACCESS read-write
	STATUS mandatory
	DESCRIPTION "&<caiWinA3.1390>Name of the job to be searched for when checking the Windows System for a list of available resources. A job is a set of processes that is handled as a process group. This name is used as a filter element and can be a regular expression (case-insensitive). It restricts the list of resources displayed in the available table."
	DEFVAL { ".*" }
	::= { winA3AvailJobGroup 1 }

winA3AvailJobMatchType OBJECT-TYPE
	SYNTAX INTEGER {
		positive(1),
		negative(2)
	}
	ACCESS read-write
	STATUS mandatory
	DESCRIPTION "&<caiWinA3.1391>Search algorithm the agent will apply when checking the Windows System for available job resources. The filter is the logical AND of all attributes used to identify or otherwise narrow down resources. If set to 1 (positive), the agent searches for job resources that match the filter. If set to 2 (negative), the agent searches for job resources that do not match the filter."
	DEFVAL { 1 }
	::= { winA3AvailJobGroup 2 }

winA3AvailJobViewWindow OBJECT-TYPE
	SYNTAX DisplayString
	ACCESS read-only
	STATUS mandatory
	DESCRIPTION "&<caiWinA3.1392>This attribute indicates the number of the currently displayed buffer and the total number of buffers constituting the list of job resources that are currently known to the agent and are available for monitoring."
	::= { winA3AvailJobGroup 3 }

winA3AvailJobButton OBJECT-TYPE
	SYNTAX INTEGER {
		none(1),
		next(2),
		previous(3),
		refresh(4)
	}
	ACCESS read-write
	STATUS mandatory
	DESCRIPTION "&<caiWinA3.1393>This attribute is used to update the list of job resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailJobGroup 4 }

winA3AvailJobCount OBJECT-TYPE
	SYNTAX INTEGER
	ACCESS read-only
	STATUS mandatory
	DESCRIPTION "&<caiWinA3.1394>Number of job resources that are currently known to the agent and are available for monitoring."
	::= { winA3AvailJobGroup 5 }

--winA3AvailJobTable OBJECT-TYPE
--	SYNTAX SEQUENCE OF WinA3AvailJobEntry
--	ACCESS not-accessible
--	STATUS mandatory
--	DESCRIPTION "&<caiWinA3.1395>Table containing a list of job resources that are currently known to the agent and are available for monitoring."
--	::= { winA3AvailJobGroup 6 }

--winA3AvailJobEntry OBJECT-TYPE
--	SYNTAX WinA3AvailJobEntry
--	ACCESS not-accessible
--	STATUS mandatory
--	DESCRIPTION "&<caiWinA3.1396>Entry in the table of available job resources."
--	::= { winA3AvailJobTable 1 }

--WinA3AvailJobEntry ::= SEQUENCE {
--	winA3AvailJobName DisplayString
--}

--winA3AvailJobName OBJECT-TYPE
--	SYNTAX DisplayString
--	ACCESS read-only
--	STATUS mandatory
--	DESCRIPTION "&<caiWinA3.1397>Name of the job. A job is a set of processes that is handled as a process group."
--	::= { winA3AvailJobEntry 1 }

--
-- The AvailSess Group
--

winA3AvailSessClientFilter OBJECT-TYPE
	SYNTAX DisplayString
	ACCESS read-write
	STATUS mandatory
	DESCRIPTION "&<caiWinA3.1398>Client name of the session. The client name is the name of the host, from where this session was initiated. This name is used as a filter element and can be a regular expression (case-insensitive). It restricts the list of resources displayed in the available table."
	DEFVAL { ".*" }
	::= { winA3AvailSessGroup 1 }

winA3AvailSessUserFilter OBJECT-TYPE
	SYNTAX DisplayString
	ACCESS read-write
	STATUS mandatory
	DESCRIPTION "&<caiWinA3.1399>User name of the session. The user name specifies the user, who logged in and is in the form 'domainName\\userName' This name is used as a filter element and can be a regular expression (case-insensitive). It restricts the list of resources displayed in the available table."
	DEFVAL { ".*" }
	::= { winA3AvailSessGroup 2 }

winA3AvailSessMatchType OBJECT-TYPE
	SYNTAX INTEGER {
		positive(1),
		negative(2)
	}
	ACCESS read-write
	STATUS mandatory
	DESCRIPTION "&<caiWinA3.1400>Search algorithm the agent will apply when checking the Windows System for available terminal session resources. The filter is the logical AND of all attributes used to identify or otherwise narrow down resources. If set to 1 (positive), the agent searches for terminal session resources that match the filter. If set to 2 (negative), the agent searches for terminal session resources that do not match the filter."
	DEFVAL { 1 }
	::= { winA3AvailSessGroup 3 }

winA3AvailSessViewWindow OBJECT-TYPE
	SYNTAX DisplayString
	ACCESS read-only
	STATUS mandatory
	DESCRIPTION "&<caiWinA3.1401>This attribute indicates the number of the currently displayed buffer and the total number of buffers constituting the list of terminal session resources that are currently known to the agent and are available for monitoring."
	::= { winA3AvailSessGroup 4 }

winA3AvailSessButton OBJECT-TYPE
	SYNTAX INTEGER {
		none(1),
		next(2),
		previous(3),
		refresh(4)
	}
	ACCESS read-write
	STATUS mandatory
	DESCRIPTION "&<caiWinA3.1402>This attribute is used to update the list of terminal session resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailSessGroup 5 }

winA3AvailSessCount OBJECT-TYPE
	SYNTAX INTEGER
	ACCESS read-only
	STATUS mandatory
	DESCRIPTION "&<caiWinA3.1403>Number of terminal session resources that are currently known to the agent and are available for monitoring."
	::= { winA3AvailSessGroup 6 }

--winA3AvailSessTable OBJECT-TYPE
--	SYNTAX SEQUENCE OF WinA3AvailSessEntry
--	ACCESS not-accessible
--	STATUS mandatory
--	DESCRIPTION "&<caiWinA3.1404>Table containing a list of terminal session resources that are currently known to the agent and are available for monitoring."
--	::= { winA3AvailSessGroup 7 }

--winA3AvailSessEntry OBJECT-TYPE
--	SYNTAX WinA3AvailSessEntry
--	ACCESS not-accessible
--	STATUS mandatory
--	DESCRIPTION "&<caiWinA3.1405>Entry in the table of available terminal session resources."
--	::= { winA3AvailSessTable 1 }

--WinA3AvailSessEntry ::= SEQUENCE {
--	winA3AvailSessSid INTEGER,
--	winA3AvailSessClient DisplayString,
--	winA3AvailSessUser DisplayString
--}

--winA3AvailSessSid OBJECT-TYPE
--	SYNTAX INTEGER
--	ACCESS read-only
--	STATUS mandatory
--	DESCRIPTION "&<caiWinA3.1406>The session ID of the session. Note that monitoring of sessions is not applicable on Windows XP and on Windows 2000 Professional."
--	::= { winA3AvailSessEntry 1 }

--winA3AvailSessClient OBJECT-TYPE
--	SYNTAX DisplayString
--	ACCESS read-only
--	STATUS mandatory
--	DESCRIPTION "&<caiWinA3.1407>Client name of the session. The client name is the name of the host, from where this session was initiated. Note that monitoring of sessions is not applicable on Windows XP and on Windows 2000 Professional."
--	::= { winA3AvailSessEntry 2 }

--winA3AvailSessUser OBJECT-TYPE
--	SYNTAX DisplayString
--	ACCESS read-only
--	STATUS mandatory
--	DESCRIPTION "&<caiWinA3.1408>User name of the session. The user name specifies the user, who logged in and is in the form 'domainName\\userName'. Note that monitoring of sessions is not applicable on Windows XP and on Windows 2000 Professional."
--	::= { winA3AvailSessEntry 3 }

--
-- The AvailPrn Group
--

winA3AvailPrnNameFilter OBJECT-TYPE
	SYNTAX DisplayString
	ACCESS read-write
	STATUS mandatory
	DESCRIPTION "&<caiWinA3.1409>Name of the printer to be searched for when checking the Windows System for a list of available resources. This name is used as a filter element and can be a regular expression (case-insensitive). It restricts the list of resources displayed in the available table."
	DEFVAL { ".*" }
	::= { winA3AvailPrnGroup 1 }

winA3AvailPrnMatchType OBJECT-TYPE
	SYNTAX INTEGER {
		positive(1),
		negative(2)
	}
	ACCESS read-write
	STATUS mandatory
	DESCRIPTION "&<caiWinA3.1410>Search algorithm the agent will apply when checking the Windows System for available printer resources. The filter is the logical AND of all attributes used to identify or otherwise narrow down resources. If set to 1 (positive), the agent searches for printer resources that match the filter. If set to 2 (negative), the agent searches for printer resources that do not match the filter."
	DEFVAL { 1 }
	::= { winA3AvailPrnGroup 2 }

winA3AvailPrnViewWindow OBJECT-TYPE
	SYNTAX DisplayString
	ACCESS read-only
	STATUS mandatory
	DESCRIPTION "&<caiWinA3.1411>This attribute indicates the number of the currently displayed buffer and the total number of buffers constituting the list of printer resources that are currently known to the agent and are available for monitoring."
	::= { winA3AvailPrnGroup 3 }

winA3AvailPrnButton OBJECT-TYPE
	SYNTAX INTEGER {
		none(1),
		next(2),
		previous(3),
		refresh(4)
	}
	ACCESS read-write
	STATUS mandatory
	DESCRIPTION "&<caiWinA3.1412>This attribute is used to update the list of printer resources that are currently known to the agent and are available for monitoring. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailPrnGroup 4 }

winA3AvailPrnCount OBJECT-TYPE
	SYNTAX INTEGER
	ACCESS read-only
	STATUS mandatory
	DESCRIPTION "&<caiWinA3.1413>Number of printer resources that are currently known to the agent and are available for monitoring."
	::= { winA3AvailPrnGroup 5 }

--winA3AvailPrnTable OBJECT-TYPE
--	SYNTAX SEQUENCE OF WinA3AvailPrnEntry
--	ACCESS not-accessible
--	STATUS mandatory
--	DESCRIPTION "&<caiWinA3.1414>Table containing a list of printer resources that are currently known to the agent and are available for monitoring."
--	::= { winA3AvailPrnGroup 6 }

--winA3AvailPrnEntry OBJECT-TYPE
--	SYNTAX WinA3AvailPrnEntry
--	ACCESS not-accessible
--	STATUS mandatory
--	DESCRIPTION "&<caiWinA3.1415>Entry in the table of available printer resources."
--	::= { winA3AvailPrnTable 1 }

--WinA3AvailPrnEntry ::= SEQUENCE {
--	winA3AvailPrnName DisplayString
--}

--winA3AvailPrnName OBJECT-TYPE
--	SYNTAX DisplayString
--	ACCESS read-only
--	STATUS mandatory
--	DESCRIPTION "&<caiWinA3.1416>Name of the printer."
--	::= { winA3AvailPrnEntry 1 }

--
-- The AvailHardwr Group
--

winA3AvailHardwrResNameFilter OBJECT-TYPE
	SYNTAX DisplayString
	ACCESS read-write
	STATUS mandatory
	DESCRIPTION "&<caiWinA3.1417>A regular expression (case-insensitive) used to filter the resource names in order to determine the set of rows displayed in the available table."
	DEFVAL { ".*" }
	::= { winA3AvailHardwrGroup 1 }

winA3AvailHardwrResSubNameFilter OBJECT-TYPE
	SYNTAX DisplayString
	ACCESS read-write
	STATUS mandatory
	DESCRIPTION "&<caiWinA3.1418>A regular expression (case-insensitive) used to filter the resource subnames in order to determine the set of rows displayed in the available table."
	DEFVAL { ".*" }
	::= { winA3AvailHardwrGroup 2 }

winA3AvailHardwrInstNameFilter OBJECT-TYPE
	SYNTAX DisplayString
	ACCESS read-write
	STATUS mandatory
	DESCRIPTION "&<caiWinA3.1419>A regular expression (case-insensitive) used to filter the instance names in order to determine the set of rows displayed in the available table."
	DEFVAL { ".*" }
	::= { winA3AvailHardwrGroup 3 }

winA3AvailHardwrMatchType OBJECT-TYPE
	SYNTAX INTEGER {
		positive(1),
		negative(2)
	}
	ACCESS read-write
	STATUS mandatory
	DESCRIPTION "&<caiWinA3.1420>Search algorithm the agent will apply when checking the Windows System for available hardware resources. The filter is the logical AND of all attributes used to identify or otherwise narrow down resources. If set to 1 (positive), the agent searches for hardware resources that match the filter. If set to 2 (negative), the agent searches for hardware resources that do not match the filter."
	DEFVAL { 1 }
	::= { winA3AvailHardwrGroup 4 }

winA3AvailHardwrViewWindow OBJECT-TYPE
	SYNTAX DisplayString
	ACCESS read-only
	STATUS mandatory
	DESCRIPTION "&<caiWinA3.1421>This attribute indicates the number of the currently displayed buffer and the total number of buffers constituting the list of hardware resources that are currently known to the agent and are available for monitoring."
	::= { winA3AvailHardwrGroup 5 }

--winA3AvailHardwrButton OBJECT-TYPE
--	SYNTAX INTEGER {
--		none(1),
--		next(2),
--		previous(3),
--		refresh(4),
--		reinit(5),
--		recreate(6)
--	}
--	ACCESS read-write
--	STATUS mandatory
--	DESCRIPTION "&<caiWinA3.1422>This attribute is used to update the list of hardware resources that are currently known to the agent and are available for monitoring. If set to 6 (recreate), 5 (reinit), or 4 (refresh), the agent re-reads the 'Generic.ini' file and refreshes its internal data with the current content of this file. If the file defines resources that support instances, the agent starts all corresponding instance scripts to retrieve a list of available instances for automatic watcher creation or for display in the table (see below). Setting the value to 5 (reinit) has the same effect as refresh; in addition, the agent creates watchers from any new definitions in the ini file or for any new instances found by the instance scripts. Setting the value to 6 (recreate) has the same effect as reinit; in addition, the agent deletes all hardware status and auto watchers beforehand. If set to 4 (refresh), the agent checks the Windows System for available resources and updates the table with the contents o--f the first buffer constituting the beginning of the list of available resources found. If set to 2 (next), the agent updates the table with the contents of the next buffer. If set to 3 (previous), the agent updates the table with the contents of the previous buffer. This attribute cannot be set to 1 (none)."
--	DEFVAL { 1 }
--	::= { winA3AvailHardwrGroup 6 }


winA3AvailHardwrCount OBJECT-TYPE
	SYNTAX INTEGER
	ACCESS read-only
	STATUS mandatory
	DESCRIPTION "&<caiWinA3.1423>Number of hardware resources that are currently known to the agent and are available for monitoring."
	::= { winA3AvailHardwrGroup 7 }

--winA3AvailHardwrTable OBJECT-TYPE
--	SYNTAX SEQUENCE OF WinA3AvailHardwrEntry
--	ACCESS not-accessible
--	STATUS mandatory
--	DESCRIPTION "&<caiWinA3.1424>Table containing a list of hardware resources that are currently known to the agent and are available for monitoring."
--	::= { winA3AvailHardwrGroup 8 }

--winA3AvailHardwrEntry OBJECT-TYPE
--	SYNTAX WinA3AvailHardwrEntry
--	ACCESS not-accessible
--	STATUS mandatory
--	DESCRIPTION "&<caiWinA3.1425>Entry in the table of available hardware resources."
--	::= { winA3AvailHardwrTable 1 }

--WinA3AvailHardwrEntry ::= SEQUENCE {
--	winA3AvailHardwrResName DisplayString,
--	winA3AvailHardwrResSubName DisplayString,
--	winA3AvailHardwrInstName DisplayString,
--	winA3AvailHardwrAutoWatch INTEGER,
--	winA3AvailHardwrInstSupport INTEGER,
--	winA3AvailHardwrInstScript DisplayString,
--	winA3AvailHardwrInstArgs DisplayString,
--	winA3AvailHardwrCollectScript DisplayString,
--	winA3AvailHardwrCollectArgs DisplayString,
--	winA3AvailHardwrUserName DisplayString,
--	winA3AvailHardwrSkipCount INTEGER,
--	winA3AvailHardwrErrorMsgPattern DisplayString,
--	winA3AvailHardwrErrorMsgMonitor INTEGER,
--	winA3AvailHardwrResultLag INTEGER,
--	winA3AvailHardwrResultWarnMin DisplayString,
--	winA3AvailHardwrResultWarnMax DisplayString,
--	winA3AvailHardwrResultCritMin DisplayString,
--	winA3AvailHardwrResultCritMax DisplayString,
--	winA3AvailHardwrResultMonitor INTEGER,
--	winA3AvailHardwrLossAction INTEGER,
--	winA3AvailHardwrDescription DisplayString
--}

--winA3AvailHardwrResName OBJECT-TYPE
--	SYNTAX DisplayString
--	ACCESS read-only
--	STATUS mandatory
--	DESCRIPTION "&<caiWinA3.1426>The name of the resource. This is the first index used by the agent in the different MIB tables for this resource (e.g. PowerSupply)."
--	::= { winA3AvailHardwrEntry 1 }

--winA3AvailHardwrResSubName OBJECT-TYPE
--	SYNTAX DisplayString
--	ACCESS read-only
--	STATUS mandatory
--	DESCRIPTION "&<caiWinA3.1427>The subname of the resource. This is the second index used by the agent in the different MIB tables for this resource (e.g. Voltage)."
--	::= { winA3AvailHardwrEntry 2 }

--winA3AvailHardwrInstName OBJECT-TYPE
--	SYNTAX DisplayString
--	ACCESS read-only
--	STATUS mandatory
--	DESCRIPTION "&<caiWinA3.1428>If a resource supports instances, this is the name of an instance. The instance names are retrieved by the corresponding instance script. The agent uses ...<PENDING>... as value for the instance name as long as the instance script of this resource is still runing. The agent uses ...<TIMEOUT>... as value, if the instance script timed out. The instance name is the third index used by the agent in the different MIB tables for this resource. If a resource does not support instances, the agent automatically uses <none> as third index."
--	::= { winA3AvailHardwrEntry 3 }

--winA3AvailHardwrAutoWatch OBJECT-TYPE
--	SYNTAX INTEGER {
--		no(1),
--		yes(2)
--	}
--	ACCESS read-only
--	STATUS mandatory
--	DESCRIPTION "&<caiWinA3.1429>Determines if status watchers or auto watchers (in case the resource supports instances) should be automatically created for each available resource or not."
--	::= { winA3AvailHardwrEntry 4 }

--winA3AvailHardwrInstSupport OBJECT-TYPE
--	SYNTAX INTEGER {
--		no(1),
--		yes(2)
--	}
--	ACCESS read-only
--	STATUS mandatory
--	DESCRIPTION "&<caiWinA3.1430>Defines whether the resource supports instances or not."
--	::= { winA3AvailHardwrEntry 5 }

--winA3AvailHardwrInstScript OBJECT-TYPE
--	SYNTAX DisplayString
--	ACCESS read-only
--	STATUS mandatory
--	DESCRIPTION "&<caiWinA3.1431>Script to be called to retrieve the available instances (could be the same as the CollectScript). The script must be in a dedicated directory (agents\config\caiWinA3). Any path element will be ignored."
--	::= { winA3AvailHardwrEntry 6 }

--winA3AvailHardwrInstArgs OBJECT-TYPE
--	SYNTAX DisplayString
--	ACCESS read-only
--	STATUS mandatory
--	DESCRIPTION "&<caiWinA3.1432>Arguments passed to the instance script."
--	::= { winA3AvailHardwrEntry 7 }

--winA3AvailHardwrCollectScript OBJECT-TYPE
--	SYNTAX DisplayString
--	ACCESS read-only
--	STATUS mandatory
--	DESCRIPTION "&<caiWinA3.1433>Script to be called to retrieve the value for a resource. If a resource supports instances, the script needs to gather the values for all required instances in one call. The script must be in a dedicated directory (agents\config\caiWinA3). Any path element will be ignored."
--	::= { winA3AvailHardwrEntry 8 }

--winA3AvailHardwrCollectArgs OBJECT-TYPE
--	SYNTAX DisplayString
--	ACCESS read-only
--	STATUS mandatory
--	DESCRIPTION "&<caiWinA3.1434>Arguments passed to the collect script. If a resource supports instances, the names of all monitored instances are always appended and passed as last parameters."
--	::= { winA3AvailHardwrEntry 9 }

--winA3AvailHardwrUserName OBJECT-TYPE
--	SYNTAX DisplayString
--	ACCESS read-only
--	STATUS mandatory
--	DESCRIPTION "&<caiWinA3.1435>Specifies the user ID and the password (Syntax: user,passwd) to be used for the execution of any script."
--	::= { winA3AvailHardwrEntry 10 }

--winA3AvailHardwrSkipCount OBJECT-TYPE
--	SYNTAX INTEGER
--	ACCESS read-only
--	STATUS mandatory
--	DESCRIPTION "&<caiWinA3.1436>Number of polls to be skipped before calling the collect script of this resource again."
--	::= { winA3AvailHardwrEntry 11 }

--winA3AvailHardwrErrorMsgPattern OBJECT-TYPE
--	SYNTAX DisplayString
--	ACCESS read-only
--	STATUS mandatory
--	DESCRIPTION "&<caiWinA3.1437>The default value for the pattern attribute used if a status watcher is created."
--	::= { winA3AvailHardwrEntry 12 }

--winA3AvailHardwrErrorMsgMonitor OBJECT-TYPE
--	SYNTAX INTEGER {
--		do-not-monitor(1),
--		down-warning(2),
--		down-critical(3)
--	}
--	ACCESS read-only
--	STATUS mandatory
--	DESCRIPTION "&<caiWinA3.1438>The default value for the monitor attribute used if a status watcher is created. If set to 1 (do-not-monitor), the agent does not evaluate the actual state of the resource and sets the status to ok. If set to 2 (down-warning), the agent uses a warning severity if the resource is in bad condition. If set to 3 (down-critical), the agent uses a critical severity if the resource is in bad condition."
--	::= { winA3AvailHardwrEntry 13 }

--winA3AvailHardwrResultLag OBJECT-TYPE
--	SYNTAX INTEGER
--	ACCESS read-only
--	STATUS mandatory
--	DESCRIPTION "&<caiWinA3.1439>The default value for the lag attribute used if a status watcher is created."
--	::= { winA3AvailHardwrEntry 14 }

--winA3AvailHardwrResultWarnMin OBJECT-TYPE
--	SYNTAX DisplayString
--	ACCESS read-only
--	STATUS mandatory
--	DESCRIPTION "&<caiWinA3.1440>The default value for the warning minimum attribute used if a status watcher is created."
--	::= { winA3AvailHardwrEntry 15 }

--winA3AvailHardwrResultWarnMax OBJECT-TYPE
--	SYNTAX DisplayString
--	ACCESS read-only
--	STATUS mandatory
--	DESCRIPTION "&<caiWinA3.1441>The default value for the warning maximum attribute used if a status watcher is created."
--	::= { winA3AvailHardwrEntry 16 }

--winA3AvailHardwrResultCritMin OBJECT-TYPE
--	SYNTAX DisplayString
--	ACCESS read-only
--	STATUS mandatory
--	DESCRIPTION "&<caiWinA3.1442>The default value for the critical minimum attribute used if a status watcher is created."
--	::= { winA3AvailHardwrEntry 17 }

--winA3AvailHardwrResultCritMax OBJECT-TYPE
--	SYNTAX DisplayString
--	ACCESS read-only
--	STATUS mandatory
--	DESCRIPTION "&<caiWinA3.1443>The default value for the critical maximum attribute used if a status watcher is created."
--	::= { winA3AvailHardwrEntry 18 }

--winA3AvailHardwrResultMonitor OBJECT-TYPE
--	SYNTAX INTEGER {
--		do-not-monitor(1),
--		warning-only(2),
--		critical-only(3),
--		minimum-only(4),
--		maximum-only(5),
--		all(6)
--	}
--	ACCESS read-only
--	STATUS mandatory
--	DESCRIPTION "&<caiWinA3.1444>The default value for the monitor attribute used if a status watcher is created. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
--	::= { winA3AvailHardwrEntry 19 }

--winA3AvailHardwrLossAction OBJECT-TYPE
--	SYNTAX INTEGER {
--		remove(1),
--		up(2),
--		down-warning(3),
--		down-critical(4)
--	}
--	ACCESS read-only
--	STATUS mandatory
--	DESCRIPTION "&<caiWinA3.1445>The default value for the loss action attribute used if a status watcher is created. Specifies the action to take if the monitored hardware resource is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
--	::= { winA3AvailHardwrEntry 20 }

--winA3AvailHardwrDescription OBJECT-TYPE
--	SYNTAX DisplayString
--	ACCESS read-only
--	STATUS mandatory
--	DESCRIPTION "&<caiWinA3.1446>Description for the hardware resource."
--	::= { winA3AvailHardwrEntry 21 }

-- The AvailProgrm Group
--

winA3AvailProgrmResNameFilter OBJECT-TYPE
	SYNTAX DisplayString
	ACCESS read-write
	STATUS mandatory
	DESCRIPTION "&<caiWinA3.1447>A regular expression (case-insensitive) used to filter the resource names in order to determine the set of rows displayed in the available table."
	DEFVAL { ".*" }
	::= { winA3AvailProgrmGroup 1 }

winA3AvailProgrmResSubNameFilter OBJECT-TYPE
	SYNTAX DisplayString
	ACCESS read-write
	STATUS mandatory
	DESCRIPTION "&<caiWinA3.1448>A regular expression (case-insensitive) used to filter the resource subnames in order to determine the set of rows displayed in the available table."
	DEFVAL { ".*" }
	::= { winA3AvailProgrmGroup 2 }

winA3AvailProgrmInstNameFilter OBJECT-TYPE
	SYNTAX DisplayString
	ACCESS read-write
	STATUS mandatory
	DESCRIPTION "&<caiWinA3.1449>A regular expression (case-insensitive) used to filter the instance names in order to determine the set of rows displayed in the available table."
	DEFVAL { ".*" }
	::= { winA3AvailProgrmGroup 3 }

winA3AvailProgrmMatchType OBJECT-TYPE
	SYNTAX INTEGER {
		positive(1),
		negative(2)
	}
	ACCESS read-write
	STATUS mandatory
	DESCRIPTION "&<caiWinA3.1450>Search algorithm the agent will apply when checking the Windows System for available programmable resources. The filter is the logical AND of all attributes used to identify or otherwise narrow down resources. If set to 1 (positive), the agent searches for programmable resources that match the filter. If set to 2 (negative), the agent searches for programmable resources that do not match the filter."
	DEFVAL { 1 }
	::= { winA3AvailProgrmGroup 4 }

winA3AvailProgrmViewWindow OBJECT-TYPE
	SYNTAX DisplayString
	ACCESS read-only
	STATUS mandatory
	DESCRIPTION "&<caiWinA3.1451>This attribute indicates the number of the currently displayed buffer and the total number of buffers constituting the list of programmable resources that are currently known to the agent and are available for monitoring."
	::= { winA3AvailProgrmGroup 5 }

winA3AvailProgrmButton OBJECT-TYPE
	SYNTAX INTEGER {
		none(1),
		next(2),
		previous(3),
		refresh(4),
		reinit(5),
		recreate(6)
	}
	ACCESS read-write
	STATUS mandatory
	DESCRIPTION "&<caiWinA3.1452>This attribute is used to update the list of programmable resources that are currently known to the agent and are available for monitoring. If set to 6 (recreate), 5 (reinit), or 4 (refresh), the agent re-reads the 'Generic.ini' file and refreshes its internal data with the current content of this file. If the file defines resources that support instances, the agent starts all corresponding instance scripts to retrieve a list of available instances for automatic watcher creation or for display in the table (see below). Setting the value to 5 (reinit) has the same effect as refresh; in addition, the agent creates watchers from any new definitions in the ini file or for any new instances found by the instance scripts. Setting the value to 6 (recreate) has the same effect as reinit; in addition, the agent deletes all programmable status and auto watchers beforehand. If set to 4 (refresh), the agent checks the Windows System for available resources and updates the table with the contents of the first buffer constituting the beginning of the list of available resources found. If set to 2 (next), the agent updates the table with the contents of the next buffer. If set to 3 (previous), the agent updates the table with the contents of the previous buffer. This attribute cannot be set to 1 (none)."
	DEFVAL { 1 }
	::= { winA3AvailProgrmGroup 6 }

winA3AvailProgrmCount OBJECT-TYPE
	SYNTAX INTEGER
	ACCESS read-only
	STATUS mandatory
	DESCRIPTION "&<caiWinA3.1453>Number of programmable resources that are currently known to the agent and are available for monitoring."
	::= { winA3AvailProgrmGroup 7 }

--winA3AvailProgrmTable OBJECT-TYPE
--	SYNTAX SEQUENCE OF WinA3AvailProgrmEntry
--	ACCESS not-accessible
--	STATUS mandatory
--	DESCRIPTION "&<caiWinA3.1454>Table containing a list of programmable resources that are currently known to the agent and are available for monitoring."
--	::= { winA3AvailProgrmGroup 8 }

--winA3AvailProgrmEntry OBJECT-TYPE
--	SYNTAX WinA3AvailProgrmEntry
--	ACCESS not-accessible
--	STATUS mandatory
--	DESCRIPTION "&<caiWinA3.1455>Entry in the table of available programmable resources."
--	::= { winA3AvailProgrmTable 1 }

--WinA3AvailProgrmEntry ::= SEQUENCE {
--	winA3AvailProgrmResName DisplayString,
--	winA3AvailProgrmResSubName DisplayString,
--	winA3AvailProgrmInstName DisplayString,
--	winA3AvailProgrmAutoWatch INTEGER,
--	winA3AvailProgrmInstSupport INTEGER,
--	winA3AvailProgrmInstScript DisplayString,
--	winA3AvailProgrmInstArgs DisplayString,
--	winA3AvailProgrmCollectScript DisplayString,
--	winA3AvailProgrmCollectArgs DisplayString,
--	winA3AvailProgrmUserName DisplayString,
--	winA3AvailProgrmSkipCount INTEGER,
--	winA3AvailProgrmErrorMsgPattern DisplayString,
--	winA3AvailProgrmErrorMsgMonitor INTEGER,
--	winA3AvailProgrmResultLag INTEGER,
--	winA3AvailProgrmResultWarnMin DisplayString,
--	winA3AvailProgrmResultWarnMax DisplayString,
--	winA3AvailProgrmResultCritMin DisplayString,
--	winA3AvailProgrmResultCritMax DisplayString,
--	winA3AvailProgrmResultMonitor INTEGER,
--	winA3AvailProgrmLossAction INTEGER,
--	winA3AvailProgrmDescription DisplayString
--}

--winA3AvailProgrmResName OBJECT-TYPE
--	SYNTAX DisplayString
--	ACCESS read-only
--	STATUS mandatory
--	DESCRIPTION "&<caiWinA3.1456>The name of the resource. This is the first index used by the agent in the different MIB tables for this resource (e.g. PowerSupply)."
--	::= { winA3AvailProgrmEntry 1 }

--winA3AvailProgrmResSubName OBJECT-TYPE
--	SYNTAX DisplayString
--	ACCESS read-only
--	STATUS mandatory
--	DESCRIPTION "&<caiWinA3.1457>The subname of the resource. This is the second index used by the agent in the different MIB tables for this resource (e.g. Voltage)."
--	::= { winA3AvailProgrmEntry 2 }

--winA3AvailProgrmInstName OBJECT-TYPE
--	SYNTAX DisplayString
--	ACCESS read-only
--	STATUS mandatory
--	DESCRIPTION "&<caiWinA3.1458>If a resource supports instances, this is the name of an instance. The instance names are retrieved by the corresponding instance script. The agent uses ...<PENDING>... as value for the instance name as long as the instance script of this resource is still runing. The agent uses ...<TIMEOUT>... as value, if the instance script timed out. The instance name is the third index used by the agent in the different MIB tables for this resource. If a resource does not support instances, the agent automatically uses <none> as third index."
--	::= { winA3AvailProgrmEntry 3 }

--winA3AvailProgrmAutoWatch OBJECT-TYPE
--	SYNTAX INTEGER {
--		no(1),
--		yes(2)
--	}
--	ACCESS read-only
--	STATUS mandatory
--	DESCRIPTION "&<caiWinA3.1459>Determines if status watchers or auto watchers (in case the resource supports instances) should be automatically created for each available resource or not."
--	::= { winA3AvailProgrmEntry 4 }

--winA3AvailProgrmInstSupport OBJECT-TYPE
--	SYNTAX INTEGER {
--		no(1),
--		yes(2)
--	}
--	ACCESS read-only
--	STATUS mandatory
--	DESCRIPTION "&<caiWinA3.1460>Defines whether the resource supports instances or not."
--	::= { winA3AvailProgrmEntry 5 }

--winA3AvailProgrmInstScript OBJECT-TYPE
--	SYNTAX DisplayString
--	ACCESS read-only
--	STATUS mandatory
--	DESCRIPTION "&<caiWinA3.1461>Script to be called to retrieve the available instances (could be the same as the CollectScript). The script must be in a dedicated directory (agents\config\caiWinA3). Any path element will be ignored."
--	::= { winA3AvailProgrmEntry 6 }

--winA3AvailProgrmInstArgs OBJECT-TYPE
--	SYNTAX DisplayString
--	ACCESS read-only
--	STATUS mandatory
--	DESCRIPTION "&<caiWinA3.1462>Arguments passed to the instance script."
--	::= { winA3AvailProgrmEntry 7 }

--winA3AvailProgrmCollectScript OBJECT-TYPE
--	SYNTAX DisplayString
--	ACCESS read-only
--	STATUS mandatory
--	DESCRIPTION "&<caiWinA3.1463>Script to be called to retrieve the value for a resource. If a resource supports instances, the script needs to gather the values for all required instances in one call. The script must be in a dedicated directory (agents\config\caiWinA3). Any path element will be ignored."
--	::= { winA3AvailProgrmEntry 8 }

--winA3AvailProgrmCollectArgs OBJECT-TYPE
--	SYNTAX DisplayString
--	ACCESS read-only
--	STATUS mandatory
--	DESCRIPTION "&<caiWinA3.1464>Arguments passed to the collect script. If a resource supports instances, the names of all monitored instances are always appended and passed as last parameters."
--	::= { winA3AvailProgrmEntry 9 }

--winA3AvailProgrmUserName OBJECT-TYPE
--	SYNTAX DisplayString
--	ACCESS read-only
--	STATUS mandatory
--	DESCRIPTION "&<caiWinA3.1465>Specifies the user ID and the password (Syntax: user,passwd) to be used for the execution of any script."
--	::= { winA3AvailProgrmEntry 10 }

--winA3AvailProgrmSkipCount OBJECT-TYPE
--	SYNTAX INTEGER
--	ACCESS read-only
--	STATUS mandatory
--	DESCRIPTION "&<caiWinA3.1466>Number of polls to be skipped before calling the collect script of this resource again."
--	::= { winA3AvailProgrmEntry 11 }

--winA3AvailProgrmErrorMsgPattern OBJECT-TYPE
--	SYNTAX DisplayString
--	ACCESS read-only
--	STATUS mandatory
--	DESCRIPTION "&<caiWinA3.1467>The default value for the pattern attribute used if a status watcher is created."
--	::= { winA3AvailProgrmEntry 12 }

--winA3AvailProgrmErrorMsgMonitor OBJECT-TYPE
--	SYNTAX INTEGER {
--		do-not-monitor(1),
--		down-warning(2),
--		down-critical(3)
--	}
--	ACCESS read-only
--	STATUS mandatory
--	DESCRIPTION "&<caiWinA3.1468>The default value for the monitor attribute used if a status watcher is created. If set to 1 (do-not-monitor), the agent does not evaluate the actual state of the resource and sets the status to ok. If set to 2 (down-warning), the agent uses a warning severity if the resource is in bad condition. If set to 3 (down-critical), the agent uses a critical severity if the resource is in bad condition."
--	::= { winA3AvailProgrmEntry 13 }

--winA3AvailProgrmResultLag OBJECT-TYPE
--	SYNTAX INTEGER
--	ACCESS read-only
--	STATUS mandatory
--	DESCRIPTION "&<caiWinA3.1469>The default value for the lag attribute used if a status watcher is created."
--	::= { winA3AvailProgrmEntry 14 }

--winA3AvailProgrmResultWarnMin OBJECT-TYPE
--	SYNTAX DisplayString
--	ACCESS read-only
--	STATUS mandatory
--	DESCRIPTION "&<caiWinA3.1470>The default value for the warning minimum attribute used if a status watcher is created."
--	::= { winA3AvailProgrmEntry 15 }

--winA3AvailProgrmResultWarnMax OBJECT-TYPE
--	SYNTAX DisplayString
--	ACCESS read-only
--	STATUS mandatory
--	DESCRIPTION "&<caiWinA3.1471>The default value for the warning maximum attribute used if a status watcher is created."
--	::= { winA3AvailProgrmEntry 16 }

--winA3AvailProgrmResultCritMin OBJECT-TYPE
--	SYNTAX DisplayString
--	ACCESS read-only
--	STATUS mandatory
--	DESCRIPTION "&<caiWinA3.1472>The default value for the critical minimum attribute used if a status watcher is created."
--	::= { winA3AvailProgrmEntry 17 }

--winA3AvailProgrmResultCritMax OBJECT-TYPE
--	SYNTAX DisplayString
--	ACCESS read-only
--	STATUS mandatory
--	DESCRIPTION "&<caiWinA3.1473>The default value for the critical maximum attribute used if a status watcher is created."
--	::= { winA3AvailProgrmEntry 18 }

--winA3AvailProgrmResultMonitor OBJECT-TYPE
--	SYNTAX INTEGER {
--		do-not-monitor(1),
--		warning-only(2),
--		critical-only(3),
--		minimum-only(4),
--		maximum-only(5),
--		all(6)
--	}
--	ACCESS read-only
--	STATUS mandatory
--	DESCRIPTION "&<caiWinA3.1474>The default value for the monitor attribute used if a status watcher is created. If set to 1 (do-not-monitor), the agent disregards all thresholds and sets the status to ok. If set to 2 (warning-only), the agent evaluates only the warning thresholds (both minimum and maximum) to determine the status of the resource. If set to 3 (critical-only), the agent evaluates only the critical thresholds (both minimum and maximum) to determine the status of the resource. If set to 4 (minimum-only), the agent evaluates only the minimum thresholds (both warning and critical) to determine the status of the resource. If set to 5 (maximum-only), the agent evaluates only the maximum thresholds (both warning and critical) to determine the status of the resource. If set to 6 (all), the agent evaluates all thresholds to determine the status of the resource."
--	::= { winA3AvailProgrmEntry 19 }

--winA3AvailProgrmLossAction OBJECT-TYPE
--	SYNTAX INTEGER {
--		remove(1),
--		up(2),
--		down-warning(3),
--		down-critical(4)
--	}
--	ACCESS read-only
--	STATUS mandatory
--	DESCRIPTION "&<caiWinA3.1475>The default value for the loss action attribute used if a status watcher is created. Specifies the action to take if the monitored programmable resource is removed from the Windows System configuration. If set to 1 (remove), the agent automatically removes the watcher. If set to 2 (up), the agent sets all statuses to ok. If set to 3 (down-warning), the agent sets the loss and aggregate statuses to warning and all other statuses to ok. If set to 4 (down-critical), the agent sets the loss and aggregate statuses to critical and all other statuses to ok."
--	::= { winA3AvailProgrmEntry 20 }

--winA3AvailProgrmDescription OBJECT-TYPE
--	SYNTAX DisplayString
--	ACCESS read-only
--	STATUS mandatory
--	DESCRIPTION "&<caiWinA3.1476>Description for the programmable resource."
--	::= { winA3AvailProgrmEntry 21 }

--
-- The History Group
--

winA3HistoryCPUCollect OBJECT-TYPE
	SYNTAX INTEGER {
		no(1),
		yes(2)
	}
	ACCESS read-write
	STATUS mandatory
	DESCRIPTION "&<caiWinA3.1477>This attribute is used to enable/disable the collection of CPU status traps in the history table. If set to 2 (yes), the agent collects status traps in the history table. If set to 1 (no) these traps are not stored in the history table."
	DEFVAL { 1 }
	::= { winA3HistoryGroup 1 }

winA3HistoryMemCollect OBJECT-TYPE
	SYNTAX INTEGER {
		no(1),
		yes(2)
	}
	ACCESS read-write
	STATUS mandatory
	DESCRIPTION "&<caiWinA3.1478>This attribute is used to enable/disable the collection of memory status traps in the history table. If set to 2 (yes), the agent collects status traps in the history table. If set to 1 (no) these traps are not stored in the history table."
	DEFVAL { 1 }
	::= { winA3HistoryGroup 2 }

winA3HistoryLVolCollect OBJECT-TYPE
	SYNTAX INTEGER {
		no(1),
		yes(2)
	}
	ACCESS read-write
	STATUS mandatory
	DESCRIPTION "&<caiWinA3.1479>This attribute is used to enable/disable the collection of logical volume status traps in the history table. If set to 2 (yes), the agent collects status traps in the history table. If set to 1 (no) these traps are not stored in the history table."
	DEFVAL { 1 }
	::= { winA3HistoryGroup 3 }

winA3HistoryMntCollect OBJECT-TYPE
	SYNTAX INTEGER {
		no(1),
		yes(2)
	}
	ACCESS read-write
	STATUS mandatory
	DESCRIPTION "&<caiWinA3.1480>This attribute is used to enable/disable the collection of mount status traps in the history table. If set to 2 (yes), the agent collects status traps in the history table. If set to 1 (no) these traps are not stored in the history table."
	DEFVAL { 1 }
	::= { winA3HistoryGroup 4 }

winA3HistoryDfsCollect OBJECT-TYPE
	SYNTAX INTEGER {
		no(1),
		yes(2)
	}
	ACCESS read-write
	STATUS mandatory
	DESCRIPTION "&<caiWinA3.1481>This attribute is used to enable/disable the collection of distributed file system link status traps in the history table. If set to 2 (yes), the agent collects status traps in the history table. If set to 1 (no) these traps are not stored in the history table."
	DEFVAL { 1 }
	::= { winA3HistoryGroup 5 }

winA3HistoryQuotaCollect OBJECT-TYPE
	SYNTAX INTEGER {
		no(1),
		yes(2)
	}
	ACCESS read-write
	STATUS mandatory
	DESCRIPTION "&<caiWinA3.1482>This attribute is used to enable/disable the collection of quota status traps in the history table. If set to 2 (yes), the agent collects status traps in the history table. If set to 1 (no) these traps are not stored in the history table."
	DEFVAL { 1 }
	::= { winA3HistoryGroup 6 }

winA3HistoryDirCollect OBJECT-TYPE
	SYNTAX INTEGER {
		no(1),
		yes(2)
	}
	ACCESS read-write
	STATUS mandatory
	DESCRIPTION "&<caiWinA3.1483>This attribute is used to enable/disable the collection of directory status traps in the history table. If set to 2 (yes), the agent collects status traps in the history table. If set to 1 (no) these traps are not stored in the history table."
	DEFVAL { 1 }
	::= { winA3HistoryGroup 7 }

winA3HistoryFileCollect OBJECT-TYPE
	SYNTAX INTEGER {
		no(1),
		yes(2)
	}
	ACCESS read-write
	STATUS mandatory
	DESCRIPTION "&<caiWinA3.1484>This attribute is used to enable/disable the collection of file status traps in the history table. If set to 2 (yes), the agent collects status traps in the history table. If set to 1 (no) these traps are not stored in the history table."
	DEFVAL { 1 }
	::= { winA3HistoryGroup 8 }

winA3HistoryProcCollect OBJECT-TYPE
	SYNTAX INTEGER {
		no(1),
		yes(2)
	}
	ACCESS read-write
	STATUS mandatory
	DESCRIPTION "&<caiWinA3.1485>This attribute is used to enable/disable the collection of process status traps in the history table. If set to 2 (yes), the agent collects status traps in the history table. If set to 1 (no) these traps are not stored in the history table."
	DEFVAL { 1 }
	::= { winA3HistoryGroup 9 }

winA3HistorySrvcCollect OBJECT-TYPE
	SYNTAX INTEGER {
		no(1),
		yes(2)
	}
	ACCESS read-write
	STATUS mandatory
	DESCRIPTION "&<caiWinA3.1486>This attribute is used to enable/disable the collection of service status traps in the history table. If set to 2 (yes), the agent collects status traps in the history table. If set to 1 (no) these traps are not stored in the history table."
	DEFVAL { 1 }
	::= { winA3HistoryGroup 10 }

winA3HistoryJobCollect OBJECT-TYPE
	SYNTAX INTEGER {
		no(1),
		yes(2)
	}
	ACCESS read-write
	STATUS mandatory
	DESCRIPTION "&<caiWinA3.1487>This attribute is used to enable/disable the collection of job status traps in the history table. If set to 2 (yes), the agent collects status traps in the history table. If set to 1 (no) these traps are not stored in the history table."
	DEFVAL { 1 }
	::= { winA3HistoryGroup 11 }

winA3HistorySessCollect OBJECT-TYPE
	SYNTAX INTEGER {
		no(1),
		yes(2)
	}
	ACCESS read-write
	STATUS mandatory
	DESCRIPTION "&<caiWinA3.1488>This attribute is used to enable/disable the collection of terminal session status traps in the history table. If set to 2 (yes), the agent collects status traps in the history table. If set to 1 (no) these traps are not stored in the history table."
	DEFVAL { 1 }
	::= { winA3HistoryGroup 12 }

winA3HistoryPrnCollect OBJECT-TYPE
	SYNTAX INTEGER {
		no(1),
		yes(2)
	}
	ACCESS read-write
	STATUS mandatory
	DESCRIPTION "&<caiWinA3.1489>This attribute is used to enable/disable the collection of printer status traps in the history table. If set to 2 (yes), the agent collects status traps in the history table. If set to 1 (no) these traps are not stored in the history table."
	DEFVAL { 1 }
	::= { winA3HistoryGroup 13 }

winA3HistoryNetCollect OBJECT-TYPE
	SYNTAX INTEGER {
		no(1),
		yes(2)
	}
	ACCESS read-write
	STATUS mandatory
	DESCRIPTION "&<caiWinA3.1490>This attribute is used to enable/disable the collection of network interface status traps in the history table. If set to 2 (yes), the agent collects status traps in the history table. If set to 1 (no) these traps are not stored in the history table."
	DEFVAL { 1 }
	::= { winA3HistoryGroup 14 }

winA3HistoryRegCollect OBJECT-TYPE
	SYNTAX INTEGER {
		no(1),
		yes(2)
	}
	ACCESS read-write
	STATUS mandatory
	DESCRIPTION "&<caiWinA3.1491>This attribute is used to enable/disable the collection of registry entry status traps in the history table. If set to 2 (yes), the agent collects status traps in the history table. If set to 1 (no) these traps are not stored in the history table."
	DEFVAL { 1 }
	::= { winA3HistoryGroup 15 }

winA3HistoryHardwrCollect OBJECT-TYPE
	SYNTAX INTEGER {
		no(1),
		yes(2)
	}
	ACCESS read-write
	STATUS mandatory
	DESCRIPTION "&<caiWinA3.1492>This attribute is used to enable/disable the collection of hardware resource status traps in the history table. If set to 2 (yes), the agent collects status traps in the history table. If set to 1 (no) these traps are not stored in the history table."
	DEFVAL { 1 }
	::= { winA3HistoryGroup 16 }

winA3HistoryProgrmCollect OBJECT-TYPE
	SYNTAX INTEGER {
		no(1),
		yes(2)
	}
	ACCESS read-write
	STATUS mandatory
	DESCRIPTION "&<caiWinA3.1493>This attribute is used to enable/disable the collection of programmable resource status traps in the history table. If set to 2 (yes), the agent collects status traps in the history table. If set to 1 (no) these traps are not stored in the history table."
	DEFVAL { 1 }
	::= { winA3HistoryGroup 17 }

winA3HistoryMaxEntries OBJECT-TYPE
	SYNTAX INTEGER
	ACCESS read-write
	STATUS mandatory
	DESCRIPTION "&<caiWinA3.1494>Maximum number of entries to be stored in the history table. Valid values are 0 to 100. If set to 0 no history information of traps is stored."
	DEFVAL { 50 }
	::= { winA3HistoryGroup 18 }

winA3HistoryButton OBJECT-TYPE
	SYNTAX INTEGER {
		none(1),
		clear(2)
	}
	ACCESS read-write
	STATUS mandatory
	DESCRIPTION "&<caiWinA3.1495>This attribute is used to clear the history table. If set to 2 (clear), the agent empties the history table. This attribute cannot be set to 1 (none)."
	DEFVAL { 1 }
	::= { winA3HistoryGroup 19 }

winA3HistoryCount OBJECT-TYPE
	SYNTAX INTEGER
	ACCESS read-only
	STATUS mandatory
	DESCRIPTION "&<caiWinA3.1496>Number of the last enterprise specific status traps raised by the agent."
	::= { winA3HistoryGroup 20 }

--winA3HistoryTable OBJECT-TYPE
--	SYNTAX SEQUENCE OF WinA3HistoryEntry
--	ACCESS not-accessible
--	STATUS mandatory
--	DESCRIPTION "&<caiWinA3.1497>Table containing the last enterprise specific status traps raised by the agent."
--	::= { winA3HistoryGroup 21 }

--winA3HistoryEntry OBJECT-TYPE
--	SYNTAX WinA3HistoryEntry
--	ACCESS not-accessible
--	STATUS mandatory
--	DESCRIPTION "&<caiWinA3.1498>Entry in the history table."
--	::= { winA3HistoryTable 1 }

--WinA3HistoryEntry ::= SEQUENCE {
--	winA3HistoryTrapName DisplayString,
--	winA3HistoryTrapNumber INTEGER,
--	winA3HistoryTrapTime DisplayString,
--	winA3HistoryTrapVarBind DisplayString
--}

--winA3HistoryTrapName OBJECT-TYPE
--	SYNTAX DisplayString
--	ACCESS read-only
--	STATUS mandatory
--	DESCRIPTION "&<caiWinA3.1499>Name of the trap as defined in the MIB."
--	::= { winA3HistoryEntry 1 }

--winA3HistoryTrapNumber OBJECT-TYPE
--	SYNTAX INTEGER
--	ACCESS read-only
--	STATUS mandatory
--	DESCRIPTION "&<caiWinA3.1500>Enterprise specific trap type number."
--	::= { winA3HistoryEntry 2 }

--winA3HistoryTrapTime OBJECT-TYPE
--	SYNTAX DisplayString
--	ACCESS read-only
--	STATUS mandatory
--	DESCRIPTION "&<caiWinA3.1501>Date and time the trap was sent."
--	::= { winA3HistoryEntry 3 }

--winA3HistoryTrapVarBind OBJECT-TYPE
--	SYNTAX DisplayString
--	ACCESS read-only
--	STATUS mandatory
--	DESCRIPTION "&<caiWinA3.1502>A comma separated list of the varbinds the agent sent with the trap. Each element has the form 'attribute=value'."
--	::= { winA3HistoryEntry 4 }

--
-- The Traps
--

--
-- The CPUTotal Traps
--

winA3CPUTotalUnknown TRAP-TYPE
	ENTERPRISE caiWinA3
	VARIABLES {
		winA3ConfigGeneralAgentVersion
	}
	DESCRIPTION "&<caiWinA3.1503>A watcher monitoring a CPU resource changed its status to 'unknown'. The varbind list contains a varbind with detailed information, encoded as a single string, including the type and value of the involved metric; if applicable, the varbind also includes the current threshold settings and other information useful for automation purposes."
	::= 10000

winA3CPUTotalOk TRAP-TYPE
	ENTERPRISE caiWinA3
	VARIABLES {
		winA3ConfigGeneralAgentVersion
	}
	DESCRIPTION "&<caiWinA3.1504>A watcher monitoring a CPU resource changed its status to 'ok'. The varbind list contains a varbind with detailed information, encoded as a single string, including the type and value of the involved metric; if applicable, the varbind also includes the current threshold settings and other information useful for automation purposes."
	::= 10001

winA3CPUTotalWarning TRAP-TYPE
	ENTERPRISE caiWinA3
	VARIABLES {
		winA3ConfigGeneralAgentVersion
	}
	DESCRIPTION "&<caiWinA3.1505>A watcher monitoring a CPU resource changed its status to 'warning'. The varbind list contains a varbind with detailed information, encoded as a single string, including the type and value of the involved metric; if applicable, the varbind also includes the current threshold settings and other information useful for automation purposes."
	::= 10002

winA3CPUTotalCritical TRAP-TYPE
	ENTERPRISE caiWinA3
	VARIABLES {
		winA3ConfigGeneralAgentVersion
	}
	DESCRIPTION "&<caiWinA3.1506>A watcher monitoring a CPU resource changed its status to 'critical'. The varbind list contains a varbind with detailed information, encoded as a single string, including the type and value of the involved metric; if applicable, the varbind also includes the current threshold settings and other information useful for automation purposes."
	::= 10003

winA3CPUTotalActive TRAP-TYPE
	ENTERPRISE caiWinA3
	VARIABLES {
		winA3ConfigGeneralAgentVersion
	}
	DESCRIPTION "&<caiWinA3.1507>A watcher monitoring a CPU resource changed its status from 'passive'. The varbind list contains a varbind with detailed information, encoded as a single string, including the type and value of the involved metric; if applicable, the varbind also includes the current threshold settings and other information useful for automation purposes."
	::= 10004

winA3CPUTotalPassive TRAP-TYPE
	ENTERPRISE caiWinA3
	VARIABLES {
		winA3ConfigGeneralAgentVersion
	}
	DESCRIPTION "&<caiWinA3.1508>A watcher monitoring a CPU resource changed its status to 'passive'. The varbind list contains a varbind with detailed information, encoded as a single string, including the type and value of the involved metric; if applicable, the varbind also includes the current threshold settings and other information useful for automation purposes."
	::= 10005

winA3CPUTotalInfo TRAP-TYPE
	ENTERPRISE caiWinA3
	VARIABLES {
		winA3ConfigGeneralAgentVersion
	}
	DESCRIPTION "&<caiWinA3.1509>A watcher monitoring a CPU resource changed a sub-state. The varbind list contains a varbind with detailed information, encoded as a single string, including the old and the new status, and the type and value of the involved metric; if applicable, the varbind also includes the current threshold settings and other information useful for automation purposes."
	::= 10008

winA3CPUTotalModified TRAP-TYPE
	ENTERPRISE caiWinA3
	VARIABLES {
		winA3ConfigGeneralAgentVersion
	}
	DESCRIPTION "&<caiWinA3.1510>The watcher configuration for a CPU resource changed. The varbind list contains a varbind with detailed information, encoded as a single string, including the changed attribute with its old value and with its new value."
	::= 10009

--
-- The CPU Traps
--

winA3CPUUnknown TRAP-TYPE
	ENTERPRISE caiWinA3
	VARIABLES {
		winA3StatusCPUName,
		winA3ConfigGeneralAgentVersion
	}
	DESCRIPTION "&<caiWinA3.1511>A watcher monitoring a CPU resource changed its status to 'unknown'. The varbind list contains a varbind with detailed information, encoded as a single string, including the name of the involved resource and the type and value of the involved metric; if applicable, the varbind also includes the current threshold settings and other information useful for automation purposes."
	::= 10990

winA3CPUOk TRAP-TYPE
	ENTERPRISE caiWinA3
	VARIABLES {
		winA3StatusCPUName,
		winA3ConfigGeneralAgentVersion
	}
	DESCRIPTION "&<caiWinA3.1512>A watcher monitoring a CPU resource changed its status to 'ok'. The varbind list contains a varbind with detailed information, encoded as a single string, including the name of the involved resource and the type and value of the involved metric; if applicable, the varbind also includes the current threshold settings and other information useful for automation purposes."
	::= 10991

winA3CPUWarning TRAP-TYPE
	ENTERPRISE caiWinA3
	VARIABLES {
		winA3StatusCPUName,
		winA3ConfigGeneralAgentVersion
	}
	DESCRIPTION "&<caiWinA3.1513>A watcher monitoring a CPU resource changed its status to 'warning'. The varbind list contains a varbind with detailed information, encoded as a single string, including the name of the involved resource and the type and value of the involved metric; if applicable, the varbind also includes the current threshold settings and other information useful for automation purposes."
	::= 10992

winA3CPUCritical TRAP-TYPE
	ENTERPRISE caiWinA3
	VARIABLES {
		winA3StatusCPUName,
		winA3ConfigGeneralAgentVersion
	}
	DESCRIPTION "&<caiWinA3.1514>A watcher monitoring a CPU resource changed its status to 'critical'. The varbind list contains a varbind with detailed information, encoded as a single string, including the name of the involved resource and the type and value of the involved metric; if applicable, the varbind also includes the current threshold settings and other information useful for automation purposes."
	::= 10993

winA3CPUActive TRAP-TYPE
	ENTERPRISE caiWinA3
	VARIABLES {
		winA3StatusCPUName,
		winA3ConfigGeneralAgentVersion
	}
	DESCRIPTION "&<caiWinA3.1515>A watcher monitoring a CPU resource changed its status from 'passive'. The varbind list contains a varbind with detailed information, encoded as a single string, including the name of the involved resource and the type and value of the involved metric; if applicable, the varbind also includes the current threshold settings and other information useful for automation purposes."
	::= 10994

winA3CPUPassive TRAP-TYPE
	ENTERPRISE caiWinA3
	VARIABLES {
		winA3StatusCPUName,
		winA3ConfigGeneralAgentVersion
	}
	DESCRIPTION "&<caiWinA3.1516>A watcher monitoring a CPU resource changed its status to 'passive'. The varbind list contains a varbind with detailed information, encoded as a single string, including the name of the involved resource and the type and value of the involved metric; if applicable, the varbind also includes the current threshold settings and other information useful for automation purposes."
	::= 10995

winA3CPUAdded TRAP-TYPE
	ENTERPRISE caiWinA3
	VARIABLES {
		winA3StatusCPUName
	}
	DESCRIPTION "&<caiWinA3.1517>A watcher monitoring a CPU resource was added. The varbind list contains the name of the involved resource."
	::= 10996

winA3CPUDeleted TRAP-TYPE
	ENTERPRISE caiWinA3
	VARIABLES {
		winA3StatusCPUName
	}
	DESCRIPTION "&<caiWinA3.1518>A watcher monitoring a CPU resource was removed. The varbind list contains the name of the involved resource."
	::= 10997

winA3CPUInfo TRAP-TYPE
	ENTERPRISE caiWinA3
	VARIABLES {
		winA3ConfigGeneralAgentVersion
	}
	DESCRIPTION "&<caiWinA3.1519>A watcher monitoring a CPU resource changed a sub-state. The varbind list contains a varbind with detailed information, encoded as a single string, including the name of the involved resource, the old and the new status, and the type and value of the involved metric; if applicable, the varbind also includes the current threshold settings and other information useful for automation purposes."
	::= 10998

winA3CPUModified TRAP-TYPE
	ENTERPRISE caiWinA3
	VARIABLES {
		winA3ConfigGeneralAgentVersion
	}
	DESCRIPTION "&<caiWinA3.1520>The watcher configuration for a CPU resource changed. The varbind list contains a varbind with detailed information, encoded as a single string, including the name of the involved resource and the changed attribute with its old value and with its new value."
	::= 10999

--
-- The MemVirt Traps
--

winA3MemVirtUnknown TRAP-TYPE
	ENTERPRISE caiWinA3
	VARIABLES {
		winA3ConfigGeneralAgentVersion
	}
	DESCRIPTION "&<caiWinA3.1521>A watcher monitoring the virtual memory utilization of a memory resource changed its status to 'unknown'. The varbind list contains a varbind with detailed information, encoded as a single string, including the type and value of the involved metric; if applicable, the varbind also includes the current threshold settings and other information useful for automation purposes."
	::= 11010

winA3MemVirtOk TRAP-TYPE
	ENTERPRISE caiWinA3
	VARIABLES {
		winA3ConfigGeneralAgentVersion
	}
	DESCRIPTION "&<caiWinA3.1522>A watcher monitoring the virtual memory utilization of a memory resource changed its status to 'ok'. The varbind list contains a varbind with detailed information, encoded as a single string, including the type and value of the involved metric; if applicable, the varbind also includes the current threshold settings and other information useful for automation purposes."
	::= 11011

winA3MemVirtWarning TRAP-TYPE
	ENTERPRISE caiWinA3
	VARIABLES {
		winA3ConfigGeneralAgentVersion
	}
	DESCRIPTION "&<caiWinA3.1523>A watcher monitoring the virtual memory utilization of a memory resource changed its status to 'warning'. The varbind list contains a varbind with detailed information, encoded as a single string, including the type and value of the involved metric; if applicable, the varbind also includes the current threshold settings and other information useful for automation purposes."
	::= 11012

winA3MemVirtCritical TRAP-TYPE
	ENTERPRISE caiWinA3
	VARIABLES {
		winA3ConfigGeneralAgentVersion
	}
	DESCRIPTION "&<caiWinA3.1524>A watcher monitoring the virtual memory utilization of a memory resource changed its status to 'critical'. The varbind list contains a varbind with detailed information, encoded as a single string, including the type and value of the involved metric; if applicable, the varbind also includes the current threshold settings and other information useful for automation purposes."
	::= 11013

winA3MemVirtActive TRAP-TYPE
	ENTERPRISE caiWinA3
	VARIABLES {
		winA3ConfigGeneralAgentVersion
	}
	DESCRIPTION "&<caiWinA3.1525>A watcher monitoring the virtual memory utilization of a memory resource changed its status from 'passive'. The varbind list contains a varbind with detailed information, encoded as a single string, including the type and value of the involved metric; if applicable, the varbind also includes the current threshold settings and other information useful for automation purposes."
	::= 11014

winA3MemVirtPassive TRAP-TYPE
	ENTERPRISE caiWinA3
	VARIABLES {
		winA3ConfigGeneralAgentVersion
	}
	DESCRIPTION "&<caiWinA3.1526>A watcher monitoring the virtual memory utilization of a memory resource changed its status to 'passive'. The varbind list contains a varbind with detailed information, encoded as a single string, including the type and value of the involved metric; if applicable, the varbind also includes the current threshold settings and other information useful for automation purposes."
	::= 11015

winA3MemVirtModified TRAP-TYPE
	ENTERPRISE caiWinA3
	VARIABLES {
		winA3ConfigGeneralAgentVersion
	}
	DESCRIPTION "&<caiWinA3.1527>The watcher configuration for the virtual memory utilization monitoring of a memory resource changed. The varbind list contains a varbind with detailed information, encoded as a single string, including the changed attribute with its old value and with its new value."
	::= 11019

--
-- The MemPhys Traps
--

winA3MemPhysUnknown TRAP-TYPE
	ENTERPRISE caiWinA3
	VARIABLES {
		winA3ConfigGeneralAgentVersion
	}
	DESCRIPTION "&<caiWinA3.1528>A watcher monitoring the physical memory utilization of a memory resource changed its status to 'unknown'. The varbind list contains a varbind with detailed information, encoded as a single string, including the type and value of the involved metric; if applicable, the varbind also includes the current threshold settings and other information useful for automation purposes."
	::= 11020

winA3MemPhysOk TRAP-TYPE
	ENTERPRISE caiWinA3
	VARIABLES {
		winA3ConfigGeneralAgentVersion
	}
	DESCRIPTION "&<caiWinA3.1529>A watcher monitoring the physical memory utilization of a memory resource changed its status to 'ok'. The varbind list contains a varbind with detailed information, encoded as a single string, including the type and value of the involved metric; if applicable, the varbind also includes the current threshold settings and other information useful for automation purposes."
	::= 11021

winA3MemPhysWarning TRAP-TYPE
	ENTERPRISE caiWinA3
	VARIABLES {
		winA3ConfigGeneralAgentVersion
	}
	DESCRIPTION "&<caiWinA3.1530>A watcher monitoring the physical memory utilization of a memory resource changed its status to 'warning'. The varbind list contains a varbind with detailed information, encoded as a single string, including the type and value of the involved metric; if applicable, the varbind also includes the current threshold settings and other information useful for automation purposes."
	::= 11022

winA3MemPhysCritical TRAP-TYPE
	ENTERPRISE caiWinA3
	VARIABLES {
		winA3ConfigGeneralAgentVersion
	}
	DESCRIPTION "&<caiWinA3.1531>A watcher monitoring the physical memory utilization of a memory resource changed its status to 'critical'. The varbind list contains a varbind with detailed information, encoded as a single string, including the type and value of the involved metric; if applicable, the varbind also includes the current threshold settings and other information useful for automation purposes."
	::= 11023

winA3MemPhysActive TRAP-TYPE
	ENTERPRISE caiWinA3
	VARIABLES {
		winA3ConfigGeneralAgentVersion
	}
	DESCRIPTION "&<caiWinA3.1532>A watcher monitoring the physical memory utilization of a memory resource changed its status from 'passive'. The varbind list contains a varbind with detailed information, encoded as a single string, including the type and value of the involved metric; if applicable, the varbind also includes the current threshold settings and other information useful for automation purposes."
	::= 11024

winA3MemPhysPassive TRAP-TYPE
	ENTERPRISE caiWinA3
	VARIABLES {
		winA3ConfigGeneralAgentVersion
	}
	DESCRIPTION "&<caiWinA3.1533>A watcher monitoring the physical memory utilization of a memory resource changed its status to 'passive'. The varbind list contains a varbind with detailed information, encoded as a single string, including the type and value of the involved metric; if applicable, the varbind also includes the current threshold settings and other information useful for automation purposes."
	::= 11025

winA3MemPhysModified TRAP-TYPE
	ENTERPRISE caiWinA3
	VARIABLES {
		winA3ConfigGeneralAgentVersion
	}
	DESCRIPTION "&<caiWinA3.1534>The watcher configuration for the physical memory utilization monitoring of a memory resource changed. The varbind list contains a varbind with detailed information, encoded as a single string, including the changed attribute with its old value and with its new value."
	::= 11029

--
-- The MemPage Traps
--

winA3MemPageUnknown TRAP-TYPE
	ENTERPRISE caiWinA3
	VARIABLES {
		winA3ConfigGeneralAgentVersion
	}
	DESCRIPTION "&<caiWinA3.1535>A watcher monitoring the paging memory utilization of a memory resource changed its status to 'unknown'. The varbind list contains a varbind with detailed information, encoded as a single string, including the type and value of the involved metric; if applicable, the varbind also includes the current threshold settings and other information useful for automation purposes."
	::= 11030

winA3MemPageOk TRAP-TYPE
	ENTERPRISE caiWinA3
	VARIABLES {
		winA3ConfigGeneralAgentVersion
	}
	DESCRIPTION "&<caiWinA3.1536>A watcher monitoring the paging memory utilization of a memory resource changed its status to 'ok'. The varbind list contains a varbind with detailed information, encoded as a single string, including the type and value of the involved metric; if applicable, the varbind also includes the current threshold settings and other information useful for automation purposes."
	::= 11031

winA3MemPageWarning TRAP-TYPE
	ENTERPRISE caiWinA3
	VARIABLES {
		winA3ConfigGeneralAgentVersion
	}
	DESCRIPTION "&<caiWinA3.1537>A watcher monitoring the paging memory utilization of a memory resource changed its status to 'warning'. The varbind list contains a varbind with detailed information, encoded as a single string, including the type and value of the involved metric; if applicable, the varbind also includes the current threshold settings and other information useful for automation purposes."
	::= 11032

winA3MemPageCritical TRAP-TYPE
	ENTERPRISE caiWinA3
	VARIABLES {
		winA3ConfigGeneralAgentVersion
	}
	DESCRIPTION "&<caiWinA3.1538>A watcher monitoring the paging memory utilization of a memory resource changed its status to 'critical'. The varbind list contains a varbind with detailed information, encoded as a single string, including the type and value of the involved metric; if applicable, the varbind also includes the current threshold settings and other information useful for automation purposes."
	::= 11033

winA3MemPageActive TRAP-TYPE
	ENTERPRISE caiWinA3
	VARIABLES {
		winA3ConfigGeneralAgentVersion
	}
	DESCRIPTION "&<caiWinA3.1539>A watcher monitoring the paging memory utilization of a memory resource changed its status from 'passive'. The varbind list contains a varbind with detailed information, encoded as a single string, including the type and value of the involved metric; if applicable, the varbind also includes the current threshold settings and other information useful for automation purposes."
	::= 11034

winA3MemPagePassive TRAP-TYPE
	ENTERPRISE caiWinA3
	VARIABLES {
		winA3ConfigGeneralAgentVersion
	}
	DESCRIPTION "&<caiWinA3.1540>A watcher monitoring the paging memory utilization of a memory resource changed its status to 'passive'. The varbind list contains a varbind with detailed information, encoded as a single string, including the type and value of the involved metric; if applicable, the varbind also includes the current threshold settings and other information useful for automation purposes."
	::= 11035

winA3MemPageModified TRAP-TYPE
	ENTERPRISE caiWinA3
	VARIABLES {
		winA3ConfigGeneralAgentVersion
	}
	DESCRIPTION "&<caiWinA3.1541>The watcher configuration for the paging memory utilization monitoring of a memory resource changed. The varbind list contains a varbind with detailed information, encoded as a single string, including the changed attribute with its old value and with its new value."
	::= 11039

--
-- The LVol Traps
--

winA3LVolUnknown TRAP-TYPE
	ENTERPRISE caiWinA3
	VARIABLES {
		winA3StatusLVolName,
		winA3ConfigGeneralAgentVersion
	}
	DESCRIPTION "&<caiWinA3.1542>A watcher monitoring a logical volume resource changed its status to 'unknown'. The varbind list contains a varbind with detailed information, encoded as a single string, including the name of the involved resource and the type and value of the involved metric; if applicable, the varbind also includes the current threshold settings and other information useful for automation purposes."
	::= 12980

winA3LVolOk TRAP-TYPE
	ENTERPRISE caiWinA3
	VARIABLES {
		winA3StatusLVolName,
		winA3ConfigGeneralAgentVersion
	}
	DESCRIPTION "&<caiWinA3.1543>A watcher monitoring a logical volume resource changed its status to 'ok'. The varbind list contains a varbind with detailed information, encoded as a single string, including the name of the involved resource and the type and value of the involved metric; if applicable, the varbind also includes the current threshold settings and other information useful for automation purposes."
	::= 12981

winA3LVolWarning TRAP-TYPE
	ENTERPRISE caiWinA3
	VARIABLES {
		winA3StatusLVolName,
		winA3ConfigGeneralAgentVersion
	}
	DESCRIPTION "&<caiWinA3.1544>A watcher monitoring a logical volume resource changed its status to 'warning'. The varbind list contains a varbind with detailed information, encoded as a single string, including the name of the involved resource and the type and value of the involved metric; if applicable, the varbind also includes the current threshold settings and other information useful for automation purposes."
	::= 12982

winA3LVolCritical TRAP-TYPE
	ENTERPRISE caiWinA3
	VARIABLES {
		winA3StatusLVolName,
		winA3ConfigGeneralAgentVersion
	}
	DESCRIPTION "&<caiWinA3.1545>A watcher monitoring a logical volume resource changed its status to 'critical'. The varbind list contains a varbind with detailed information, encoded as a single string, including the name of the involved resource and the type and value of the involved metric; if applicable, the varbind also includes the current threshold settings and other information useful for automation purposes."
	::= 12983

winA3LVolActive TRAP-TYPE
	ENTERPRISE caiWinA3
	VARIABLES {
		winA3StatusLVolName,
		winA3ConfigGeneralAgentVersion
	}
	DESCRIPTION "&<caiWinA3.1546>A watcher monitoring a logical volume resource changed its status from 'passive'. The varbind list contains a varbind with detailed information, encoded as a single string, including the name of the involved resource and the type and value of the involved metric; if applicable, the varbind also includes the current threshold settings and other information useful for automation purposes."
	::= 12984

winA3LVolPassive TRAP-TYPE
	ENTERPRISE caiWinA3
	VARIABLES {
		winA3StatusLVolName,
		winA3ConfigGeneralAgentVersion
	}
	DESCRIPTION "&<caiWinA3.1547>A watcher monitoring a logical volume resource changed its status to 'passive'. The varbind list contains a varbind with detailed information, encoded as a single string, including the name of the involved resource and the type and value of the involved metric; if applicable, the varbind also includes the current threshold settings and other information useful for automation purposes."
	::= 12985

winA3LVolAdded TRAP-TYPE
	ENTERPRISE caiWinA3
	VARIABLES {
		winA3StatusLVolName
	}
	DESCRIPTION "&<caiWinA3.1548>A watcher monitoring a logical volume resource was added. The varbind list contains the name of the involved resource."
	::= 12986

winA3LVolDeleted TRAP-TYPE
	ENTERPRISE caiWinA3
	VARIABLES {
		winA3StatusLVolName
	}
	DESCRIPTION "&<caiWinA3.1549>A watcher monitoring a logical volume resource was removed. The varbind list contains the name of the involved resource."
	::= 12987

winA3LVolInfo TRAP-TYPE
	ENTERPRISE caiWinA3
	VARIABLES {
		winA3ConfigGeneralAgentVersion
	}
	DESCRIPTION "&<caiWinA3.1550>A watcher monitoring a logical volume resource changed a sub-state. The varbind list contains a varbind with detailed information, encoded as a single string, including the name of the involved resource, the old and the new status, and the type and value of the involved metric; if applicable, the varbind also includes the current threshold settings and other information useful for automation purposes."
	::= 12988

winA3LVolModified TRAP-TYPE
	ENTERPRISE caiWinA3
	VARIABLES {
		winA3ConfigGeneralAgentVersion
	}
	DESCRIPTION "&<caiWinA3.1551>The watcher configuration for a logical volume resource changed. The varbind list contains a varbind with detailed information, encoded as a single string, including the name of the involved resource and the changed attribute with its old value and with its new value."
	::= 12989

--
-- The Mnt Traps
--

winA3MntUnknown TRAP-TYPE
	ENTERPRISE caiWinA3
	VARIABLES {
		winA3StatusMntName,
		winA3ConfigGeneralAgentVersion
	}
	DESCRIPTION "&<caiWinA3.1552>A watcher monitoring a mount resource changed its status to 'unknown'. The varbind list contains a varbind with detailed information, encoded as a single string, including the name of the involved resource and the type and value of the involved metric; if applicable, the varbind also includes the current threshold settings and other information useful for automation purposes."
	::= 13980

winA3MntOk TRAP-TYPE
	ENTERPRISE caiWinA3
	VARIABLES {
		winA3StatusMntName,
		winA3ConfigGeneralAgentVersion
	}
	DESCRIPTION "&<caiWinA3.1553>A watcher monitoring a mount resource changed its status to 'ok'. The varbind list contains a varbind with detailed information, encoded as a single string, including the name of the involved resource and the type and value of the involved metric; if applicable, the varbind also includes the current threshold settings and other information useful for automation purposes."
	::= 13981

winA3MntWarning TRAP-TYPE
	ENTERPRISE caiWinA3
	VARIABLES {
		winA3StatusMntName,
		winA3ConfigGeneralAgentVersion
	}
	DESCRIPTION "&<caiWinA3.1554>A watcher monitoring a mount resource changed its status to 'warning'. The varbind list contains a varbind with detailed information, encoded as a single string, including the name of the involved resource and the type and value of the involved metric; if applicable, the varbind also includes the current threshold settings and other information useful for automation purposes."
	::= 13982

winA3MntCritical TRAP-TYPE
	ENTERPRISE caiWinA3
	VARIABLES {
		winA3StatusMntName,
		winA3ConfigGeneralAgentVersion
	}
	DESCRIPTION "&<caiWinA3.1555>A watcher monitoring a mount resource changed its status to 'critical'. The varbind list contains a varbind with detailed information, encoded as a single string, including the name of the involved resource and the type and value of the involved metric; if applicable, the varbind also includes the current threshold settings and other information useful for automation purposes."
	::= 13983

winA3MntActive TRAP-TYPE
	ENTERPRISE caiWinA3
	VARIABLES {
		winA3StatusMntName,
		winA3ConfigGeneralAgentVersion
	}
	DESCRIPTION "&<caiWinA3.1556>A watcher monitoring a mount resource changed its status from 'passive'. The varbind list contains a varbind with detailed information, encoded as a single string, including the name of the involved resource and the type and value of the involved metric; if applicable, the varbind also includes the current threshold settings and other information useful for automation purposes."
	::= 13984

winA3MntPassive TRAP-TYPE
	ENTERPRISE caiWinA3
	VARIABLES {
		winA3StatusMntName,
		winA3ConfigGeneralAgentVersion
	}
	DESCRIPTION "&<caiWinA3.1557>A watcher monitoring a mount resource changed its status to 'passive'. The varbind list contains a varbind with detailed information, encoded as a single string, including the name of the involved resource and the type and value of the involved metric; if applicable, the varbind also includes the current threshold settings and other information useful for automation purposes."
	::= 13985

winA3MntAdded TRAP-TYPE
	ENTERPRISE caiWinA3
	VARIABLES {
		winA3StatusMntName
	}
	DESCRIPTION "&<caiWinA3.1558>A watcher monitoring a mount resource was added. The varbind list contains the name of the involved resource."
	::= 13986

winA3MntDeleted TRAP-TYPE
	ENTERPRISE caiWinA3
	VARIABLES {
		winA3StatusMntName
	}
	DESCRIPTION "&<caiWinA3.1559>A watcher monitoring a mount resource was removed. The varbind list contains the name of the involved resource."
	::= 13987

winA3MntInfo TRAP-TYPE
	ENTERPRISE caiWinA3
	VARIABLES {
		winA3ConfigGeneralAgentVersion
	}
	DESCRIPTION "&<caiWinA3.1560>A watcher monitoring a mount resource changed a sub-state. The varbind list contains a varbind with detailed information, encoded as a single string, including the name of the involved resource, the old and the new status, and the type and value of the involved metric; if applicable, the varbind also includes the current threshold settings and other information useful for automation purposes."
	::= 13988

winA3MntModified TRAP-TYPE
	ENTERPRISE caiWinA3
	VARIABLES {
		winA3ConfigGeneralAgentVersion
	}
	DESCRIPTION "&<caiWinA3.1561>The watcher configuration for a mount resource changed. The varbind list contains a varbind with detailed information, encoded as a single string, including the name of the involved resource and the changed attribute with its old value and with its new value."
	::= 13989

--
-- The Dfs Traps
--

winA3DfsUnknown TRAP-TYPE
	ENTERPRISE caiWinA3
	VARIABLES {
		winA3StatusDfsName,
		winA3ConfigGeneralAgentVersion
	}
	DESCRIPTION "&<caiWinA3.1562>A watcher monitoring a distributed file system link resource changed its status to 'unknown'. The varbind list contains a varbind with detailed information, encoded as a single string, including the name of the involved resource and the type and value of the involved metric; if applicable, the varbind also includes the current threshold settings and other information useful for automation purposes."
	::= 14980

winA3DfsOk TRAP-TYPE
	ENTERPRISE caiWinA3
	VARIABLES {
		winA3StatusDfsName,
		winA3ConfigGeneralAgentVersion
	}
	DESCRIPTION "&<caiWinA3.1563>A watcher monitoring a distributed file system link resource changed its status to 'ok'. The varbind list contains a varbind with detailed information, encoded as a single string, including the name of the involved resource and the type and value of the involved metric; if applicable, the varbind also includes the current threshold settings and other information useful for automation purposes."
	::= 14981

winA3DfsWarning TRAP-TYPE
	ENTERPRISE caiWinA3
	VARIABLES {
		winA3StatusDfsName,
		winA3ConfigGeneralAgentVersion
	}
	DESCRIPTION "&<caiWinA3.1564>A watcher monitoring a distributed file system link resource changed its status to 'warning'. The varbind list contains a varbind with detailed information, encoded as a single string, including the name of the involved resource and the type and value of the involved metric; if applicable, the varbind also includes the current threshold settings and other information useful for automation purposes."
	::= 14982

winA3DfsCritical TRAP-TYPE
	ENTERPRISE caiWinA3
	VARIABLES {
		winA3StatusDfsName,
		winA3ConfigGeneralAgentVersion
	}
	DESCRIPTION "&<caiWinA3.1565>A watcher monitoring a distributed file system link resource changed its status to 'critical'. The varbind list contains a varbind with detailed information, encoded as a single string, including the name of the involved resource and the type and value of the involved metric; if applicable, the varbind also includes the current threshold settings and other information useful for automation purposes."
	::= 14983

winA3DfsActive TRAP-TYPE
	ENTERPRISE caiWinA3
	VARIABLES {
		winA3StatusDfsName,
		winA3ConfigGeneralAgentVersion
	}
	DESCRIPTION "&<caiWinA3.1566>A watcher monitoring a distributed file system link resource changed its status from 'passive'. The varbind list contains a varbind with detailed information, encoded as a single string, including the name of the involved resource and the type and value of the involved metric; if applicable, the varbind also includes the current threshold settings and other information useful for automation purposes."
	::= 14984

winA3DfsPassive TRAP-TYPE
	ENTERPRISE caiWinA3
	VARIABLES {
		winA3StatusDfsName,
		winA3ConfigGeneralAgentVersion
	}
	DESCRIPTION "&<caiWinA3.1567>A watcher monitoring a distributed file system link resource changed its status to 'passive'. The varbind list contains a varbind with detailed information, encoded as a single string, including the name of the involved resource and the type and value of the involved metric; if applicable, the varbind also includes the current threshold settings and other information useful for automation purposes."
	::= 14985

winA3DfsAdded TRAP-TYPE
	ENTERPRISE caiWinA3
	VARIABLES {
		winA3StatusDfsName
	}
	DESCRIPTION "&<caiWinA3.1568>A watcher monitoring a distributed file system link resource was added. The varbind list contains the name of the involved resource."
	::= 14986

winA3DfsDeleted TRAP-TYPE
	ENTERPRISE caiWinA3
	VARIABLES {
		winA3StatusDfsName
	}
	DESCRIPTION "&<caiWinA3.1569>A watcher monitoring a distributed file system link resource was removed. The varbind list contains the name of the involved resource."
	::= 14987

winA3DfsInfo TRAP-TYPE
	ENTERPRISE caiWinA3
	VARIABLES {
		winA3ConfigGeneralAgentVersion
	}
	DESCRIPTION "&<caiWinA3.1570>A watcher monitoring a distributed file system link resource changed a sub-state. The varbind list contains a varbind with detailed information, encoded as a single string, including the name of the involved resource, the old and the new status, and the type and value of the involved metric; if applicable, the varbind also includes the current threshold settings and other information useful for automation purposes."
	::= 14988

winA3DfsModified TRAP-TYPE
	ENTERPRISE caiWinA3
	VARIABLES {
		winA3ConfigGeneralAgentVersion
	}
	DESCRIPTION "&<caiWinA3.1571>The watcher configuration for a distributed file system link resource changed. The varbind list contains a varbind with detailed information, encoded as a single string, including the name of the involved resource and the changed attribute with its old value and with its new value."
	::= 14989

--
-- The Quota Traps
--

winA3QuotaUnknown TRAP-TYPE
	ENTERPRISE caiWinA3
	VARIABLES {
		winA3StatusQuotaLVolName,
		winA3StatusQuotaUserName,
		winA3ConfigGeneralAgentVersion
	}
	DESCRIPTION "&<caiWinA3.1572>A watcher monitoring a quota resource changed its status to 'unknown'. The varbind list contains a varbind with detailed information, encoded as a single string, including the name of the involved resource and the type and value of the involved metric; if applicable, the varbind also includes the current threshold settings and other information useful for automation purposes."
	::= 15980

winA3QuotaOk TRAP-TYPE
	ENTERPRISE caiWinA3
	VARIABLES {
		winA3StatusQuotaLVolName,
		winA3StatusQuotaUserName,
		winA3ConfigGeneralAgentVersion
	}
	DESCRIPTION "&<caiWinA3.1573>A watcher monitoring a quota resource changed its status to 'ok'. The varbind list contains a varbind with detailed information, encoded as a single string, including the name of the involved resource and the type and value of the involved metric; if applicable, the varbind also includes the current threshold settings and other information useful for automation purposes."
	::= 15981

winA3QuotaWarning TRAP-TYPE
	ENTERPRISE caiWinA3
	VARIABLES {
		winA3StatusQuotaLVolName,
		winA3StatusQuotaUserName,
		winA3ConfigGeneralAgentVersion
	}
	DESCRIPTION "&<caiWinA3.1574>A watcher monitoring a quota resource changed its status to 'warning'. The varbind list contains a varbind with detailed information, encoded as a single string, including the name of the involved resource and the type and value of the involved metric; if applicable, the varbind also includes the current threshold settings and other information useful for automation purposes."
	::= 15982

winA3QuotaCritical TRAP-TYPE
	ENTERPRISE caiWinA3
	VARIABLES {
		winA3StatusQuotaLVolName,
		winA3StatusQuotaUserName,
		winA3ConfigGeneralAgentVersion
	}
	DESCRIPTION "&<caiWinA3.1575>A watcher monitoring a quota resource changed its status to 'critical'. The varbind list contains a varbind with detailed information, encoded as a single string, including the name of the involved resource and the type and value of the involved metric; if applicable, the varbind also includes the current threshold settings and other information useful for automation purposes."
	::= 15983

winA3QuotaActive TRAP-TYPE
	ENTERPRISE caiWinA3
	VARIABLES {
		winA3StatusQuotaLVolName,
		winA3StatusQuotaUserName,
		winA3ConfigGeneralAgentVersion
	}
	DESCRIPTION "&<caiWinA3.1576>A watcher monitoring a quota resource changed its status from 'passive'. The varbind list contains a varbind with detailed information, encoded as a single string, including the name of the involved resource and the type and value of the involved metric; if applicable, the varbind also includes the current threshold settings and other information useful for automation purposes."
	::= 15984

winA3QuotaPassive TRAP-TYPE
	ENTERPRISE caiWinA3
	VARIABLES {
		winA3StatusQuotaLVolName,
		winA3StatusQuotaUserName,
		winA3ConfigGeneralAgentVersion
	}
	DESCRIPTION "&<caiWinA3.1577>A watcher monitoring a quota resource changed its status to 'passive'. The varbind list contains a varbind with detailed information, encoded as a single string, including the name of the involved resource and the type and value of the involved metric; if applicable, the varbind also includes the current threshold settings and other information useful for automation purposes."
	::= 15985

winA3QuotaAdded TRAP-TYPE
	ENTERPRISE caiWinA3
	VARIABLES {
		winA3StatusQuotaLVolName,
		winA3StatusQuotaUserName
	}
	DESCRIPTION "&<caiWinA3.1578>A watcher monitoring a quota resource was added. The varbind list contains the name of the involved resource."
	::= 15986

winA3QuotaDeleted TRAP-TYPE
	ENTERPRISE caiWinA3
	VARIABLES {
		winA3StatusQuotaLVolName,
		winA3StatusQuotaUserName
	}
	DESCRIPTION "&<caiWinA3.1579>A watcher monitoring a quota resource was removed. The varbind list contains the name of the involved resource."
	::= 15987

winA3QuotaInfo TRAP-TYPE
	ENTERPRISE caiWinA3
	VARIABLES {
		winA3ConfigGeneralAgentVersion
	}
	DESCRIPTION "&<caiWinA3.1580>A watcher monitoring a quota resource changed a sub-state. The varbind list contains a varbind with detailed information, encoded as a single string, including the name of the involved resource, the old and the new status, and the type and value of the involved metric; if applicable, the varbind also includes the current threshold settings and other information useful for automation purposes."
	::= 15988

winA3QuotaModified TRAP-TYPE
	ENTERPRISE caiWinA3
	VARIABLES {
		winA3ConfigGeneralAgentVersion
	}
	DESCRIPTION "&<caiWinA3.1581>The watcher configuration for a quota resource changed. The varbind list contains a varbind with detailed information, encoded as a single string, including the name of the involved resource and the changed attribute with its old value and with its new value."
	::= 15989

--
-- The Dir Traps
--

winA3DirUnknown TRAP-TYPE
	ENTERPRISE caiWinA3
	VARIABLES {
		winA3StatusDirWatcherName,
		winA3ConfigGeneralAgentVersion
	}
	DESCRIPTION "&<caiWinA3.1582>A watcher monitoring a directory resource changed its status to 'unknown'. The varbind list contains a varbind with detailed information, encoded as a single string, including the name of the involved resource and the type and value of the involved metric; if applicable, the varbind also includes the current threshold settings and other information useful for automation purposes."
	::= 16980

winA3DirOk TRAP-TYPE
	ENTERPRISE caiWinA3
	VARIABLES {
		winA3StatusDirWatcherName,
		winA3ConfigGeneralAgentVersion
	}
	DESCRIPTION "&<caiWinA3.1583>A watcher monitoring a directory resource changed its status to 'ok'. The varbind list contains a varbind with detailed information, encoded as a single string, including the name of the involved resource and the type and value of the involved metric; if applicable, the varbind also includes the current threshold settings and other information useful for automation purposes."
	::= 16981

winA3DirWarning TRAP-TYPE
	ENTERPRISE caiWinA3
	VARIABLES {
		winA3StatusDirWatcherName,
		winA3ConfigGeneralAgentVersion
	}
	DESCRIPTION "&<caiWinA3.1584>A watcher monitoring a directory resource changed its status to 'warning'. The varbind list contains a varbind with detailed information, encoded as a single string, including the name of the involved resource and the type and value of the involved metric; if applicable, the varbind also includes the current threshold settings and other information useful for automation purposes."
	::= 16982

winA3DirCritical TRAP-TYPE
	ENTERPRISE caiWinA3
	VARIABLES {
		winA3StatusDirWatcherName,
		winA3ConfigGeneralAgentVersion
	}
	DESCRIPTION "&<caiWinA3.1585>A watcher monitoring a directory resource changed its status to 'critical'. The varbind list contains a varbind with detailed information, encoded as a single string, including the name of the involved resource and the type and value of the involved metric; if applicable, the varbind also includes the current threshold settings and other information useful for automation purposes."
	::= 16983

winA3DirActive TRAP-TYPE
	ENTERPRISE caiWinA3
	VARIABLES {
		winA3StatusDirWatcherName,
		winA3ConfigGeneralAgentVersion
	}
	DESCRIPTION "&<caiWinA3.1586>A watcher monitoring a directory resource changed its status from 'passive'. The varbind list contains a varbind with detailed information, encoded as a single string, including the name of the involved resource and the type and value of the involved metric; if applicable, the varbind also includes the current threshold settings and other information useful for automation purposes."
	::= 16984

winA3DirPassive TRAP-TYPE
	ENTERPRISE caiWinA3
	VARIABLES {
		winA3StatusDirWatcherName,
		winA3ConfigGeneralAgentVersion
	}
	DESCRIPTION "&<caiWinA3.1587>A watcher monitoring a directory resource changed its status to 'passive'. The varbind list contains a varbind with detailed information, encoded as a single string, including the name of the involved resource and the type and value of the involved metric; if applicable, the varbind also includes the current threshold settings and other information useful for automation purposes."
	::= 16985

winA3DirAdded TRAP-TYPE
	ENTERPRISE caiWinA3
	VARIABLES {
		winA3StatusDirWatcherName
	}
	DESCRIPTION "&<caiWinA3.1588>A watcher monitoring a directory resource was added. The varbind list contains the name of the involved resource."
	::= 16986

winA3DirDeleted TRAP-TYPE
	ENTERPRISE caiWinA3
	VARIABLES {
		winA3StatusDirWatcherName
	}
	DESCRIPTION "&<caiWinA3.1589>A watcher monitoring a directory resource was removed. The varbind list contains the name of the involved resource."
	::= 16987

winA3DirInfo TRAP-TYPE
	ENTERPRISE caiWinA3
	VARIABLES {
		winA3ConfigGeneralAgentVersion
	}
	DESCRIPTION "&<caiWinA3.1590>A watcher monitoring a directory resource changed a sub-state. The varbind list contains a varbind with detailed information, encoded as a single string, including the name of the involved resource, the old and the new status, and the type and value of the involved metric; if applicable, the varbind also includes the current threshold settings and other information useful for automation purposes."
	::= 16988

winA3DirModified TRAP-TYPE
	ENTERPRISE caiWinA3
	VARIABLES {
		winA3ConfigGeneralAgentVersion
	}
	DESCRIPTION "&<caiWinA3.1591>The watcher configuration for a directory resource changed. The varbind list contains a varbind with detailed information, encoded as a single string, including the name of the involved resource and the changed attribute with its old value and with its new value."
	::= 16989

--
-- The File Traps
--

winA3FileUnknown TRAP-TYPE
	ENTERPRISE caiWinA3
	VARIABLES {
		winA3StatusFileWatcherName,
		winA3ConfigGeneralAgentVersion
	}
	DESCRIPTION "&<caiWinA3.1592>A watcher monitoring a file resource changed its status to 'unknown'. The varbind list contains a varbind with detailed information, encoded as a single string, including the name of the involved resource and the type and value of the involved metric; if applicable, the varbind also includes the current threshold settings and other information useful for automation purposes."
	::= 17980

winA3FileOk TRAP-TYPE
	ENTERPRISE caiWinA3
	VARIABLES {
		winA3StatusFileWatcherName,
		winA3ConfigGeneralAgentVersion
	}
	DESCRIPTION "&<caiWinA3.1593>A watcher monitoring a file resource changed its status to 'ok'. The varbind list contains a varbind with detailed information, encoded as a single string, including the name of the involved resource and the type and value of the involved metric; if applicable, the varbind also includes the current threshold settings and other information useful for automation purposes."
	::= 17981

winA3FileWarning TRAP-TYPE
	ENTERPRISE caiWinA3
	VARIABLES {
		winA3StatusFileWatcherName,
		winA3ConfigGeneralAgentVersion
	}
	DESCRIPTION "&<caiWinA3.1594>A watcher monitoring a file resource changed its status to 'warning'. The varbind list contains a varbind with detailed information, encoded as a single string, including the name of the involved resource and the type and value of the involved metric; if applicable, the varbind also includes the current threshold settings and other information useful for automation purposes."
	::= 17982

winA3FileCritical TRAP-TYPE
	ENTERPRISE caiWinA3
	VARIABLES {
		winA3StatusFileWatcherName,
		winA3ConfigGeneralAgentVersion
	}
	DESCRIPTION "&<caiWinA3.1595>A watcher monitoring a file resource changed its status to 'critical'. The varbind list contains a varbind with detailed information, encoded as a single string, including the name of the involved resource and the type and value of the involved metric; if applicable, the varbind also includes the current threshold settings and other information useful for automation purposes."
	::= 17983

winA3FileActive TRAP-TYPE
	ENTERPRISE caiWinA3
	VARIABLES {
		winA3StatusFileWatcherName,
		winA3ConfigGeneralAgentVersion
	}
	DESCRIPTION "&<caiWinA3.1596>A watcher monitoring a file resource changed its status from 'passive'. The varbind list contains a varbind with detailed information, encoded as a single string, including the name of the involved resource and the type and value of the involved metric; if applicable, the varbind also includes the current threshold settings and other information useful for automation purposes."
	::= 17984

winA3FilePassive TRAP-TYPE
	ENTERPRISE caiWinA3
	VARIABLES {
		winA3StatusFileWatcherName,
		winA3ConfigGeneralAgentVersion
	}
	DESCRIPTION "&<caiWinA3.1597>A watcher monitoring a file resource changed its status to 'passive'. The varbind list contains a varbind with detailed information, encoded as a single string, including the name of the involved resource and the type and value of the involved metric; if applicable, the varbind also includes the current threshold settings and other information useful for automation purposes."
	::= 17985

winA3FileAdded TRAP-TYPE
	ENTERPRISE caiWinA3
	VARIABLES {
		winA3StatusFileWatcherName
	}
	DESCRIPTION "&<caiWinA3.1598>A watcher monitoring a file resource was added. The varbind list contains the name of the involved resource."
	::= 17986

winA3FileDeleted TRAP-TYPE
	ENTERPRISE caiWinA3
	VARIABLES {
		winA3StatusFileWatcherName
	}
	DESCRIPTION "&<caiWinA3.1599>A watcher monitoring a file resource was removed. The varbind list contains the name of the involved resource."
	::= 17987

winA3FileInfo TRAP-TYPE
	ENTERPRISE caiWinA3
	VARIABLES {
		winA3ConfigGeneralAgentVersion
	}
	DESCRIPTION "&<caiWinA3.1600>A watcher monitoring a file resource changed a sub-state. The varbind list contains a varbind with detailed information, encoded as a single string, including the name of the involved resource, the old and the new status, and the type and value of the involved metric; if applicable, the varbind also includes the current threshold settings and other information useful for automation purposes."
	::= 17988

winA3FileModified TRAP-TYPE
	ENTERPRISE caiWinA3
	VARIABLES {
		winA3ConfigGeneralAgentVersion
	}
	DESCRIPTION "&<caiWinA3.1601>The watcher configuration for a file resource changed. The varbind list contains a varbind with detailed information, encoded as a single string, including the name of the involved resource and the changed attribute with its old value and with its new value."
	::= 17989

--
-- The Proc Traps
--

winA3ProcUnknown TRAP-TYPE
	ENTERPRISE caiWinA3
	VARIABLES {
		winA3StatusProcWatcherName,
		winA3ConfigGeneralAgentVersion
	}
	DESCRIPTION "&<caiWinA3.1602>A watcher monitoring a process resource changed its status to 'unknown'. The varbind list contains a varbind with detailed information, encoded as a single string, including the name of the involved resource and the type and value of the involved metric; if applicable, the varbind also includes the current threshold settings and other information useful for automation purposes."
	::= 18980

winA3ProcOk TRAP-TYPE
	ENTERPRISE caiWinA3
	VARIABLES {
		winA3StatusProcWatcherName,
		winA3ConfigGeneralAgentVersion
	}
	DESCRIPTION "&<caiWinA3.1603>A watcher monitoring a process resource changed its status to 'ok'. The varbind list contains a varbind with detailed information, encoded as a single string, including the name of the involved resource and the type and value of the involved metric; if applicable, the varbind also includes the current threshold settings and other information useful for automation purposes."
	::= 18981

winA3ProcWarning TRAP-TYPE
	ENTERPRISE caiWinA3
	VARIABLES {
		winA3StatusProcWatcherName,
		winA3ConfigGeneralAgentVersion
	}
	DESCRIPTION "&<caiWinA3.1604>A watcher monitoring a process resource changed its status to 'warning'. The varbind list contains a varbind with detailed information, encoded as a single string, including the name of the involved resource and the type and value of the involved metric; if applicable, the varbind also includes the current threshold settings and other information useful for automation purposes."
	::= 18982

winA3ProcCritical TRAP-TYPE
	ENTERPRISE caiWinA3
	VARIABLES {
		winA3StatusProcWatcherName,
		winA3ConfigGeneralAgentVersion
	}
	DESCRIPTION "&<caiWinA3.1605>A watcher monitoring a process resource changed its status to 'critical'. The varbind list contains a varbind with detailed information, encoded as a single string, including the name of the involved resource and the type and value of the involved metric; if applicable, the varbind also includes the current threshold settings and other information useful for automation purposes."
	::= 18983

winA3ProcActive TRAP-TYPE
	ENTERPRISE caiWinA3
	VARIABLES {
		winA3StatusProcWatcherName,
		winA3ConfigGeneralAgentVersion
	}
	DESCRIPTION "&<caiWinA3.1606>A watcher monitoring a process resource changed its status from 'passive'. The varbind list contains a varbind with detailed information, encoded as a single string, including the name of the involved resource and the type and value of the involved metric; if applicable, the varbind also includes the current threshold settings and other information useful for automation purposes."
	::= 18984

winA3ProcPassive TRAP-TYPE
	ENTERPRISE caiWinA3
	VARIABLES {
		winA3StatusProcWatcherName,
		winA3ConfigGeneralAgentVersion
	}
	DESCRIPTION "&<caiWinA3.1607>A watcher monitoring a process resource changed its status to 'passive'. The varbind list contains a varbind with detailed information, encoded as a single string, including the name of the involved resource and the type and value of the involved metric; if applicable, the varbind also includes the current threshold settings and other information useful for automation purposes."
	::= 18985

winA3ProcAdded TRAP-TYPE
	ENTERPRISE caiWinA3
	VARIABLES {
		winA3StatusProcWatcherName
	}
	DESCRIPTION "&<caiWinA3.1608>A watcher monitoring a process resource was added. The varbind list contains the name of the involved resource."
	::= 18986

winA3ProcDeleted TRAP-TYPE
	ENTERPRISE caiWinA3
	VARIABLES {
		winA3StatusProcWatcherName
	}
	DESCRIPTION "&<caiWinA3.1609>A watcher monitoring a process resource was removed. The varbind list contains the name of the involved resource."
	::= 18987

winA3ProcInfo TRAP-TYPE
	ENTERPRISE caiWinA3
	VARIABLES {
		winA3ConfigGeneralAgentVersion
	}
	DESCRIPTION "&<caiWinA3.1610>A watcher monitoring a process resource changed a sub-state. The varbind list contains a varbind with detailed information, encoded as a single string, including the name of the involved resource, the old and the new status, and the type and value of the involved metric; if applicable, the varbind also includes the current threshold settings and other information useful for automation purposes."
	::= 18988

winA3ProcModified TRAP-TYPE
	ENTERPRISE caiWinA3
	VARIABLES {
		winA3ConfigGeneralAgentVersion
	}
	DESCRIPTION "&<caiWinA3.1611>The watcher configuration for a process resource changed. The varbind list contains a varbind with detailed information, encoded as a single string, including the name of the involved resource and the changed attribute with its old value and with its new value."
	::= 18989

--
-- The Srvc Traps
--

winA3SrvcUnknown TRAP-TYPE
	ENTERPRISE caiWinA3
	VARIABLES {
		winA3StatusSrvcName,
		winA3ConfigGeneralAgentVersion
	}
	DESCRIPTION "&<caiWinA3.1612>A watcher monitoring a service resource changed its status to 'unknown'. The varbind list contains a varbind with detailed information, encoded as a single string, including the name of the involved resource and the type and value of the involved metric; if applicable, the varbind also includes the current threshold settings and other information useful for automation purposes."
	::= 19980

winA3SrvcOk TRAP-TYPE
	ENTERPRISE caiWinA3
	VARIABLES {
		winA3StatusSrvcName,
		winA3ConfigGeneralAgentVersion
	}
	DESCRIPTION "&<caiWinA3.1613>A watcher monitoring a service resource changed its status to 'ok'. The varbind list contains a varbind with detailed information, encoded as a single string, including the name of the involved resource and the type and value of the involved metric; if applicable, the varbind also includes the current threshold settings and other information useful for automation purposes."
	::= 19981

winA3SrvcWarning TRAP-TYPE
	ENTERPRISE caiWinA3
	VARIABLES {
		winA3StatusSrvcName,
		winA3ConfigGeneralAgentVersion
	}
	DESCRIPTION "&<caiWinA3.1614>A watcher monitoring a service resource changed its status to 'warning'. The varbind list contains a varbind with detailed information, encoded as a single string, including the name of the involved resource and the type and value of the involved metric; if applicable, the varbind also includes the current threshold settings and other information useful for automation purposes."
	::= 19982

winA3SrvcCritical TRAP-TYPE
	ENTERPRISE caiWinA3
	VARIABLES {
		winA3StatusSrvcName,
		winA3ConfigGeneralAgentVersion
	}
	DESCRIPTION "&<caiWinA3.1615>A watcher monitoring a service resource changed its status to 'critical'. The varbind list contains a varbind with detailed information, encoded as a single string, including the name of the involved resource and the type and value of the involved metric; if applicable, the varbind also includes the current threshold settings and other information useful for automation purposes."
	::= 19983

winA3SrvcActive TRAP-TYPE
	ENTERPRISE caiWinA3
	VARIABLES {
		winA3StatusSrvcName,
		winA3ConfigGeneralAgentVersion
	}
	DESCRIPTION "&<caiWinA3.1616>A watcher monitoring a service resource changed its status from 'passive'. The varbind list contains a varbind with detailed information, encoded as a single string, including the name of the involved resource and the type and value of the involved metric; if applicable, the varbind also includes the current threshold settings and other information useful for automation purposes."
	::= 19984

winA3SrvcPassive TRAP-TYPE
	ENTERPRISE caiWinA3
	VARIABLES {
		winA3StatusSrvcName,
		winA3ConfigGeneralAgentVersion
	}
	DESCRIPTION "&<caiWinA3.1617>A watcher monitoring a service resource changed its status to 'passive'. The varbind list contains a varbind with detailed information, encoded as a single string, including the name of the involved resource and the type and value of the involved metric; if applicable, the varbind also includes the current threshold settings and other information useful for automation purposes."
	::= 19985

winA3SrvcAdded TRAP-TYPE
	ENTERPRISE caiWinA3
	VARIABLES {
		winA3StatusSrvcName
	}
	DESCRIPTION "&<caiWinA3.1618>A watcher monitoring a service resource was added. The varbind list contains the name of the involved resource."
	::= 19986

winA3SrvcDeleted TRAP-TYPE
	ENTERPRISE caiWinA3
	VARIABLES {
		winA3StatusSrvcName
	}
	DESCRIPTION "&<caiWinA3.1619>A watcher monitoring a service resource was removed. The varbind list contains the name of the involved resource."
	::= 19987

winA3SrvcInfo TRAP-TYPE
	ENTERPRISE caiWinA3
	VARIABLES {
		winA3ConfigGeneralAgentVersion
	}
	DESCRIPTION "&<caiWinA3.1620>A watcher monitoring a service resource changed a sub-state. The varbind list contains a varbind with detailed information, encoded as a single string, including the name of the involved resource, the old and the new status, and the type and value of the involved metric; if applicable, the varbind also includes the current threshold settings and other information useful for automation purposes."
	::= 19988

winA3SrvcModified TRAP-TYPE
	ENTERPRISE caiWinA3
	VARIABLES {
		winA3ConfigGeneralAgentVersion
	}
	DESCRIPTION "&<caiWinA3.1621>The watcher configuration for a service resource changed. The varbind list contains a varbind with detailed information, encoded as a single string, including the name of the involved resource and the changed attribute with its old value and with its new value."
	::= 19989

--
-- The Job Traps
--

winA3JobUnknown TRAP-TYPE
	ENTERPRISE caiWinA3
	VARIABLES {
		winA3StatusJobName,
		winA3ConfigGeneralAgentVersion
	}
	DESCRIPTION "&<caiWinA3.1622>A watcher monitoring a job resource changed its status to 'unknown'. The varbind list contains a varbind with detailed information, encoded as a single string, including the name of the involved resource and the type and value of the involved metric; if applicable, the varbind also includes the current threshold settings and other information useful for automation purposes."
	::= 20980

winA3JobOk TRAP-TYPE
	ENTERPRISE caiWinA3
	VARIABLES {
		winA3StatusJobName,
		winA3ConfigGeneralAgentVersion
	}
	DESCRIPTION "&<caiWinA3.1623>A watcher monitoring a job resource changed its status to 'ok'. The varbind list contains a varbind with detailed information, encoded as a single string, including the name of the involved resource and the type and value of the involved metric; if applicable, the varbind also includes the current threshold settings and other information useful for automation purposes."
	::= 20981

winA3JobWarning TRAP-TYPE
	ENTERPRISE caiWinA3
	VARIABLES {
		winA3StatusJobName,
		winA3ConfigGeneralAgentVersion
	}
	DESCRIPTION "&<caiWinA3.1624>A watcher monitoring a job resource changed its status to 'warning'. The varbind list contains a varbind with detailed information, encoded as a single string, including the name of the involved resource and the type and value of the involved metric; if applicable, the varbind also includes the current threshold settings and other information useful for automation purposes."
	::= 20982

winA3JobCritical TRAP-TYPE
	ENTERPRISE caiWinA3
	VARIABLES {
		winA3StatusJobName,
		winA3ConfigGeneralAgentVersion
	}
	DESCRIPTION "&<caiWinA3.1625>A watcher monitoring a job resource changed its status to 'critical'. The varbind list contains a varbind with detailed information, encoded as a single string, including the name of the involved resource and the type and value of the involved metric; if applicable, the varbind also includes the current threshold settings and other information useful for automation purposes."
	::= 20983

winA3JobActive TRAP-TYPE
	ENTERPRISE caiWinA3
	VARIABLES {
		winA3StatusJobName,
		winA3ConfigGeneralAgentVersion
	}
	DESCRIPTION "&<caiWinA3.1626>A watcher monitoring a job resource changed its status from 'passive'. The varbind list contains a varbind with detailed information, encoded as a single string, including the name of the involved resource and the type and value of the involved metric; if applicable, the varbind also includes the current threshold settings and other information useful for automation purposes."
	::= 20984

winA3JobPassive TRAP-TYPE
	ENTERPRISE caiWinA3
	VARIABLES {
		winA3StatusJobName,
		winA3ConfigGeneralAgentVersion
	}
	DESCRIPTION "&<caiWinA3.1627>A watcher monitoring a job resource changed its status to 'passive'. The varbind list contains a varbind with detailed information, encoded as a single string, including the name of the involved resource and the type and value of the involved metric; if applicable, the varbind also includes the current threshold settings and other information useful for automation purposes."
	::= 20985

winA3JobAdded TRAP-TYPE
	ENTERPRISE caiWinA3
	VARIABLES {
		winA3StatusJobName
	}
	DESCRIPTION "&<caiWinA3.1628>A watcher monitoring a job resource was added. The varbind list contains the name of the involved resource."
	::= 20986

winA3JobDeleted TRAP-TYPE
	ENTERPRISE caiWinA3
	VARIABLES {
		winA3StatusJobName
	}
	DESCRIPTION "&<caiWinA3.1629>A watcher monitoring a job resource was removed. The varbind list contains the name of the involved resource."
	::= 20987

winA3JobInfo TRAP-TYPE
	ENTERPRISE caiWinA3
	VARIABLES {
		winA3ConfigGeneralAgentVersion
	}
	DESCRIPTION "&<caiWinA3.1630>A watcher monitoring a job resource changed a sub-state. The varbind list contains a varbind with detailed information, encoded as a single string, including the name of the involved resource, the old and the new status, and the type and value of the involved metric; if applicable, the varbind also includes the current threshold settings and other information useful for automation purposes."
	::= 20988

winA3JobModified TRAP-TYPE
	ENTERPRISE caiWinA3
	VARIABLES {
		winA3ConfigGeneralAgentVersion
	}
	DESCRIPTION "&<caiWinA3.1631>The watcher configuration for a job resource changed. The varbind list contains a varbind with detailed information, encoded as a single string, including the name of the involved resource and the changed attribute with its old value and with its new value."
	::= 20989

--
-- The Sess Traps
--

winA3SessUnknown TRAP-TYPE
	ENTERPRISE caiWinA3
	VARIABLES {
		winA3StatusSessWatcherName,
		winA3ConfigGeneralAgentVersion
	}
	DESCRIPTION "&<caiWinA3.1632>A watcher monitoring a terminal session resource changed its status to 'unknown'. The varbind list contains a varbind with detailed information, encoded as a single string, including the name of the involved resource and the type and value of the involved metric; if applicable, the varbind also includes the current threshold settings and other information useful for automation purposes."
	::= 21980

winA3SessOk TRAP-TYPE
	ENTERPRISE caiWinA3
	VARIABLES {
		winA3StatusSessWatcherName,
		winA3ConfigGeneralAgentVersion
	}
	DESCRIPTION "&<caiWinA3.1633>A watcher monitoring a terminal session resource changed its status to 'ok'. The varbind list contains a varbind with detailed information, encoded as a single string, including the name of the involved resource and the type and value of the involved metric; if applicable, the varbind also includes the current threshold settings and other information useful for automation purposes."
	::= 21981

winA3SessWarning TRAP-TYPE
	ENTERPRISE caiWinA3
	VARIABLES {
		winA3StatusSessWatcherName,
		winA3ConfigGeneralAgentVersion
	}
	DESCRIPTION "&<caiWinA3.1634>A watcher monitoring a terminal session resource changed its status to 'warning'. The varbind list contains a varbind with detailed information, encoded as a single string, including the name of the involved resource and the type and value of the involved metric; if applicable, the varbind also includes the current threshold settings and other information useful for automation purposes."
	::= 21982

winA3SessCritical TRAP-TYPE
	ENTERPRISE caiWinA3
	VARIABLES {
		winA3StatusSessWatcherName,
		winA3ConfigGeneralAgentVersion
	}
	DESCRIPTION "&<caiWinA3.1635>A watcher monitoring a terminal session resource changed its status to 'critical'. The varbind list contains a varbind with detailed information, encoded as a single string, including the name of the involved resource and the type and value of the involved metric; if applicable, the varbind also includes the current threshold settings and other information useful for automation purposes."
	::= 21983

winA3SessActive TRAP-TYPE
	ENTERPRISE caiWinA3
	VARIABLES {
		winA3StatusSessWatcherName,
		winA3ConfigGeneralAgentVersion
	}
	DESCRIPTION "&<caiWinA3.1636>A watcher monitoring a terminal session resource changed its status from 'passive'. The varbind list contains a varbind with detailed information, encoded as a single string, including the name of the involved resource and the type and value of the involved metric; if applicable, the varbind also includes the current threshold settings and other information useful for automation purposes."
	::= 21984

winA3SessPassive TRAP-TYPE
	ENTERPRISE caiWinA3
	VARIABLES {
		winA3StatusSessWatcherName,
		winA3ConfigGeneralAgentVersion
	}
	DESCRIPTION "&<caiWinA3.1637>A watcher monitoring a terminal session resource changed its status to 'passive'. The varbind list contains a varbind with detailed information, encoded as a single string, including the name of the involved resource and the type and value of the involved metric; if applicable, the varbind also includes the current threshold settings and other information useful for automation purposes."
	::= 21985

winA3SessAdded TRAP-TYPE
	ENTERPRISE caiWinA3
	VARIABLES {
		winA3StatusSessWatcherName
	}
	DESCRIPTION "&<caiWinA3.1638>A watcher monitoring a terminal session resource was added. The varbind list contains the name of the involved resource."
	::= 21986

winA3SessDeleted TRAP-TYPE
	ENTERPRISE caiWinA3
	VARIABLES {
		winA3StatusSessWatcherName
	}
	DESCRIPTION "&<caiWinA3.1639>A watcher monitoring a terminal session resource was removed. The varbind list contains the name of the involved resource."
	::= 21987

winA3SessInfo TRAP-TYPE
	ENTERPRISE caiWinA3
	VARIABLES {
		winA3ConfigGeneralAgentVersion
	}
	DESCRIPTION "&<caiWinA3.1640>A watcher monitoring a terminal session resource changed a sub-state. The varbind list contains a varbind with detailed information, encoded as a single string, including the name of the involved resource, the old and the new status, and the type and value of the involved metric; if applicable, the varbind also includes the current threshold settings and other information useful for automation purposes."
	::= 21988

winA3SessModified TRAP-TYPE
	ENTERPRISE caiWinA3
	VARIABLES {
		winA3ConfigGeneralAgentVersion
	}
	DESCRIPTION "&<caiWinA3.1641>The watcher configuration for a terminal session resource changed. The varbind list contains a varbind with detailed information, encoded as a single string, including the name of the involved resource and the changed attribute with its old value and with its new value."
	::= 21989

--
-- The Prn Traps
--

winA3PrnUnknown TRAP-TYPE
	ENTERPRISE caiWinA3
	VARIABLES {
		winA3StatusPrnName,
		winA3ConfigGeneralAgentVersion
	}
	DESCRIPTION "&<caiWinA3.1642>A watcher monitoring a printer resource changed its status to 'unknown'. The varbind list contains a varbind with detailed information, encoded as a single string, including the name of the involved resource and the type and value of the involved metric; if applicable, the varbind also includes the current threshold settings and other information useful for automation purposes."
	::= 22980

winA3PrnOk TRAP-TYPE
	ENTERPRISE caiWinA3
	VARIABLES {
		winA3StatusPrnName,
		winA3ConfigGeneralAgentVersion
	}
	DESCRIPTION "&<caiWinA3.1643>A watcher monitoring a printer resource changed its status to 'ok'. The varbind list contains a varbind with detailed information, encoded as a single string, including the name of the involved resource and the type and value of the involved metric; if applicable, the varbind also includes the current threshold settings and other information useful for automation purposes."
	::= 22981

winA3PrnWarning TRAP-TYPE
	ENTERPRISE caiWinA3
	VARIABLES {
		winA3StatusPrnName,
		winA3ConfigGeneralAgentVersion
	}
	DESCRIPTION "&<caiWinA3.1644>A watcher monitoring a printer resource changed its status to 'warning'. The varbind list contains a varbind with detailed information, encoded as a single string, including the name of the involved resource and the type and value of the involved metric; if applicable, the varbind also includes the current threshold settings and other information useful for automation purposes."
	::= 22982

winA3PrnCritical TRAP-TYPE
	ENTERPRISE caiWinA3
	VARIABLES {
		winA3StatusPrnName,
		winA3ConfigGeneralAgentVersion
	}
	DESCRIPTION "&<caiWinA3.1645>A watcher monitoring a printer resource changed its status to 'critical'. The varbind list contains a varbind with detailed information, encoded as a single string, including the name of the involved resource and the type and value of the involved metric; if applicable, the varbind also includes the current threshold settings and other information useful for automation purposes."
	::= 22983

winA3PrnActive TRAP-TYPE
	ENTERPRISE caiWinA3
	VARIABLES {
		winA3StatusPrnName,
		winA3ConfigGeneralAgentVersion
	}
	DESCRIPTION "&<caiWinA3.1646>A watcher monitoring a printer resource changed its status from 'passive'. The varbind list contains a varbind with detailed information, encoded as a single string, including the name of the involved resource and the type and value of the involved metric; if applicable, the varbind also includes the current threshold settings and other information useful for automation purposes."
	::= 22984

winA3PrnPassive TRAP-TYPE
	ENTERPRISE caiWinA3
	VARIABLES {
		winA3StatusPrnName,
		winA3ConfigGeneralAgentVersion
	}
	DESCRIPTION "&<caiWinA3.1647>A watcher monitoring a printer resource changed its status to 'passive'. The varbind list contains a varbind with detailed information, encoded as a single string, including the name of the involved resource and the type and value of the involved metric; if applicable, the varbind also includes the current threshold settings and other information useful for automation purposes."
	::= 22985

winA3PrnAdded TRAP-TYPE
	ENTERPRISE caiWinA3
	VARIABLES {
		winA3StatusPrnName
	}
	DESCRIPTION "&<caiWinA3.1648>A watcher monitoring a printer resource was added. The varbind list contains the name of the involved resource."
	::= 22986

winA3PrnDeleted TRAP-TYPE
	ENTERPRISE caiWinA3
	VARIABLES {
		winA3StatusPrnName
	}
	DESCRIPTION "&<caiWinA3.1649>A watcher monitoring a printer resource was removed. The varbind list contains the name of the involved resource."
	::= 22987

winA3PrnInfo TRAP-TYPE
	ENTERPRISE caiWinA3
	VARIABLES {
		winA3ConfigGeneralAgentVersion
	}
	DESCRIPTION "&<caiWinA3.1650>A watcher monitoring a printer resource changed a sub-state. The varbind list contains a varbind with detailed information, encoded as a single string, including the name of the involved resource, the old and the new status, and the type and value of the involved metric; if applicable, the varbind also includes the current threshold settings and other information useful for automation purposes."
	::= 22988

winA3PrnModified TRAP-TYPE
	ENTERPRISE caiWinA3
	VARIABLES {
		winA3ConfigGeneralAgentVersion
	}
	DESCRIPTION "&<caiWinA3.1651>The watcher configuration for a printer resource changed. The varbind list contains a varbind with detailed information, encoded as a single string, including the name of the involved resource and the changed attribute with its old value and with its new value."
	::= 22989

--
-- The NetTotal Traps
--

winA3NetTotalUnknown TRAP-TYPE
	ENTERPRISE caiWinA3
	VARIABLES {
		winA3ConfigGeneralAgentVersion
	}
	DESCRIPTION "&<caiWinA3.1652>A watcher monitoring a network interface resource changed its status to 'unknown'. The varbind list contains a varbind with detailed information, encoded as a single string, including the type and value of the involved metric; if applicable, the varbind also includes the current threshold settings and other information useful for automation purposes."
	::= 23000

winA3NetTotalOk TRAP-TYPE
	ENTERPRISE caiWinA3
	VARIABLES {
		winA3ConfigGeneralAgentVersion
	}
	DESCRIPTION "&<caiWinA3.1653>A watcher monitoring a network interface resource changed its status to 'ok'. The varbind list contains a varbind with detailed information, encoded as a single string, including the type and value of the involved metric; if applicable, the varbind also includes the current threshold settings and other information useful for automation purposes."
	::= 23001

winA3NetTotalWarning TRAP-TYPE
	ENTERPRISE caiWinA3
	VARIABLES {
		winA3ConfigGeneralAgentVersion
	}
	DESCRIPTION "&<caiWinA3.1654>A watcher monitoring a network interface resource changed its status to 'warning'. The varbind list contains a varbind with detailed information, encoded as a single string, including the type and value of the involved metric; if applicable, the varbind also includes the current threshold settings and other information useful for automation purposes."
	::= 23002

winA3NetTotalCritical TRAP-TYPE
	ENTERPRISE caiWinA3
	VARIABLES {
		winA3ConfigGeneralAgentVersion
	}
	DESCRIPTION "&<caiWinA3.1655>A watcher monitoring a network interface resource changed its status to 'critical'. The varbind list contains a varbind with detailed information, encoded as a single string, including the type and value of the involved metric; if applicable, the varbind also includes the current threshold settings and other information useful for automation purposes."
	::= 23003

winA3NetTotalActive TRAP-TYPE
	ENTERPRISE caiWinA3
	VARIABLES {
		winA3ConfigGeneralAgentVersion
	}
	DESCRIPTION "&<caiWinA3.1656>A watcher monitoring a network interface resource changed its status from 'passive'. The varbind list contains a varbind with detailed information, encoded as a single string, including the type and value of the involved metric; if applicable, the varbind also includes the current threshold settings and other information useful for automation purposes."
	::= 23004

winA3NetTotalPassive TRAP-TYPE
	ENTERPRISE caiWinA3
	VARIABLES {
		winA3ConfigGeneralAgentVersion
	}
	DESCRIPTION "&<caiWinA3.1657>A watcher monitoring a network interface resource changed its status to 'passive'. The varbind list contains a varbind with detailed information, encoded as a single string, including the type and value of the involved metric; if applicable, the varbind also includes the current threshold settings and other information useful for automation purposes."
	::= 23005

winA3NetTotalInfo TRAP-TYPE
	ENTERPRISE caiWinA3
	VARIABLES {
		winA3ConfigGeneralAgentVersion
	}
	DESCRIPTION "&<caiWinA3.1658>A watcher monitoring a network interface resource changed a sub-state. The varbind list contains a varbind with detailed information, encoded as a single string, including the old and the new status, and the type and value of the involved metric; if applicable, the varbind also includes the current threshold settings and other information useful for automation purposes."
	::= 23008

winA3NetTotalModified TRAP-TYPE
	ENTERPRISE caiWinA3
	VARIABLES {
		winA3ConfigGeneralAgentVersion
	}
	DESCRIPTION "&<caiWinA3.1659>The watcher configuration for a network interface resource changed. The varbind list contains a varbind with detailed information, encoded as a single string, including the changed attribute with its old value and with its new value."
	::= 23009

--
-- The Net Traps
--

winA3NetUnknown TRAP-TYPE
	ENTERPRISE caiWinA3
	VARIABLES {
		winA3StatusNetName,
		winA3ConfigGeneralAgentVersion
	}
	DESCRIPTION "&<caiWinA3.1660>A watcher monitoring a network interface resource changed its status to 'unknown'. The varbind list contains a varbind with detailed information, encoded as a single string, including the name of the involved resource and the type and value of the involved metric; if applicable, the varbind also includes the current threshold settings and other information useful for automation purposes."
	::= 23990

winA3NetOk TRAP-TYPE
	ENTERPRISE caiWinA3
	VARIABLES {
		winA3StatusNetName,
		winA3ConfigGeneralAgentVersion
	}
	DESCRIPTION "&<caiWinA3.1661>A watcher monitoring a network interface resource changed its status to 'ok'. The varbind list contains a varbind with detailed information, encoded as a single string, including the name of the involved resource and the type and value of the involved metric; if applicable, the varbind also includes the current threshold settings and other information useful for automation purposes."
	::= 23991

winA3NetWarning TRAP-TYPE
	ENTERPRISE caiWinA3
	VARIABLES {
		winA3StatusNetName,
		winA3ConfigGeneralAgentVersion
	}
	DESCRIPTION "&<caiWinA3.1662>A watcher monitoring a network interface resource changed its status to 'warning'. The varbind list contains a varbind with detailed information, encoded as a single string, including the name of the involved resource and the type and value of the involved metric; if applicable, the varbind also includes the current threshold settings and other information useful for automation purposes."
	::= 23992

winA3NetCritical TRAP-TYPE
	ENTERPRISE caiWinA3
	VARIABLES {
		winA3StatusNetName,
		winA3ConfigGeneralAgentVersion
	}
	DESCRIPTION "&<caiWinA3.1663>A watcher monitoring a network interface resource changed its status to 'critical'. The varbind list contains a varbind with detailed information, encoded as a single string, including the name of the involved resource and the type and value of the involved metric; if applicable, the varbind also includes the current threshold settings and other information useful for automation purposes."
	::= 23993

winA3NetActive TRAP-TYPE
	ENTERPRISE caiWinA3
	VARIABLES {
		winA3StatusNetName,
		winA3ConfigGeneralAgentVersion
	}
	DESCRIPTION "&<caiWinA3.1664>A watcher monitoring a network interface resource changed its status from 'passive'. The varbind list contains a varbind with detailed information, encoded as a single string, including the name of the involved resource and the type and value of the involved metric; if applicable, the varbind also includes the current threshold settings and other information useful for automation purposes."
	::= 23994

winA3NetPassive TRAP-TYPE
	ENTERPRISE caiWinA3
	VARIABLES {
		winA3StatusNetName,
		winA3ConfigGeneralAgentVersion
	}
	DESCRIPTION "&<caiWinA3.1665>A watcher monitoring a network interface resource changed its status to 'passive'. The varbind list contains a varbind with detailed information, encoded as a single string, including the name of the involved resource and the type and value of the involved metric; if applicable, the varbind also includes the current threshold settings and other information useful for automation purposes."
	::= 23995

winA3NetAdded TRAP-TYPE
	ENTERPRISE caiWinA3
	VARIABLES {
		winA3StatusNetName
	}
	DESCRIPTION "&<caiWinA3.1666>A watcher monitoring a network interface resource was added. The varbind list contains the name of the involved resource."
	::= 23996

winA3NetDeleted TRAP-TYPE
	ENTERPRISE caiWinA3
	VARIABLES {
		winA3StatusNetName
	}
	DESCRIPTION "&<caiWinA3.1667>A watcher monitoring a network interface resource was removed. The varbind list contains the name of the involved resource."
	::= 23997

winA3NetInfo TRAP-TYPE
	ENTERPRISE caiWinA3
	VARIABLES {
		winA3ConfigGeneralAgentVersion
	}
	DESCRIPTION "&<caiWinA3.1668>A watcher monitoring a network interface resource changed a sub-state. The varbind list contains a varbind with detailed information, encoded as a single string, including the name of the involved resource, the old and the new status, and the type and value of the involved metric; if applicable, the varbind also includes the current threshold settings and other information useful for automation purposes."
	::= 23998

winA3NetModified TRAP-TYPE
	ENTERPRISE caiWinA3
	VARIABLES {
		winA3ConfigGeneralAgentVersion
	}
	DESCRIPTION "&<caiWinA3.1669>The watcher configuration for a network interface resource changed. The varbind list contains a varbind with detailed information, encoded as a single string, including the name of the involved resource and the changed attribute with its old value and with its new value."
	::= 23999

--
-- The Reg Traps
--

winA3RegUnknown TRAP-TYPE
	ENTERPRISE caiWinA3
	VARIABLES {
		winA3StatusRegWatcherName,
		winA3ConfigGeneralAgentVersion
	}
	DESCRIPTION "&<caiWinA3.1670>A watcher monitoring a registry entry resource changed its status to 'unknown'. The varbind list contains a varbind with detailed information, encoded as a single string, including the name of the involved resource and the type and value of the involved metric; if applicable, the varbind also includes the current threshold settings and other information useful for automation purposes."
	::= 24980

winA3RegOk TRAP-TYPE
	ENTERPRISE caiWinA3
	VARIABLES {
		winA3StatusRegWatcherName,
		winA3ConfigGeneralAgentVersion
	}
	DESCRIPTION "&<caiWinA3.1671>A watcher monitoring a registry entry resource changed its status to 'ok'. The varbind list contains a varbind with detailed information, encoded as a single string, including the name of the involved resource and the type and value of the involved metric; if applicable, the varbind also includes the current threshold settings and other information useful for automation purposes."
	::= 24981

winA3RegWarning TRAP-TYPE
	ENTERPRISE caiWinA3
	VARIABLES {
		winA3StatusRegWatcherName,
		winA3ConfigGeneralAgentVersion
	}
	DESCRIPTION "&<caiWinA3.1672>A watcher monitoring a registry entry resource changed its status to 'warning'. The varbind list contains a varbind with detailed information, encoded as a single string, including the name of the involved resource and the type and value of the involved metric; if applicable, the varbind also includes the current threshold settings and other information useful for automation purposes."
	::= 24982

winA3RegCritical TRAP-TYPE
	ENTERPRISE caiWinA3
	VARIABLES {
		winA3StatusRegWatcherName,
		winA3ConfigGeneralAgentVersion
	}
	DESCRIPTION "&<caiWinA3.1673>A watcher monitoring a registry entry resource changed its status to 'critical'. The varbind list contains a varbind with detailed information, encoded as a single string, including the name of the involved resource and the type and value of the involved metric; if applicable, the varbind also includes the current threshold settings and other information useful for automation purposes."
	::= 24983

winA3RegActive TRAP-TYPE
	ENTERPRISE caiWinA3
	VARIABLES {
		winA3StatusRegWatcherName,
		winA3ConfigGeneralAgentVersion
	}
	DESCRIPTION "&<caiWinA3.1674>A watcher monitoring a registry entry resource changed its status from 'passive'. The varbind list contains a varbind with detailed information, encoded as a single string, including the name of the involved resource and the type and value of the involved metric; if applicable, the varbind also includes the current threshold settings and other information useful for automation purposes."
	::= 24984

winA3RegPassive TRAP-TYPE
	ENTERPRISE caiWinA3
	VARIABLES {
		winA3StatusRegWatcherName,
		winA3ConfigGeneralAgentVersion
	}
	DESCRIPTION "&<caiWinA3.1675>A watcher monitoring a registry entry resource changed its status to 'passive'. The varbind list contains a varbind with detailed information, encoded as a single string, including the name of the involved resource and the type and value of the involved metric; if applicable, the varbind also includes the current threshold settings and other information useful for automation purposes."
	::= 24985

winA3RegAdded TRAP-TYPE
	ENTERPRISE caiWinA3
	VARIABLES {
		winA3StatusRegWatcherName
	}
	DESCRIPTION "&<caiWinA3.1676>A watcher monitoring a registry entry resource was added. The varbind list contains the name of the involved resource."
	::= 24986

winA3RegDeleted TRAP-TYPE
	ENTERPRISE caiWinA3
	VARIABLES {
		winA3StatusRegWatcherName
	}
	DESCRIPTION "&<caiWinA3.1677>A watcher monitoring a registry entry resource was removed. The varbind list contains the name of the involved resource."
	::= 24987

winA3RegInfo TRAP-TYPE
	ENTERPRISE caiWinA3
	VARIABLES {
		winA3ConfigGeneralAgentVersion
	}
	DESCRIPTION "&<caiWinA3.1678>A watcher monitoring a registry entry resource changed a sub-state. The varbind list contains a varbind with detailed information, encoded as a single string, including the name of the involved resource, the old and the new status, and the type and value of the involved metric; if applicable, the varbind also includes the current threshold settings and other information useful for automation purposes."
	::= 24988

winA3RegModified TRAP-TYPE
	ENTERPRISE caiWinA3
	VARIABLES {
		winA3ConfigGeneralAgentVersion
	}
	DESCRIPTION "&<caiWinA3.1679>The watcher configuration for a registry entry resource changed. The varbind list contains a varbind with detailed information, encoded as a single string, including the name of the involved resource and the changed attribute with its old value and with its new value."
	::= 24989

--
-- The Hardwr Traps
--

winA3HardwrUnknown TRAP-TYPE
	ENTERPRISE caiWinA3
	VARIABLES {
		winA3StatusHardwrResName,
		winA3StatusHardwrResSubName,
		winA3StatusHardwrInstName,
		winA3ConfigGeneralAgentVersion
	}
	DESCRIPTION "&<caiWinA3.1680>A watcher monitoring a hardware resource changed its status to 'unknown'. The varbind list contains a varbind with detailed information, encoded as a single string, including the name of the involved resource and the type and value of the involved metric; if applicable, the varbind also includes the current threshold settings and other information useful for automation purposes."
	::= 25980

winA3HardwrOk TRAP-TYPE
	ENTERPRISE caiWinA3
	VARIABLES {
		winA3StatusHardwrResName,
		winA3StatusHardwrResSubName,
		winA3StatusHardwrInstName,
		winA3ConfigGeneralAgentVersion
	}
	DESCRIPTION "&<caiWinA3.1681>A watcher monitoring a hardware resource changed its status to 'ok'. The varbind list contains a varbind with detailed information, encoded as a single string, including the name of the involved resource and the type and value of the involved metric; if applicable, the varbind also includes the current threshold settings and other information useful for automation purposes."
	::= 25981

winA3HardwrWarning TRAP-TYPE
	ENTERPRISE caiWinA3
	VARIABLES {
		winA3StatusHardwrResName,
		winA3StatusHardwrResSubName,
		winA3StatusHardwrInstName,
		winA3ConfigGeneralAgentVersion
	}
	DESCRIPTION "&<caiWinA3.1682>A watcher monitoring a hardware resource changed its status to 'warning'. The varbind list contains a varbind with detailed information, encoded as a single string, including the name of the involved resource and the type and value of the involved metric; if applicable, the varbind also includes the current threshold settings and other information useful for automation purposes."
	::= 25982

winA3HardwrCritical TRAP-TYPE
	ENTERPRISE caiWinA3
	VARIABLES {
		winA3StatusHardwrResName,
		winA3StatusHardwrResSubName,
		winA3StatusHardwrInstName,
		winA3ConfigGeneralAgentVersion
	}
	DESCRIPTION "&<caiWinA3.1683>A watcher monitoring a hardware resource changed its status to 'critical'. The varbind list contains a varbind with detailed information, encoded as a single string, including the name of the involved resource and the type and value of the involved metric; if applicable, the varbind also includes the current threshold settings and other information useful for automation purposes."
	::= 25983

winA3HardwrActive TRAP-TYPE
	ENTERPRISE caiWinA3
	VARIABLES {
		winA3StatusHardwrResName,
		winA3StatusHardwrResSubName,
		winA3StatusHardwrInstName,
		winA3ConfigGeneralAgentVersion
	}
	DESCRIPTION "&<caiWinA3.1684>A watcher monitoring a hardware resource changed its status from 'passive'. The varbind list contains a varbind with detailed information, encoded as a single string, including the name of the involved resource and the type and value of the involved metric; if applicable, the varbind also includes the current threshold settings and other information useful for automation purposes."
	::= 25984

winA3HardwrPassive TRAP-TYPE
	ENTERPRISE caiWinA3
	VARIABLES {
		winA3StatusHardwrResName,
		winA3StatusHardwrResSubName,
		winA3StatusHardwrInstName,
		winA3ConfigGeneralAgentVersion
	}
	DESCRIPTION "&<caiWinA3.1685>A watcher monitoring a hardware resource changed its status to 'passive'. The varbind list contains a varbind with detailed information, encoded as a single string, including the name of the involved resource and the type and value of the involved metric; if applicable, the varbind also includes the current threshold settings and other information useful for automation purposes."
	::= 25985

winA3HardwrAdded TRAP-TYPE
	ENTERPRISE caiWinA3
	VARIABLES {
		winA3StatusHardwrResName,
		winA3StatusHardwrResSubName,
		winA3StatusHardwrInstName
	}
	DESCRIPTION "&<caiWinA3.1686>A watcher monitoring a hardware resource was added. The varbind list contains the name of the involved resource."
	::= 25986

winA3HardwrDeleted TRAP-TYPE
	ENTERPRISE caiWinA3
	VARIABLES {
		winA3StatusHardwrResName,
		winA3StatusHardwrResSubName,
		winA3StatusHardwrInstName
	}
	DESCRIPTION "&<caiWinA3.1687>A watcher monitoring a hardware resource was removed. The varbind list contains the name of the involved resource."
	::= 25987

winA3HardwrInfo TRAP-TYPE
	ENTERPRISE caiWinA3
	VARIABLES {
		winA3ConfigGeneralAgentVersion
	}
	DESCRIPTION "&<caiWinA3.1688>A watcher monitoring a hardware resource changed a sub-state. The varbind list contains a varbind with detailed information, encoded as a single string, including the name of the involved resource, the old and the new status, and the type and value of the involved metric; if applicable, the varbind also includes the current threshold settings and other information useful for automation purposes."
	::= 25988

winA3HardwrModified TRAP-TYPE
	ENTERPRISE caiWinA3
	VARIABLES {
		winA3ConfigGeneralAgentVersion
	}
	DESCRIPTION "&<caiWinA3.1689>The watcher configuration for a hardware resource changed. The varbind list contains a varbind with detailed information, encoded as a single string, including the name of the involved resource and the changed attribute with its old value and with its new value."
	::= 25989

--
-- The Progrm Traps
--

winA3ProgrmUnknown TRAP-TYPE
	ENTERPRISE caiWinA3
	VARIABLES {
		winA3StatusProgrmResName,
		winA3StatusProgrmResSubName,
		winA3StatusProgrmInstName,
		winA3ConfigGeneralAgentVersion
	}
	DESCRIPTION "&<caiWinA3.1690>A watcher monitoring a programmable resource changed its status to 'unknown'. The varbind list contains a varbind with detailed information, encoded as a single string, including the name of the involved resource and the type and value of the involved metric; if applicable, the varbind also includes the current threshold settings and other information useful for automation purposes."
	::= 26980

winA3ProgrmOk TRAP-TYPE
	ENTERPRISE caiWinA3
	VARIABLES {
		winA3StatusProgrmResName,
		winA3StatusProgrmResSubName,
		winA3StatusProgrmInstName,
		winA3ConfigGeneralAgentVersion
	}
	DESCRIPTION "&<caiWinA3.1691>A watcher monitoring a programmable resource changed its status to 'ok'. The varbind list contains a varbind with detailed information, encoded as a single string, including the name of the involved resource and the type and value of the involved metric; if applicable, the varbind also includes the current threshold settings and other information useful for automation purposes."
	::= 26981

winA3ProgrmWarning TRAP-TYPE
	ENTERPRISE caiWinA3
	VARIABLES {
		winA3StatusProgrmResName,
		winA3StatusProgrmResSubName,
		winA3StatusProgrmInstName,
		winA3ConfigGeneralAgentVersion
	}
	DESCRIPTION "&<caiWinA3.1692>A watcher monitoring a programmable resource changed its status to 'warning'. The varbind list contains a varbind with detailed information, encoded as a single string, including the name of the involved resource and the type and value of the involved metric; if applicable, the varbind also includes the current threshold settings and other information useful for automation purposes."
	::= 26982

winA3ProgrmCritical TRAP-TYPE
	ENTERPRISE caiWinA3
	VARIABLES {
		winA3StatusProgrmResName,
		winA3StatusProgrmResSubName,
		winA3StatusProgrmInstName,
		winA3ConfigGeneralAgentVersion
	}
	DESCRIPTION "&<caiWinA3.1693>A watcher monitoring a programmable resource changed its status to 'critical'. The varbind list contains a varbind with detailed information, encoded as a single string, including the name of the involved resource and the type and value of the involved metric; if applicable, the varbind also includes the current threshold settings and other information useful for automation purposes."
	::= 26983

winA3ProgrmActive TRAP-TYPE
	ENTERPRISE caiWinA3
	VARIABLES {
		winA3StatusProgrmResName,
		winA3StatusProgrmResSubName,
		winA3StatusProgrmInstName,
		winA3ConfigGeneralAgentVersion
	}
	DESCRIPTION "&<caiWinA3.1694>A watcher monitoring a programmable resource changed its status from 'passive'. The varbind list contains a varbind with detailed information, encoded as a single string, including the name of the involved resource and the type and value of the involved metric; if applicable, the varbind also includes the current threshold settings and other information useful for automation purposes."
	::= 26984

winA3ProgrmPassive TRAP-TYPE
	ENTERPRISE caiWinA3
	VARIABLES {
		winA3StatusProgrmResName,
		winA3StatusProgrmResSubName,
		winA3StatusProgrmInstName,
		winA3ConfigGeneralAgentVersion
	}
	DESCRIPTION "&<caiWinA3.1695>A watcher monitoring a programmable resource changed its status to 'passive'. The varbind list contains a varbind with detailed information, encoded as a single string, including the name of the involved resource and the type and value of the involved metric; if applicable, the varbind also includes the current threshold settings and other information useful for automation purposes."
	::= 26985

winA3ProgrmAdded TRAP-TYPE
	ENTERPRISE caiWinA3
	VARIABLES {
		winA3StatusProgrmResName,
		winA3StatusProgrmResSubName,
		winA3StatusProgrmInstName
	}
	DESCRIPTION "&<caiWinA3.1696>A watcher monitoring a programmable resource was added. The varbind list contains the name of the involved resource."
	::= 26986

winA3ProgrmDeleted TRAP-TYPE
	ENTERPRISE caiWinA3
	VARIABLES {
		winA3StatusProgrmResName,
		winA3StatusProgrmResSubName,
		winA3StatusProgrmInstName
	}
	DESCRIPTION "&<caiWinA3.1697>A watcher monitoring a programmable resource was removed. The varbind list contains the name of the involved resource."
	::= 26987

winA3ProgrmInfo TRAP-TYPE
	ENTERPRISE caiWinA3
	VARIABLES {
		winA3ConfigGeneralAgentVersion
	}
	DESCRIPTION "&<caiWinA3.1698>A watcher monitoring a programmable resource changed a sub-state. The varbind list contains a varbind with detailed information, encoded as a single string, including the name of the involved resource, the old and the new status, and the type and value of the involved metric; if applicable, the varbind also includes the current threshold settings and other information useful for automation purposes."
	::= 26988

winA3ProgrmModified TRAP-TYPE
	ENTERPRISE caiWinA3
	VARIABLES {
		winA3ConfigGeneralAgentVersion
	}
	DESCRIPTION "&<caiWinA3.1699>The watcher configuration for a programmable resource changed. The varbind list contains a varbind with detailed information, encoded as a single string, including the name of the involved resource and the changed attribute with its old value and with its new value."
	::= 26989


--  ========================================================================
--
--  Extension groups of caiWinA3 MIB:
--  ---------------------------------
--  winEHGroup added to support reports for Concord eHealth
--
--  ========================================================================
winA3ExtensionGroup OBJECT IDENTIFIER ::= { caiWinA3 5 }

winEHGroup OBJECT IDENTIFIER ::= { winA3ExtensionGroup 1 }


--  ---------------------------------
--  Poll information
--  ---------------------------------
winEHPollMethod OBJECT-TYPE
	SYNTAX INTEGER {
		disabled(1),
		enabled(2)
	}
	ACCESS read-write
	STATUS mandatory
	DESCRIPTION "The poll method for the eHealth group. If set to disabled, polling of this group is not possible."
	DEFVAL { 2 }
	::= { winEHGroup 1 }

winEHLastPoll OBJECT-TYPE
	SYNTAX TimeTicks
	ACCESS read-only
	STATUS mandatory
	DESCRIPTION "The value of winEHSrvSystemUpTime at the point in time the winEHSrvGroup group (and all winEH tables) was last polled."
	::= { winEHGroup 2 }


--  ---------------------------------
--  Server group
--  ---------------------------------
winEHSrvGroup OBJECT IDENTIFIER ::= { winEHGroup 3 }

winEHSrvSystemUpTime OBJECT-TYPE
	SYNTAX TimeTicks
	ACCESS read-only
	STATUS mandatory
	DESCRIPTION "The time (in hundredths of a second) since the system was last started."
	::= { winEHSrvGroup 1 }

winEHSrvSystemNumUsers OBJECT-TYPE
	SYNTAX Gauge
	ACCESS read-only
	STATUS mandatory
	DESCRIPTION "The number of users."
	::= { winEHSrvGroup 2 }

winEHSrvSystemProcesses OBJECT-TYPE
	SYNTAX Gauge
	ACCESS read-only
	STATUS mandatory
	DESCRIPTION "The number of processes."
	::= { winEHSrvGroup 3 }

winEHSrvMemorySize OBJECT-TYPE
	SYNTAX KBytes
	ACCESS read-only
	STATUS mandatory
	DESCRIPTION "The amount of physical main memory contained by the host."
	::= { winEHSrvGroup 4 }

winEHSrvMemInUse OBJECT-TYPE
	SYNTAX Gauge
	ACCESS read-only
	STATUS mandatory
	DESCRIPTION "The total real KBytes of memory in use."
	::= { winEHSrvGroup 5 }

winEHSrvTotalSwapSpace OBJECT-TYPE
	SYNTAX INTEGER
	ACCESS read-only
	STATUS mandatory
	DESCRIPTION "Total system swap space in KBytes."
	::= { winEHSrvGroup 6 }

winEHSrvSwapInUse OBJECT-TYPE
	SYNTAX Gauge
	ACCESS read-only
	STATUS mandatory
	DESCRIPTION "The amount of swap space in KBytes currently in use by the system."
	::= { winEHSrvGroup 7 }

winEHSrvLoadAverage5Min OBJECT-TYPE
	SYNTAX INTEGER
	ACCESS read-only
	STATUS mandatory
	DESCRIPTION "The load average over the last 5 minutes. The load average represents the average number of jobs in the run queue over the specified time range. The value reported is the load average multiplied by 100."
	::= { winEHSrvGroup 8 }

winEHSrvNumBreadRequests OBJECT-TYPE
	SYNTAX Counter
	ACCESS read-only
	STATUS mandatory
	DESCRIPTION "The total number of calls to the kernel's bread() function."
	::= { winEHSrvGroup 9 }

winEHSrvNumBreadHits OBJECT-TYPE
	SYNTAX Counter
	ACCESS read-only
	STATUS mandatory
	DESCRIPTION "The number of kernel buffer cache 'hits'."
	::= { winEHSrvGroup 10 }

winEHSrvSystemCalls OBJECT-TYPE
	SYNTAX Counter
	ACCESS read-only
	STATUS mandatory
	DESCRIPTION "The number of calls to system service routines."
	::= { winEHSrvGroup 11 }

winEHSrvInterrupts OBJECT-TYPE
	SYNTAX Counter
	ACCESS read-only
	STATUS mandatory
	DESCRIPTION "The number of hardware interrupts that have occurred."
	::= { winEHSrvGroup 12 }

winEHSrvPageFaults OBJECT-TYPE
	SYNTAX Counter
	ACCESS read-only
	STATUS mandatory
	DESCRIPTION "Number of page faults in the processor."
	::= { winEHSrvGroup 13 }

winEHSrvPagesInput OBJECT-TYPE
	SYNTAX Counter
	ACCESS read-only
	STATUS mandatory
	DESCRIPTION "Number of pages read from disk to resolve memory references."
	::= { winEHSrvGroup 14 }

winEHSrvPagesOutput OBJECT-TYPE
	SYNTAX Counter
	ACCESS read-only
	STATUS mandatory
	DESCRIPTION "Number of pages written to disk because the pages were modified."
	::= { winEHSrvGroup 15 }

winEHSrvIfNumber OBJECT-TYPE
	SYNTAX INTEGER
	ACCESS read-only
	STATUS mandatory
	DESCRIPTION "The number of network interfaces."
	::= { winEHSrvGroup 16 }


--  ---------------------------------
--  Cpu table
--  ---------------------------------
winEHCpuTable OBJECT-TYPE
	SYNTAX SEQUENCE OF WinEHCpuEntry
	ACCESS not-accessible
	STATUS mandatory
	DESCRIPTION ""
	::= { winEHGroup 4 }

winEHCpuEntry OBJECT-TYPE
	SYNTAX WinEHCpuEntry
	ACCESS not-accessible
	STATUS mandatory
	DESCRIPTION ""
	INDEX { winEHCpuIndex }
	::= { winEHCpuTable 1 }

WinEHCpuEntry ::= SEQUENCE {
	winEHCpuIndex INTEGER,
	winEHCpuName DisplayString,
	winEHCpuIdlePercent INTEGER,
	winEHCpuUserPercent INTEGER,
	winEHCpuSysPercent INTEGER
}

winEHCpuIndex OBJECT-TYPE
	SYNTAX INTEGER (1..2147483647)
	ACCESS read-only
	STATUS mandatory
	DESCRIPTION "The unique index of this table entry."
	::= { winEHCpuEntry 1 }

winEHCpuName OBJECT-TYPE
	SYNTAX DisplayString
	ACCESS read-only
	STATUS mandatory
	DESCRIPTION "The name of the CPU (in the format 'Cpu-N')."
	::= { winEHCpuEntry 2 }

winEHCpuIdlePercent OBJECT-TYPE
	SYNTAX INTEGER (0..100)
	ACCESS read-only
	STATUS mandatory
	DESCRIPTION "The percentage of time (over the sample period) that the system's Cpu was idle."
	::= { winEHCpuEntry 3 }

winEHCpuUserPercent OBJECT-TYPE
	SYNTAX INTEGER (0..100)
	ACCESS read-only
	STATUS mandatory
	DESCRIPTION "The percentage of time (over the sample period) that the system's Cpu was executing in user mode."
	::= { winEHCpuEntry 4 }

winEHCpuSysPercent OBJECT-TYPE
	SYNTAX INTEGER (0..100)
	ACCESS read-only
	STATUS mandatory
	DESCRIPTION "The percentage of time (over the sample period) that the system's Cpu was executing the kernel or operating system."
	::= { winEHCpuEntry 5 }


--  ---------------------------------
--  Disk table
--  ---------------------------------
winEHDiskTable OBJECT-TYPE
	SYNTAX SEQUENCE OF WinEHDiskEntry
	ACCESS not-accessible
	STATUS mandatory
	DESCRIPTION ""
	::= { winEHGroup 5 }

winEHDiskEntry OBJECT-TYPE
	SYNTAX WinEHDiskEntry
	ACCESS not-accessible
	STATUS mandatory
	DESCRIPTION ""
	INDEX { winEHDiskIndex }
	::= { winEHDiskTable 1 }

WinEHDiskEntry ::= SEQUENCE {
	winEHDiskIndex INTEGER,
	winEHDiskName DisplayString,
	winEHDiskDeviceErrors Counter,
	winEHDiskStorageCapacity INTEGER,
	winEHDiskQueueLength Gauge,
	winEHDiskUtilization INTEGER,
	winEHDiskKBytesTransferred Counter,
	winEHDiskReads Counter,
	winEHDiskWrites Counter
}

winEHDiskIndex OBJECT-TYPE
	SYNTAX INTEGER (1..2147483647)
	ACCESS read-only
	STATUS mandatory
	DESCRIPTION "The unique index of this table entry."
	::= { winEHDiskEntry 1 }

winEHDiskName OBJECT-TYPE
	SYNTAX DisplayString
	ACCESS read-only
	STATUS mandatory
	DESCRIPTION "The name of the disk (in the format 'HarddiskN')."
	::= { winEHDiskEntry 2 }

winEHDiskDeviceErrors OBJECT-TYPE
	SYNTAX Counter
	ACCESS read-only
	STATUS mandatory
	DESCRIPTION "The number of errors detected on this disk."
	::= { winEHDiskEntry 3 }

winEHDiskStorageCapacity OBJECT-TYPE
	SYNTAX INTEGER (0..2147483647)
	ACCESS read-only
	STATUS mandatory
	DESCRIPTION "Disk capacity in KB."
	::= { winEHDiskEntry 4 }

winEHDiskQueueLength OBJECT-TYPE
	SYNTAX Gauge
	ACCESS read-only
	STATUS mandatory
	DESCRIPTION "The average number of operations waiting in the disk's service queue over the last measurement period."
	::= { winEHDiskEntry 5 }

winEHDiskUtilization OBJECT-TYPE
	SYNTAX INTEGER (0..100)
	ACCESS read-only
	STATUS mandatory
	DESCRIPTION "The utilization rate (percentage) for this disk over the last measurement period."
	::= { winEHDiskEntry 6 }

winEHDiskKBytesTransferred OBJECT-TYPE
	SYNTAX Counter
	ACCESS read-only
	STATUS mandatory
	DESCRIPTION "The number of KBytes transferred to/from this disk."
	::= { winEHDiskEntry 7}

winEHDiskReads OBJECT-TYPE
	SYNTAX Counter
	ACCESS read-only
	STATUS mandatory
	DESCRIPTION "The number of read operations from this disk."
	::= { winEHDiskEntry 8 }

winEHDiskWrites OBJECT-TYPE
	SYNTAX Counter
	ACCESS read-only
	STATUS mandatory
	DESCRIPTION "The number of write operations to this disk."
	::= { winEHDiskEntry 9 }


--  ---------------------------------
--  Device (partition) table
--  ---------------------------------
winEHDevTable OBJECT-TYPE
	SYNTAX SEQUENCE OF WinEHDevEntry
	ACCESS not-accessible
	STATUS mandatory
	DESCRIPTION ""
	::= { winEHGroup 6 }

winEHDevEntry OBJECT-TYPE
	SYNTAX WinEHDevEntry
	ACCESS not-accessible
	STATUS mandatory
	DESCRIPTION ""
	INDEX { winEHDevIndex }
	::= { winEHDevTable 1 }

WinEHDevEntry ::= SEQUENCE {
	winEHDevIndex INTEGER,
	winEHDevName DisplayString,
	winEHDevStorageAllocationUnits INTEGER,
	winEHDevStorageSize INTEGER,
	winEHDevStorageUsed INTEGER,
	winEHDevStorageAllocationFailures Counter
}

winEHDevIndex OBJECT-TYPE
	SYNTAX INTEGER (1..2147483647)
	ACCESS read-only
	STATUS mandatory
	DESCRIPTION "The unique index of this table entry."
	::= { winEHDevEntry 1 }

winEHDevName OBJECT-TYPE
	SYNTAX DisplayString
	ACCESS read-only
	STATUS mandatory
	DESCRIPTION "The name of the device (partition)."
	::= { winEHDevEntry 2 }

winEHDevStorageAllocationUnits OBJECT-TYPE
	SYNTAX INTEGER (1..2147483647)
	ACCESS read-only
	STATUS mandatory
	DESCRIPTION "The size, in bytes, of the data objects allocated from this device."
	::= { winEHDevEntry 3 }

winEHDevStorageSize OBJECT-TYPE
	SYNTAX INTEGER (0..2147483647)
	ACCESS read-only
	STATUS mandatory
	DESCRIPTION "The size of the storage represented by this entry, in units of StorageAllocationUnits."
	::= { winEHDevEntry 4 }

winEHDevStorageUsed OBJECT-TYPE
	SYNTAX INTEGER (0..2147483647)
	ACCESS read-only
	STATUS mandatory
	DESCRIPTION "The amount of the storage represented by this entry that is allocated, in units of StorageAllocationUnits."
	::= { winEHDevEntry 5 }

winEHDevStorageAllocationFailures OBJECT-TYPE
	SYNTAX Counter
	ACCESS read-only
	STATUS mandatory
	DESCRIPTION "The number of requests for storage represented by this entry that could not be honored due to not enough storage."
	::= { winEHDevEntry 6 }


--  ---------------------------------
--  Network interface table
--  ---------------------------------
winEHIfTable OBJECT-TYPE
	SYNTAX SEQUENCE OF WinEHIfEntry
	ACCESS not-accessible
	STATUS mandatory
	DESCRIPTION ""
	::= { winEHGroup 7 }

winEHIfEntry OBJECT-TYPE
	SYNTAX WinEHIfEntry
	ACCESS not-accessible
	STATUS mandatory
	DESCRIPTION ""
	INDEX { winEHIfIndex }
	::= { winEHIfTable 1 }

WinEHIfEntry ::= SEQUENCE {
	winEHIfIndex INTEGER,
	winEHIfDescr DisplayString,
	winEHIfType INTEGER,
	winEHIfSpeed Gauge,
	winEHIfPhysAddress PhysAddress,
	winEHIfAdminStatus INTEGER,
	winEHIfOperStatus INTEGER,
	winEHIfLastChange TimeTicks,
	winEHIfInOctets Counter,
	winEHIfInUcastPkts Counter,
	winEHIfInNUcastPkts Counter,
	winEHIfInDiscards Counter,
	winEHIfInErrors Counter,
	winEHIfInUnknownProtos Counter,
	winEHIfOutOctets Counter,
	winEHIfOutUcastPkts Counter,
	winEHIfOutNUcastPkts Counter,
	winEHIfOutDiscards Counter,
	winEHIfOutErrors Counter,
	winEHIfIpAdEntAddr IpAddress
}

winEHIfIndex OBJECT-TYPE
	SYNTAX INTEGER (1..2147483647)
	ACCESS read-only
	STATUS mandatory
	DESCRIPTION "The unique index of this table entry."
	::= { winEHIfEntry 1 }

winEHIfDescr OBJECT-TYPE
	SYNTAX DisplayString
	ACCESS read-only
	STATUS mandatory
	DESCRIPTION "The description of the network interface."
	::= { winEHIfEntry 2 }

winEHIfType OBJECT-TYPE
	SYNTAX INTEGER
	ACCESS read-only
	STATUS mandatory
	DESCRIPTION "The type of interface."
	::= { winEHIfEntry 3 }

winEHIfSpeed OBJECT-TYPE
	SYNTAX Gauge
	ACCESS read-only
	STATUS mandatory
	DESCRIPTION "An estimate of the interface's current bandwidth in bits per second."
	::= { winEHIfEntry 4 }

winEHIfPhysAddress OBJECT-TYPE
	SYNTAX PhysAddress
	ACCESS read-only
	STATUS mandatory
	DESCRIPTION "The interface's address at the protocol layer."
	::= { winEHIfEntry 5 }

winEHIfAdminStatus OBJECT-TYPE
	SYNTAX INTEGER {
		up(1),
		down(2),
		testing(3),
		unknown(4),
		dormant(5)
	}
	ACCESS read-only
	STATUS mandatory
	DESCRIPTION "The desired state of the interface."
	::= { winEHIfEntry 6 }

winEHIfOperStatus OBJECT-TYPE
	SYNTAX INTEGER {
		up(1),
		down(2),
		testing(3),
		unknown(4),
		dormant(5)
	}
	ACCESS read-only
	STATUS mandatory
	DESCRIPTION "The current operational state of the interface."
	::= { winEHIfEntry 7 }

winEHIfLastChange OBJECT-TYPE
	SYNTAX TimeTicks
	ACCESS read-only
	STATUS mandatory
	DESCRIPTION "The value of sysUpTime at the time the interface entered its current operational state."
	::= { winEHIfEntry 8 }

winEHIfInOctets OBJECT-TYPE
	SYNTAX Counter
	ACCESS read-only
	STATUS mandatory
	DESCRIPTION "The total number of octets received on the interface, including framing characters."
	::= { winEHIfEntry 9 }

winEHIfInUcastPkts OBJECT-TYPE
	SYNTAX Counter
	ACCESS read-only
	STATUS mandatory
	DESCRIPTION "The number of subnetwork-unicast packets delivered to a higher-layer protocol."
	::= { winEHIfEntry 10 }

winEHIfInNUcastPkts OBJECT-TYPE
	SYNTAX Counter
	ACCESS read-only
	STATUS mandatory
	DESCRIPTION "The number of non-unicast (i.e., subnetwork-broadcast or subnetwork-multicast) packets delivered to a higher-layer protocol."
	::= { winEHIfEntry 11 }

winEHIfInDiscards OBJECT-TYPE
	SYNTAX Counter
	ACCESS read-only
	STATUS mandatory
	DESCRIPTION "The number of inbound packets which were chosen to be discarded even though no errors had been detected to prevent their being deliverable to a higher-layer protocol."
	::= { winEHIfEntry 12 }

winEHIfInErrors OBJECT-TYPE
	SYNTAX Counter
	ACCESS read-only
	STATUS mandatory
	DESCRIPTION "The number of inbound packets that contained errors preventing them from being deliverable to a higher-layer protocol."
	::= { winEHIfEntry 13 }

winEHIfInUnknownProtos OBJECT-TYPE
	SYNTAX Counter
	ACCESS read-only
	STATUS mandatory
	DESCRIPTION "The number of packets received via the interface which were discarded because of an unknown or unsupported protocol."
	::= { winEHIfEntry 14 }

winEHIfOutOctets OBJECT-TYPE
	SYNTAX Counter
	ACCESS read-only
	STATUS mandatory
	DESCRIPTION "The total number of octets transmitted out of the interface, including framing characters."
	::= { winEHIfEntry 15 }

winEHIfOutUcastPkts OBJECT-TYPE
	SYNTAX Counter
	ACCESS read-only
	STATUS mandatory
	DESCRIPTION "The total number of packets that higher-level protocols requested be transmitted to a subnetwork-unicast address, including those that were discarded or not sent."
	::= { winEHIfEntry 16 }

winEHIfOutNUcastPkts OBJECT-TYPE
	SYNTAX Counter
	ACCESS read-only
	STATUS mandatory
	DESCRIPTION "The total number of packets that higher-level protocols requested be transmitted to a non-unicast (i.e., a subnetwork-broadcast or subnetwork-multicast) address, including those that were discarded or not sent."
	::= { winEHIfEntry 17 }

winEHIfOutDiscards OBJECT-TYPE
	SYNTAX Counter
	ACCESS read-only
	STATUS mandatory
	DESCRIPTION "The number of outbound packets which were chosen to be discarded even though no errors had been detected to prevent their being transmitted."
	::= { winEHIfEntry 18 }

winEHIfOutErrors OBJECT-TYPE
	SYNTAX Counter
	ACCESS read-only
	STATUS mandatory
	DESCRIPTION "The number of outbound packets that could not be transmitted because of errors."
	::= { winEHIfEntry 19 }

winEHIfIpAdEntAddr OBJECT-TYPE
	SYNTAX IpAddress
	ACCESS read-only
	STATUS mandatory
	DESCRIPTION "The IP address."
	::= { winEHIfEntry 20 }


--  ---------------------------------
--  Process table
--  ---------------------------------
winEHProcTable OBJECT-TYPE
	SYNTAX SEQUENCE OF WinEHProcEntry
	ACCESS not-accessible
	STATUS mandatory
	DESCRIPTION ""
	::= { winEHGroup 8 }

winEHProcEntry OBJECT-TYPE
	SYNTAX WinEHProcEntry
	ACCESS not-accessible
	STATUS mandatory
	DESCRIPTION ""
	INDEX { winEHProcName }
	::= { winEHProcTable 1 }

WinEHProcEntry ::= SEQUENCE {
	winEHProcName DisplayString,
	winEHProcNumber INTEGER,
	winEHProcPid DisplayString,
	winEHProcState INTEGER,
	winEHProcSize Gauge,
	winEHProcRSS Gauge,
	winEHProcTime INTEGER,
	winEHProcNumThreads INTEGER,
	winEHProcMajorPgFlts Counter
}

winEHProcName OBJECT-TYPE
	SYNTAX DisplayString
	ACCESS read-only
	STATUS mandatory
	DESCRIPTION "The unique index (process name) of this table entry. This name is case-sensitive."
	::= { winEHProcEntry 1 }

winEHProcNumber OBJECT-TYPE
	SYNTAX INTEGER
	ACCESS read-only
	STATUS mandatory
	DESCRIPTION "The number of processes with this name."
	::= { winEHProcEntry 2 }

winEHProcPid OBJECT-TYPE
	SYNTAX DisplayString
	ACCESS read-only
	STATUS mandatory
	DESCRIPTION "The process identifier (PID). If winEHProcNumber is greater one, this attribute lists all PIDs, delimited by a pipe sign."
	::= { winEHProcEntry 3 }

winEHProcState OBJECT-TYPE
	SYNTAX INTEGER {
		starting(1),
		runnable(2),
		active(3),
		wait(4),
		sleeping(5),
		swapped(6),
		sleep(7),
		stop(8),
		other(9),
		zombie(10)
	}
	ACCESS read-only
	STATUS deprecated
	DESCRIPTION "The process state. Possible states on Windows are: starting(1), runnable(2), active(3), sleeping(5), other(9) and zombie(10). If winEHProcNumber is greater one, this attribute is set to other(9)."
	::= { winEHProcEntry 4 }

winEHProcSize OBJECT-TYPE
	SYNTAX Gauge
	ACCESS read-only
	STATUS mandatory
	DESCRIPTION "The combined size of the text, data and stack segments in KBytes. If winEHProcNumber is greater one, this attribute is the accumulated value."
::= { winEHProcEntry 5 }

winEHProcRSS OBJECT-TYPE
	SYNTAX Gauge
	ACCESS read-only
	STATUS mandatory
	DESCRIPTION "Real memory (resident set) size of the process in KBytes. If winEHProcNumber is greater one, this attribute is the accumulated value."
::= { winEHProcEntry 6 }

winEHProcTime OBJECT-TYPE
	SYNTAX INTEGER
	ACCESS read-only
	STATUS mandatory
	DESCRIPTION "This process' accumulated CPU time in seconds. If winEHProcNumber is greater one, this attribute is the accumulated value."
::= { winEHProcEntry 7 }

winEHProcNumThreads OBJECT-TYPE
	SYNTAX INTEGER
	ACCESS read-only
	STATUS mandatory
	DESCRIPTION "The number of threads executing within this process. If winEHProcNumber is greater one, this attribute is the accumulated value."
	::= { winEHProcEntry 8 }

winEHProcMajorPgFlts OBJECT-TYPE
	SYNTAX Counter
	ACCESS read-only
	STATUS mandatory
	DESCRIPTION "The number of major page faults incurred by this process. Major faults require I/O to retrieve the page. If winEHProcNumber is greater one, this attribute is the accumulated value."
::= { winEHProcEntry 9 }


END
