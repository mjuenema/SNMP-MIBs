--MibName=caiUxOs
--	------------------------------------------------------------------------
--
--	This material contains, and is a part of a computer software program
--	which is, proprietary and confidential information owned by:
--	               COMPUTER ASSOCIATES INTERNATIONAL, INC.
--	The program, including this material, may not be duplicated, disclosed
--	or reproduced in whole or in part for any purpose without the express
--	written authorisation of COMPUTER ASSOCIATES.  All authorised
--	reproductions must be marked with this legend.
--
--	        Copyright 1998 - 2006 Computer Associates International, Inc.
--	                 The Software that Manages eBusiness
--
--	------------------------------------------------------------------------

CAIUXOS DEFINITIONS ::= BEGIN                          -- defined by IETF
IMPORTS
              OBJECT-TYPE, Counter, Gauge, DisplayString, enterprises, IpAddress    FROM RFC1155-SMI
              PhysAddress	FROM RFC1213-MIB;

-- FROM RFC1514-MIB
KBytes ::= INTEGER (0..2147483647)

cai			OBJECT IDENTIFIER ::= { enterprises 791 }
caiSysMgr		OBJECT IDENTIFIER ::= { cai 2 }
agentWorks		OBJECT IDENTIFIER ::= { caiSysMgr 9 }
unix			OBJECT IDENTIFIER ::= { agentWorks 4 }

caiUxOs		OBJECT IDENTIFIER ::= { unix 5 }

--
-- caiUxOs
--
uxsConfigGroup OBJECT IDENTIFIER
	::= { caiUxOs 1 }

uxsStatusGroup OBJECT IDENTIFIER
	::= { caiUxOs 2 }

uxsAvailableGroup OBJECT IDENTIFIER
	::= { caiUxOs 3 }

uxsPollGroup OBJECT IDENTIFIER
	::= { caiUxOs 4 }

--
-- uxsConfigGroup
--
uxsConfigGeneralGroup OBJECT IDENTIFIER
	::= { uxsConfigGroup 1 }

uxsConfigSysGroup OBJECT IDENTIFIER
	::= { uxsConfigGroup 2 }

uxsConfigCPUGroup OBJECT IDENTIFIER
	::= { uxsConfigGroup 3 }

uxsConfigLoadGroup OBJECT IDENTIFIER
	::= { uxsConfigGroup 4 }

uxsConfigMemGroup OBJECT IDENTIFIER
	::= { uxsConfigGroup 5 }

uxsConfigSwapGroup OBJECT IDENTIFIER
	::= { uxsConfigGroup 6 }

uxsConfigFSysGroup OBJECT IDENTIFIER
	::= { uxsConfigGroup 7 }

uxsConfigDiskGroup OBJECT IDENTIFIER
	::= { uxsConfigGroup 8 }

uxsConfigFileGroup OBJECT IDENTIFIER
	::= { uxsConfigGroup 9 }

uxsConfigProcGroup OBJECT IDENTIFIER
	::= { uxsConfigGroup 10 }

uxsConfigPrnGroup OBJECT IDENTIFIER
	::= { uxsConfigGroup 11 }

uxsConfigNetGroup OBJECT IDENTIFIER
	::= { uxsConfigGroup 12 }

uxsConfigIPCGroup OBJECT IDENTIFIER
	::= { uxsConfigGroup 13 }

--
-- uxsStatusGroup
--
uxsStatusGeneralGroup OBJECT IDENTIFIER
	::= { uxsStatusGroup 1 }

uxsStatusCPUGroup OBJECT IDENTIFIER
	::= { uxsStatusGroup 2 }

uxsStatusLoadGroup OBJECT IDENTIFIER
	::= { uxsStatusGroup 3 }

uxsStatusMemGroup OBJECT IDENTIFIER
	::= { uxsStatusGroup 4 }

uxsStatusSwapGroup OBJECT IDENTIFIER
	::= { uxsStatusGroup 5 }

uxsStatusFSysGroup OBJECT IDENTIFIER
	::= { uxsStatusGroup 6 }

uxsStatusDiskGroup OBJECT IDENTIFIER
	::= { uxsStatusGroup 7 }

uxsStatusFileGroup OBJECT IDENTIFIER
	::= { uxsStatusGroup 8 }

uxsStatusProcGroup OBJECT IDENTIFIER
	::= { uxsStatusGroup 9 }

uxsStatusPrnGroup OBJECT IDENTIFIER
	::= { uxsStatusGroup 10 }

uxsStatusNetGroup OBJECT IDENTIFIER
	::= { uxsStatusGroup 11 }

uxsStatusIPCGroup OBJECT IDENTIFIER
	::= { uxsStatusGroup 12 }

--
-- uxsAvailableGroup
--
uxsAvailFSysRefresh OBJECT-TYPE
	SYNTAX  INTEGER {
		none(1),
		refresh(2)
	}
	ACCESS  read-write
	STATUS  mandatory
	DESCRIPTION
		"&<caiUxOs.100>Set this value to refresh(2) to check the operating system for recently configured file systems. The user can not set the value to none(1)."
	::= { uxsAvailableGroup 1 }

uxsAvailFSysTable OBJECT-TYPE
	SYNTAX  SEQUENCE OF UxsAvailFSysSequence
	ACCESS  not-accessible
	STATUS	mandatory
	DESCRIPTION
		"&<caiUxOs.101>The table containing a list of file systems that are currently known to the agent and are available for monitoring."
	::= { uxsAvailableGroup 2 }

uxsAvailDiskRefresh OBJECT-TYPE
	SYNTAX  INTEGER {
		none(1),
		refresh(2)
	}
	ACCESS  read-write
	STATUS  mandatory
	DESCRIPTION
		"&<caiUxOs.102>Set this value to refresh(2) to check the operating system for recently configured physical disks. The user can not set the value to none(1)."
	::= { uxsAvailableGroup 3 }

uxsAvailDiskTable OBJECT-TYPE
	SYNTAX  SEQUENCE OF UxsAvailDiskSequence
	ACCESS  not-accessible
	STATUS	mandatory
	DESCRIPTION
		"&<caiUxOs.103>The table containing a list of physical disks that are currently known to the agent and are available for monitoring."
	::= { uxsAvailableGroup 4 }

uxsAvailPrnRefresh OBJECT-TYPE
	SYNTAX  INTEGER {
		none(1),
		refresh(2)
	}
	ACCESS  read-write
	STATUS  mandatory
	DESCRIPTION
		"&<caiUxOs.104>Set this value to refresh(2) to check the operating system for recently configured printers or printer queues. The user can not set the value to none(1)."
	::= { uxsAvailableGroup 5 }

uxsAvailPrnTable OBJECT-TYPE
	SYNTAX  SEQUENCE OF UxsAvailPrnSequence
	ACCESS  not-accessible
	STATUS	mandatory
	DESCRIPTION
		"&<caiUxOs.105>The table containing a list of printers and printer queues that are currently known to the agent and are available for monitoring."
	::= { uxsAvailableGroup 6 }

--
-- uxsPollGroup
--
uxsPollNetGroup OBJECT IDENTIFIER
	::= { uxsPollGroup 1 }

uxsPollIPCGroup OBJECT IDENTIFIER
	::= { uxsPollGroup 2 }

--
-- uxsConfigGeneralGroup
--
uxsConfigGeneralAgentVersion OBJECT-TYPE
	SYNTAX  DisplayString
	ACCESS  read-only
	STATUS  mandatory
	DESCRIPTION
		"&<caiUxOs.106>The version of the agent that is running."
	::= { uxsConfigGeneralGroup 1 }

uxsConfigGeneralColdStartTime OBJECT-TYPE
	SYNTAX  DisplayString
	ACCESS  read-only
	STATUS  mandatory
	DESCRIPTION
		"&<caiUxOs.107>The date/time the agent was started."
	::= { uxsConfigGeneralGroup 2 }

uxsConfigGeneralWarmStartTime OBJECT-TYPE
	SYNTAX  DisplayString
	ACCESS  read-only
	STATUS  mandatory
	DESCRIPTION
		"&<caiUxOs.108>The date/time that the agent was last reconfigured through the SNMP interface."
	::= { uxsConfigGeneralGroup 3 }

uxsConfigGeneralCPUPollTime OBJECT-TYPE
	SYNTAX  DisplayString
	ACCESS  read-only
	STATUS  mandatory
	DESCRIPTION
		"&<caiUxOs.109>The last date/time that the CPU information was polled."
	::= { uxsConfigGeneralGroup 4 }

uxsConfigGeneralLoadPollTime OBJECT-TYPE
	SYNTAX  DisplayString
	ACCESS  read-only
	STATUS  mandatory
	DESCRIPTION
		"&<caiUxOs.110>The last date/time that the load average information was polled."
	::= { uxsConfigGeneralGroup 5 }

uxsConfigGeneralMemPollTime OBJECT-TYPE
	SYNTAX  DisplayString
	ACCESS  read-only
	STATUS  mandatory
	DESCRIPTION
		"&<caiUxOs.111>The last date/time that the real memory information was polled."
	::= { uxsConfigGeneralGroup 6 }

uxsConfigGeneralSwapPollTime OBJECT-TYPE
	SYNTAX  DisplayString
	ACCESS  read-only
	STATUS  mandatory
	DESCRIPTION
		"&<caiUxOs.112>The last date/time that the swap information was polled."
	::= { uxsConfigGeneralGroup 7 }

uxsConfigGeneralFSysPollTime OBJECT-TYPE
	SYNTAX  DisplayString
	ACCESS  read-only
	STATUS  mandatory
	DESCRIPTION
		"&<caiUxOs.113>The last date/time that the file system information was polled."
	::= { uxsConfigGeneralGroup 8 }

uxsConfigGeneralDiskPollTime OBJECT-TYPE
	SYNTAX  DisplayString
	ACCESS  read-only
	STATUS  mandatory
	DESCRIPTION
		"&<caiUxOs.114>The last date/time that the physical disk information was polled."
	::= { uxsConfigGeneralGroup 9 }

uxsConfigGeneralFilePollTime OBJECT-TYPE
	SYNTAX  DisplayString
	ACCESS  read-only
	STATUS  mandatory
	DESCRIPTION
		"&<caiUxOs.115>The last date/time that the file information was polled."
	::= { uxsConfigGeneralGroup 10 }

uxsConfigGeneralProcPollTime OBJECT-TYPE
	SYNTAX  DisplayString
	ACCESS  read-only
	STATUS  mandatory
	DESCRIPTION
		"&<caiUxOs.116>The last date/time that the process information was polled."
	::= { uxsConfigGeneralGroup 11 }

uxsConfigGeneralPrnPollTime OBJECT-TYPE
	SYNTAX  DisplayString
	ACCESS  read-only
	STATUS  mandatory
	DESCRIPTION
		"&<caiUxOs.117>The last date/time that the printer queue information was polled."
	::= { uxsConfigGeneralGroup 12 }

uxsConfigGeneralNetPollTime OBJECT-TYPE
	SYNTAX  DisplayString
	ACCESS  read-only
	STATUS  mandatory
	DESCRIPTION
		"&<caiUxOs.118>The last date/time that the Network Interface was polled."
	::= { uxsConfigGeneralGroup 13 }

uxsConfigGeneralIPCPollTime OBJECT-TYPE
	SYNTAX  DisplayString
	ACCESS  read-only
	STATUS  mandatory
	DESCRIPTION
		"&<caiUxOs.119>The last date/time that the Inter Process Communication information was polled."
	::= { uxsConfigGeneralGroup 14 }

--
-- uxsConfigSysGroup
--
uxsConfigSysNodeName OBJECT-TYPE
	SYNTAX  DisplayString
	ACCESS  read-only
	STATUS  mandatory
	DESCRIPTION
		"&<caiUxOs.120>The name of the UNIX node."
	::= { uxsConfigSysGroup 1 }

uxsConfigSysSystemName OBJECT-TYPE
	SYNTAX  DisplayString
	ACCESS  read-only
	STATUS  mandatory
	DESCRIPTION
		"&<caiUxOs.121>The name of the operating system installed on the machine."
	::= { uxsConfigSysGroup 2 }

uxsConfigSysRelease OBJECT-TYPE
	SYNTAX  DisplayString
	ACCESS  read-only
	STATUS  mandatory
	DESCRIPTION
		"&<caiUxOs.122>The release of the operating system installed on the machine."
	::= { uxsConfigSysGroup 3 }

uxsConfigSysVersion OBJECT-TYPE
	SYNTAX  DisplayString
	ACCESS  read-only
	STATUS  mandatory
	DESCRIPTION
		"&<caiUxOs.123>The version of the operating system installed on the machine."
	::= { uxsConfigSysGroup 4 }

uxsConfigSysHardware OBJECT-TYPE
	SYNTAX  DisplayString
	ACCESS  read-only
	STATUS  mandatory
	DESCRIPTION
		"&<caiUxOs.124>The name of the hardware type of the machine."
	::= { uxsConfigSysGroup 5 }

uxsConfigSysBootTime OBJECT-TYPE
	SYNTAX  DisplayString
	ACCESS  read-only
	STATUS  mandatory
	DESCRIPTION
		"&<caiUxOs.125>The date/time the machine was booted."
	::= { uxsConfigSysGroup 6 }

uxsConfigSysRunLevel OBJECT-TYPE
	SYNTAX  DisplayString
	ACCESS  read-only
	STATUS  mandatory
	DESCRIPTION
		"&<caiUxOs.126>The run level of the machine at the time the agent started."
	::= { uxsConfigSysGroup 7 }

--
-- uxsConfigCPUGroup
--
uxsConfigCPUPollInterval OBJECT-TYPE
	SYNTAX  INTEGER
	ACCESS  read-write
	STATUS  mandatory
	DESCRIPTION
		"&<caiUxOs.127>The time, in seconds, between the collections of the CPU information. Valid ranges: -1 (Suspended), 30 seconds or greater."
	::= { uxsConfigCPUGroup 1 }

uxsConfigCPUPollMethod OBJECT-TYPE
	SYNTAX  INTEGER {
		disabled(1),
		poll-interval-and-query(2),
		poll-interval-only(3),
		query-only(4)
	}
	ACCESS  read-write
	STATUS  mandatory
	DESCRIPTION
		"&<caiUxOs.128>If set to 'disabled', the agent no more retrieves the processor information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigCPUGroup 2 }

uxsConfigCPULag OBJECT-TYPE
	SYNTAX  INTEGER
	ACCESS  read-write
	STATUS  mandatory
	DESCRIPTION
        "&<caiUxOs.129>The number of times that the threshold has to be reached before the state changes. Valid range: Greater than 0."
	::= { uxsConfigCPUGroup 3 }

uxsConfigCPUWarn OBJECT-TYPE
	SYNTAX  DisplayString
	ACCESS  read-write
	STATUS  mandatory
	DESCRIPTION
		"&<caiUxOs.130>The value for CPU usage, as a percentage, that is considered a warning level for that resource. Valid ranges: Greater than 0, less than 99, not greater than or equal to the critical threshold."
	::= { uxsConfigCPUGroup 4 }

uxsConfigCPUCrit OBJECT-TYPE
	SYNTAX  DisplayString
	ACCESS  read-write
	STATUS  mandatory
	DESCRIPTION
		"&<caiUxOs.131>The value for CPU usage, as a percentage, that is considered a critical level for that resource. Valid ranges: Greater than 1, less than 100, not less than or equal to the warning threshold."
	::= { uxsConfigCPUGroup 5 }

uxsConfigCPUMonitor OBJECT-TYPE
	SYNTAX  INTEGER {
		do-not-monitor(1),
		warning-only(2),
		critical-only(3),
		both(4)
	}
	ACCESS  read-write
	STATUS  mandatory
	DESCRIPTION
		"&<caiUxOs.132>Defines the level of monitoring for the resource's status. Valid values: do-not-monitor(1), warning-only(2), critical-only(3) or both(4)."
	::= { uxsConfigCPUGroup 6 }

uxsConfigCPULossAction OBJECT-TYPE
	SYNTAX  INTEGER {
		remove(1),
		up(2),
		down(3)
	}
	ACCESS  read-write
	STATUS  mandatory
	DESCRIPTION
		"&<caiUxOs.133>Defines the action to take if the CPU is removed from the machine. Valid values: remove(1), up(2) or down(3)."
	::= { uxsConfigCPUGroup 7 }

--
-- uxsConfigLoadGroup
--
uxsConfigLoadPollInterval OBJECT-TYPE
	SYNTAX  INTEGER
	ACCESS  read-write
	STATUS  mandatory
	DESCRIPTION
		"&<caiUxOs.134>The time, in seconds, between the collections of the load average information. Valid ranges: -1 (Suspended), 30 seconds or greater."
	::= { uxsConfigLoadGroup 1 }

uxsConfigLoadPollMethod OBJECT-TYPE
	SYNTAX  INTEGER {
		disabled(1),
		poll-interval-and-query(2),
		poll-interval-only(3),
		query-only(4)
	}
	ACCESS  read-write
	STATUS  mandatory
	DESCRIPTION
		"&<caiUxOs.135>If set to 'disabled', the agent no more retrieves the load average information (not by polling, nor by get request) and sets all statuses to ok. If set to 'poll-interval-and-query', the agent retrieves the information in both cases (polling and get request). If set to 'poll-interval-only', the agent only retrieves the information by polling, but not by get request. If set to 'query-only', the agent retreves the information for get requests only."
	::= { uxsConfigLoadGroup 2 }

--
-- uxsConfigMemGroup
--
uxsConfigMemPollInterval OBJECT-TYPE
	SYNTAX  INTEGER
	ACCESS  read-write
	STATUS  mandatory
	DESCRIPTION
		"&<caiUxOs.136>The time, in seconds, between the collections of the real memory information. Valid ranges: -1 (Suspended), 30 seconds or greater."
	::= { uxsConfigMemGroup 1 }

uxsConfigMemPollMethod OBJECT-TYPE
	SYNTAX  INTEGER {
		disabled(1),
		poll-interval-and-query(2),
		poll-interval-only(3),
		query-only(4)
	}
	ACCESS  read-write
	STATUS  mandatory
	DESCRIPTION
		"&<caiUxOs.137>If set to 'disabled', the agent no more retrieves the memory information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigMemGroup 2 }

--
-- uxsConfigSwapGroup
--
uxsConfigSwapPollInterval OBJECT-TYPE
	SYNTAX  INTEGER
	ACCESS  read-write
	STATUS  mandatory
	DESCRIPTION
		"&<caiUxOs.138>The time, in seconds, between the collections of the swap usage information. Valid ranges: -1 (Suspended), 30 seconds or greater."
	::= { uxsConfigSwapGroup 1 }

uxsConfigSwapPollMethod OBJECT-TYPE
	SYNTAX  INTEGER {
		disabled(1),
		poll-interval-and-query(2),
		poll-interval-only(3),
		query-only(4)
	}
	ACCESS  read-write
	STATUS  mandatory
	DESCRIPTION
		"&<caiUxOs.139>If set to 'disabled', the agent no more retrieves the swap usage information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigSwapGroup 2 }

uxsConfigSwapLag OBJECT-TYPE
	SYNTAX  INTEGER
	ACCESS  read-write
	STATUS  mandatory
	DESCRIPTION
		"&<caiUxOs.140>The number of times that the threshold has to be reached before the state changes. Valid range: Greater than 0."
	::= { uxsConfigSwapGroup 3 }

uxsConfigSwapWarn OBJECT-TYPE
	SYNTAX  DisplayString
	ACCESS  read-write
	STATUS  mandatory
	DESCRIPTION
		"&<caiUxOs.141>The value for used swap space, either as a percentage or in kilobytes, that is considered a warning level for that resource. Valid ranges: Greater than 0, less than total swap - 1, not greater than or equal to the critical threshold."
	::= { uxsConfigSwapGroup 4 }

uxsConfigSwapCrit OBJECT-TYPE
	SYNTAX  DisplayString
	ACCESS  read-write
	STATUS  mandatory
	DESCRIPTION
		"&<caiUxOs.142>The value for used swap space, either as a percentage or in kilobytes, that is considered a critical level for that resource. Valid ranges: Greater than 1, less than total swap, not less than or equal to the warning threshold."
	::= { uxsConfigSwapGroup 5 }

uxsConfigSwapMonitor OBJECT-TYPE
	SYNTAX  INTEGER {
		do-not-monitor(1),
		warning-only(2),
		critical-only(3),
		both(4)
	}
	ACCESS  read-write
	STATUS  mandatory
	DESCRIPTION
		"&<caiUxOs.143>Defines the level of monitoring for the resource's status. Valid values: do-not-monitor(1), warning-only(2), critical-only(3) or both(4)."
	::= { uxsConfigSwapGroup 6 }

uxsConfigSwapLossAction OBJECT-TYPE
	SYNTAX  INTEGER {
		remove(1),
		up(2),
		down(3)
	}
	ACCESS  read-write
	STATUS  mandatory
	DESCRIPTION
		"&<caiUxOs.144>Defines the action to take if the swap partition is removed from the machine. Valid values: remove(1), up(2) or down(3)."
	::= { uxsConfigSwapGroup 7 }

--
-- uxsConfigFSysGroup
--
uxsConfigFSysPollInterval OBJECT-TYPE
	SYNTAX  INTEGER
	ACCESS  read-write
	STATUS  mandatory
	DESCRIPTION
		"&<caiUxOs.145>The time, in seconds, between the collections of the file system information. Valid ranges: -1 (Suspended), 30 seconds or greater."
	::= { uxsConfigFSysGroup 1 }

uxsConfigFSysPollMethod OBJECT-TYPE
	SYNTAX  INTEGER {
		disabled(1),
		poll-interval-and-query(2),
		poll-interval-only(3),
		query-only(4)
	}
	ACCESS  read-write
	STATUS  mandatory
	DESCRIPTION
		"&<caiUxOs.146>If set to 'disabled', the agent no more retrieves the file system information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigFSysGroup 2 }

uxsConfigFSysSpaceWarn OBJECT-TYPE
	SYNTAX  DisplayString
	ACCESS  read-write
	STATUS  mandatory
	DESCRIPTION
		"&<caiUxOs.147>The value for file system space, either as a percentage or in kilobytes, that is considered a warning level for that resource. Valid ranges: Greater than 0, less than file system size - 1, not greater than or equal to the critical threshold."
	::= { uxsConfigFSysGroup 3 }

uxsConfigFSysSpaceCrit OBJECT-TYPE
	SYNTAX  DisplayString
	ACCESS  read-write
	STATUS  mandatory
	DESCRIPTION
		"&<caiUxOs.148>The value for file system space, either as a percentage or in kilobytes, that is considered a critical level for that resource. Valid ranges: Greater than 1, less than file system size, not less than or equal to the warning threshold."
	::= { uxsConfigFSysGroup 4 }

uxsConfigFSysSpaceMonitor OBJECT-TYPE
	SYNTAX  INTEGER {
		do-not-monitor(1),
		warning-only(2),
		critical-only(3),
		both(4)
	}
	ACCESS  read-write
	STATUS  mandatory
	DESCRIPTION
		"&<caiUxOs.149>Defines the level of monitoring for the resource's status. Valid values: do-not-monitor(1), warning-only(2), critical-only(3) or both(4)."
	::= { uxsConfigFSysGroup 5 }

uxsConfigFSysSpaceDWarn OBJECT-TYPE
	SYNTAX  DisplayString
	ACCESS  read-write
	STATUS  mandatory
	DESCRIPTION
		"&<caiUxOs.150>The value for file system delta space, either as a percentage or in kilobytes, that is considered a warning level for that resource. Valid ranges: Greater than 0, not greater than or equal to the critical threshold."
	::= { uxsConfigFSysGroup 6 }

uxsConfigFSysSpaceDCrit OBJECT-TYPE
	SYNTAX  DisplayString
	ACCESS  read-write
	STATUS  mandatory
	DESCRIPTION
		"&<caiUxOs.151>The value for file system delta space, either as a percentage or in kilobytes, that is considered a critical level for that resource. Valid ranges: Greater than 1, not less than or equal to the warning threshold."
	::= { uxsConfigFSysGroup 7 }

uxsConfigFSysSpaceDMonitor OBJECT-TYPE
	SYNTAX  INTEGER {
		do-not-monitor(1),
		warning-only(2),
		critical-only(3),
		both(4)
	}
	ACCESS  read-write
	STATUS  mandatory
	DESCRIPTION
		"&<caiUxOs.152>Defines the level of monitoring for the resource's status. Valid values: do-not-monitor(1), warning-only(2), critical-only(3) or both(4)."
	::= { uxsConfigFSysGroup 8 }

uxsConfigFSysInodesWarn OBJECT-TYPE
	SYNTAX  DisplayString
	ACCESS  read-write
	STATUS  mandatory
	DESCRIPTION
		"&<caiUxOs.153>The value for inodes, either as a percentage or absolute value, that is considered a warning level for that resource. Valid ranges: Greater than 0, less than total inodes - 1, not greater than or equal to the critical threshold."
	::= { uxsConfigFSysGroup 9 }

uxsConfigFSysInodesCrit OBJECT-TYPE
	SYNTAX  DisplayString
	ACCESS  read-write
	STATUS  mandatory
	DESCRIPTION
		"&<caiUxOs.154>The value for inodes, either as percentage or absolute value, that is considered a critical level for that resource. Valid ranges: Greater than 1, less than total inodes, not less than or equal to the warning threshold."
	::= { uxsConfigFSysGroup 10 }

uxsConfigFSysInodesMonitor OBJECT-TYPE
	SYNTAX  INTEGER {
		do-not-monitor(1),
		warning-only(2),
		critical-only(3),
		both(4)
	}
	ACCESS  read-write
	STATUS  mandatory
	DESCRIPTION
		"&<caiUxOs.155>Defines the level of monitoring for the resource's status. Valid values: do-not-monitor(1), warning-only(2), critical-only(3) or both(4)."
	::= { uxsConfigFSysGroup 11 }

uxsConfigFSysInodesDWarn OBJECT-TYPE
	SYNTAX  DisplayString
	ACCESS  read-write
	STATUS  mandatory
	DESCRIPTION
		"&<caiUxOs.156>The value for inodes delta, either as a percentage or absolute value, that is considered a warning level for that resource. Valid ranges: Greater than 0, not greater than or equal to the critical threshold."
	::= { uxsConfigFSysGroup 12 }

uxsConfigFSysInodesDCrit OBJECT-TYPE
	SYNTAX  DisplayString
	ACCESS  read-write
	STATUS  mandatory
	DESCRIPTION
		"&<caiUxOs.157>The value for inodes delta, either as a percentage or absolute value, that is considered a critical level for that resource. Valid ranges: Greater than 1, not less than or equal to the warning threshold."
	::= { uxsConfigFSysGroup 13 }

uxsConfigFSysInodesDMonitor OBJECT-TYPE
	SYNTAX  INTEGER {
		do-not-monitor(1),
		warning-only(2),
		critical-only(3),
		both(4)
	}
	ACCESS  read-write
	STATUS  mandatory
	DESCRIPTION
		"&<caiUxOs.158>Defines the level of monitoring for the resource's status. Valid values: do-not-monitor(1), warning-only(2), critical-only(3) or both(4)."
	::= { uxsConfigFSysGroup 14 }

uxsConfigFSysMountedMonitor OBJECT-TYPE
	SYNTAX  INTEGER {
		do-not-monitor(1),
		monitor(2)
	}
	ACCESS  read-write
	STATUS  mandatory
	DESCRIPTION
		"&<caiUxOs.159>Defines the level of monitoring for the resource's status. Valid values: do-not-monitor(1) or monitor(2)."
	::= { uxsConfigFSysGroup 15 }

uxsConfigFSysLossAction OBJECT-TYPE
	SYNTAX  INTEGER {
		remove(1),
		up(2),
		down(3)
	}
	ACCESS  read-write
	STATUS  mandatory
	DESCRIPTION
		"&<caiUxOs.160>Defines the action to take if the file system is removed from the file system table. Valid values: remove(1), up(2) or down(3)."
	::= { uxsConfigFSysGroup 16 }

uxsConfigFSysNameAdd OBJECT-TYPE
	SYNTAX  DisplayString
	ACCESS  read-write
	STATUS  mandatory
	DESCRIPTION
		"&<caiUxOs.161>Defines the name of the file system watcher to add."
	::= { uxsConfigFSysGroup 17 }

uxsConfigFSysNameRemove OBJECT-TYPE
	SYNTAX  DisplayString
	ACCESS  read-write
	STATUS  mandatory
	DESCRIPTION
		"&<caiUxOs.162>Defines the name of the file system watcher to remove."
	::= { uxsConfigFSysGroup 18 }

--
-- uxsConfigDiskGroup
--
uxsConfigDiskPollInterval OBJECT-TYPE
	SYNTAX  INTEGER
	ACCESS  read-write
	STATUS  mandatory
	DESCRIPTION
		"&<caiUxOs.163>The time, in seconds, between the collections of the physical disk information. Valid ranges: -1 (Suspended), 30 seconds or greater."
	::= { uxsConfigDiskGroup 1 }

uxsConfigDiskPollMethod OBJECT-TYPE
	SYNTAX  INTEGER {
		disabled(1),
		poll-interval-and-query(2),
		poll-interval-only(3),
		query-only(4)
	}
	ACCESS  read-write
	STATUS  mandatory
	DESCRIPTION
		"&<caiUxOs.164>If set to 'disabled', the agent no more retrieves the physical disk information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigDiskGroup 2 }

uxsConfigDiskTPutWarn OBJECT-TYPE
	SYNTAX  INTEGER
	ACCESS  read-write
	STATUS  mandatory
	DESCRIPTION
		"&<caiUxOs.165>The value for physical disk throughput in kilobytes per second that is considered a warning level for that resource. Valid ranges: Greater than 0, not greater than or equal to the critical threshold."
	::= { uxsConfigDiskGroup 3 }

uxsConfigDiskTPutCrit OBJECT-TYPE
	SYNTAX  INTEGER
	ACCESS  read-write
	STATUS  mandatory
	DESCRIPTION
		"&<caiUxOs.166>The value for physical disk throughput in kilobytes per second that is considered a critical level for that resource. Valid ranges: Greater than 1, not less than or equal to the warning threshold."
	::= { uxsConfigDiskGroup 4 }

uxsConfigDiskTPutMonitor OBJECT-TYPE
	SYNTAX  INTEGER {
		do-not-monitor(1),
		warning-only(2),
		critical-only(3),
		both(4)
	}
	ACCESS  read-write
	STATUS  mandatory
	DESCRIPTION
		"&<caiUxOs.167>Defines the level of monitoring for the resource's status. Valid values: do-not-monitor(1), warning-only(2), critical-only(3) or both(4)."
	::= { uxsConfigDiskGroup 5 }

uxsConfigDiskLossAction OBJECT-TYPE
	SYNTAX  INTEGER {
		remove(1),
		up(2),
		down(3)
	}
	ACCESS  read-write
	STATUS  mandatory
	DESCRIPTION
		"&<caiUxOs.168>Defines the action to take if the physical disk is removed from the machine. Valid values: remove(1), up(2) or down(3)."
	::= { uxsConfigDiskGroup 6 }

uxsConfigDiskNameAdd OBJECT-TYPE
	SYNTAX  DisplayString
	ACCESS  read-write
	STATUS  mandatory
	DESCRIPTION
		"&<caiUxOs.169>Defines the name of the physical disk watcher to add."
	::= { uxsConfigDiskGroup 7 }

uxsConfigDiskNameRemove OBJECT-TYPE
	SYNTAX  DisplayString
	ACCESS  read-write
	STATUS  mandatory
	DESCRIPTION
		"&<caiUxOs.170>Defines the name of the physical disk watcher to remove."
	::= { uxsConfigDiskGroup 8 }

--
-- uxsConfigFileGroup
--
uxsConfigFilePollInterval OBJECT-TYPE
	SYNTAX  INTEGER
	ACCESS  read-write
	STATUS  mandatory
	DESCRIPTION
		"&<caiUxOs.171>The time, in seconds, between the collections of the file information. Valid ranges: -1 (Suspended), 30 seconds or greater."
	::= { uxsConfigFileGroup 1 }

uxsConfigFilePollMethod OBJECT-TYPE
	SYNTAX  INTEGER {
		disabled(1),
		poll-interval-and-query(2),
		poll-interval-only(3),
		query-only(4)
	}
	ACCESS  read-write
	STATUS  mandatory
	DESCRIPTION
		"&<caiUxOs.172>If set to 'disabled', the agent no more retrieves the file information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigFileGroup 2 }

uxsConfigFileDesc OBJECT-TYPE
	SYNTAX  DisplayString
	ACCESS  read-write
	STATUS  mandatory
	DESCRIPTION
		"&<caiUxOs.173>The description associated with the file watcher."
	::= { uxsConfigFileGroup 3 }

uxsConfigFileExist OBJECT-TYPE
	SYNTAX  INTEGER {
		should-exist(1),
		should-not-exist(2)
	}
	ACCESS  read-write
	STATUS  mandatory
	DESCRIPTION
		"&<caiUxOs.174>The type of existence monitoring to apply to the file watcher. Valid values: should-exist(1) or should-not-exist(2)"
	::= { uxsConfigFileGroup 4 }

uxsConfigFileExistMonitor OBJECT-TYPE
	SYNTAX  INTEGER {
		do-not-monitor(1),
		monitor(2)
	}
	ACCESS  read-write
	STATUS  mandatory
	DESCRIPTION
		"&<caiUxOs.175>Defines the level of monitoring for the resource's status. Valid values: do-not-monitor(1) or monitor(2)."
	::= { uxsConfigFileGroup 5 }

uxsConfigFileModTimeMonitor OBJECT-TYPE
	SYNTAX  INTEGER {
		do-not-monitor(1),
		monitor(2)
	}
	ACCESS  read-write
	STATUS  mandatory
	DESCRIPTION
		"&<caiUxOs.176>Defines the level of monitoring for the resource's status. Valid values: do-not-monitor(1) or monitor(2)."
	::= { uxsConfigFileGroup 6 }

uxsConfigFileSizeWarn OBJECT-TYPE
	SYNTAX  DisplayString
	ACCESS  read-write
	STATUS  mandatory
	DESCRIPTION
		"&<caiUxOs.177>The value for file size, either as a percentage of the total or as an absolute value, that is considered a warning level for that resource. Valid ranges: Greater than 0, not greater than or equal to the critical threshold."
	::= { uxsConfigFileGroup 7 }

uxsConfigFileSizeCrit OBJECT-TYPE
	SYNTAX  DisplayString
	ACCESS  read-write
	STATUS  mandatory
	DESCRIPTION
		"&<caiUxOs.178>The value for file size, either as a percentage of the total or as an absolute value, that is considered a critical level for that resource. Valid ranges: Greater than 1, not less than or equal to the warning threshold."
	::= { uxsConfigFileGroup 8 }

uxsConfigFileSizeMonitor OBJECT-TYPE
	SYNTAX  INTEGER {
		do-not-monitor(1),
		warning-only(2),
		critical-only(3),
		both(4)
	}
	ACCESS  read-write
	STATUS  mandatory
	DESCRIPTION
		"&<caiUxOs.179>Defines the level of monitoring for the resource's status. Valid values: do-not-monitor(1), warning-only(2), critical-only(3) or both(4)."
	::= { uxsConfigFileGroup 9 }

uxsConfigFileSizeDWarn OBJECT-TYPE
	SYNTAX  DisplayString
	ACCESS  read-write
	STATUS  mandatory
	DESCRIPTION
		"&<caiUxOs.180>The value for file size delta, either as a percentage of the total or as an absolute value, that is considered a warning level for that resource. Valid ranges: Greater than 0, not greater than or equal to the critical threshold."
	::= { uxsConfigFileGroup 10 }

uxsConfigFileSizeDCrit OBJECT-TYPE
	SYNTAX  DisplayString
	ACCESS  read-write
	STATUS  mandatory
	DESCRIPTION
		"&<caiUxOs.181>The value for file size delta, either as a percentage of the total or as an absolute value, that is considered a critical level for that resource. Valid ranges: Greater than 1, not less than or equal to the warning threshold."
	::= { uxsConfigFileGroup 11 }

uxsConfigFileSizeDMonitor OBJECT-TYPE
	SYNTAX  INTEGER {
		do-not-monitor(1),
		warning-only(2),
		critical-only(3),
		both(4)
	}
	ACCESS  read-write
	STATUS  mandatory
	DESCRIPTION
		"&<caiUxOs.182>Defines the level of monitoring for the resource's status. Valid values: do-not-monitor(1), warning-only(2), critical-only(3) or both(4)."
	::= { uxsConfigFileGroup 12 }

uxsConfigFileNameAdd OBJECT-TYPE
	SYNTAX  DisplayString
	ACCESS  read-write
	STATUS  mandatory
	DESCRIPTION
		"&<caiUxOs.183>Defines the name of the file watcher to add."
	::= { uxsConfigFileGroup 13 }

uxsConfigFileNameRemove OBJECT-TYPE
	SYNTAX  DisplayString
	ACCESS  read-write
	STATUS  mandatory
	DESCRIPTION
		"&<caiUxOs.184>Defines the name of the file watcher to remove."
	::= { uxsConfigFileGroup 14 }

--
-- uxsConfigProcGroup
--
uxsConfigProcPollInterval OBJECT-TYPE
	SYNTAX  INTEGER
	ACCESS  read-write
	STATUS  mandatory
	DESCRIPTION
		"&<caiUxOs.185>The time, in seconds, between the collections of the process information. Valid ranges: -1 (Suspended), 30 seconds or greater."
	::= { uxsConfigProcGroup 1 }

uxsConfigProcPollMethod OBJECT-TYPE
	SYNTAX  INTEGER {
		disabled(1),
		poll-interval-and-query(2),
		poll-interval-only(3),
		query-only(4)
	}
	ACCESS  read-write
	STATUS  mandatory
	DESCRIPTION
		"&<caiUxOs.186>If set to 'disabled', the agent no more retrieves the process information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigProcGroup 2 }

uxsConfigProcPath OBJECT-TYPE
	SYNTAX  DisplayString
	ACCESS  read-write
	STATUS  mandatory
	DESCRIPTION
		"&<caiUxOs.187>The path of the process to match. Valid values are a string with an optional * at the end of the string for wild card matching."
	::= { uxsConfigProcGroup 3 }

uxsConfigProcArgs OBJECT-TYPE
	SYNTAX  DisplayString
	ACCESS  read-write
	STATUS  mandatory
	DESCRIPTION
		"&<caiUxOs.188>A section of the processes arguments to match."
	::= { uxsConfigProcGroup 4 }

uxsConfigProcUsers OBJECT-TYPE
	SYNTAX  DisplayString
	ACCESS  read-write
	STATUS  mandatory
	DESCRIPTION
		"&<caiUxOs.189>List of users to match. Format details of the string are documented in the online help."
	::= { uxsConfigProcGroup 5 }

uxsConfigProcInstMin OBJECT-TYPE
	SYNTAX  INTEGER
	ACCESS  read-write
	STATUS  mandatory
	DESCRIPTION
		"&<caiUxOs.190>Minimum number of instances expected to match the key. Valid values:  -1, 0 or greater."
	::= { uxsConfigProcGroup 6 }

uxsConfigProcInstMax OBJECT-TYPE
	SYNTAX  INTEGER
	ACCESS  read-write
	STATUS  mandatory
	DESCRIPTION
		"&<caiUxOs.191>Maximum number of instances expected to match the key. Valid values:  -1, 0 or greater."
	::= { uxsConfigProcGroup 7 }

uxsConfigProcInstMonitor OBJECT-TYPE
	SYNTAX  INTEGER {
		do-not-monitor(1),
		monitor(2)
	}
	ACCESS  read-write
	STATUS  mandatory
	DESCRIPTION
		"&<caiUxOs.192>Defines the level of monitoring for the resource's status. Valid values: do-not-monitor(1) or monitor(2)."
	::= { uxsConfigProcGroup 8 }

uxsConfigProcChldMin OBJECT-TYPE
	SYNTAX  INTEGER
	ACCESS  read-write
	STATUS  mandatory
	DESCRIPTION
		"&<caiUxOs.193>Minimum number of children (based on lowest for all instances). Valid values: -1, 0 or greater."
	::= { uxsConfigProcGroup 9 }

uxsConfigProcChldMax OBJECT-TYPE
	SYNTAX  INTEGER
	ACCESS  read-write
	STATUS  mandatory
	DESCRIPTION
		"&<caiUxOs.194>Maximum number of children (based on highest for all instances). Valid values: -1, 0 or greater."
	::= { uxsConfigProcGroup 10 }

uxsConfigProcChldMonitor OBJECT-TYPE
	SYNTAX  INTEGER {
		do-not-monitor(1),
		monitor(2)
	}
	ACCESS  read-write
	STATUS  mandatory
	DESCRIPTION
		"&<caiUxOs.195>Defines the level of monitoring for the resource's status. Valid values: do-not-monitor(1) or monitor(2)."
	::= { uxsConfigProcGroup 11 }

uxsConfigProcSizeMin OBJECT-TYPE
	SYNTAX  INTEGER
	ACCESS  read-write
	STATUS  mandatory
	DESCRIPTION
		"&<caiUxOs.196>Minimum size in kilobytes (based on lowest for all instances). Valid values: -1, 0 or greater."
	::= { uxsConfigProcGroup 12 }

uxsConfigProcSizeMax OBJECT-TYPE
	SYNTAX  INTEGER
	ACCESS  read-write
	STATUS  mandatory
	DESCRIPTION
		"&<caiUxOs.197>Maximum size in kilobytes (based on highest for all instances). Valid values: -1, 0 or greater."
	::= { uxsConfigProcGroup 13 }

uxsConfigProcSizeMonitor OBJECT-TYPE
	SYNTAX  INTEGER {
		do-not-monitor(1),
		monitor(2)
	}
	ACCESS  read-write
	STATUS  mandatory
	DESCRIPTION
		"&<caiUxOs.198>Defines the level of monitoring for the resource's status. Valid values: do-not-monitor(1) or monitor(2)."
	::= { uxsConfigProcGroup 14 }

uxsConfigProcCPUWarn OBJECT-TYPE
	SYNTAX  INTEGER
	ACCESS  read-write
	STATUS  mandatory
	DESCRIPTION
		"&<caiUxOs.199>The percentage of used CPU that is considered a warning level for that resource. Valid ranges: Greater than 0, less than 100, not greater than or equal to the critical threshold."
	::= { uxsConfigProcGroup 15 }

uxsConfigProcCPUCrit OBJECT-TYPE
	SYNTAX  INTEGER
	ACCESS  read-write
	STATUS  mandatory
	DESCRIPTION
		"&<caiUxOs.200>The percentage of used CPU, that is considered a critical level for that resource. Valid ranges: Greater than 1, less than or equal to 100, not less than or equal to the warning threshold."
	::= { uxsConfigProcGroup 16 }

uxsConfigProcCPUMonitor OBJECT-TYPE
	SYNTAX  INTEGER {
		do-not-monitor(1),
		warning-only(2),
		critical-only(3),
		both(4)
	}
	ACCESS  read-write
	STATUS  mandatory
	DESCRIPTION
		"&<caiUxOs.201>Defines the level of monitoring for the resource's status. Valid values: do-not-monitor(1), warning-only(2), critical-only(3) or both(4)."
	::= { uxsConfigProcGroup 17 }

uxsConfigProcNameAdd OBJECT-TYPE
	SYNTAX  DisplayString
	ACCESS  read-write
	STATUS  mandatory
	DESCRIPTION
		"&<caiUxOs.202>The name of the process to monitor. Valid values are a string with an optional * at the end of the string for wild card matching. Note: Setting this attribute causes the watcher to be added."
	::= { uxsConfigProcGroup 18 }

uxsConfigProcNameRemove OBJECT-TYPE
	SYNTAX  DisplayString
	ACCESS  read-write
	STATUS  mandatory
	DESCRIPTION
		"&<caiUxOs.203>The process name of the watcher to delete. Set this attribute with the other KEY fields. Setting this causes the delete action."
	::= { uxsConfigProcGroup 19 }

uxsConfigProcNameSig OBJECT-TYPE
	SYNTAX  INTEGER
	ACCESS  read-only
	STATUS  mandatory
	DESCRIPTION
		"&<caiUxOs.204>The number of significant bytes that the agent uses for matching the process name against."
	::= { uxsConfigProcGroup 20 }

uxsConfigProcPathSig OBJECT-TYPE
	SYNTAX  INTEGER
	ACCESS  read-only
	STATUS  mandatory
	DESCRIPTION
		"&<caiUxOs.205>The number of significant bytes that the agent uses for matching the process path against."
	::= { uxsConfigProcGroup 21 }

uxsConfigProcArgsSig OBJECT-TYPE
	SYNTAX  INTEGER
	ACCESS  read-only
	STATUS  mandatory
	DESCRIPTION
		"&<caiUxOs.206>The number of significant bytes that the agent uses for matching the process arguments against."
	::= { uxsConfigProcGroup 22 }

--
-- uxsConfigPrnGroup
--
uxsConfigPrnPollInterval OBJECT-TYPE
	SYNTAX  INTEGER
	ACCESS  read-write
	STATUS  mandatory
	DESCRIPTION
		"&<caiUxOs.207>The time, in seconds, between the collections of the printer queue information. Valid ranges: -1 (Suspended), 30 seconds or greater."
	::= { uxsConfigPrnGroup 1 }

uxsConfigPrnPollMethod OBJECT-TYPE
	SYNTAX  INTEGER {
		disabled(1),
		poll-interval-and-query(2),
		poll-interval-only(3),
		query-only(4)
	}
	ACCESS  read-write
	STATUS  mandatory
	DESCRIPTION
		"&<caiUxOs.208>If set to 'disabled', the agent no more retrieves the printer queue information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigPrnGroup 2 }

uxsConfigPrnDesc OBJECT-TYPE
	SYNTAX  DisplayString
	ACCESS  read-write
	STATUS  mandatory
	DESCRIPTION
		"&<caiUxOs.209>Description of the printer queue watcher."
	::= { uxsConfigPrnGroup 3 }

uxsConfigPrnItemsWarn OBJECT-TYPE
	SYNTAX  INTEGER
	ACCESS  read-write
	STATUS  mandatory
	DESCRIPTION
		"&<caiUxOs.210>The number of items on the printer queue that is considered a warning level for that resource. Valid ranges: Greater than 0, not greater than or equal to the critical threshold."
	::= { uxsConfigPrnGroup 4 }

uxsConfigPrnItemsCrit OBJECT-TYPE
	SYNTAX  INTEGER
	ACCESS  read-write
	STATUS  mandatory
	DESCRIPTION
		"&<caiUxOs.211>The number of items on the printer queue that is considered a critical level for that resource. Valid ranges: Greater than 0, not less than or equal to the warning threshold."
	::= { uxsConfigPrnGroup 5 }

uxsConfigPrnItemsMonitor OBJECT-TYPE
	SYNTAX  INTEGER {
		do-not-monitor(1),
		warning-only(2),
		critical-only(3),
		both(4)
	}
	ACCESS  read-write
	STATUS  mandatory
	DESCRIPTION
		"&<caiUxOs.212>Defines the level of monitoring for the resource's status. Valid values: do-not-monitor(1), warning-only(2), critical-only(3) or both(4)."
	::= { uxsConfigPrnGroup 6 }

uxsConfigPrnLossAction OBJECT-TYPE
	SYNTAX  INTEGER {
		remove(1),
		up(2),
		down(3)
	}
	ACCESS  read-write
	STATUS  mandatory
	DESCRIPTION
		"&<caiUxOs.213>Defines the action to take if the printer queue configuration is removed from the machine. Valid values: remove(1), up(2) or down(3)."
	::= { uxsConfigPrnGroup 7 }

uxsConfigPrnNameAdd OBJECT-TYPE
	SYNTAX  DisplayString
	ACCESS  read-write
	STATUS  mandatory
	DESCRIPTION
		"&<caiUxOs.214>Setting this attribute causes a new watcher to be added for the printer queue name specified."
	::= { uxsConfigPrnGroup 8 }

uxsConfigPrnNameRemove OBJECT-TYPE
	SYNTAX  DisplayString
	ACCESS  read-write
	STATUS  mandatory
	DESCRIPTION
		"&<caiUxOs.215>Setting this attribute causes the watcher with the printer queue name specified to be deleted."
	::= { uxsConfigPrnGroup 9 }

--
-- uxsConfigNetGroup
--
uxsConfigNetPollInterval OBJECT-TYPE
	SYNTAX  INTEGER
	ACCESS  read-write
	STATUS  mandatory
	DESCRIPTION
		"&<caiUxOs.216>The time, in seconds, between the collections of the Network Interface information. Valid ranges: -1 (Suspended), 30 seconds or greater."
	::= { uxsConfigNetGroup 1 }

uxsConfigNetPollMethod OBJECT-TYPE
	SYNTAX  INTEGER {
		disabled(1),
		poll-interval-and-query(2),
		poll-interval-only(3),
		query-only(4)
	}
	ACCESS  read-write
	STATUS  mandatory
	DESCRIPTION
		"&<caiUxOs.217>If set to 'disabled', the agent no more retrieves the network interface information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigNetGroup 2 }

uxsConfigNetIPktWarn OBJECT-TYPE
	SYNTAX  INTEGER
	ACCESS  read-write
	STATUS  mandatory
	DESCRIPTION
		"&<caiUxOs.218>The number of input packets per second that is considered a warning level for that resource. Valid ranges: Greater than 0, not greater than or equal to the critical threshold."
	::= { uxsConfigNetGroup 3 }

uxsConfigNetIPktCrit OBJECT-TYPE
	SYNTAX  INTEGER
	ACCESS  read-write
	STATUS  mandatory
	DESCRIPTION
		"&<caiUxOs.219>The number of input packets per second that is considered a critical level for that resource. Valid ranges: Greater than 1, not less than or equal to the warning threshold."
	::= { uxsConfigNetGroup 4 }

uxsConfigNetIPktMonitor OBJECT-TYPE
	SYNTAX  INTEGER {
		do-not-monitor(1),
		warning-only(2),
		critical-only(3),
		both(4)
	}
	ACCESS  read-write
	STATUS  mandatory
	DESCRIPTION
		"&<caiUxOs.220>Defines the level of monitoring for the resource's status. Valid values: do-not-monitor(1), warning-only(2), critical-only(3) or both(4)."
	::= { uxsConfigNetGroup 5 }

uxsConfigNetIErrWarn OBJECT-TYPE
	SYNTAX  INTEGER
	ACCESS  read-write
	STATUS  mandatory
	DESCRIPTION
		"&<caiUxOs.221>The number of input errors per pollinterval that is considered a warning level for that resource. Valid ranges: Greater than 0, not greater than or equal to the critical threshold."
	::= { uxsConfigNetGroup 6 }

uxsConfigNetIErrCrit OBJECT-TYPE
	SYNTAX  INTEGER
	ACCESS  read-write
	STATUS  mandatory
	DESCRIPTION
		"&<caiUxOs.222>The number of input errors per pollinterval that is considered a critical level for that resource. Valid ranges: Greater than 1, not less than or equal to the warning threshold."
	::= { uxsConfigNetGroup 7 }

uxsConfigNetIErrMonitor OBJECT-TYPE
	SYNTAX  INTEGER {
		do-not-monitor(1),
		warning-only(2),
		critical-only(3),
		both(4)
	}
	ACCESS  read-write
	STATUS  mandatory
	DESCRIPTION
		"&<caiUxOs.223>Defines the level of monitoring for the resource's status. Valid values: do-not-monitor(1), warning-only(2), critical-only(3) or both(4)."
	::= { uxsConfigNetGroup 8 }

uxsConfigNetOPktWarn OBJECT-TYPE
	SYNTAX  INTEGER
	ACCESS  read-write
	STATUS  mandatory
	DESCRIPTION
		"&<caiUxOs.224>The number of output packets per second that is considered a warning level for that resource. Valid ranges: Greater than 0, not greater than or equal to the critical threshold."
	::= { uxsConfigNetGroup 9 }

uxsConfigNetOPktCrit OBJECT-TYPE
	SYNTAX  INTEGER
	ACCESS  read-write
	STATUS  mandatory
	DESCRIPTION
		"&<caiUxOs.225>The number of output packets per second that is considered a critical level for that resource. Valid ranges: Greater than 1, not less than or equal to the warning threshold."
	::= { uxsConfigNetGroup 10 }

uxsConfigNetOPktMonitor OBJECT-TYPE
	SYNTAX  INTEGER {
		do-not-monitor(1),
		warning-only(2),
		critical-only(3),
		both(4)
	}
	ACCESS  read-write
	STATUS  mandatory
	DESCRIPTION
		"&<caiUxOs.226>Defines the level of monitoring for the resource's status. Valid values: do-not-monitor(1), warning-only(2), critical-only(3) or both(4)."
	::= { uxsConfigNetGroup 11 }

uxsConfigNetOErrWarn OBJECT-TYPE
	SYNTAX  INTEGER
	ACCESS  read-write
	STATUS  mandatory
	DESCRIPTION
		"&<caiUxOs.227>The number of output errors per pollinterval that is considered a warning level for that resource. Valid ranges: Greater than 0, not greater than or equal to the critical threshold."
	::= { uxsConfigNetGroup 12 }

uxsConfigNetOErrCrit OBJECT-TYPE
	SYNTAX  INTEGER
	ACCESS  read-write
	STATUS  mandatory
	DESCRIPTION
		"&<caiUxOs.228>The number of output errors per pollinterval that is considered a critical level for that resource. Valid ranges: Greater than 1, not less than or equal to the warning threshold."
	::= { uxsConfigNetGroup 13 }

uxsConfigNetOErrMonitor OBJECT-TYPE
	SYNTAX  INTEGER {
		do-not-monitor(1),
		warning-only(2),
		critical-only(3),
		both(4)
	}
	ACCESS  read-write
	STATUS  mandatory
	DESCRIPTION
		"&<caiUxOs.229>Defines the level of monitoring for the resource's status. Valid values: do-not-monitor(1), warning-only(2), critical-only(3) or both(4)."
	::= { uxsConfigNetGroup 14 }

uxsConfigNetCollWarn OBJECT-TYPE
	SYNTAX  INTEGER
	ACCESS  read-write
	STATUS  mandatory
	DESCRIPTION
		"&<caiUxOs.230>The number of collisions per pollinterval that is considered a warning level for that resource. Valid ranges: Greater than 0, not greater than or equal to the critical threshold."
	::= { uxsConfigNetGroup 15 }

uxsConfigNetCollCrit OBJECT-TYPE
	SYNTAX  INTEGER
	ACCESS  read-write
	STATUS  mandatory
	DESCRIPTION
		"&<caiUxOs.231>The number of collisions per pollinterval that is considered a critical level for that resource. Valid ranges: Greater than 1, not less than or equal to the warning threshold."
	::= { uxsConfigNetGroup 16 }

uxsConfigNetCollMonitor OBJECT-TYPE
	SYNTAX  INTEGER {
		do-not-monitor(1),
		warning-only(2),
		critical-only(3),
		both(4)
	}
	ACCESS  read-write
	STATUS  mandatory
	DESCRIPTION
		"&<caiUxOs.232>Defines the level of monitoring for the resource's status. Valid values: do-not-monitor(1), warning-only(2), critical-only(3) or both(4)."
	::= { uxsConfigNetGroup 17 }

uxsConfigNetLossAction OBJECT-TYPE
	SYNTAX  INTEGER {
		remove(1),
		up(2),
		down(3)
	}
	ACCESS  read-write
	STATUS  mandatory
	DESCRIPTION
		"&<caiUxOs.233>Defines the action to take if the Network Interface is removed from the machine. Valid values: remove(1), up(2) or down(3)."
	::= { uxsConfigNetGroup 18 }

--
-- uxsConfigIPCGroup
--
uxsConfigIPCPollInterval OBJECT-TYPE
	SYNTAX  INTEGER
	ACCESS  read-write
	STATUS  mandatory
	DESCRIPTION
		"&<caiUxOs.234>The time, in seconds, between the collections of the Inter Process Communications information. Valid ranges: -1 (Suspended), 30 seconds or greater."
	::= { uxsConfigIPCGroup 1 }

uxsConfigIPCPollMethod OBJECT-TYPE
	SYNTAX  INTEGER {
		disabled(1),
		poll-interval-and-query(2),
		poll-interval-only(3),
		query-only(4)
	}
	ACCESS  read-write
	STATUS  mandatory
	DESCRIPTION
		"&<caiUxOs.235>If set to 'disabled', the agent no more retrieves the Inter Process Communications information (not by polling, nor by get request) and sets all statuses to ok. If set to 'poll-interval-and-query', the agent retrieves the information in both cases (polling and get request). If set to 'poll-interval-only', the agent only retrieves the information by polling, but not by get request. If set to 'query-only', the agent retrieves the information for get requests only."
	::= { uxsConfigIPCGroup 2 }

uxsConfigIPCMQBytesLag OBJECT-TYPE
	SYNTAX  INTEGER
	ACCESS  read-write
	STATUS  mandatory
	DESCRIPTION
		"&<caiUxOs.236>The number of times that the threshold has to be reached before the state changes. Valid range: Greater than 0."
	::= { uxsConfigIPCGroup 3 }

uxsConfigIPCMQBytesWarn OBJECT-TYPE
	SYNTAX  DisplayString
	ACCESS  read-write
	STATUS  mandatory
	DESCRIPTION
		"&<caiUxOs.237>The value for used message queue bytes that is considered a warning level for that resource. Valid ranges: Greater than 0, not greater than or equal to the critical threshold."
	::= { uxsConfigIPCGroup 4 }

uxsConfigIPCMQBytesCrit OBJECT-TYPE
	SYNTAX  DisplayString
	ACCESS  read-write
	STATUS  mandatory
	DESCRIPTION
		"&<caiUxOs.238>The value for used message queue bytes that is considered a critical level for that resource. Valid ranges: Greater than 1, not less than or equal to the warning threshold."
	::= { uxsConfigIPCGroup 5 }

uxsConfigIPCMQBytesMonitor OBJECT-TYPE
	SYNTAX  INTEGER {
		do-not-monitor(1),
		warning-only(2),
		critical-only(3),
		both(4)
	}
	ACCESS  read-write
	STATUS  mandatory
	DESCRIPTION
		"&<caiUxOs.239>Defines the level of monitoring for the resource's status. Valid values: do-not-monitor(1), warning-only(2), critical-only(3) or both(4)."
	::= { uxsConfigIPCGroup 6 }

--
-- uxsStatusGeneralGroup
--
uxsStatusGeneralTotalCount OBJECT-TYPE
	SYNTAX  INTEGER
	ACCESS  read-only
	STATUS  mandatory
	DESCRIPTION
		"&<caiUxOs.240>Total number of resources that the agent is configured to monitor."
	::= { uxsStatusGeneralGroup 1 }

uxsStatusGeneralTotalWarning OBJECT-TYPE
	SYNTAX  INTEGER
	ACCESS  read-only
	STATUS  mandatory
	DESCRIPTION
		"&<caiUxOs.241>Total number of the resources that the agent is configured to monitor that are in a warning state."
	::= { uxsStatusGeneralGroup 2 }

uxsStatusGeneralTotalCritical OBJECT-TYPE
	SYNTAX  INTEGER
	ACCESS  read-only
	STATUS  mandatory
	DESCRIPTION
		"&<caiUxOs.242>Total number of the resources that the agent is configured to monitor that are in a critical state."
	::= { uxsStatusGeneralGroup 3 }

uxsStatusGeneralCPUCount OBJECT-TYPE
	SYNTAX  INTEGER
	ACCESS  read-only
	STATUS  mandatory
	DESCRIPTION
		"&<caiUxOs.243>The total number of this resource type that are being monitored."
	::= { uxsStatusGeneralGroup 4 }

uxsStatusGeneralCPUWarning OBJECT-TYPE
	SYNTAX  INTEGER
	ACCESS  read-only
	STATUS  mandatory
	DESCRIPTION
		"&<caiUxOs.244>The total number of this resource type that are being monitored and are in a warning state."
	::= { uxsStatusGeneralGroup 5 }

uxsStatusGeneralCPUCritical OBJECT-TYPE
	SYNTAX  INTEGER
	ACCESS  read-only
	STATUS  mandatory
	DESCRIPTION
		"&<caiUxOs.245>The total number of this resource type that are being monitored and are in a critical state."
	::= { uxsStatusGeneralGroup 6 }

uxsStatusGeneralLoadCount OBJECT-TYPE
	SYNTAX  INTEGER
	ACCESS  read-only
	STATUS  mandatory
	DESCRIPTION
		"&<caiUxOs.246>The total number of this resource type that are being monitored."
	::= { uxsStatusGeneralGroup 7 }

uxsStatusGeneralLoadWarning OBJECT-TYPE
	SYNTAX  INTEGER
	ACCESS  read-only
	STATUS  mandatory
	DESCRIPTION
		"&<caiUxOs.247>The total number of this resource type that are being monitored and are in a warning state."
	::= { uxsStatusGeneralGroup 8 }

uxsStatusGeneralLoadCritical OBJECT-TYPE
	SYNTAX  INTEGER
	ACCESS  read-only
	STATUS  mandatory
	DESCRIPTION
		"&<caiUxOs.248>The total number of this resource type that are being monitored and are in a critical state."
	::= { uxsStatusGeneralGroup 9 }

uxsStatusGeneralMemCount OBJECT-TYPE
	SYNTAX  INTEGER
	ACCESS  read-only
	STATUS  mandatory
	DESCRIPTION
		"&<caiUxOs.249>The total number of this resource type that are being monitored."
	::= { uxsStatusGeneralGroup 10 }

uxsStatusGeneralMemWarning OBJECT-TYPE
	SYNTAX  INTEGER
	ACCESS  read-only
	STATUS  mandatory
	DESCRIPTION
		"&<caiUxOs.250>The total number of this resource type that are being monitored and are in a warning state."
	::= { uxsStatusGeneralGroup 11 }

uxsStatusGeneralMemCritical OBJECT-TYPE
	SYNTAX  INTEGER
	ACCESS  read-only
	STATUS  mandatory
	DESCRIPTION
		"&<caiUxOs.251>The total number of this resource type that are being monitored and are in a critical state."
	::= { uxsStatusGeneralGroup 12 }

uxsStatusGeneralSwapCount OBJECT-TYPE
	SYNTAX  INTEGER
	ACCESS  read-only
	STATUS  mandatory
	DESCRIPTION
		"&<caiUxOs.252>The total number of this resource type that are being monitored."
	::= { uxsStatusGeneralGroup 13 }

uxsStatusGeneralSwapWarning OBJECT-TYPE
	SYNTAX  INTEGER
	ACCESS  read-only
	STATUS  mandatory
	DESCRIPTION
		"&<caiUxOs.253>The total number of this resource type that are being monitored and are in a warning state."
	::= { uxsStatusGeneralGroup 14 }

uxsStatusGeneralSwapCritical OBJECT-TYPE
	SYNTAX  INTEGER
	ACCESS  read-only
	STATUS  mandatory
	DESCRIPTION
		"&<caiUxOs.254>The total number of this resource type that are being monitored and are in a critical state."
	::= { uxsStatusGeneralGroup 15 }

uxsStatusGeneralFSysCount OBJECT-TYPE
	SYNTAX  INTEGER
	ACCESS  read-only
	STATUS  mandatory
	DESCRIPTION
		"&<caiUxOs.255>The total number of this resource type that are being monitored."
	::= { uxsStatusGeneralGroup 16 }

uxsStatusGeneralFSysWarning OBJECT-TYPE
	SYNTAX  INTEGER
	ACCESS  read-only
	STATUS  mandatory
	DESCRIPTION
		"&<caiUxOs.256>The total number of this resource type that are being monitored and are in a warning state."
	::= { uxsStatusGeneralGroup 17 }

uxsStatusGeneralFSysCritical OBJECT-TYPE
	SYNTAX  INTEGER
	ACCESS  read-only
	STATUS  mandatory
	DESCRIPTION
		"&<caiUxOs.257>The total number of this resource type that are being monitored and are in a critical state."
	::= { uxsStatusGeneralGroup 18 }

uxsStatusGeneralDiskCount OBJECT-TYPE
	SYNTAX  INTEGER
	ACCESS  read-only
	STATUS  mandatory
	DESCRIPTION
		"&<caiUxOs.258>The total number of this resource type that are being monitored."
	::= { uxsStatusGeneralGroup 19 }

uxsStatusGeneralDiskWarning OBJECT-TYPE
	SYNTAX  INTEGER
	ACCESS  read-only
	STATUS  mandatory
	DESCRIPTION
		"&<caiUxOs.259>The total number of this resource type that are being monitored and are in a warning state."
	::= { uxsStatusGeneralGroup 20 }

uxsStatusGeneralDiskCritical OBJECT-TYPE
	SYNTAX  INTEGER
	ACCESS  read-only
	STATUS  mandatory
	DESCRIPTION
		"&<caiUxOs.260>The total number of this resource type that are being monitored and are in a critical state."
	::= { uxsStatusGeneralGroup 21 }

uxsStatusGeneralFileCount OBJECT-TYPE
	SYNTAX  INTEGER
	ACCESS  read-only
	STATUS  mandatory
	DESCRIPTION
		"&<caiUxOs.261>The total number of this resource type that are being monitored."
	::= { uxsStatusGeneralGroup 22 }

uxsStatusGeneralFileWarning OBJECT-TYPE
	SYNTAX  INTEGER
	ACCESS  read-only
	STATUS  mandatory
	DESCRIPTION
		"&<caiUxOs.262>The total number of this resource type that are being monitored and are in a warning state."
	::= { uxsStatusGeneralGroup 23 }

uxsStatusGeneralFileCritical OBJECT-TYPE
	SYNTAX  INTEGER
	ACCESS  read-only
	STATUS  mandatory
	DESCRIPTION
		"&<caiUxOs.263>The total number of this resource type that are being monitored and are in a critical state."
	::= { uxsStatusGeneralGroup 24 }

uxsStatusGeneralProcCount OBJECT-TYPE
	SYNTAX  INTEGER
	ACCESS  read-only
	STATUS  mandatory
	DESCRIPTION
		"&<caiUxOs.264>The total number of this resource type that are being monitored."
	::= { uxsStatusGeneralGroup 25 }

uxsStatusGeneralProcWarning OBJECT-TYPE
	SYNTAX  INTEGER
	ACCESS  read-only
	STATUS  mandatory
	DESCRIPTION
		"&<caiUxOs.265>The total number of this resource type that are being monitored and are in a warning state."
	::= { uxsStatusGeneralGroup 26 }

uxsStatusGeneralProcCritical OBJECT-TYPE
	SYNTAX  INTEGER
	ACCESS  read-only
	STATUS  mandatory
	DESCRIPTION
		"&<caiUxOs.266>The total number of this resource type that are being monitored and are in a critical state."
	::= { uxsStatusGeneralGroup 27 }

uxsStatusGeneralPrnCount OBJECT-TYPE
	SYNTAX  INTEGER
	ACCESS  read-only
	STATUS  mandatory
	DESCRIPTION
		"&<caiUxOs.267>The total number of this resource type that are being monitored."
	::= { uxsStatusGeneralGroup 28 }

uxsStatusGeneralPrnWarning OBJECT-TYPE
	SYNTAX  INTEGER
	ACCESS  read-only
	STATUS  mandatory
	DESCRIPTION
		"&<caiUxOs.268>The total number of this resource type that are being monitored and are in a warning state."
	::= { uxsStatusGeneralGroup 29 }

uxsStatusGeneralPrnCritical OBJECT-TYPE
	SYNTAX  INTEGER
	ACCESS  read-only
	STATUS  mandatory
	DESCRIPTION
		"&<caiUxOs.269>The total number of this resource type that are being monitored and are in a critical state."
	::= { uxsStatusGeneralGroup 30 }

uxsStatusGeneralNetCount OBJECT-TYPE
	SYNTAX  INTEGER
	ACCESS  read-only
	STATUS  mandatory
	DESCRIPTION
		"&<caiUxOs.270>The total number of this resource type that are being monitored."
	::= { uxsStatusGeneralGroup 31 }

uxsStatusGeneralNetWarning OBJECT-TYPE
	SYNTAX  INTEGER
	ACCESS  read-only
	STATUS  mandatory
	DESCRIPTION
		"&<caiUxOs.271>The total number of this resource type that are being monitored and are in a warning state."
	::= { uxsStatusGeneralGroup 32 }

uxsStatusGeneralNetCritical OBJECT-TYPE
	SYNTAX  INTEGER
	ACCESS  read-only
	STATUS  mandatory
	DESCRIPTION
		"&<caiUxOs.272>The total number of this resource type that are being monitored and are in a critical state."
	::= { uxsStatusGeneralGroup 33 }

uxsStatusGeneralIPCCount OBJECT-TYPE
	SYNTAX  INTEGER
	ACCESS  read-only
	STATUS  mandatory
	DESCRIPTION
		"&<caiUxOs.273>The total number of this resource type that are being monitored."
	::= { uxsStatusGeneralGroup 34 }

uxsStatusGeneralIPCWarning OBJECT-TYPE
	SYNTAX  INTEGER
	ACCESS  read-only
	STATUS  mandatory
	DESCRIPTION
		"&<caiUxOs.274>The total number of this resource type that are being monitored and are in a warning state."
	::= { uxsStatusGeneralGroup 35 }

uxsStatusGeneralIPCCritical OBJECT-TYPE
	SYNTAX  INTEGER
	ACCESS  read-only
	STATUS  mandatory
	DESCRIPTION
		"&<caiUxOs.275>The total number of this resource type that are being monitored and are in a critical state."
	::= { uxsStatusGeneralGroup 36 }

--
-- uxsStatusCPUGroup
--
uxsStatusCPUTotalName OBJECT-TYPE
	SYNTAX  DisplayString
	ACCESS  read-only
	STATUS  mandatory
	DESCRIPTION
		"&<caiUxOs.276>The name the agent gives for the total number of CPUs."
	::= { uxsStatusCPUGroup 1 }

uxsStatusCPUTotalUser OBJECT-TYPE
	SYNTAX  INTEGER
	ACCESS  read-only
	STATUS  mandatory
	DESCRIPTION
		"&<caiUxOs.277>The percentage of time that the CPUs spent servicing user requests."
	::= { uxsStatusCPUGroup 2 }

uxsStatusCPUTotalSys OBJECT-TYPE
	SYNTAX  INTEGER
	ACCESS  read-only
	STATUS  mandatory
	DESCRIPTION
		"&<caiUxOs.278>The percentage of time that the CPUs spent servicing system requests."
	::= { uxsStatusCPUGroup 3 }

uxsStatusCPUTotalIdle OBJECT-TYPE
	SYNTAX  INTEGER
	ACCESS  read-only
	STATUS  mandatory
	DESCRIPTION
		"&<caiUxOs.279>The percentage of time that the CPUs were idle."
	::= { uxsStatusCPUGroup 4 }

uxsStatusCPUTotalWIO OBJECT-TYPE
	SYNTAX  INTEGER
	ACCESS  read-only
	STATUS  mandatory
	DESCRIPTION
		"&<caiUxOs.280>The percentage of time that the CPUs spent waiting for blocking I/O requests."
	::= { uxsStatusCPUGroup 5 }

uxsStatusCPUTotalUsedValue OBJECT-TYPE
	SYNTAX  INTEGER
	ACCESS  read-only
	STATUS  mandatory
	DESCRIPTION
		"&<caiUxOs.281>The total percentage of the CPUs' time that the processors were busy. i.e. 100 - idle% - iowait%."
	::= { uxsStatusCPUGroup 6 }

uxsStatusCPUTotalLagValue OBJECT-TYPE
	SYNTAX  INTEGER
	ACCESS  read-only
	STATUS  mandatory
	DESCRIPTION
		"&<caiUxOs.282>The number of times that the threshold has been reached."
	::= { uxsStatusCPUGroup 7 }

uxsStatusCPUTotalLag OBJECT-TYPE
	SYNTAX  INTEGER
	ACCESS  read-write
	STATUS  mandatory
	DESCRIPTION
		"&<caiUxOs.283>The number of times that the threshold has to be reached before the state changes. Valid range: Greater than 0."
	::= { uxsStatusCPUGroup 8 }

uxsStatusCPUTotalWarn OBJECT-TYPE
	SYNTAX  DisplayString
	ACCESS  read-write
	STATUS  mandatory
	DESCRIPTION
		"&<caiUxOs.284>The percentage of total CPU usage that is considered a warning level for that resource. Valid ranges: Greater than 0, less than 99, not greater than or equal to the critical threshold."
	::= { uxsStatusCPUGroup 9 }

uxsStatusCPUTotalCrit OBJECT-TYPE
	SYNTAX  DisplayString
	ACCESS  read-write
	STATUS  mandatory
	DESCRIPTION
		"&<caiUxOs.285>The percentage of total CPU usage that is considered a critical level for that resource. Valid ranges: Greater than 1, less than 100, not less than or equal to the warning threshold."
	::= { uxsStatusCPUGroup 10 }

uxsStatusCPUTotalMonitor OBJECT-TYPE
	SYNTAX  INTEGER {
		do-not-monitor(1),
		warning-only(2),
		critical-only(3),
		both(4)
	}
	ACCESS  read-write
	STATUS  mandatory
	DESCRIPTION
		"&<caiUxOs.286>Defines the level of monitoring for the resource's status. Valid values: do-not-monitor(1), warning-only(2), critical-only(3) or both(4)."
	::= { uxsStatusCPUGroup 11 }

uxsStatusCPUTotalStatus OBJECT-TYPE
	SYNTAX  INTEGER {
		unknown(1),
		ok(2),
		warning(3),
		critical(4)
	}
	ACCESS  read-only
	STATUS  mandatory
	DESCRIPTION
		"&<caiUxOs.287>The current status of the resource: unknown(1) - An error occurred during data collection, ok(2) - The resource is within the defined limits, warning(3) - The resource has breached the warning threshold, critical(4) - The resource has breached the critical threshold."
	::= { uxsStatusCPUGroup 12 }

uxsStatusCPUCount OBJECT-TYPE
	SYNTAX  INTEGER
	ACCESS  read-only
	STATUS  mandatory
	DESCRIPTION
		"&<caiUxOs.288>The number of CPU instances in the table."
	::= { uxsStatusCPUGroup 13 }

uxsStatusCPUTable OBJECT-TYPE
	SYNTAX  SEQUENCE OF UxsStatusCPUSequence
	ACCESS  not-accessible
	STATUS  mandatory
	DESCRIPTION
		"&<caiUxOs.289>The table of CPU instances."
	::= { uxsStatusCPUGroup 14 }

uxsStatusCPUTotalCallBackRef OBJECT-TYPE
	SYNTAX DisplayString
	ACCESS read-only
	STATUS mandatory
	DESCRIPTION
		"&<caiUxOs.731>The name of the Call-Back reference that should be invoked in case of a status change."
	::= { uxsStatusCPUGroup 15 }

--
-- uxsStatusCPUTable
--
uxsStatusCPUEntry OBJECT-TYPE
	SYNTAX  UxsStatusCPUSequence
	ACCESS  not-accessible
	STATUS  mandatory
	DESCRIPTION
		"&<caiUxOs.290>"
	INDEX   { uxsStatusCPUName }
	::= { uxsStatusCPUTable 1 }

UxsStatusCPUSequence ::=
	SEQUENCE {
		uxsStatusCPUName	    DisplayString,
		uxsStatusCPUUser	    INTEGER,
		uxsStatusCPUSys		    INTEGER,
		uxsStatusCPUIdle	    INTEGER,
		uxsStatusCPUWIO		    INTEGER,
		uxsStatusCPUAggStatus       INTEGER,
		uxsStatusCPUUsedValue	    INTEGER,
		uxsStatusCPULagValue	    INTEGER,
		uxsStatusCPULag		    INTEGER,
		uxsStatusCPUWarn	    INTEGER,
		uxsStatusCPUCrit	    INTEGER,
		uxsStatusCPUMonitor	    INTEGER,
		uxsStatusCPUStatus	    INTEGER,
		uxsStatusCPULossAction      INTEGER,
		uxsStatusCPULossStatus      INTEGER,
		uxsStatusCPUCallBackRef	DisplayString
	}

--
-- uxsStatusCPUEntry
--
uxsStatusCPUName OBJECT-TYPE
	SYNTAX  DisplayString
	ACCESS  read-only
	STATUS  mandatory
	DESCRIPTION
		"&<caiUxOs.291>The name the agent gives the first CPU on which it gets details. No assumptions should be made about which slot the CPU is in from the CPU name."
	::= { uxsStatusCPUEntry 1 }

uxsStatusCPUUser OBJECT-TYPE
	SYNTAX  INTEGER
	ACCESS  read-only
	STATUS  mandatory
	DESCRIPTION
		"&<caiUxOs.292>The percentage of time that the processor was doing user work."
	::= { uxsStatusCPUEntry 2 }

uxsStatusCPUSys OBJECT-TYPE
	SYNTAX  INTEGER
	ACCESS  read-only
	STATUS  mandatory
	DESCRIPTION
		"&<caiUxOs.293>The percentage of time that the processor was doing system work."
	::= { uxsStatusCPUEntry 3 }

uxsStatusCPUIdle OBJECT-TYPE
	SYNTAX  INTEGER
	ACCESS  read-only
	STATUS  mandatory
	DESCRIPTION
		"&<caiUxOs.294>The percentage of time that the processor was idle."
	::= { uxsStatusCPUEntry 4 }

uxsStatusCPUWIO OBJECT-TYPE
	SYNTAX  INTEGER
	ACCESS  read-only
	STATUS  mandatory
	DESCRIPTION
		"&<caiUxOs.295>The percentage of time that the processor was waiting for I/O."
	::= { uxsStatusCPUEntry 5 }

uxsStatusCPUAggStatus OBJECT-TYPE
        SYNTAX  INTEGER {
                unknown(1),
                ok(2),
                warning(3),
                critical(4),
                down(5)
        }
        ACCESS  read-only
        STATUS  mandatory
        DESCRIPTION
                "&<caiUxOs.296>The current status of the resource: unknown(1) - An error occurred during data collection, ok(2) - The resource is within the defined limits, warning(3) - The resource has breached the warning threshold, critical(4) - The resource has breached the critical threshold, down(5) - The resource is in a down state."
        ::= { uxsStatusCPUEntry 6 }

uxsStatusCPUUsedValue OBJECT-TYPE
	SYNTAX  INTEGER
	ACCESS  read-only
	STATUS  mandatory
	DESCRIPTION
		"&<caiUxOs.297>The percentage of time that the processor was busy. i.e. 100 - idle% - iowait%."
	::= { uxsStatusCPUEntry 7 }

uxsStatusCPULagValue OBJECT-TYPE
	SYNTAX  INTEGER
	ACCESS  read-only
	STATUS  mandatory
	DESCRIPTION
		"&<caiUxOs.298>The number of times that the threshold has been reached."
	::= { uxsStatusCPUEntry 8 }

uxsStatusCPULag OBJECT-TYPE
	SYNTAX  INTEGER
	ACCESS  read-write
	STATUS  mandatory
	DESCRIPTION
		"&<caiUxOs.299>The number of times that the threshold has to be reached before the state changes. Valid range: Greater than 0."
	::= { uxsStatusCPUEntry 9 }

uxsStatusCPUWarn OBJECT-TYPE
	SYNTAX  DisplayString
	ACCESS  read-write
	STATUS  mandatory
	DESCRIPTION
		"&<caiUxOs.300>The value for the CPU used percentage that is considered a warning level for that resource. Valid ranges: Greater than 0, less than 99, not greater than or equal to the critical threshold."
	::= { uxsStatusCPUEntry 10 }

uxsStatusCPUCrit OBJECT-TYPE
	SYNTAX  DisplayString
	ACCESS  read-write
	STATUS  mandatory
	DESCRIPTION
		"&<caiUxOs.301>The value for the CPU used percentage that is considered a critical level for that resource. Valid ranges: Greater than 1, less than 100, not less than or equal to the warning threshold."
	::= { uxsStatusCPUEntry 11 }

uxsStatusCPUMonitor OBJECT-TYPE
	SYNTAX  INTEGER {
		do-not-monitor(1),
		warning-only(2),
		critical-only(3),
		both(4)
	}
	ACCESS  read-write
	STATUS  mandatory
	DESCRIPTION
		"&<caiUxOs.302>Defines the level of monitoring for the resource's status. Valid values: do-not-monitor(1), warning-only(2), critical-only(3) or both(4)."
	::= { uxsStatusCPUEntry 12 }

uxsStatusCPUStatus OBJECT-TYPE
	SYNTAX  INTEGER {
		unknown(1),
		ok(2),
		warning(3),
		critical(4)
	}
	ACCESS  read-only
	STATUS  mandatory
	DESCRIPTION
		"&<caiUxOs.303>The current status of the resource: unknown(1) - An error occurred during data collection, ok(2) - The resource is within the defined limits, warning(3) - The resource has breached the warning threshold, critical(4) - The resource has breached the critical threshold."
	::= { uxsStatusCPUEntry 13 }

uxsStatusCPULossAction OBJECT-TYPE
	SYNTAX  INTEGER {
		remove(1),
		up(2),
		down(3)
	}
	ACCESS  read-write
	STATUS  mandatory
	DESCRIPTION
		"&<caiUxOs.304>Defines the action to take if the CPU is removed from the machine. Valid values: remove(1), up(2) or down(3)."
	::= { uxsStatusCPUEntry 14 }

uxsStatusCPULossStatus OBJECT-TYPE
	SYNTAX  INTEGER {
		unknown(1),
		up(2),
		down(3)
	}
	ACCESS  read-only
	STATUS  mandatory
	DESCRIPTION
		"&<caiUxOs.305>The status relating to the existence of the object. Valid values: unknown(1), up(2) or down(3)."
	::= { uxsStatusCPUEntry 15 }

uxsStatusCPUCallBackRef OBJECT-TYPE
	SYNTAX DisplayString
	ACCESS read-only
	STATUS mandatory
	DESCRIPTION
		"&<caiUxOs.731>The name of the Call-Back reference that should be invoked in case of a status change."
	::= { uxsStatusCPUEntry 16 }

--
-- uxsStatusLoadGroup
--
uxsStatusLoad1MinValue OBJECT-TYPE
	SYNTAX  DisplayString
	ACCESS  read-only
	STATUS  mandatory
	DESCRIPTION
		"&<caiUxOs.306>The current 1 minute average value."
	::= { uxsStatusLoadGroup 1 }

uxsStatusLoad1MinWarn OBJECT-TYPE
	SYNTAX  DisplayString
	ACCESS  read-write
	STATUS  mandatory
	DESCRIPTION
		"&<caiUxOs.307>The value for load average that is considered a warning level for that resource. Valid ranges: Greater than 0.000000, not greater than or equal to the critical threshold."
	::= { uxsStatusLoadGroup 2 }

uxsStatusLoad1MinCrit OBJECT-TYPE
	SYNTAX  DisplayString
	ACCESS  read-write
	STATUS  mandatory
	DESCRIPTION
		"&<caiUxOs.308>The value for load average that is considered a critical level for that resource. Valid ranges: Greater than 0.000001, not less than or equal to the warning threshold."
	::= { uxsStatusLoadGroup 3 }

uxsStatusLoad1MinMonitor OBJECT-TYPE
	SYNTAX  INTEGER {
		do-not-monitor(1),
		warning-only(2),
		critical-only(3),
		both(4)
	}
	ACCESS  read-write
	STATUS  mandatory
	DESCRIPTION
		"&<caiUxOs.309>Defines the level of monitoring for the resource's status. Valid values: do-not-monitor(1), warning-only(2), critical-only(3) or both(4)."
	::= { uxsStatusLoadGroup 4 }

uxsStatusLoad1MinStatus OBJECT-TYPE
	SYNTAX  INTEGER {
		unknown(1),
		ok(2),
		warning(3),
		critical(4)
	}
	ACCESS  read-only
	STATUS  mandatory
	DESCRIPTION
		"&<caiUxOs.310>The current status of the resource: unknown(1) - An error occurred during data collection, ok(2) - The resource is within the defined limits, warning(3) - The resource has breached the warning threshold, critical(4) - The resource has breached the critical threshold."
	::= { uxsStatusLoadGroup 5 }

uxsStatusLoad5MinValue OBJECT-TYPE
	SYNTAX  DisplayString
	ACCESS  read-only
	STATUS  mandatory
	DESCRIPTION
		"&<caiUxOs.311>The current 5 minute average value."
	::= { uxsStatusLoadGroup 6 }

uxsStatusLoad5MinWarn OBJECT-TYPE
	SYNTAX  DisplayString
	ACCESS  read-write
	STATUS  mandatory
	DESCRIPTION
		"&<caiUxOs.312>The value for load average that is considered a warning level for that resource. Valid ranges: Greater than 0.000000, not greater than or equal to the critical threshold."
	::= { uxsStatusLoadGroup 7 }

uxsStatusLoad5MinCrit OBJECT-TYPE
	SYNTAX  DisplayString
	ACCESS  read-write
	STATUS  mandatory
	DESCRIPTION
		"&<caiUxOs.313>The value for load average that is considered a critical level for that resource. Valid ranges: Greater than 0.000001, not less than or equal to the warning threshold."
	::= { uxsStatusLoadGroup 8 }

uxsStatusLoad5MinMonitor OBJECT-TYPE
	SYNTAX  INTEGER {
		do-not-monitor(1),
		warning-only(2),
		critical-only(3),
		both(4)
	}
	ACCESS  read-write
	STATUS  mandatory
	DESCRIPTION
		"&<caiUxOs.314>Defines the level of monitoring for the resource's status. Valid values: do-not-monitor(1), warning-only(2), critical-only(3) or both(4)."
	::= { uxsStatusLoadGroup 9 }

uxsStatusLoad5MinStatus OBJECT-TYPE
	SYNTAX  INTEGER {
		unknown(1),
		ok(2),
		warning(3),
		critical(4)
	}
	ACCESS  read-only
	STATUS  mandatory
	DESCRIPTION
		"&<caiUxOs.315>The current status of the resource: unknown(1) - An error occurred during data collection, ok(2) - The resource is within the defined limits, warning(3) - The resource has breached the warning threshold, critical(4) - The resource has breached the critical threshold."
	::= { uxsStatusLoadGroup 10 }

uxsStatusLoad15MinValue OBJECT-TYPE
	SYNTAX  DisplayString
	ACCESS  read-only
	STATUS  mandatory
	DESCRIPTION
		"&<caiUxOs.316>The current 15 minute average value."
	::= { uxsStatusLoadGroup 11 }

uxsStatusLoad15MinWarn OBJECT-TYPE
	SYNTAX  DisplayString
	ACCESS  read-write
	STATUS  mandatory
	DESCRIPTION
		"&<caiUxOs.317>The value for load average that is considered a warning level for that resource. Valid ranges: Greater than 0.000000, not greater than or equal to the critical threshold."
	::= { uxsStatusLoadGroup 12 }

uxsStatusLoad15MinCrit OBJECT-TYPE
	SYNTAX  DisplayString
	ACCESS  read-write
	STATUS  mandatory
	DESCRIPTION
		"&<caiUxOs.318>The value for load average that is considered a critical level for that resource. Valid ranges: Greater than 0.000001, not less than or equal to the warning threshold."
	::= { uxsStatusLoadGroup 13 }

uxsStatusLoad15MinMonitor OBJECT-TYPE
	SYNTAX  INTEGER {
		do-not-monitor(1),
		warning-only(2),
		critical-only(3),
		both(4)
	}
	ACCESS  read-write
	STATUS  mandatory
	DESCRIPTION
		"&<caiUxOs.319>Defines the level of monitoring for the resource's status. Valid values: do-not-monitor(1), warning-only(2), critical-only(3) or both(4)."
	::= { uxsStatusLoadGroup 14 }

uxsStatusLoad15MinStatus OBJECT-TYPE
	SYNTAX  INTEGER {
		unknown(1),
		ok(2),
		warning(3),
		critical(4)
	}
	ACCESS  read-only
	STATUS  mandatory
	DESCRIPTION
		"&<caiUxOs.320>The current status of the resource: unknown(1) - An error occurred during data collection, ok(2) - The resource is within the defined limits, warning(3) - The resource has breached the warning threshold, critical(4) - The resource has breached the critical threshold."
	::= { uxsStatusLoadGroup 15 }

uxsStatusLoadCallBackRef OBJECT-TYPE
	SYNTAX DisplayString
	ACCESS read-only
	STATUS mandatory
	DESCRIPTION
		"&<caiUxOs.731>The name of the Call-Back reference that should be invoked in case of a status change."
	::= { uxsStatusLoadGroup 16 }

--
-- uxsStatusMemGroup
--
uxsStatusMemTotal OBJECT-TYPE
	SYNTAX  INTEGER
	ACCESS  read-only
	STATUS  mandatory
	DESCRIPTION
		"&<caiUxOs.321>The total memory configured on the machine in kilobytes."
	::= { uxsStatusMemGroup 1 }

uxsStatusMemValue OBJECT-TYPE
	SYNTAX  INTEGER
	ACCESS  read-only
	STATUS  mandatory
	DESCRIPTION
		"&<caiUxOs.322>The memory used by the machine in kilobytes."
	::= { uxsStatusMemGroup 2 }

uxsStatusMemLagValue OBJECT-TYPE
	SYNTAX  INTEGER
	ACCESS  read-only
	STATUS  mandatory
	DESCRIPTION
		"&<caiUxOs.323>The number of times that the threshold has been reached."
	::= { uxsStatusMemGroup 3 }

uxsStatusMemLag OBJECT-TYPE
	SYNTAX  INTEGER
	ACCESS  read-write
	STATUS  mandatory
	DESCRIPTION
		"&<caiUxOs.324>The number of times that the threshold has to be reached before the state changes. Valid range: Greater than 0."
	::= { uxsStatusMemGroup 4 }

uxsStatusMemWarnValue OBJECT-TYPE
	SYNTAX  DisplayString
	ACCESS  read-only
	STATUS  mandatory
	DESCRIPTION
		"&<caiUxOs.325>The absolute value used for threshold calculation based on the configured warning value."
	::= { uxsStatusMemGroup 5 }

uxsStatusMemCritValue OBJECT-TYPE
	SYNTAX  DisplayString
	ACCESS  read-only
	STATUS  mandatory
	DESCRIPTION
		"&<caiUxOs.326>The absolute value used for threshold calculation based on the configured critical value."
	::= { uxsStatusMemGroup 6 }

uxsStatusMemWarn OBJECT-TYPE
	SYNTAX  DisplayString
	ACCESS  read-write
	STATUS  mandatory
	DESCRIPTION
		"&<caiUxOs.327>The value for used memory, either as a percentage or in kilobytes, that is considered a warning level for that resource. Valid ranges: Greater than 0, less than total memory - 1, not greater than or equal to the critical threshold."
	::= { uxsStatusMemGroup 7 }

uxsStatusMemCrit OBJECT-TYPE
	SYNTAX  DisplayString
	ACCESS  read-write
	STATUS  mandatory
	DESCRIPTION
		"&<caiUxOs.328>The value for used memory, either as a percentage or in kilobytes, that is considered a critical level for that resource. Valid ranges: Greater than 1, less than total memory, not less than or equal to the warning threshold."
	::= { uxsStatusMemGroup 8 }

uxsStatusMemMonitor OBJECT-TYPE
	SYNTAX  INTEGER {
		do-not-monitor(1),
		warning-only(2),
		critical-only(3),
		both(4)
	}
	ACCESS  read-write
	STATUS  mandatory
	DESCRIPTION
		"&<caiUxOs.329>Defines the level of monitoring for the resource's status. Valid values: do-not-monitor(1), warning-only(2), critical-only(3) or both(4)."
	::= { uxsStatusMemGroup 9 }

uxsStatusMemStatus OBJECT-TYPE
	SYNTAX  INTEGER {
		unknown(1),
		ok(2),
		warning(3),
		critical(4)
	}
	ACCESS  read-only
	STATUS  mandatory
	DESCRIPTION
		"&<caiUxOs.330>The current status of the resource: unknown(1) - An error occurred during data collection, ok(2) - The resource is within the defined limits, warning(3) - The resource has breached the warning threshold, critical(4) - The resource has breached the critical threshold."
	::= { uxsStatusMemGroup 10 }

uxsStatusMemCallBackRef OBJECT-TYPE
	SYNTAX DisplayString
	ACCESS read-only
	STATUS mandatory
	DESCRIPTION
		"&<caiUxOs.731>The name of the Call-Back reference that should be invoked in case of a status change."
	::= { uxsStatusMemGroup 11 }

--
-- uxsStatusSwapGroup
--
uxsStatusSwapTotalName OBJECT-TYPE
	SYNTAX  DisplayString
	ACCESS  read-only
	STATUS  mandatory
	DESCRIPTION
		"&<caiUxOs.331>The name the agent gives the total swap information."
	::= { uxsStatusSwapGroup 1 }

uxsStatusSwapTotalAvailable OBJECT-TYPE
	SYNTAX  INTEGER
	ACCESS  read-only
	STATUS  mandatory
	DESCRIPTION
		"&<caiUxOs.332>The total amount of swap configured on the machine in kilobytes."
	::= { uxsStatusSwapGroup 2 }

uxsStatusSwapTotalUsedValue OBJECT-TYPE
	SYNTAX  INTEGER
	ACCESS  read-only
	STATUS  mandatory
	DESCRIPTION
		"&<caiUxOs.333>The total amount of swap space in use on the machine in kilobytes."
	::= { uxsStatusSwapGroup 3 }

uxsStatusSwapTotalLagValue OBJECT-TYPE
	SYNTAX  INTEGER
	ACCESS  read-only
	STATUS  mandatory
	DESCRIPTION
		"&<caiUxOs.334>The number of times that the threshold has been reached."
	::= { uxsStatusSwapGroup 4 }

uxsStatusSwapTotalLag OBJECT-TYPE
	SYNTAX  INTEGER
	ACCESS  read-write
	STATUS  mandatory
	DESCRIPTION
		"&<caiUxOs.335>The number of times that the threshold has to be reached before the state changes. Valid range: Greater than 0."
	::= { uxsStatusSwapGroup 5 }

uxsStatusSwapTotalWarnValue OBJECT-TYPE
	SYNTAX  DisplayString
	ACCESS  read-only
	STATUS  mandatory
	DESCRIPTION
		"&<caiUxOs.336>The absolute value used for threshold calculation based on the configured warning value."
	::= { uxsStatusSwapGroup 6 }

uxsStatusSwapTotalCritValue OBJECT-TYPE
	SYNTAX  DisplayString
	ACCESS  read-only
	STATUS  mandatory
	DESCRIPTION
		"&<caiUxOs.337>The absolute value used for threshold calculation based on the configured critical value."
	::= { uxsStatusSwapGroup 7 }

uxsStatusSwapTotalWarn OBJECT-TYPE
	SYNTAX  DisplayString
	ACCESS  read-write
	STATUS  mandatory
	DESCRIPTION
		"&<caiUxOs.338>The value for total swap space, either as a percentage or in kilobytes, that is considered a warning level for that resource. Valid ranges: Greater than 0, less than total swap space - 1, not greater than or equal to the critical threshold."
	::= { uxsStatusSwapGroup 8 }

uxsStatusSwapTotalCrit OBJECT-TYPE
	SYNTAX  DisplayString
	ACCESS  read-write
	STATUS  mandatory
	DESCRIPTION
		"&<caiUxOs.339>The value for total swap space, either as a percentage or in kilobytes, that is considered a critical level for that resource. Valid ranges: Greater than 1, less than total swap space, not less than or equal to the warning threshold."
	::= { uxsStatusSwapGroup 9 }

uxsStatusSwapTotalMonitor OBJECT-TYPE
	SYNTAX  INTEGER {
		do-not-monitor(1),
		warning-only(2),
		critical-only(3),
		both(4)
	}
	ACCESS  read-write
	STATUS  mandatory
	DESCRIPTION
		"&<caiUxOs.340>Defines the level of monitoring for the resource's status. Valid values: do-not-monitor(1), warning-only(2), critical-only(3) or both(4)."
	::= { uxsStatusSwapGroup 10 }

uxsStatusSwapTotalStatus OBJECT-TYPE
	SYNTAX  INTEGER {
		unknown(1),
		ok(2),
		warning(3),
		critical(4)
	}
	ACCESS  read-only
	STATUS  mandatory
	DESCRIPTION
		"&<caiUxOs.341>The current status of the resource: unknown(1) - An error occurred during data collection, ok(2) - The resource is within the defined limits, warning(3) - The resource has breached the warning threshold, critical(4) - The resource has breached the critical threshold."
	::= { uxsStatusSwapGroup 11 }

uxsStatusSwapCount OBJECT-TYPE
	SYNTAX  INTEGER
	ACCESS  read-only
	STATUS  mandatory
	DESCRIPTION
		"&<caiUxOs.342>Number of swap partitions in the swap table."
	::= { uxsStatusSwapGroup 12 }

uxsStatusSwapTable OBJECT-TYPE
	SYNTAX  SEQUENCE OF UxsStatusSwapSequence
	ACCESS  not-accessible
	STATUS  mandatory
	DESCRIPTION
		"&<caiUxOs.343>The table detailing the individual swap devices."
	::= { uxsStatusSwapGroup 13 }

uxsStatusSwapTotalCallBackRef OBJECT-TYPE
	SYNTAX DisplayString
	ACCESS read-only
	STATUS mandatory
	DESCRIPTION
		"&<caiUxOs.731>The name of the Call-Back reference that should be invoked in case of a status change."
	::= { uxsStatusSwapGroup 14 }

--
-- uxsStatusSwapTable
--
uxsStatusSwapEntry OBJECT-TYPE
	SYNTAX	UxsStatusSwapSequence
	ACCESS  not-accessible
	STATUS  mandatory
	DESCRIPTION
		"&<caiUxOs.344>"
	INDEX   { uxsStatusSwapName }
	::= { uxsStatusSwapTable 1 }

UxsStatusSwapSequence ::=
	SEQUENCE {
	    	uxsStatusSwapName	DisplayString,
	    	uxsStatusSwapAggStatus  INTEGER,
	   	uxsStatusSwapAvailable	INTEGER,
	    	uxsStatusSwapUsedValue	INTEGER,
	    	uxsStatusSwapLagValue	INTEGER,
	    	uxsStatusSwapLag	INTEGER,
	    	uxsStatusSwapWarnValue	INTEGER,
	    	uxsStatusSwapCritValue	INTEGER,
	    	uxsStatusSwapWarn	INTEGER,
	    	uxsStatusSwapCrit	INTEGER,
	    	uxsStatusSwapMonitor	INTEGER,
	    	uxsStatusSwapStatus	INTEGER,
	    	uxsStatusSwapLossAction INTEGER,
	    	uxsStatusSwapLossStatus INTEGER,
			uxsStatusSwapCallBackRef	DisplayString
	}

uxsStatusSwapName OBJECT-TYPE
	SYNTAX  DisplayString
	ACCESS  read-only
	STATUS  mandatory
	DESCRIPTION
		"&<caiUxOs.345>The name of the swap device that this watcher monitors."
	::= { uxsStatusSwapEntry 1 }

uxsStatusSwapAggStatus OBJECT-TYPE
	SYNTAX  INTEGER {
		unknown(1),
		ok(2),
		warning(3),
		critical(4),
		down(5)
	}
	ACCESS  read-only
	STATUS  mandatory
	DESCRIPTION
		"&<caiUxOs.346>The current status of the resource: unknown(1) - An error occurred during data collection, ok(2) - The resource is within the defined limits, warning(3) - The resource has breached the warning threshold, critical(4) - The resource has breached the critical threshold, down(5) - The resource is in a down state."
	::= { uxsStatusSwapEntry 2 }

uxsStatusSwapAvailable OBJECT-TYPE
	SYNTAX  INTEGER
	ACCESS  read-only
	STATUS  mandatory
	DESCRIPTION
		"&<caiUxOs.347>The amount of swap configured on the device in kilobytes."
	::= { uxsStatusSwapEntry 3 }

uxsStatusSwapUsedValue OBJECT-TYPE
	SYNTAX  INTEGER
	ACCESS  read-only
	STATUS  mandatory
	DESCRIPTION
		"&<caiUxOs.348>The amount of swap space in use on the device in kilobytes."
	::= { uxsStatusSwapEntry 4 }

uxsStatusSwapLagValue OBJECT-TYPE
	SYNTAX  INTEGER
	ACCESS  read-only
	STATUS  mandatory
	DESCRIPTION
		"&<caiUxOs.349>The number of times that the threshold has been reached."
	::= { uxsStatusSwapEntry 5 }

uxsStatusSwapLag OBJECT-TYPE
	SYNTAX  INTEGER
	ACCESS  read-write
	STATUS  mandatory
	DESCRIPTION
		"&<caiUxOs.350>The number of times that the threshold has to be reached before the state changes. Valid range: Greater than 0."
	::= { uxsStatusSwapEntry 6 }

uxsStatusSwapWarnValue OBJECT-TYPE
	SYNTAX  DisplayString
	ACCESS  read-only
	STATUS  mandatory
	DESCRIPTION
		"&<caiUxOs.351>The absolute value used for threshold calculation based on the configured warning value."
	::= { uxsStatusSwapEntry 7 }

uxsStatusSwapCritValue OBJECT-TYPE
	SYNTAX  DisplayString
	ACCESS  read-only
	STATUS  mandatory
	DESCRIPTION
		"&<caiUxOs.352>The absolute value used for threshold calculation based on the configured critical value."
	::= { uxsStatusSwapEntry 8 }

uxsStatusSwapWarn OBJECT-TYPE
	SYNTAX  DisplayString
	ACCESS  read-write
	STATUS  mandatory
	DESCRIPTION
		"&<caiUxOs.353>The value for device swap space, either as a percentage or in kilobytes, that is considered a warning level for that resource. Valid ranges: Greater than 0, less than device swap space - 1, not greater than or equal to the critical threshold."
	::= { uxsStatusSwapEntry 9 }

uxsStatusSwapCrit OBJECT-TYPE
	SYNTAX  DisplayString
	ACCESS  read-write
	STATUS  mandatory
	DESCRIPTION
		"&<caiUxOs.354>The value for device swap space, either as a percentage or in kilobytes, that is considered a critical level for that resource. Valid ranges: Greater than 1, less than device swap space, not less than or equal to the warning threshold."
	::= { uxsStatusSwapEntry 10 }

uxsStatusSwapMonitor OBJECT-TYPE
	SYNTAX  INTEGER {
		do-not-monitor(1),
		warning-only(2),
		critical-only(3),
		both(4)
	}
	ACCESS  read-write
	STATUS  mandatory
	DESCRIPTION
		"&<caiUxOs.355>Defines the level of monitoring for the resource's status. Valid values: do-not-monitor(1), warning-only(2), critical-only(3) or both(4)."
	::= { uxsStatusSwapEntry 11 }

uxsStatusSwapStatus OBJECT-TYPE
	SYNTAX  INTEGER {
		unknown(1),
		ok(2),
		warning(3),
		critical(4)
	}
	ACCESS  read-only
	STATUS  mandatory
	DESCRIPTION
		"&<caiUxOs.356>The current status of the resource: unknown(1) - An error occurred during data collection, ok(2) - The resource is within the defined limits, warning(3) - The resource has breached the warning threshold, critical(4) - The resource has breached the critical threshold."
	::= { uxsStatusSwapEntry 12 }

uxsStatusSwapLossAction OBJECT-TYPE
	SYNTAX  INTEGER {
		remove(1),
		up(2),
		down(3)
	}
	ACCESS  read-write
	STATUS  mandatory
	DESCRIPTION
		"&<caiUxOs.357>Defines the action to take if the swap file is removed from the machine. Valid values: remove(1), up(2) or down(3)."
	::= { uxsStatusSwapEntry 13 }

uxsStatusSwapLossStatus OBJECT-TYPE
	SYNTAX  INTEGER {
		unknown(1),
		up(2),
		down(3)
	}
	ACCESS  read-only
	STATUS  mandatory
	DESCRIPTION
		"&<caiUxOs.358>The status relating to the existence of the object. Valid values: unknown(1), up(2) or down(3)."
	::= { uxsStatusSwapEntry 14 }

uxsStatusSwapCallBackRef OBJECT-TYPE
	SYNTAX DisplayString
	ACCESS read-only
	STATUS mandatory
	DESCRIPTION
		"&<caiUxOs.731>The name of the Call-Back reference that should be invoked in case of a status change."
	::= { uxsStatusSwapEntry 15 }

--
-- uxsStatusFSysGroup
--
uxsStatusFSysCount OBJECT-TYPE
	SYNTAX  INTEGER
	ACCESS  read-only
	STATUS  mandatory
	DESCRIPTION
		"&<caiUxOs.359>The number of monitored file systems."
	::= { uxsStatusFSysGroup 1 }

uxsStatusFSysTable OBJECT-TYPE
	SYNTAX  SEQUENCE OF UxsStatusFSysSequence
	ACCESS  not-accessible
	STATUS  mandatory
	DESCRIPTION
		"&<caiUxOs.360>The table of monitored file systems."
	::= { uxsStatusFSysGroup 2 }

--
-- uxsStatusFSysTable
--
uxsStatusFSysEntry OBJECT-TYPE
	SYNTAX  UxsStatusFSysSequence
	ACCESS  not-accessible
	STATUS  mandatory
	DESCRIPTION
		"&<caiUxOs.361>"
	INDEX   { uxsStatusFSysName }
	::= { uxsStatusFSysTable 1 }

UxsStatusFSysSequence ::=
	SEQUENCE {
		uxsStatusFSysName 		DisplayString,
		uxsStatusFSysRelatedTo 	    	DisplayString,
		uxsStatusFSysType 		DisplayString,
		uxsStatusFSysStatus 		INTEGER,
		uxsStatusFSysSpaceTotal 	INTEGER,
		uxsStatusFSysSpaceValue 	INTEGER,
		uxsStatusFSysSpaceWarnValue	DisplayString,
		uxsStatusFSysSpaceCritValue	DisplayString,
		uxsStatusFSysSpaceWarn 		DisplayString,
		uxsStatusFSysSpaceCrit	 	DisplayString,
		uxsStatusFSysSpaceMonitor 	INTEGER,
		uxsStatusFSysSpaceStatus 	INTEGER,
		uxsStatusFSysSpaceDValue 	INTEGER,
		uxsStatusFSysSpaceDWarnValue 	DisplayString,
		uxsStatusFSysSpaceDCritValue 	DisplayString,
		uxsStatusFSysSpaceDWarn 	DisplayString,
		uxsStatusFSysSpaceDCrit 	DisplayString,
		uxsStatusFSysSpaceDMonitor 	INTEGER,
		uxsStatusFSysSpaceDStatus 	INTEGER,
		uxsStatusFSysInodesTotal 	INTEGER,
		uxsStatusFSysInodesValue 	INTEGER,
		uxsStatusFSysInodesWarnValue 	DisplayString,
		uxsStatusFSysInodesCritValue 	DisplayString,
		uxsStatusFSysInodesWarn 	DisplayString,
		uxsStatusFSysInodesCrit 	DisplayString,
		uxsStatusFSysInodesMonitor 	INTEGER,
		uxsStatusFSysInodesStatus  	INTEGER,
		uxsStatusFSysInodesDValue 	INTEGER,
		uxsStatusFSysInodesDWarnValue 	DisplayString,
		uxsStatusFSysInodesDCritValue	DisplayString,
		uxsStatusFSysInodesDWarn 	DisplayString,
		uxsStatusFSysInodesDCrit 	DisplayString,
		uxsStatusFSysInodesDMonitor 	INTEGER,
		uxsStatusFSysInodesDStatus 	INTEGER,
		uxsStatusFSysMountedMonitor 	INTEGER,
		uxsStatusFSysMountedStatus 	INTEGER,
		uxsStatusFSysLossAction         INTEGER,
		uxsStatusFSysLossStatus         INTEGER,
		uxsStatusFSysRemove 		INTEGER,
		uxsStatusFSysCallBackRef	DisplayString
	}

uxsStatusFSysName OBJECT-TYPE
	SYNTAX  DisplayString
	ACCESS  read-only
	STATUS  mandatory
	DESCRIPTION
		"&<caiUxOs.362>The file system mount name."
	::= { uxsStatusFSysEntry 1 }

uxsStatusFSysRelatedTo OBJECT-TYPE
	SYNTAX  DisplayString
	ACCESS  read-only
	STATUS  mandatory
	DESCRIPTION
		"&<caiUxOs.363>The device from which the file system is mounted."
	::= { uxsStatusFSysEntry 2 }

uxsStatusFSysType OBJECT-TYPE
	SYNTAX  DisplayString
	ACCESS  read-only
	STATUS  mandatory
	DESCRIPTION
		"&<caiUxOs.364>The type of the mounted file system. The value is platform dependent."
	::= { uxsStatusFSysEntry 3 }

uxsStatusFSysStatus OBJECT-TYPE
	SYNTAX  INTEGER {
		unknown(1),
		ok(2),
		warning(3),
		critical(4),
		down(5)
	}
	ACCESS  read-only
	STATUS  mandatory
	DESCRIPTION
		"&<caiUxOs.365>The current status of the resource: unknown(1) - An error occurred during data collection, ok(2) - The resource is within the defined limits, warning(3) - The resource has breached the warning threshold, critical(4) - The resource has breached the critical threshold, down(5) - The resource is in a down state."
	::= { uxsStatusFSysEntry 4 }

uxsStatusFSysSpaceTotal OBJECT-TYPE
	SYNTAX  INTEGER
	ACCESS  read-only
	STATUS  mandatory
	DESCRIPTION
		"&<caiUxOs.366>The amount of space available on the file system in kilobytes."
	::= { uxsStatusFSysEntry 5 }

uxsStatusFSysSpaceValue OBJECT-TYPE
	SYNTAX  INTEGER
	ACCESS  read-only
	STATUS  mandatory
	DESCRIPTION
		"&<caiUxOs.367>The amount of space used on the file system in kilobytes."
	::= { uxsStatusFSysEntry 6 }

uxsStatusFSysSpaceWarnValue OBJECT-TYPE
	SYNTAX  DisplayString
	ACCESS  read-only
	STATUS  mandatory
	DESCRIPTION
		"&<caiUxOs.368>The absolute value used for threshold calculation based on the configured warning value."
	::= { uxsStatusFSysEntry 7 }

uxsStatusFSysSpaceCritValue OBJECT-TYPE
	SYNTAX  DisplayString
	ACCESS  read-only
	STATUS  mandatory
	DESCRIPTION
		"&<caiUxOs.369>The absolute value used for threshold calculation based on the configured critical value."
	::= { uxsStatusFSysEntry 8 }

uxsStatusFSysSpaceWarn OBJECT-TYPE
	SYNTAX  DisplayString
	ACCESS  read-write
	STATUS  mandatory
	DESCRIPTION
		"&<caiUxOs.370>The value for used file system space, either as a percentage or in kilobytes, that is considered a warning level for that resource. Valid ranges: Greater than 0, less than total space - 1, not greater than or equal to the critical threshold."
	::= { uxsStatusFSysEntry 9 }

uxsStatusFSysSpaceCrit OBJECT-TYPE
	SYNTAX  DisplayString
	ACCESS  read-write
	STATUS  mandatory
	DESCRIPTION
		"&<caiUxOs.371>The value for used file system space, either as a percentage or in kilobytes, that is considered a critical level for that resource. Valid ranges: Greater than 1, less than total space, not less than or equal to the warning threshold."
	::= { uxsStatusFSysEntry 10 }

uxsStatusFSysSpaceMonitor OBJECT-TYPE
	SYNTAX  INTEGER {
		do-not-monitor(1),
		warning-only(2),
		critical-only(3),
		both(4)
	}
	ACCESS  read-write
	STATUS  mandatory
	DESCRIPTION
		"&<caiUxOs.372>Defines the level of monitoring for the resource's status. Valid values: do-not-monitor(1), warning-only(2), critical-only(3) or both(4)."
	::= { uxsStatusFSysEntry 11 }

uxsStatusFSysSpaceStatus OBJECT-TYPE
	SYNTAX  INTEGER {
		unknown(1),
		ok(2),
		warning(3),
		critical(4)
	}
	ACCESS  read-only
	STATUS  mandatory
	DESCRIPTION
		"&<caiUxOs.373>The current status of the resource: unknown(1) - An error occurred during data collection, ok(2) - The resource is within the defined limits, warning(3) - The resource has breached the warning threshold, critical(4) - The resource has breached the critical threshold."
	::= { uxsStatusFSysEntry 12 }

uxsStatusFSysSpaceDValue OBJECT-TYPE
	SYNTAX  INTEGER
	ACCESS  read-only
	STATUS  mandatory
	DESCRIPTION
		"&<caiUxOs.374>The difference of used space, in kilobytes, since the last poll."
	::= { uxsStatusFSysEntry 13 }

uxsStatusFSysSpaceDWarnValue OBJECT-TYPE
	SYNTAX  DisplayString
	ACCESS  read-only
	STATUS  mandatory
	DESCRIPTION
		"&<caiUxOs.375>The absolute value used for threshold calculation based on the configured warning value."
	::= { uxsStatusFSysEntry 14 }

uxsStatusFSysSpaceDCritValue OBJECT-TYPE
	SYNTAX  DisplayString
	ACCESS  read-only
	STATUS  mandatory
	DESCRIPTION
		"&<caiUxOs.376>The absolute value used for threshold calculation based on the configured critical value."
	::= { uxsStatusFSysEntry 15 }

uxsStatusFSysSpaceDWarn OBJECT-TYPE
	SYNTAX  DisplayString
	ACCESS  read-write
	STATUS  mandatory
	DESCRIPTION
		"&<caiUxOs.377>The value for used file system space delta, either as a percentage or in kilobytes, that is considered a warning level for that resource. Valid ranges: Greater than 0, less than total space - 1, not greater than or equal to the critical threshold."
	::= { uxsStatusFSysEntry 16 }

uxsStatusFSysSpaceDCrit OBJECT-TYPE
	SYNTAX  DisplayString
	ACCESS  read-write
	STATUS  mandatory
	DESCRIPTION
		"&<caiUxOs.378>The value for used file system space delta, either as a percentage or in kilobytes, that is considered a critical level for that resource. Valid ranges: Greater than 1, less than total memory, not less than or equal to the warning threshold."
	::= { uxsStatusFSysEntry 17 }

uxsStatusFSysSpaceDMonitor OBJECT-TYPE
	SYNTAX  INTEGER {
		do-not-monitor(1),
		warning-only(2),
		critical-only(3),
		both(4)
	}
	ACCESS  read-write
	STATUS  mandatory
	DESCRIPTION
		"&<caiUxOs.379>Defines the level of monitoring for the resource's status. Valid values: do-not-monitor(1), warning-only(2), critical-only(3) or both(4)."
	::= { uxsStatusFSysEntry 18 }

uxsStatusFSysSpaceDStatus OBJECT-TYPE
	SYNTAX  INTEGER {
		unknown(1),
		ok(2),
		warning(3),
		critical(4)
	}
	ACCESS  read-only
	STATUS  mandatory
	DESCRIPTION
		"&<caiUxOs.380>The current status of the resource: unknown(1) - An error occurred during data collection, ok(2) - The resource is within the defined limits, warning(3) - The resource has breached the warning threshold, critical(4) - The resource has breached the critical threshold."
	::= { uxsStatusFSysEntry 19 }

uxsStatusFSysInodesTotal OBJECT-TYPE
	SYNTAX  INTEGER
	ACCESS  read-only
	STATUS  mandatory
	DESCRIPTION
		"&<caiUxOs.381>The amount of inodes configured on the file system."
	::= { uxsStatusFSysEntry 20 }

uxsStatusFSysInodesValue OBJECT-TYPE
	SYNTAX  INTEGER
	ACCESS  read-only
	STATUS  mandatory
	DESCRIPTION
		"&<caiUxOs.382>The amount of used inodes on the file system."
	::= { uxsStatusFSysEntry 21 }

uxsStatusFSysInodesWarnValue OBJECT-TYPE
	SYNTAX  DisplayString
	ACCESS  read-only
	STATUS  mandatory
	DESCRIPTION
		"&<caiUxOs.383>The absolute value used for threshold calculation based on the configured warning value."
	::= { uxsStatusFSysEntry 22 }

uxsStatusFSysInodesCritValue OBJECT-TYPE
	SYNTAX  DisplayString
	ACCESS  read-only
	STATUS  mandatory
	DESCRIPTION
		"&<caiUxOs.384>The absolute value used for threshold calculation based on the configured critical value."
	::= { uxsStatusFSysEntry 23 }

uxsStatusFSysInodesWarn OBJECT-TYPE
	SYNTAX  DisplayString
	ACCESS  read-write
	STATUS  mandatory
	DESCRIPTION
		"&<caiUxOs.385>The value for inodes, either as a percentage or absolute value, that is considered a warning level for that resource. Valid ranges: Greater than 0, less than total inodes - 1, not greater than or equal to the critical threshold."
	::= { uxsStatusFSysEntry 24 }

uxsStatusFSysInodesCrit OBJECT-TYPE
	SYNTAX  DisplayString
	ACCESS  read-write
	STATUS  mandatory
	DESCRIPTION
		"&<caiUxOs.386>The value for inodes, either as a percentage or absolute value, that is considered a critical level for that resource. Valid ranges: Greater than 1, less than total space, not less than or equal to the warning threshold."
	::= { uxsStatusFSysEntry 25 }

uxsStatusFSysInodesMonitor OBJECT-TYPE
	SYNTAX  INTEGER {
		do-not-monitor(1),
		warning-only(2),
		critical-only(3),
		both(4)
	}
	ACCESS  read-write
	STATUS  mandatory
	DESCRIPTION
		"&<caiUxOs.387>Defines the level of monitoring for the resource's status. Valid values: do-not-monitor(1), warning-only(2), critical-only(3) or both(4)."
	::= { uxsStatusFSysEntry 26 }

uxsStatusFSysInodesStatus OBJECT-TYPE
	SYNTAX   INTEGER {
		unknown(1),
		ok(2),
		warning(3),
		critical(4)
	}
	ACCESS  read-only
	STATUS  mandatory
	DESCRIPTION
		"&<caiUxOs.388>The current status of the resource: unknown(1) - An error occurred during data collection, ok(2) - The resource is within the defined limits, warning(3) - The resource has breached the warning threshold, critical(4) - The resource has breached the critical threshold."
	::= { uxsStatusFSysEntry 27 }

uxsStatusFSysInodesDValue OBJECT-TYPE
	SYNTAX  INTEGER
	ACCESS  read-only
	STATUS  mandatory
	DESCRIPTION
		"&<caiUxOs.389>The difference in the number of used inodes since the last poll."
	::= { uxsStatusFSysEntry 28 }

uxsStatusFSysInodesDWarnValue OBJECT-TYPE
	SYNTAX  DisplayString
	ACCESS  read-only
	STATUS  mandatory
	DESCRIPTION
		"&<caiUxOs.390>The absolute value used for threshold calculation based on the configured warning value."
	::= { uxsStatusFSysEntry 29 }

uxsStatusFSysInodesDCritValue OBJECT-TYPE
	SYNTAX  DisplayString
	ACCESS  read-only
	STATUS  mandatory
	DESCRIPTION
		"&<caiUxOs.391>The absolute value used for threshold calculation based on the configured critical value."
	::= { uxsStatusFSysEntry 30 }

uxsStatusFSysInodesDWarn OBJECT-TYPE
	SYNTAX  DisplayString
	ACCESS  read-write
	STATUS  mandatory
	DESCRIPTION
		"&<caiUxOs.392>The value for inodes delta, either as a percentage or absolute value, that is considered a warning level for that resource. Valid ranges: Greater than 0, less than total inodes - 1, not greater than or equal to the critical threshold."
	::= { uxsStatusFSysEntry 31 }

uxsStatusFSysInodesDCrit OBJECT-TYPE
	SYNTAX  DisplayString
	ACCESS  read-write
	STATUS  mandatory
	DESCRIPTION
		"&<caiUxOs.393>The value for inodes delta, either as a percentage or absolute value, that is considered a critical level for that resource. Valid ranges: Greater than 1, less than total space, not less than or equal to the warning threshold."
	::= { uxsStatusFSysEntry 32 }

uxsStatusFSysInodesDMonitor OBJECT-TYPE
	SYNTAX  INTEGER {
		do-not-monitor(1),
		warning-only(2),
		critical-only(3),
		both(4)
	}
	ACCESS  read-write
	STATUS  mandatory
	DESCRIPTION
		"&<caiUxOs.394>Defines the level of monitoring for the resource's status. Valid values: do-not-monitor(1), warning-only(2), critical-only(3) or both(4)."
	::= { uxsStatusFSysEntry 33 }

uxsStatusFSysInodesDStatus OBJECT-TYPE
	SYNTAX  INTEGER {
		unknown(1),
		ok(2),
		warning(3),
		critical(4)
	}
	ACCESS  read-only
	STATUS  mandatory
	DESCRIPTION
		"&<caiUxOs.395>The current status of the resource: unknown(1) - An error occurred during data collection, ok(2) - The resource is within the defined limits, warning(3) - The resource has breached the warning threshold, critical(4) - The resource has breached the critical threshold."
	::= { uxsStatusFSysEntry 34 }

uxsStatusFSysMountedMonitor OBJECT-TYPE
	SYNTAX  INTEGER {
		do-not-monitor(1),
		monitor(2)
	}
	ACCESS  read-write
	STATUS  mandatory
	DESCRIPTION
		"&<caiUxOs.396>Defines the level of monitoring for the resource's status. Valid values: do-not-monitor(1) or monitor(2)."
	::= { uxsStatusFSysEntry 35 }

uxsStatusFSysMountedStatus OBJECT-TYPE
	SYNTAX  INTEGER {
		unknown(1),
		up(2),
		down(3)
	}
	ACCESS  read-only
	STATUS  mandatory
	DESCRIPTION
		"&<caiUxOs.397>The mounted status of the device: unknown(1) - An error occurred collecting the file system information. up(2) - The file system is mounted, down(3) The file system is not mounted."
	::= { uxsStatusFSysEntry 36 }

uxsStatusFSysLossAction OBJECT-TYPE
	SYNTAX  INTEGER {
		remove(1),
		up(2),
		down(3)
	}
	ACCESS  read-write
	STATUS  mandatory
	DESCRIPTION
		"&<caiUxOs.398>Defines the action to take if the file system is removed from the file system table. Valid values: remove(1), up(2) or down(3)."
	::= { uxsStatusFSysEntry 37 }

uxsStatusFSysLossStatus OBJECT-TYPE
	SYNTAX  INTEGER {
		unknown(1),
		up(2),
		down(3)
	}
	ACCESS  read-only
	STATUS  mandatory
	DESCRIPTION
		"&<caiUxOs.399>The status relating to the existence of the object. Valid values: unknown(1), up(2) or down(3)."
	::= { uxsStatusFSysEntry 38 }

uxsStatusFSysRemove OBJECT-TYPE
	SYNTAX  INTEGER {
		none(1),
		remove(2)
	}
	ACCESS  read-write
	STATUS  mandatory
	DESCRIPTION
		"&<caiUxOs.400>Removes the file system watcher from the agent."
	::= { uxsStatusFSysEntry 39 }

uxsStatusFSysCallBackRef OBJECT-TYPE
	SYNTAX DisplayString
	ACCESS read-only
	STATUS mandatory
	DESCRIPTION
		"&<caiUxOs.731>The name of the Call-Back reference that should be invoked in case of a status change."
	::= { uxsStatusFSysEntry 40 }

--
-- uxsStatusDiskGroup
--
uxsStatusDiskCount OBJECT-TYPE
	SYNTAX  INTEGER
	ACCESS  read-only
	STATUS  mandatory
	DESCRIPTION
		"&<caiUxOs.401>The number of physical disks monitored by the agent."
	::= { uxsStatusDiskGroup 1 }

uxsStatusDiskTable OBJECT-TYPE
	SYNTAX  SEQUENCE OF UxsStatusDiskSequence
	ACCESS  not-accessible
	STATUS  mandatory
	DESCRIPTION
		"&<caiUxOs.402>The table of monitored physical disks."
	::= { uxsStatusDiskGroup 2 }

--
-- uxsStatusDiskTable
--

uxsStatusDiskEntry OBJECT-TYPE
	SYNTAX  UxsStatusDiskSequence
	ACCESS  not-accessible
	STATUS  mandatory
	DESCRIPTION
		"&<caiUxOs.403>"
	INDEX   { uxsStatusDiskName }
	::= { uxsStatusDiskTable 1 }

UxsStatusDiskSequence ::=
	SEQUENCE {
		uxsStatusDiskName 		DisplayString,
		uxsStatusDiskAggStatus 	    	INTEGER,
		uxsStatusDiskTPutValue 		INTEGER,
		uxsStatusDiskTPutWarn 		INTEGER,
		uxsStatusDiskTPutCrit 		INTEGER,
		uxsStatusDiskTPutMonitor 	INTEGER,
		uxsStatusDiskTPutStatus 	INTEGER,
		uxsStatusDiskLossAction 	INTEGER,
		uxsStatusDiskLossStatus 	INTEGER,
		uxsStatusDiskRemove 		INTEGER,
		uxsStatusDiskCallBackRef	DisplayString
	}

uxsStatusDiskName OBJECT-TYPE
	SYNTAX  DisplayString
	ACCESS  read-only
	STATUS  mandatory
	DESCRIPTION
		"&<caiUxOs.404>The device name of the physical disk that is being monitored."
	::= { uxsStatusDiskEntry 1 }

uxsStatusDiskAggStatus OBJECT-TYPE
	SYNTAX  INTEGER {
		unknown(1),
		ok(2),
		warning(3),
		critical(4),
		down(5)
	}
	ACCESS  read-only
	STATUS  mandatory
	DESCRIPTION
		"&<caiUxOs.405>The current status of the resource: unknown(1) - An error occurred during data collection, ok(2) - The resource is within the defined limits, warning(3) - The resource has breached the warning threshold, critical(4) - The resource has breached the critical threshold, down(5) - The resource is in a down state."
	::= { uxsStatusDiskEntry 2 }

uxsStatusDiskTPutValue OBJECT-TYPE
	SYNTAX  INTEGER
	ACCESS  read-only
	STATUS  mandatory
	DESCRIPTION
		"&<caiUxOs.406>The kilobytes in blocks per second."
	::= { uxsStatusDiskEntry 3 }

uxsStatusDiskTPutWarn OBJECT-TYPE
	SYNTAX  INTEGER
	ACCESS  read-write
	STATUS  mandatory
	DESCRIPTION
		"&<caiUxOs.407>The value for physical disk kilobytes per second throughput that is considered a warning level for that resource. Valid ranges: Greater than 0, not greater than or equal to the critical threshold."
	::= { uxsStatusDiskEntry 4 }

uxsStatusDiskTPutCrit OBJECT-TYPE
	SYNTAX  INTEGER
	ACCESS  read-write
	STATUS  mandatory
	DESCRIPTION
		"&<caiUxOs.408>The value for physical disk kilobytes per second throughput that is considered a critical level for that resource. Valid ranges: Greater than 1, not less than or equal to the warning threshold."
	::= { uxsStatusDiskEntry 5 }

uxsStatusDiskTPutMonitor OBJECT-TYPE
	SYNTAX  INTEGER {
		do-not-monitor(1),
		warning-only(2),
		critical-only(3),
		both(4)
	}
	ACCESS  read-write
	STATUS  mandatory
	DESCRIPTION
		"&<caiUxOs.409>Defines the level of monitoring for the resource's status. Valid values: do-not-monitor(1), warning-only(2), critical-only(3) or both(4)."
	::= { uxsStatusDiskEntry 6 }

uxsStatusDiskTPutStatus OBJECT-TYPE
	SYNTAX  INTEGER {
		unknown(1),
		ok(2),
		warning(3),
		critical(4)
	}
	ACCESS  read-only
	STATUS  mandatory
	DESCRIPTION
		"&<caiUxOs.410>The current status of the resource: unknown(1) - An error occurred during data collection, ok(2) - The resource is within the defined limits, warning(3) - The resource has breached the warning threshold, critical(4) - The resource has breached the critical threshold."
	::= { uxsStatusDiskEntry 7 }

uxsStatusDiskLossAction OBJECT-TYPE
	SYNTAX  INTEGER {
		remove(1),
		up(2),
		down(3)
	}
	ACCESS  read-write
	STATUS  mandatory
	DESCRIPTION
		"&<caiUxOs.411>Defines the action to take if the physical disk is removed from the machine. Valid values: remove(1), up(2) or down(3)."
	::= { uxsStatusDiskEntry 8 }

uxsStatusDiskLossStatus OBJECT-TYPE
	SYNTAX  INTEGER {
		unknown(1),
		up(2),
		down(3)
	}
	ACCESS  read-only
	STATUS  mandatory
	DESCRIPTION
		"&<caiUxOs.412>The status relating to the existence of the object. Valid values: unknown(1), up(2) or down(3)."
	::= { uxsStatusDiskEntry 9 }

uxsStatusDiskRemove OBJECT-TYPE
	SYNTAX  INTEGER {
		none(1),
		remove(2)
	}
	ACCESS  read-write
	STATUS  mandatory
	DESCRIPTION
		"&<caiUxOs.413>Removes the physical disk watcher from the agent."
	::= { uxsStatusDiskEntry 10 }

uxsStatusDiskCallBackRef OBJECT-TYPE
	SYNTAX DisplayString
	ACCESS read-only
	STATUS mandatory
	DESCRIPTION
		"&<caiUxOs.731>The name of the Call-Back reference that should be invoked in case of a status change."
	::= { uxsStatusDiskEntry 11 }

--
-- uxsStatusFileGroup
--
uxsStatusFileCount OBJECT-TYPE
	SYNTAX  INTEGER
	ACCESS  read-only
	STATUS  mandatory
	DESCRIPTION
		"&<caiUxOs.414>The number of file watchers configured for the agent."
	::= { uxsStatusFileGroup 1 }

uxsStatusFileTable OBJECT-TYPE
	SYNTAX  SEQUENCE OF UxsStatusFileSequence
	ACCESS  not-accessible
	STATUS  mandatory
	DESCRIPTION
		"&<caiUxOs.415>The table of file watchers."
	::= { uxsStatusFileGroup 2 }

--
-- uxsStatusFileTable
--
uxsStatusFileEntry OBJECT-TYPE
	SYNTAX  UxsStatusFileSequence
	ACCESS  not-accessible
	STATUS  mandatory
	DESCRIPTION
		"&<caiUxOs.416>"
	INDEX   { uxsStatusFileName }
	::= { uxsStatusFileTable 1 }

UxsStatusFileSequence ::=
	SEQUENCE {
		uxsStatusFileName 		DisplayString,
		uxsStatusFileDesc 		DisplayString,
		uxsStatusFileStatus 		INTEGER,
		uxsStatusFileExist 		INTEGER,
		uxsStatusFileExistMonitor 	INTEGER,
		uxsStatusFileExistStatus 	INTEGER,
		uxsStatusFileModTime		INTEGER,
		uxsStatusFileModTimeValue 	INTEGER,
		uxsStatusFileModTimeMonitor 	INTEGER,
		uxsStatusFileModTimeStatus 	INTEGER,
		uxsStatusFileSizeValue 		INTEGER,
		uxsStatusFileSizeWarn 		INTEGER,
		uxsStatusFileSizeCrit 		INTEGER,
		uxsStatusFileSizeMonitor 	INTEGER,
		uxsStatusFileSizeStatus 	INTEGER,
		uxsStatusFileSizeDValue 	INTEGER,
		uxsStatusFileSizeDWarn 		INTEGER,
		uxsStatusFileSizeDCrit 		INTEGER,
		uxsStatusFileSizeDMonitor 	INTEGER,
		uxsStatusFileSizeDStatus 	INTEGER,
		uxsStatusFileRemove 		INTEGER,
		uxsStatusFileCallBackRef	DisplayString
	}

uxsStatusFileName OBJECT-TYPE
	SYNTAX  DisplayString
	ACCESS  read-only
	STATUS  mandatory
	DESCRIPTION
		"&<caiUxOs.417>The name of the file being monitored."
	::= { uxsStatusFileEntry 1 }

uxsStatusFileDesc OBJECT-TYPE
	SYNTAX  DisplayString
	ACCESS  read-only
	STATUS  mandatory
	DESCRIPTION
		"&<caiUxOs.418>The description of the watcher provided when the watcher was created."
	::= { uxsStatusFileEntry 2 }

uxsStatusFileStatus OBJECT-TYPE
	SYNTAX  INTEGER {
		unknown(1),
		ok(2),
		warning(3),
		critical(4),
		down(5)
	}
	ACCESS  read-only
	STATUS  mandatory
	DESCRIPTION
		"&<caiUxOs.419>The current status of the resource: unknown(1) - An error occurred during data collection, ok(2) - The resource is within the defined limits, warning(3) - The resource has breached the warning threshold, critical(4) - The resource has breached the critical threshold, down(5) - The resource is in a down state."
	::= { uxsStatusFileEntry 3 }

uxsStatusFileExist OBJECT-TYPE
	SYNTAX  INTEGER {
		should-exist(1),
		should-not-exist(2)
	}
	ACCESS  read-write
	STATUS  mandatory
	DESCRIPTION
		"&<caiUxOs.420>The test to perform for file existence. Valid values: should-exist(1) or should-not-exist(2)."
	::= { uxsStatusFileEntry 4 }

uxsStatusFileExistMonitor OBJECT-TYPE
	SYNTAX  INTEGER {
		do-not-monitor(1),
		monitor(2)
	}
	ACCESS  read-write
	STATUS  mandatory
	DESCRIPTION
		"&<caiUxOs.421>Defines the level of monitoring for the resource's status. Valid values: do-not-monitor(1) or monitor(2)."
	::= { uxsStatusFileEntry 5 }

uxsStatusFileExistStatus OBJECT-TYPE
	SYNTAX  INTEGER {
		unknown(1),
		up(2),
		down(3)
	}
	ACCESS  read-only
	STATUS  mandatory
	DESCRIPTION
		"&<caiUxOs.422>The status of the files existence based on the uxsStatusFileExist attribute."
	::= { uxsStatusFileEntry 6 }

uxsStatusFileModTime OBJECT-TYPE
	SYNTAX  DisplayString
	ACCESS  read-only
	STATUS  mandatory
	DESCRIPTION
		"&<caiUxOs.423>The files last modified date and time."
	::= { uxsStatusFileEntry 7 }

uxsStatusFileModTimeValue OBJECT-TYPE
	SYNTAX  DisplayString
	ACCESS  read-only
	STATUS  mandatory
	DESCRIPTION
		"&<caiUxOs.424>The time the agent compares with for the file timestamp status."
	::= { uxsStatusFileEntry 8 }

uxsStatusFileModTimeMonitor OBJECT-TYPE
	SYNTAX  INTEGER {
		do-not-monitor(1),
		monitor(2)
	}
	ACCESS  read-write
	STATUS  mandatory
	DESCRIPTION
		"&<caiUxOs.425>Defines the level of monitoring for the resource's status. Valid values: do-not-monitor(1) or monitor(2)."
	::= { uxsStatusFileEntry 9 }

uxsStatusFileModTimeStatus OBJECT-TYPE
	SYNTAX  INTEGER {
		unknown(1),
		up(2),
		down(3),
		reset(4)
	}
	ACCESS  read-write
	STATUS  mandatory
	DESCRIPTION
		"&<caiUxOs.426>The status of the timestamp monitoring. unknown(1) - An error occurred collecting the data, up(2) - The timestamp is unchanged, down(3) - The timestamp has changed, reset(4) - Reset the uxsStatusFileModTimeValue to the files current timestamp and sets the status to OK."
	::= { uxsStatusFileEntry 10 }

uxsStatusFileSizeValue OBJECT-TYPE
	SYNTAX  INTEGER
	ACCESS  read-only
	STATUS  mandatory
	DESCRIPTION
		"&<caiUxOs.427>The size of the file in kilobytes."
	::= { uxsStatusFileEntry 11 }

uxsStatusFileSizeWarn OBJECT-TYPE
	SYNTAX  INTEGER
	ACCESS  read-write
	STATUS  mandatory
	DESCRIPTION
		"&<caiUxOs.428>The value for file size that is considered a warning level for that resource. Valid ranges: Greater than 0, not greater than or equal to the critical threshold."
	::= { uxsStatusFileEntry 12 }

uxsStatusFileSizeCrit OBJECT-TYPE
	SYNTAX  INTEGER
	ACCESS  read-write
	STATUS  mandatory
	DESCRIPTION
		"&<caiUxOs.429>The value for file size that is considered a critical level for that resource. Valid ranges: Greater than 1, not less than or equal to the warning threshold."
	::= { uxsStatusFileEntry 13 }

uxsStatusFileSizeMonitor OBJECT-TYPE
	SYNTAX  INTEGER {
		do-not-monitor(1),
		warning-only(2),
		critical-only(3),
		both(4)
	}
	ACCESS  read-write
	STATUS  mandatory
	DESCRIPTION
		"&<caiUxOs.430>Defines the level of monitoring for the resource's status. Valid values: do-not-monitor(1), warning-only(2), critical-only(3) or both(4)."
	::= { uxsStatusFileEntry 14 }

uxsStatusFileSizeStatus OBJECT-TYPE
	SYNTAX  INTEGER {
		unknown(1),
		ok(2),
		warning(3),
		critical(4)
	}
	ACCESS  read-only
	STATUS  mandatory
	DESCRIPTION
		"&<caiUxOs.431>The current status of the resource: unknown(1) - An error occurred during data collection, ok(2) - The resource is within the defined limits, warning(3) - The resource has breached the warning threshold, critical(4) - The resource has breached the critical threshold."
	::= { uxsStatusFileEntry 15 }

uxsStatusFileSizeDValue OBJECT-TYPE
	SYNTAX  INTEGER
	ACCESS  read-only
	STATUS  mandatory
	DESCRIPTION
		"&<caiUxOs.432>The difference in file size since the last poll."
	::= { uxsStatusFileEntry 16 }

uxsStatusFileSizeDWarn OBJECT-TYPE
	SYNTAX  INTEGER
	ACCESS  read-write
	STATUS  mandatory
	DESCRIPTION
		"&<caiUxOs.433>The value for file size change that is considered a warning level for that resource. Valid ranges: Greater than 0, not greater than or equal to the critical threshold."
	::= { uxsStatusFileEntry 17 }

uxsStatusFileSizeDCrit OBJECT-TYPE
	SYNTAX  INTEGER
	ACCESS  read-write
	STATUS  mandatory
	DESCRIPTION
		"&<caiUxOs.434>The value for file size change that is considered a critical level for that resource. Valid ranges: Greater than 1, not less than or equal to the warning threshold."
	::= { uxsStatusFileEntry 18 }

uxsStatusFileSizeDMonitor OBJECT-TYPE
	SYNTAX  INTEGER {
		do-not-monitor(1),
		warning-only(2),
		critical-only(3),
		both(4)
	}
	ACCESS  read-write
	STATUS  mandatory
	DESCRIPTION
		"&<caiUxOs.435>Defines the level of monitoring for the resource's status. Valid values: do-not-monitor(1), warning-only(2), critical-only(3) or both(4)."
	::= { uxsStatusFileEntry 19 }

uxsStatusFileSizeDStatus OBJECT-TYPE
	SYNTAX  INTEGER {
		unknown(1),
		ok(2),
		warning(3),
		critical(4)
	}
	ACCESS  read-only
	STATUS  mandatory
	DESCRIPTION
		"&<caiUxOs.436>The current status of the resource: unknown(1) - An error occurred during data collection, ok(2) - The resource is within the defined limits, warning(3) - The resource has breached the warning threshold, critical(4) - The resource has breached the critical threshold."
	::= { uxsStatusFileEntry 20 }

uxsStatusFileRemove OBJECT-TYPE
	SYNTAX  INTEGER {
		none(1),
		remove(2)
	}
	ACCESS  read-write
	STATUS  mandatory
	DESCRIPTION
		"&<caiUxOs.437>Removes the file watcher from the agent."
	::= { uxsStatusFileEntry 21 }

uxsStatusFileCallBackRef OBJECT-TYPE
	SYNTAX DisplayString
	ACCESS read-only
	STATUS mandatory
	DESCRIPTION
		"&<caiUxOs.731>The name of the Call-Back reference that should be invoked in case of a status change."
	::= { uxsStatusFileEntry 22 }

--
-- uxsStatusProcGroup
--
uxsStatusProcCount OBJECT-TYPE
	SYNTAX  INTEGER
	ACCESS  read-only
	STATUS  mandatory
	DESCRIPTION
		"&<caiUxOs.438>The count of the number of process watchers."
	::= { uxsStatusProcGroup 1 }

uxsStatusProcTable OBJECT-TYPE
	SYNTAX  SEQUENCE OF UxsStatusProcSequence
	ACCESS  not-accessible
	STATUS  mandatory
	DESCRIPTION
		"&<caiUxOs.439>The table of process watchers."
	::= { uxsStatusProcGroup 2 }

--
-- uxsStatusProcTable
--
uxsStatusProcEntry OBJECT-TYPE
	SYNTAX  UxsStatusProcSequence
	ACCESS  not-accessible
	STATUS  mandatory
	DESCRIPTION
		"&<caiUxOs.440>"
	INDEX   { uxsStatusProcName,
                  uxsStatusProcPath,
                  uxsStatusProcArgs,
                  uxsStatusProcUsers }
	::= { uxsStatusProcTable 1 }

UxsStatusProcSequence ::=
	SEQUENCE {
		uxsStatusProcName 		DisplayString,
		uxsStatusProcPath 		DisplayString,
		uxsStatusProcArgs 		DisplayString,
		uxsStatusProcUsers 		DisplayString,
		uxsStatusProcStatus 		INTEGER,
		uxsStatusProcPIDs 		DisplayString,
		uxsStatusProcInstValue 		INTEGER,
		uxsStatusProcInstMin 		INTEGER,
		uxsStatusProcInstMax 		INTEGER,
		uxsStatusProcInstMonitor	INTEGER,
		uxsStatusProcInstStatus 	INTEGER,
		uxsStatusProcChldValue 		INTEGER,
		uxsStatusProcChldMin 		INTEGER,
		uxsStatusProcChldMax 		INTEGER,
		uxsStatusProcChldMonitor	INTEGER,
		uxsStatusProcChldStatus 	INTEGER,
		uxsStatusProcSizeValue 		INTEGER,
		uxsStatusProcSizeMin 		INTEGER,
		uxsStatusProcSizeMax 		INTEGER,
		uxsStatusProcSizeMonitor	INTEGER,
		uxsStatusProcSizeStatus 	INTEGER,
		uxsStatusProcCPUValue 		INTEGER,
		uxsStatusProcCPUWarn 		INTEGER,
		uxsStatusProcCPUCrit		INTEGER,
		uxsStatusProcCPUMonitor 	INTEGER,
		uxsStatusProcCPUStatus 		INTEGER,
		uxsStatusProcRemove 		INTEGER,
		uxsStatusProcCallBackRef	DisplayString
	}

uxsStatusProcName OBJECT-TYPE
	SYNTAX  DisplayString
	ACCESS  read-only
	STATUS  mandatory
	DESCRIPTION
		"&<caiUxOs.441>The name of the process to monitor. Valid values are a string with an optional * at the end of the string for wild card matching."
	::= { uxsStatusProcEntry 1 }

uxsStatusProcPath OBJECT-TYPE
	SYNTAX  DisplayString
	ACCESS  read-only
	STATUS  mandatory
	DESCRIPTION
		"&<caiUxOs.442>The path of the process to match. Valid values are a string with an optional * at the end of the string for wild card matching."
	::= { uxsStatusProcEntry 2 }

uxsStatusProcArgs OBJECT-TYPE
	SYNTAX  DisplayString
	ACCESS  read-only
	STATUS  mandatory
	DESCRIPTION
		"&<caiUxOs.443>A section of the processes arguments to match."
	::= { uxsStatusProcEntry 3 }

uxsStatusProcUsers OBJECT-TYPE
	SYNTAX  DisplayString
	ACCESS  read-only
	STATUS  mandatory
	DESCRIPTION
		"&<caiUxOs.444>List of users to match. Details format of the string are documented in the online help."
	::= { uxsStatusProcEntry 4 }

uxsStatusProcStatus OBJECT-TYPE
	SYNTAX  INTEGER {
		unknown(1),
		ok(2),
		warning(3),
		critical(4),
		down(5)
	}
	ACCESS  read-only
	STATUS  mandatory
	DESCRIPTION
		"&<caiUxOs.445>The current status of the resource: unknown(1) - An error occurred during data collection, ok(2) - The resource is within the defined limits, warning(3) - The resource has breached the warning threshold, critical(4) - The resource has breached the critical threshold, down(5) - The resource is in a down state."
	::= { uxsStatusProcEntry 5 }

uxsStatusProcPIDs OBJECT-TYPE
	SYNTAX  DisplayString
	ACCESS  read-only
	STATUS  mandatory
	DESCRIPTION
		"&<caiUxOs.446>The list of process IDs that caused the watcher to be in a bad state. This string is limited to 256 characters."
	::= { uxsStatusProcEntry 6 }

uxsStatusProcInstValue OBJECT-TYPE
	SYNTAX  INTEGER
	ACCESS  read-only
	STATUS  mandatory
	DESCRIPTION
		"&<caiUxOs.447>The current number of instances that match the key fields."
	::= { uxsStatusProcEntry 7 }

uxsStatusProcInstMin OBJECT-TYPE
	SYNTAX  INTEGER
	ACCESS  read-write
	STATUS  mandatory
	DESCRIPTION
		"&<caiUxOs.448>Minimum number of instances expected to match the key. Valid values: -1, 0 or greater."
	::= { uxsStatusProcEntry 8 }

uxsStatusProcInstMax OBJECT-TYPE
	SYNTAX  INTEGER
	ACCESS  read-write
	STATUS  mandatory
	DESCRIPTION
		"&<caiUxOs.449>Maximum number of instances expected to match the key. Valid values: -1, 0 or greater."
	::= { uxsStatusProcEntry 9 }

uxsStatusProcInstMonitor OBJECT-TYPE
	SYNTAX  INTEGER {
		do-not-monitor(1),
		monitor(2)
	}
	ACCESS  read-write
	STATUS  mandatory
	DESCRIPTION
		"&<caiUxOs.450>Defines the level of monitoring for process instances. Valid values: do-not-monitor(1) or monitor(2)."
	::= { uxsStatusProcEntry 10 }

uxsStatusProcInstStatus OBJECT-TYPE
	SYNTAX  INTEGER {
		unknown(1),
		up(2),
		down(3)
	}
	ACCESS  read-only
	STATUS  mandatory
	DESCRIPTION
		"&<caiUxOs.451>The current status of the resource: unknown(1) - An error occurred collecting the data, up(2) - The resource is within the monitoring parameters, down(3) - The resource is outside the monitoring parameters."
	::= { uxsStatusProcEntry 11 }

uxsStatusProcChldValue OBJECT-TYPE
	SYNTAX  INTEGER
	ACCESS  read-only
	STATUS  mandatory
	DESCRIPTION
		"&<caiUxOs.452>The number of children of the process. See the documentation for additional information."
	::= { uxsStatusProcEntry 12 }

uxsStatusProcChldMin OBJECT-TYPE
	SYNTAX  INTEGER
	ACCESS  read-write
	STATUS  mandatory
	DESCRIPTION
		"&<caiUxOs.453>Minimum number of children (based on lowest for all instances). Valid values: -1, 0 or greater."
	::= { uxsStatusProcEntry 13 }

uxsStatusProcChldMax OBJECT-TYPE
	SYNTAX  INTEGER
	ACCESS  read-write
	STATUS  mandatory
	DESCRIPTION
		"&<caiUxOs.454>Maximum number of children (based on highest for all instances). Valid values: -1, 0 or greater."
	::= { uxsStatusProcEntry 14 }

uxsStatusProcChldMonitor OBJECT-TYPE
	SYNTAX  INTEGER {
		do-not-monitor(1),
		monitor(2)
	}
	ACCESS  read-write
	STATUS  mandatory
	DESCRIPTION
		"&<caiUxOs.455>Defines the level of monitoring for the number of children of the process. Valid values: do-not-monitor(1) or monitor(2)."
	::= { uxsStatusProcEntry 15 }

uxsStatusProcChldStatus OBJECT-TYPE
	SYNTAX  INTEGER {
		unknown(1),
		up(2),
		down(3)
	}
	ACCESS  read-only
	STATUS  mandatory
	DESCRIPTION
		"&<caiUxOs.456>The status of the number of children of the process: unknown(1) - An error occurred collecting the data, up(2) - The resource is within the monitoring parameters, down(3) - The resource is outside the monitoring parameters."
	::= { uxsStatusProcEntry 16 }

uxsStatusProcSizeValue OBJECT-TYPE
	SYNTAX  INTEGER
	ACCESS  read-only
	STATUS  mandatory
	DESCRIPTION
		"&<caiUxOs.457>The size of the process in kilobytes. See the documentation for rules for which match's value is displayed."
	::= { uxsStatusProcEntry 17 }

uxsStatusProcSizeMin OBJECT-TYPE
	SYNTAX  INTEGER
	ACCESS  read-write
	STATUS  mandatory
	DESCRIPTION
		"&<caiUxOs.458>Minimum size of the process in kilobytes (based on lowest for all instances). Valid values: -1, 0 or greater."
	::= { uxsStatusProcEntry 18 }

uxsStatusProcSizeMax OBJECT-TYPE
	SYNTAX  INTEGER
	ACCESS  read-write
	STATUS  mandatory
	DESCRIPTION
		"&<caiUxOs.459>Maximum size of the process in kilobytes (based on highest for all instances). Valid values: -1, 0 or greater."
	::= { uxsStatusProcEntry 19 }

uxsStatusProcSizeMonitor OBJECT-TYPE
	SYNTAX  INTEGER {
		do-not-monitor(1),
		monitor(2)
	}
	ACCESS  read-write
	STATUS  mandatory
	DESCRIPTION
		"&<caiUxOs.460>Defines the level of monitoring for the size of the process. Valid values: do-not-monitor(1) or monitor(2)."
	::= { uxsStatusProcEntry 20 }

uxsStatusProcSizeStatus OBJECT-TYPE
	SYNTAX  INTEGER {
		unknown(1),
		up(2),
		down(3)
	}
	ACCESS  read-only
	STATUS  mandatory
	DESCRIPTION
		"&<caiUxOs.461>The status of the process size. unknown(1) - An error occurred collecting the data, up(2) - The resource is within the monitoring parameters, down(3) - The resource is outside the monitoring parameters."
	::= { uxsStatusProcEntry 21 }

uxsStatusProcCPUValue OBJECT-TYPE
	SYNTAX  INTEGER
	ACCESS  read-only
	STATUS  mandatory
	DESCRIPTION
		"&<caiUxOs.462>The highest of all CPU (user and system time) usage since the last poll as a percentage."
	::= { uxsStatusProcEntry 22 }

uxsStatusProcCPUWarn OBJECT-TYPE
	SYNTAX  INTEGER
	ACCESS  read-write
	STATUS  mandatory
	DESCRIPTION
		"&<caiUxOs.463>The percentage of used CPU that is considered a warning level for that resource. Valid ranges: Greater than 0, less than 100, not greater than or equal to the critical threshold."
	::= { uxsStatusProcEntry 23 }

uxsStatusProcCPUCrit OBJECT-TYPE
	SYNTAX  INTEGER
	ACCESS  read-write
	STATUS  mandatory
	DESCRIPTION
		"&<caiUxOs.464>The percentage of used CPU that is considered a critical level for that resource. Valid ranges: Greater than 1, less than or equal to 100, not less than or equal to the warning threshold."
	::= { uxsStatusProcEntry 24 }

uxsStatusProcCPUMonitor OBJECT-TYPE
	SYNTAX  INTEGER {
		do-not-monitor(1),
		warning-only(2),
		critical-only(3),
		both(4)	}
	ACCESS  read-write
	STATUS  mandatory
	DESCRIPTION
		"&<caiUxOs.465>Defines the level of monitoring for used CPU. Valid values: do-not-monitor(1), warning-only(2), critical-only(3) or both(4)."
	::= { uxsStatusProcEntry 25 }

uxsStatusProcCPUStatus OBJECT-TYPE
	SYNTAX  INTEGER {
		unknown(1),
		ok(2),
		warning(3),
		critical(4)
	}
	ACCESS  read-only
	STATUS  mandatory
	DESCRIPTION
		"&<caiUxOs.466>The current status of the resource: unknown(1) - An error occurred during data collection, ok(2) - The resource is within the defined limits, warning(3) - The resource has breached the warning threshold, critical(4) - The resource has breached the critical threshold."
	::= { uxsStatusProcEntry 26 }

uxsStatusProcRemove OBJECT-TYPE
	SYNTAX  INTEGER {
		none(1),
		remove(2)
	}
	ACCESS  read-write
	STATUS  mandatory
	DESCRIPTION
		"&<caiUxOs.467>Removes the process watcher from the agent."
	::= { uxsStatusProcEntry 27 }

uxsStatusProcCallBackRef OBJECT-TYPE
	SYNTAX DisplayString
	ACCESS read-only
	STATUS mandatory
	DESCRIPTION
		"&<caiUxOs.731>The name of the Call-Back reference that should be invoked in case of a status change."
	::= { uxsStatusProcEntry 28 }

--
-- uxsStatusPrnGroup
--
uxsStatusPrnCount OBJECT-TYPE
	SYNTAX  INTEGER
	ACCESS  read-only
	STATUS  mandatory
	DESCRIPTION
		"&<caiUxOs.468>The number of configured printer queue watchers."
	::= { uxsStatusPrnGroup 1 }

uxsStatusPrnTable OBJECT-TYPE
	SYNTAX  SEQUENCE OF UxsStatusPrnSequence
	ACCESS  not-accessible
	STATUS  mandatory
	DESCRIPTION
		"&<caiUxOs.469>The table of printer queue watchers."
	::= { uxsStatusPrnGroup 2 }

--
-- uxsStatusPrnTable
--
uxsStatusPrnEntry OBJECT-TYPE
	SYNTAX  UxsStatusPrnSequence
	ACCESS  not-accessible
	STATUS  mandatory
	DESCRIPTION
		"&<caiUxOs.470>"
	INDEX   { uxsStatusPrnName }
	::= { uxsStatusPrnTable 1 }

UxsStatusPrnSequence ::=
	SEQUENCE {
		uxsStatusPrnName		DisplayString,
		uxsStatusPrnDesc		DisplayString,
		uxsStatusPrnAggStatus       	INTEGER,
		uxsStatusPrnItemsValue		INTEGER,
		uxsStatusPrnItemsWarn		INTEGER,
		uxsStatusPrnItemsCrit		INTEGER,
		uxsStatusPrnItemsMonitor	INTEGER,
		uxsStatusPrnItemsStatus		INTEGER,
		uxsStatusPrnLossAction		INTEGER,
		uxsStatusPrnLossStatus		INTEGER,
		uxsStatusPrnRemove			INTEGER,
		uxsStatusPrnCallBackRef		DisplayString
	}

uxsStatusPrnName OBJECT-TYPE
	SYNTAX  DisplayString
	ACCESS  read-only
	STATUS  mandatory
	DESCRIPTION
		"&<caiUxOs.471>The name of the printer queue being monitored."
	::= { uxsStatusPrnEntry 1 }

uxsStatusPrnAggStatus OBJECT-TYPE
	SYNTAX  INTEGER {
		unknown(1),
		ok(2),
		warning(3),
		critical(4),
		down(5)
	}
	ACCESS  read-only
	STATUS  mandatory
	DESCRIPTION
		"&<caiUxOs.472>The current status of the resource: unknown(1) - An error occurred during data collection, ok(2) - The resource is within the defined limits, warning(3) - The resource has breached the warning threshold, critical(4) - The resource has breached the critical threshold, down(5) - The resource is in a down state."
	::= { uxsStatusPrnEntry 2 }

uxsStatusPrnDesc OBJECT-TYPE
	SYNTAX  DisplayString
	ACCESS  read-write
	STATUS  mandatory
	DESCRIPTION
		"&<caiUxOs.473>The description given to the printer queue watcher when it was added."
	::= { uxsStatusPrnEntry 3 }

uxsStatusPrnItemsValue OBJECT-TYPE
	SYNTAX  INTEGER
	ACCESS  read-only
	STATUS  mandatory
	DESCRIPTION
		"&<caiUxOs.474>The number of printer queue items on the queue."
	::= { uxsStatusPrnEntry 4 }

uxsStatusPrnItemsWarn OBJECT-TYPE
	SYNTAX  INTEGER
	ACCESS  read-write
	STATUS  mandatory
	DESCRIPTION
		"&<caiUxOs.475>The number of printer queue items that is considered a warning level for that resource. Valid ranges: Greater than 0, not greater than or equal to the critical threshold."
	::= { uxsStatusPrnEntry 5 }

uxsStatusPrnItemsCrit OBJECT-TYPE
	SYNTAX  INTEGER
	ACCESS  read-write
	STATUS  mandatory
	DESCRIPTION
		"&<caiUxOs.476>The number of printer queue items that is considered a critical level for that resource. Valid ranges: Greater than 1, not less than or equal to the warning threshold."
	::= { uxsStatusPrnEntry 6 }

uxsStatusPrnItemsMonitor OBJECT-TYPE
	SYNTAX  INTEGER {
		do-not-monitor(1),
		warning-only(2),
		critical-only(3),
		both(4)
	}
	ACCESS  read-write
	STATUS  mandatory
	DESCRIPTION
		"&<caiUxOs.477>Defines the level of monitoring for the resource's status. Valid values: do-not-monitor(1), warning-only(2), critical-only(3) or both(4)."
	::= { uxsStatusPrnEntry 7 }

uxsStatusPrnItemsStatus OBJECT-TYPE
	SYNTAX  INTEGER {
		unknown(1),
		ok(2),
		warning(3),
		critical(4)
	}
	ACCESS  read-only
	STATUS  mandatory
	DESCRIPTION
		"&<caiUxOs.478>The current status of the resource: unknown(1) - An error occurred during data collection, ok(2) - The resource is within the defined limits, warning(3) - The resource has breached the warning threshold, critical(4) - The resource has breached the critical threshold."
	::= { uxsStatusPrnEntry 8 }

uxsStatusPrnLossAction OBJECT-TYPE
	SYNTAX  INTEGER {
		remove(1),
		up(2),
		down(3)
	}
	ACCESS  read-write
	STATUS  mandatory
	DESCRIPTION
		"&<caiUxOs.479>Defines the action to take if the printer queue configuration is removed from the machine. Valid values: remove(1), up(2) or down(3)."
	::= { uxsStatusPrnEntry 9 }

uxsStatusPrnLossStatus OBJECT-TYPE
	SYNTAX  INTEGER {
		unknown(1),
		up(2),
		down(3)
	}
	ACCESS  read-only
	STATUS  mandatory
	DESCRIPTION
		"&<caiUxOs.480>The status relating to the existence of the object. Valid values: unknown(1), up(2) or down(3)."
	::= { uxsStatusPrnEntry 10 }

uxsStatusPrnRemove OBJECT-TYPE
	SYNTAX  INTEGER {
		none(1),
		remove(2)
	}
	ACCESS  read-write
	STATUS  mandatory
	DESCRIPTION
		"&<caiUxOs.481>Removes the printer watcher from the agent."
	::= { uxsStatusPrnEntry 11 }

uxsStatusPrnCallBackRef OBJECT-TYPE
	SYNTAX DisplayString
	ACCESS read-only
	STATUS mandatory
	DESCRIPTION
		"&<caiUxOs.731>The name of the Call-Back reference that should be invoked in case of a status change."
	::= { uxsStatusPrnEntry 12 }

--
-- uxsStatusNetGroup
--
uxsStatusNetTotalStatus OBJECT-TYPE
	SYNTAX  INTEGER {
		unknown(1),
		ok(2),
		warning(3),
		critical(4)
	}
	ACCESS  read-only
	STATUS  mandatory
	DESCRIPTION
		"&<caiUxOs.482>The current status of the resource: unknown(1) - An error occurred during data collection, ok(2) - The resource is within the defined limits, warning(3) - The resource has breached the warning threshold, critical(4) - The resource has breached the critical threshold."
	::= { uxsStatusNetGroup 1 }

uxsStatusNetTotalIPktValue OBJECT-TYPE
	SYNTAX  INTEGER
	ACCESS  read-only
	STATUS  mandatory
	DESCRIPTION
		"&<caiUxOs.483>The total number of input packets per second for all interfaces since the last poll."
	::= { uxsStatusNetGroup 2 }

uxsStatusNetTotalIPktWarn OBJECT-TYPE
	SYNTAX  INTEGER
	ACCESS  read-write
	STATUS  mandatory
	DESCRIPTION
		"&<caiUxOs.484>The number of total input packets that is considered a warning level for that resource. Valid ranges: Greater than 0, not greater than or equal to the critical threshold."
	::= { uxsStatusNetGroup 3 }

uxsStatusNetTotalIPktCrit OBJECT-TYPE
	SYNTAX  INTEGER
	ACCESS  read-write
	STATUS  mandatory
	DESCRIPTION
		"&<caiUxOs.485>The number of total input packets that is considered a critical level for that resource. Valid ranges: Greater than 1, not less than or equal to the warning threshold."
	::= { uxsStatusNetGroup 4 }

uxsStatusNetTotalIPktMonitor OBJECT-TYPE
	SYNTAX  INTEGER {
		do-not-monitor(1),
		warning-only(2),
		critical-only(3),
		both(4)
	}
	ACCESS  read-write
	STATUS  mandatory
	DESCRIPTION
		"&<caiUxOs.486>Defines the level of monitoring for the resource's status. Valid values: do-not-monitor(1), warning-only(2), critical-only(3) or both(4)."
	::= { uxsStatusNetGroup 5 }

uxsStatusNetTotalIPktStatus OBJECT-TYPE
	SYNTAX  INTEGER {
		unknown(1),
		ok(2),
		warning(3),
		critical(4)
	}
	ACCESS  read-only
	STATUS  mandatory
	DESCRIPTION
		"&<caiUxOs.487>The current status of the resource: unknown(1) - An error occurred during data collection, ok(2) - The resource is within the defined limits, warning(3) - The resource has breached the warning threshold, critical(4) - The resource has breached the critical threshold."
	::= { uxsStatusNetGroup 6 }

uxsStatusNetTotalIErrValue OBJECT-TYPE
	SYNTAX  INTEGER
	ACCESS  read-only
	STATUS  mandatory
	DESCRIPTION
		"&<caiUxOs.488>The total number of input errors for all interfaces since the last poll."
	::= { uxsStatusNetGroup 7 }

uxsStatusNetTotalIErrWarn OBJECT-TYPE
	SYNTAX  INTEGER
	ACCESS  read-write
	STATUS  mandatory
	DESCRIPTION
		"&<caiUxOs.489>The number of total input errors that is considered a warning level for that resource. Valid ranges: Greater than 0, not greater than or equal to the critical threshold."
	::= { uxsStatusNetGroup 8 }

uxsStatusNetTotalIErrCrit OBJECT-TYPE
	SYNTAX  INTEGER
	ACCESS  read-write
	STATUS  mandatory
	DESCRIPTION
		"&<caiUxOs.490>The number of total input errors that is considered a critical level for that resource. Valid ranges: Greater than 1, not less than or equal to the warning threshold."
	::= { uxsStatusNetGroup 9 }

uxsStatusNetTotalIErrMonitor OBJECT-TYPE
	SYNTAX  INTEGER {
		do-not-monitor(1),
		warning-only(2),
		critical-only(3),
		both(4)
	}
	ACCESS  read-write
	STATUS  mandatory
	DESCRIPTION
		"&<caiUxOs.491>Defines the level of monitoring for the resource's status. Valid values: do-not-monitor(1), warning-only(2), critical-only(3) or both(4)."
	::= { uxsStatusNetGroup 10 }

uxsStatusNetTotalIErrStatus OBJECT-TYPE
	SYNTAX  INTEGER {
		unknown(1),
		ok(2),
		warning(3),
		critical(4)
	}
	ACCESS  read-only
	STATUS  mandatory
	DESCRIPTION
		"&<caiUxOs.492>The current status of the resource: unknown(1) - An error occurred during data collection, ok(2) - The resource is within the defined limits, warning(3) - The resource has breached the warning threshold, critical(4) - The resource has breached the critical threshold."
	::= { uxsStatusNetGroup 11 }

uxsStatusNetTotalOPktValue OBJECT-TYPE
	SYNTAX  INTEGER
	ACCESS  read-only
	STATUS  mandatory
	DESCRIPTION
		"&<caiUxOs.493>The total number of output packets per second for all interfaces since the last poll."
	::= { uxsStatusNetGroup 12 }

uxsStatusNetTotalOPktWarn OBJECT-TYPE
	SYNTAX  INTEGER
	ACCESS  read-write
	STATUS  mandatory
	DESCRIPTION
		"&<caiUxOs.494>The number of total output packets that is considered a warning level for that resource. Valid ranges: Greater than 0, not greater than or equal to the critical threshold."
	::= { uxsStatusNetGroup 13 }

uxsStatusNetTotalOPktCrit OBJECT-TYPE
	SYNTAX  INTEGER
	ACCESS  read-write
	STATUS  mandatory
	DESCRIPTION
		"&<caiUxOs.495>The number of total output packets that is considered a critical level for that resource. Valid ranges: Greater than 1, not less than or equal to the warning threshold."
	::= { uxsStatusNetGroup 14 }

uxsStatusNetTotalOPktMonitor OBJECT-TYPE
	SYNTAX  INTEGER {
		do-not-monitor(1),
		warning-only(2),
		critical-only(3),
		both(4)
	}
	ACCESS  read-write
	STATUS  mandatory
	DESCRIPTION
		"&<caiUxOs.496>Defines the level of monitoring for the resource's status. Valid values: do-not-monitor(1), warning-only(2), critical-only(3) or both(4)."
	::= { uxsStatusNetGroup 15 }

uxsStatusNetTotalOPktStatus OBJECT-TYPE
	SYNTAX  INTEGER {
		unknown(1),
		ok(2),
		warning(3),
		critical(4)
	}
	ACCESS  read-only
	STATUS  mandatory
	DESCRIPTION
		"&<caiUxOs.497>The current status of the resource: unknown(1) - An error occurred during data collection, ok(2) - The resource is within the defined limits, warning(3) - The resource has breached the warning threshold, critical(4) - The resource has breached the critical threshold."
	::= { uxsStatusNetGroup 16 }

uxsStatusNetTotalOErrValue OBJECT-TYPE
	SYNTAX  INTEGER
	ACCESS  read-only
	STATUS  mandatory
	DESCRIPTION
		"&<caiUxOs.498>The total number of output errors for all interfaces since the last poll."
	::= { uxsStatusNetGroup 17 }

uxsStatusNetTotalOErrWarn OBJECT-TYPE
	SYNTAX  INTEGER
	ACCESS  read-write
	STATUS  mandatory
	DESCRIPTION
		"&<caiUxOs.499>The number of total output errors that is considered a warning level for that resource. Valid ranges: Greater than 0, not greater than or equal to the critical threshold."
	::= { uxsStatusNetGroup 18 }

uxsStatusNetTotalOErrCrit OBJECT-TYPE
	SYNTAX  INTEGER
	ACCESS  read-write
	STATUS  mandatory
	DESCRIPTION
		"&<caiUxOs.500>The number of total output errors that is considered a critical level for that resource. Valid ranges: Greater than 1, not less than or equal to the warning threshold."
	::= { uxsStatusNetGroup 19 }

uxsStatusNetTotalOErrMonitor OBJECT-TYPE
	SYNTAX  INTEGER {
		do-not-monitor(1),
		warning-only(2),
		critical-only(3),
		both(4)
	}
	ACCESS  read-write
	STATUS  mandatory
	DESCRIPTION
		"&<caiUxOs.501>Defines the level of monitoring for the resource's status. Valid values: do-not-monitor(1), warning-only(2), critical-only(3) or both(4)."
	::= { uxsStatusNetGroup 20 }

uxsStatusNetTotalOErrStatus OBJECT-TYPE
	SYNTAX  INTEGER {
		unknown(1),
		ok(2),
		warning(3),
		critical(4)
	}
	ACCESS  read-only
	STATUS  mandatory
	DESCRIPTION
		"&<caiUxOs.502>The current status of the resource: unknown(1) - An error occurred during data collection, ok(2) - The resource is within the defined limits, warning(3) - The resource has breached the warning threshold, critical(4) - The resource has breached the critical threshold."
	::= { uxsStatusNetGroup 21 }

uxsStatusNetTotalCollValue OBJECT-TYPE
	SYNTAX  INTEGER
	ACCESS  read-only
	STATUS  mandatory
	DESCRIPTION
		"&<caiUxOs.503>The total number of collisions for all interfaces since the last poll."
	::= { uxsStatusNetGroup 22 }

uxsStatusNetTotalCollWarn OBJECT-TYPE
	SYNTAX  INTEGER
	ACCESS  read-write
	STATUS  mandatory
	DESCRIPTION
		"&<caiUxOs.504>The number of total collisions that is considered a warning level for that resource. Valid ranges: Greater than 0, not greater than or equal to the critical threshold."
	::= { uxsStatusNetGroup 23 }

uxsStatusNetTotalCollCrit OBJECT-TYPE
	SYNTAX  INTEGER
	ACCESS  read-write
	STATUS  mandatory
	DESCRIPTION
		"&<caiUxOs.505>The number of total collisions that is considered a critical level for that resource. Valid ranges: Greater than 1, not less than or equal to the warning threshold."
	::= { uxsStatusNetGroup 24 }

uxsStatusNetTotalCollMonitor OBJECT-TYPE
	SYNTAX  INTEGER {
		do-not-monitor(1),
		warning-only(2),
		critical-only(3),
		both(4)
	}
	ACCESS  read-write
	STATUS  mandatory
	DESCRIPTION
		"&<caiUxOs.506>Defines the level of monitoring for the resource's status. Valid values: do-not-monitor(1), warning-only(2), critical-only(3) or both(4)."
	::= { uxsStatusNetGroup 25 }

uxsStatusNetTotalCollStatus OBJECT-TYPE
	SYNTAX  INTEGER {
		unknown(1),
		ok(2),
		warning(3),
		critical(4)
	}
	ACCESS  read-only
	STATUS  mandatory
	DESCRIPTION
		"&<caiUxOs.507>The current status of the resource: unknown(1) - An error occurred during data collection, ok(2) - The resource is within the defined limits, warning(3) - The resource has breached the warning threshold, critical(4) - The resource has breached the critical threshold."
	::= { uxsStatusNetGroup 26 }

uxsStatusNetCount OBJECT-TYPE
	SYNTAX  INTEGER
	ACCESS  read-only
	STATUS  mandatory
	DESCRIPTION
		"&<caiUxOs.508>The number of network interfaces in the network table."
	::= { uxsStatusNetGroup 27 }

uxsStatusNetTable OBJECT-TYPE
	SYNTAX  SEQUENCE OF UxsStatusNetSequence
	ACCESS  not-accessible
	STATUS  mandatory
	DESCRIPTION
		"&<caiUxOs.509>The network table containing the network interfaces."
	::= { uxsStatusNetGroup 28 }

uxsStatusNetTotalCallBackRef OBJECT-TYPE
	SYNTAX DisplayString
	ACCESS read-only
	STATUS mandatory
	DESCRIPTION
		"&<caiUxOs.731>The name of the Call-Back reference that should be invoked in case of a status change."
	::= { uxsStatusNetGroup 29 }

--
-- uxsStatusNetTable
--
uxsStatusNetEntry OBJECT-TYPE
	SYNTAX  UxsStatusNetSequence
	ACCESS  not-accessible
	STATUS  mandatory
	DESCRIPTION
		"&<caiUxOs.510>"
	INDEX   { uxsStatusNetName }
	::= { uxsStatusNetTable 1 }

UxsStatusNetSequence ::=
	SEQUENCE {
		uxsStatusNetName		DisplayString,
		uxsStatusNetIP			DisplayString,
		uxsStatusNetStatus		INTEGER,
		uxsStatusNetIPktValue		INTEGER,
		uxsStatusNetIPktWarn		INTEGER,
		uxsStatusNetIPktCrit		INTEGER,
		uxsStatusNetIPktMonitor		INTEGER,
		uxsStatusNetIPktStatus		INTEGER,
		uxsStatusNetIErrValue		INTEGER,
		uxsStatusNetIErrWarn		INTEGER,
		uxsStatusNetIErrCrit		INTEGER,
		uxsStatusNetIErrMonitor		INTEGER,
		uxsStatusNetIErrStatus		INTEGER,
		uxsStatusNetOPktValue		INTEGER,
		uxsStatusNetOPktWarn		INTEGER,
		uxsStatusNetOPktCrit		INTEGER,
		uxsStatusNetOPktMonitor		INTEGER,
		uxsStatusNetOPktStatus		INTEGER,
		uxsStatusNetOErrValue		INTEGER,
		uxsStatusNetOErrWarn		INTEGER,
		uxsStatusNetOErrCrit		INTEGER,
		uxsStatusNetOErrMonitor		INTEGER,
		uxsStatusNetOErrStatus		INTEGER,
		uxsStatusNetCollValue		INTEGER,
		uxsStatusNetCollWarn		INTEGER,
		uxsStatusNetCollCrit		INTEGER,
		uxsStatusNetCollMonitor		INTEGER,
		uxsStatusNetCollStatus		INTEGER,
		uxsStatusNetLossAction		INTEGER,
		uxsStatusNetLossStatus		INTEGER,
		uxsStatusNetCallBackRef		DisplayString
	}

uxsStatusNetName OBJECT-TYPE
	SYNTAX  DisplayString
	ACCESS  read-only
	STATUS  mandatory
	DESCRIPTION
		"&<caiUxOs.511>The name by which the network interface is known."
	::= { uxsStatusNetEntry 1 }

uxsStatusNetIP OBJECT-TYPE
	SYNTAX  DisplayString
	ACCESS  read-only
	STATUS  mandatory
	DESCRIPTION
		"&<caiUxOs.512>The IP address of the interface."
	::= { uxsStatusNetEntry 2 }

uxsStatusNetStatus OBJECT-TYPE
	SYNTAX  INTEGER {
		unknown(1),
		ok(2),
		warning(3),
		critical(4)
	}
	ACCESS  read-only
	STATUS  mandatory
	DESCRIPTION
		"&<caiUxOs.513>The current status of the resource: unknown(1) - An error occurred during data collection, ok(2) - The resource is within the defined limits, warning(3) - The resource has breached the warning threshold, critical(4) - The resource has breached the critical threshold."
	::= { uxsStatusNetEntry 3 }

uxsStatusNetIPktValue OBJECT-TYPE
	SYNTAX  INTEGER
	ACCESS  read-only
	STATUS  mandatory
	DESCRIPTION
		"&<caiUxOs.514>The number of input packets per second for the interface since the last poll."
	::= { uxsStatusNetEntry 4 }

uxsStatusNetIPktWarn OBJECT-TYPE
	SYNTAX  INTEGER
	ACCESS  read-write
	STATUS  mandatory
	DESCRIPTION
		"&<caiUxOs.515>The number of input packets that is considered a warning level for that resource. Valid ranges: Greater than 0, not greater than or equal to the critical threshold."
	::= { uxsStatusNetEntry 5 }

uxsStatusNetIPktCrit OBJECT-TYPE
	SYNTAX  INTEGER
	ACCESS  read-write
	STATUS  mandatory
	DESCRIPTION
		"&<caiUxOs.516>The number of input packets that is considered a critical level for that resource. Valid ranges: Greater than 1, not less than or equal to the warning threshold."
	::= { uxsStatusNetEntry 6 }

uxsStatusNetIPktMonitor OBJECT-TYPE
	SYNTAX  INTEGER {
		do-not-monitor(1),
		warning-only(2),
		critical-only(3),
		both(4)
	}
	ACCESS  read-write
	STATUS  mandatory
	DESCRIPTION
		"&<caiUxOs.517>Defines the level of monitoring for the resource's status. Valid values: do-not-monitor(1), warning-only(2), critical-only(3) or both(4)."
	::= { uxsStatusNetEntry 7 }

uxsStatusNetIPktStatus OBJECT-TYPE
	SYNTAX  INTEGER {
		unknown(1),
		ok(2),
		warning(3),
		critical(4)
	}
	ACCESS  read-only
	STATUS  mandatory
	DESCRIPTION
		"&<caiUxOs.518>The current status of the resource: unknown(1) - An error occurred during data collection, ok(2) - The resource is within the defined limits, warning(3) - The resource has breached the warning threshold, critical(4) - The resource has breached the critical threshold."
	::= { uxsStatusNetEntry 8 }

uxsStatusNetIErrValue OBJECT-TYPE
	SYNTAX  INTEGER
	ACCESS  read-only
	STATUS  mandatory
	DESCRIPTION
		"&<caiUxOs.519>The number of input errors for the interface since the last poll."
	::= { uxsStatusNetEntry 9 }

uxsStatusNetIErrWarn OBJECT-TYPE
	SYNTAX  INTEGER
	ACCESS  read-write
	STATUS  mandatory
	DESCRIPTION
		"&<caiUxOs.520>The number of input errors that is considered a warning level for that resource. Valid ranges: Greater than 0, not greater than or equal to the critical threshold."
	::= { uxsStatusNetEntry 10 }

uxsStatusNetIErrCrit OBJECT-TYPE
	SYNTAX  INTEGER
	ACCESS  read-write
	STATUS  mandatory
	DESCRIPTION
		"&<caiUxOs.521>The number of input errors that is considered a critical level for that resource. Valid ranges: Greater than 1, not less than or equal to the warning threshold."
	::= { uxsStatusNetEntry 11 }

uxsStatusNetIErrMonitor OBJECT-TYPE
	SYNTAX  INTEGER {
		do-not-monitor(1),
		warning-only(2),
		critical-only(3),
		both(4)
	}
	ACCESS  read-write
	STATUS  mandatory
	DESCRIPTION
		"&<caiUxOs.522>Defines the level of monitoring for the resource's status. Valid values: do-not-monitor(1), warning-only(2), critical-only(3) or both(4)."
	::= { uxsStatusNetEntry 12 }

uxsStatusNetIErrStatus OBJECT-TYPE
	SYNTAX  INTEGER {
		unknown(1),
		ok(2),
		warning(3),
		critical(4)
	}
	ACCESS  read-only
	STATUS  mandatory
	DESCRIPTION
		"&<caiUxOs.523>The current status of the resource: unknown(1) - An error occurred during data collection, ok(2) - The resource is within the defined limits, warning(3) - The resource has breached the warning threshold, critical(4) - The resource has breached the critical threshold."
	::= { uxsStatusNetEntry 13 }

uxsStatusNetOPktValue OBJECT-TYPE
	SYNTAX  INTEGER
	ACCESS  read-only
	STATUS  mandatory
	DESCRIPTION
		"&<caiUxOs.524>The number of output packets per second for the interface since the last poll."
	::= { uxsStatusNetEntry 14 }

uxsStatusNetOPktWarn OBJECT-TYPE
	SYNTAX  INTEGER
	ACCESS  read-write
	STATUS  mandatory
	DESCRIPTION
		"&<caiUxOs.525>The number of output packets that is considered a warning level for that resource. Valid ranges: Greater than 0, not greater than or equal to the critical threshold."
	::= { uxsStatusNetEntry 15 }

uxsStatusNetOPktCrit OBJECT-TYPE
	SYNTAX  INTEGER
	ACCESS  read-write
	STATUS  mandatory
	DESCRIPTION
		"&<caiUxOs.526>The number of output packets that is considered a critical level for that resource. Valid ranges: Greater than 1, not less than or equal to the warning threshold."
	::= { uxsStatusNetEntry 16 }

uxsStatusNetOPktMonitor OBJECT-TYPE
	SYNTAX  INTEGER {
		do-not-monitor(1),
		warning-only(2),
		critical-only(3),
		both(4)
	}
	ACCESS  read-write
	STATUS  mandatory
	DESCRIPTION
		"&<caiUxOs.527>Defines the level of monitoring for the resource's status. Valid values: do-not-monitor(1), warning-only(2), critical-only(3) or both(4)."
	::= { uxsStatusNetEntry 17 }

uxsStatusNetOPktStatus OBJECT-TYPE
	SYNTAX  INTEGER {
		unknown(1),
		ok(2),
		warning(3),
		critical(4)
	}
	ACCESS  read-only
	STATUS  mandatory
	DESCRIPTION
		"&<caiUxOs.528>The current status of the resource: unknown(1) - An error occurred during data collection, ok(2) - The resource is within the defined limits, warning(3) - The resource has breached the warning threshold, critical(4) - The resource has breached the critical threshold."
	::= { uxsStatusNetEntry 18 }

uxsStatusNetOErrValue OBJECT-TYPE
	SYNTAX  INTEGER
	ACCESS  read-only
	STATUS  mandatory
	DESCRIPTION
		"&<caiUxOs.529>The number of output errors for the interface since the last poll."
	::= { uxsStatusNetEntry 19 }

uxsStatusNetOErrWarn OBJECT-TYPE
	SYNTAX  INTEGER
	ACCESS  read-write
	STATUS  mandatory
	DESCRIPTION
		"&<caiUxOs.530>The number of output errors that is considered a warning level for that resource. Valid ranges: Greater than 0, not greater than or equal to the critical threshold."
	::= { uxsStatusNetEntry 20 }

uxsStatusNetOErrCrit OBJECT-TYPE
	SYNTAX  INTEGER
	ACCESS  read-write
	STATUS  mandatory
	DESCRIPTION
		"&<caiUxOs.531>The number of output errors that is considered a critical level for that resource. Valid ranges: Greater than 1, not less than or equal to the warning threshold."
	::= { uxsStatusNetEntry 21 }

uxsStatusNetOErrMonitor OBJECT-TYPE
	SYNTAX  INTEGER {
		do-not-monitor(1),
		warning-only(2),
		critical-only(3),
		both(4)
	}
	ACCESS  read-write
	STATUS  mandatory
	DESCRIPTION
		"&<caiUxOs.532>Defines the level of monitoring for the resource's status. Valid values: do-not-monitor(1), warning-only(2), critical-only(3) or both(4)."
	::= { uxsStatusNetEntry 22 }

uxsStatusNetOErrStatus OBJECT-TYPE
	SYNTAX  INTEGER {
		unknown(1),
		ok(2),
		warning(3),
		critical(4)
	}
	ACCESS  read-only
	STATUS  mandatory
	DESCRIPTION
		"&<caiUxOs.533>The current status of the resource: unknown(1) - An error occurred during data collection, ok(2) - The resource is within the defined limits, warning(3) - The resource has breached the warning threshold, critical(4) - The resource has breached the critical threshold."
	::= { uxsStatusNetEntry 23 }

uxsStatusNetCollValue OBJECT-TYPE
	SYNTAX  INTEGER
	ACCESS  read-only
	STATUS  mandatory
	DESCRIPTION
		"&<caiUxOs.534>The number of collisions for the interface since the last poll."
	::= { uxsStatusNetEntry 24 }

uxsStatusNetCollWarn OBJECT-TYPE
	SYNTAX  INTEGER
	ACCESS  read-write
	STATUS  mandatory
	DESCRIPTION
		"&<caiUxOs.535>The number of collisions that is considered a warning level for that resource. Valid ranges: Greater than 0, not greater than or equal to the critical threshold."
	::= { uxsStatusNetEntry 25 }

uxsStatusNetCollCrit OBJECT-TYPE
	SYNTAX  INTEGER
	ACCESS  read-write
	STATUS  mandatory
	DESCRIPTION
		"&<caiUxOs.536>The number of collisions that is considered a critical level for that resource. Valid ranges: Greater than 1, not less than or equal to the warning threshold."
	::= { uxsStatusNetEntry 26 }

uxsStatusNetCollMonitor OBJECT-TYPE
	SYNTAX  INTEGER {
		do-not-monitor(1),
		warning-only(2),
		critical-only(3),
		both(4)
	}
	ACCESS  read-write
	STATUS  mandatory
	DESCRIPTION
		"&<caiUxOs.537>Defines the level of monitoring for the resource's status. Valid values: do-not-monitor(1), warning-only(2), critical-only(3) or both(4)."
	::= { uxsStatusNetEntry 27 }

uxsStatusNetCollStatus OBJECT-TYPE
	SYNTAX  INTEGER {
		unknown(1),
		ok(2),
		warning(3),
		critical(4)
	}
	ACCESS  read-only
	STATUS  mandatory
	DESCRIPTION
		"&<caiUxOs.538>The current status of the resource: unknown(1) - An error occurred during data collection, ok(2) - The resource is within the defined limits, warning(3) - The resource has breached the warning threshold, critical(4) - The resource has breached the critical threshold."
	::= { uxsStatusNetEntry 28 }

uxsStatusNetLossAction OBJECT-TYPE
	SYNTAX  INTEGER {
		remove(1),
		up(2),
		down(3)
	}
	ACCESS  read-write
	STATUS  mandatory
	DESCRIPTION
		"&<caiUxOs.539>Defines the action to take if the network interface is removed from the machine. Valid values: remove(1), up(2) or down(3)."
	::= { uxsStatusNetEntry 29 }

uxsStatusNetLossStatus OBJECT-TYPE
	SYNTAX  INTEGER {
		unknown(1),
		up(2),
		down(3)
	}
	ACCESS  read-only
	STATUS  mandatory
	DESCRIPTION
		"&<caiUxOs.540>The status relating to the existence of the object. Valid values: unknown(1), up(2) or down(3)."
	::= { uxsStatusNetEntry 30 }

uxsStatusNetCallBackRef OBJECT-TYPE
	SYNTAX DisplayString
	ACCESS read-only
	STATUS mandatory
	DESCRIPTION
		"&<caiUxOs.731>The name of the Call-Back reference that should be invoked in case of a status change."
	::= { uxsStatusNetEntry 31 }

--
-- uxsStatusIPCGroup
--
uxsStatusIPCSHMIDSAvailable OBJECT-TYPE
	SYNTAX  INTEGER
	ACCESS  read-only
	STATUS  mandatory
	DESCRIPTION
		"&<caiUxOs.541>The number of configured shared memory IDs."
	::= { uxsStatusIPCGroup 1 }

uxsStatusIPCSHMIDSValue OBJECT-TYPE
	SYNTAX  INTEGER
	ACCESS  read-only
	STATUS  mandatory
	DESCRIPTION
		"&<caiUxOs.542>The number of shared memory IDs in use."
	::= { uxsStatusIPCGroup 2 }

uxsStatusIPCSHMIDSLagValue OBJECT-TYPE
	SYNTAX  INTEGER
	ACCESS  read-only
	STATUS  mandatory
	DESCRIPTION
		"&<caiUxOs.543>The number of times that the threshold has been reached."
	::= { uxsStatusIPCGroup 3 }

uxsStatusIPCSHMIDSLag OBJECT-TYPE
	SYNTAX  INTEGER
	ACCESS  read-write
	STATUS  mandatory
	DESCRIPTION
		"&<caiUxOs.544>The number of times that the threshold has to be reached before the state changes. Valid range: Greater than 0."
	::= { uxsStatusIPCGroup 4 }

uxsStatusIPCSHMIDSWarnValue OBJECT-TYPE
	SYNTAX  DisplayString
	ACCESS  read-only
	STATUS  mandatory
	DESCRIPTION
		"&<caiUxOs.545>The absolute value used for threshold calculation based on the configured warning value."
	::= { uxsStatusIPCGroup 5 }

uxsStatusIPCSHMIDSCritValue OBJECT-TYPE
	SYNTAX  DisplayString
	ACCESS  read-only
	STATUS  mandatory
	DESCRIPTION
		"&<caiUxOs.546>The absolute value used for threshold calculation based on the configured critical value."
	::= { uxsStatusIPCGroup 6 }

uxsStatusIPCSHMIDSWarn OBJECT-TYPE
	SYNTAX  DisplayString
	ACCESS  read-write
	STATUS  mandatory
	DESCRIPTION
		"&<caiUxOs.547>The value for used IDs, either as a percentage or absolute value, that is considered a warning level for that resource. Valid ranges: Greater than 0, less than total IDs - 1, not greater than or equal to the critical threshold."
	::= { uxsStatusIPCGroup 7 }

uxsStatusIPCSHMIDSCrit OBJECT-TYPE
	SYNTAX  DisplayString
	ACCESS  read-write
	STATUS  mandatory
	DESCRIPTION
		"&<caiUxOs.548>The value for used IDs, either as a percentage or absolute value, that is considered a critical level for that resource. Valid ranges: Greater than 1, less than total IDs, not less than or equal to the warning threshold."
	::= { uxsStatusIPCGroup 8 }

uxsStatusIPCSHMIDSMonitor OBJECT-TYPE
	SYNTAX  INTEGER {
		do-not-monitor(1),
		warning-only(2),
		critical-only(3),
		both(4)
	}
	ACCESS  read-write
	STATUS  mandatory
	DESCRIPTION
		"&<caiUxOs.549>Defines the level of monitoring for the resource's status. Valid values: do-not-monitor(1), warning-only(2), critical-only(3) or both(4)."
	::= { uxsStatusIPCGroup 9 }

uxsStatusIPCSHMIDSStatus OBJECT-TYPE
	SYNTAX  INTEGER {
		unknown(1),
		ok(2),
		warning(3),
		critical(4)
	}
	ACCESS  read-only
	STATUS  mandatory
	DESCRIPTION
		"&<caiUxOs.550>The current status of the resource: unknown(1) - An error occurred during data collection, ok(2) - The resource is within the defined limits, warning(3) - The resource has breached the warning threshold, critical(4) - The resource has breached the critical threshold."
	::= { uxsStatusIPCGroup 10 }

uxsStatusIPCSEMIDSAvailable OBJECT-TYPE
	SYNTAX  INTEGER
	ACCESS  read-only
	STATUS  mandatory
	DESCRIPTION
		"&<caiUxOs.551>The number of configured semaphore IDs."
	::= { uxsStatusIPCGroup 11 }

uxsStatusIPCSEMIDSValue OBJECT-TYPE
	SYNTAX  INTEGER
	ACCESS  read-only
	STATUS  mandatory
	DESCRIPTION
		"&<caiUxOs.552>The number of semaphore IDs in use."
	::= { uxsStatusIPCGroup 12 }

uxsStatusIPCSEMIDSLagValue OBJECT-TYPE
	SYNTAX  INTEGER
	ACCESS  read-only
	STATUS  mandatory
	DESCRIPTION
		"&<caiUxOs.553>The number of times that the threshold has been reached."
	::= { uxsStatusIPCGroup 13 }

uxsStatusIPCSEMIDSLag OBJECT-TYPE
	SYNTAX  INTEGER
	ACCESS  read-write
	STATUS  mandatory
	DESCRIPTION
		"&<caiUxOs.554>The number of times that the threshold has to be reached before the state changes. Valid range: Greater than 0."
	::= { uxsStatusIPCGroup 14 }

uxsStatusIPCSEMIDSWarnValue OBJECT-TYPE
	SYNTAX  DisplayString
	ACCESS  read-only
	STATUS  mandatory
	DESCRIPTION
		"&<caiUxOs.555>The absolute value used for threshold calculation based on the configured warning value."
	::= { uxsStatusIPCGroup 15 }

uxsStatusIPCSEMIDSCritValue OBJECT-TYPE
	SYNTAX  DisplayString
	ACCESS  read-only
	STATUS  mandatory
	DESCRIPTION
		"&<caiUxOs.556>The absolute value used for threshold calculation based on the configured critical value."
	::= { uxsStatusIPCGroup 16 }

uxsStatusIPCSEMIDSWarn OBJECT-TYPE
	SYNTAX  DisplayString
	ACCESS  read-write
	STATUS  mandatory
	DESCRIPTION
		"&<caiUxOs.557>The value for used IDs, either as a percentage or absolute value, that is considered a warning level for that resource. Valid ranges: Greater than 0, less than total IDs - 1, not greater than or equal to the critical threshold."
	::= { uxsStatusIPCGroup 17 }

uxsStatusIPCSEMIDSCrit OBJECT-TYPE
	SYNTAX  DisplayString
	ACCESS  read-write
	STATUS  mandatory
	DESCRIPTION
		"&<caiUxOs.558>The value for used IDs, either as a percentage or absolute value, that is considered a critical level for that resource. Valid ranges: Greater than 1, less than total IDs, not less than or equal to the warning threshold."
	::= { uxsStatusIPCGroup 18 }

uxsStatusIPCSEMIDSMonitor OBJECT-TYPE
	SYNTAX  INTEGER {
		do-not-monitor(1),
		warning-only(2),
		critical-only(3),
		both(4)
	}
	ACCESS  read-write
	STATUS  mandatory
	DESCRIPTION
		"&<caiUxOs.559>Defines the level of monitoring for the resource's status. Valid values: do-not-monitor(1), warning-only(2), critical-only(3) or both(4)."
	::= { uxsStatusIPCGroup 19 }

uxsStatusIPCSEMIDSStatus OBJECT-TYPE
	SYNTAX  INTEGER {
		unknown(1),
		ok(2),
		warning(3),
		critical(4)
	}
	ACCESS  read-only
	STATUS  mandatory
	DESCRIPTION
		"&<caiUxOs.560>The current status of the resource: unknown(1) - An error occurred during data collection, ok(2) - The resource is within the defined limits, warning(3) - The resource has breached the warning threshold, critical(4) - The resource has breached the critical threshold."
	::= { uxsStatusIPCGroup 20 }

uxsStatusIPCMQIDSAvailable OBJECT-TYPE
	SYNTAX  INTEGER
	ACCESS  read-only
	STATUS  mandatory
	DESCRIPTION
		"&<caiUxOs.561>The number of configured message queue IDs."
	::= { uxsStatusIPCGroup 21 }

uxsStatusIPCMQIDSValue OBJECT-TYPE
	SYNTAX  INTEGER
	ACCESS  read-only
	STATUS  mandatory
	DESCRIPTION
		"&<caiUxOs.562>The number of message queue IDs in use."
	::= { uxsStatusIPCGroup 22 }

uxsStatusIPCMQIDSLagValue OBJECT-TYPE
	SYNTAX  INTEGER
	ACCESS  read-only
	STATUS  mandatory
	DESCRIPTION
		"&<caiUxOs.563>The number of times that the threshold has been reached."
	::= { uxsStatusIPCGroup 23 }

uxsStatusIPCMQIDSLag OBJECT-TYPE
	SYNTAX  INTEGER
	ACCESS  read-write
	STATUS  mandatory
	DESCRIPTION
		"&<caiUxOs.564>The number of times that the threshold has to be reached before the state changes. Valid range: Greater than 0."
	::= { uxsStatusIPCGroup 24 }

uxsStatusIPCMQIDSWarnValue OBJECT-TYPE
	SYNTAX  DisplayString
	ACCESS  read-only
	STATUS  mandatory
	DESCRIPTION
		"&<caiUxOs.565>The absolute value used for threshold calculation based on the configured warning value."
	::= { uxsStatusIPCGroup 25 }

uxsStatusIPCMQIDSCritValue OBJECT-TYPE
	SYNTAX  DisplayString
	ACCESS  read-only
	STATUS  mandatory
	DESCRIPTION
		"&<caiUxOs.566>The absolute value used for threshold calculation based on the configured critical value."
	::= { uxsStatusIPCGroup 26 }

uxsStatusIPCMQIDSWarn OBJECT-TYPE
	SYNTAX  DisplayString
	ACCESS  read-write
	STATUS  mandatory
	DESCRIPTION
		"&<caiUxOs.567>The value for used IDs, either as a percentage or absolute value, that is considered a warning level for that resource. Valid ranges: Greater than 0, less than total IDs - 1, not greater than or equal to the critical threshold."
	::= { uxsStatusIPCGroup 27 }

uxsStatusIPCMQIDSCrit OBJECT-TYPE
	SYNTAX  DisplayString
	ACCESS  read-write
	STATUS  mandatory
	DESCRIPTION
		"&<caiUxOs.568>The value for used IDs, either as a percentage or absolute value, that is considered a critical level for that resource. Valid ranges: Greater than 1, less than total IDs, not less than or equal to the warning threshold."
	::= { uxsStatusIPCGroup 28 }

uxsStatusIPCMQIDSMonitor OBJECT-TYPE
	SYNTAX  INTEGER {
		do-not-monitor(1),
		warning-only(2),
		critical-only(3),
		both(4)
	}
	ACCESS  read-write
	STATUS  mandatory
	DESCRIPTION
		"&<caiUxOs.569>Defines the level of monitoring for the resource's status. Valid values: do-not-monitor(1), warning-only(2), critical-only(3) or both(4)."
	::= { uxsStatusIPCGroup 29 }

uxsStatusIPCMQIDSStatus OBJECT-TYPE
	SYNTAX  INTEGER {
		unknown(1),
		ok(2),
		warning(3),
		critical(4)
	}
	ACCESS  read-only
	STATUS  mandatory
	DESCRIPTION
		"&<caiUxOs.570>The current status of the resource: unknown(1) - An error occurred during data collection, ok(2) - The resource is within the defined limits, warning(3) - The resource has breached the warning threshold, critical(4) - The resource has breached the critical threshold."
	::= { uxsStatusIPCGroup 30 }

uxsStatusIPCMQMonitor OBJECT-TYPE
	SYNTAX  INTEGER {
		do-not-monitor(1),
		monitor(2)
	}
	ACCESS  read-write
	STATUS  mandatory
	DESCRIPTION
		"&<caiUxOs.571>Defines the level of monitoring for the resource's status. Valid values: do-not-monitor(1) or monitor(2)."
	::= { uxsStatusIPCGroup 31 }

uxsStatusIPCMQCount OBJECT-TYPE
	SYNTAX  INTEGER
	ACCESS  read-only
	STATUS  mandatory
	DESCRIPTION
		"&<caiUxOs.572>The number of monitored message queues."
	::= { uxsStatusIPCGroup 32 }

uxsStatusIPCMQTable OBJECT-TYPE
	SYNTAX  SEQUENCE OF UxsStatusIPCMQSequence
	ACCESS  not-accessible
	STATUS  mandatory
	DESCRIPTION
		"&<caiUxOs.573>The table of monitored message queues."
	::= { uxsStatusIPCGroup 33 }

uxsStatusIPCCallBackRef OBJECT-TYPE
	SYNTAX DisplayString
	ACCESS read-only
	STATUS mandatory
	DESCRIPTION
		"&<caiUxOs.731>The name of the Call-Back reference that should be invoked in case of a status change."
	::= { uxsStatusIPCGroup 34 }

--
-- uxsStatusIPCMQTable
--
uxsStatusIPCMQEntry OBJECT-TYPE
	SYNTAX  UxsStatusIPCMQSequence
	ACCESS  not-accessible
	STATUS  mandatory
	DESCRIPTION
		"&<caiUxOs.574>"
	INDEX   { uxsStatusIPCMQID }
	::= { uxsStatusIPCMQTable 1 }

UxsStatusIPCMQSequence ::=
	SEQUENCE {
		uxsStatusIPCMQID		DisplayString,
		uxsStatusIPCMQKey		DisplayString,
		uxsStatusIPCMQMode		DisplayString,
		uxsStatusIPCMQOwner		DisplayString,
		uxsStatusIPCMQGroup		DisplayString,
		uxsStatusIPCMQBytesAvailable	INTEGER,
		uxsStatusIPCMQBytesValue	INTEGER,
		uxsStatusIPCMQBytesLagValue	INTEGER,
		uxsStatusIPCMQBytesLag		INTEGER,
		uxsStatusIPCMQBytesWarnValue	DisplayString,
		uxsStatusIPCMQBytesCritValue	DisplayString,
		uxsStatusIPCMQBytesWarn		DisplayString,
		uxsStatusIPCMQBytesCrit		DisplayString,
		uxsStatusIPCMQBytesMonitor	INTEGER,
		uxsStatusIPCMQBytesStatus	INTEGER,
		uxsStatusIPCMQCallBackRef	DisplayString
	}

uxsStatusIPCMQID OBJECT-TYPE
	SYNTAX  DisplayString
	ACCESS  read-only
	STATUS  mandatory
	DESCRIPTION
		"&<caiUxOs.575>The message queue ID."
	::= { uxsStatusIPCMQEntry 1 }

uxsStatusIPCMQKey OBJECT-TYPE
	SYNTAX  DisplayString
	ACCESS  read-only
	STATUS  mandatory
	DESCRIPTION
		"&<caiUxOs.576>The message queue key."
	::= { uxsStatusIPCMQEntry 2 }

uxsStatusIPCMQMode OBJECT-TYPE
	SYNTAX  DisplayString
	ACCESS  read-only
	STATUS  mandatory
	DESCRIPTION
		"&<caiUxOs.577>The message queue access rights."
	::= { uxsStatusIPCMQEntry 3 }

uxsStatusIPCMQOwner OBJECT-TYPE
	SYNTAX  DisplayString
	ACCESS  read-only
	STATUS  mandatory
	DESCRIPTION
		"&<caiUxOs.578>The message queue owner."
	::= { uxsStatusIPCMQEntry 4 }

uxsStatusIPCMQGroup OBJECT-TYPE
	SYNTAX  DisplayString
	ACCESS  read-only
	STATUS  mandatory
	DESCRIPTION
		"&<caiUxOs.579>The message queue group."
	::= { uxsStatusIPCMQEntry 5 }

uxsStatusIPCMQBytesAvailable OBJECT-TYPE
	SYNTAX  INTEGER
	ACCESS  read-only
	STATUS  mandatory
	DESCRIPTION
		"&<caiUxOs.580>The number of bytes available for messages."
	::= { uxsStatusIPCMQEntry 6 }

uxsStatusIPCMQBytesValue OBJECT-TYPE
	SYNTAX  INTEGER
	ACCESS  read-only
	STATUS  mandatory
	DESCRIPTION
		"&<caiUxOs.581>The bytes used in the message queue."
	::= { uxsStatusIPCMQEntry 7 }

uxsStatusIPCMQBytesLagValue OBJECT-TYPE
	SYNTAX  INTEGER
	ACCESS  read-only
	STATUS  mandatory
	DESCRIPTION
		"&<caiUxOs.582>The number of times that the threshold has been reached."
	::= { uxsStatusIPCMQEntry 8 }

uxsStatusIPCMQBytesLag OBJECT-TYPE
	SYNTAX  INTEGER
	ACCESS  read-write
	STATUS  mandatory
	DESCRIPTION
		"&<caiUxOs.583>The number of times that the threshold has to be reached before the state changes. Valid range: Greater than 0."
	::= { uxsStatusIPCMQEntry 9 }

uxsStatusIPCMQBytesWarnValue OBJECT-TYPE
	SYNTAX  DisplayString
	ACCESS  read-only
	STATUS  mandatory
	DESCRIPTION
		"&<caiUxOs.584>The absolute value used for threshold calculation based on the configured warning value."
	::= { uxsStatusIPCMQEntry 10 }

uxsStatusIPCMQBytesCritValue OBJECT-TYPE
	SYNTAX  DisplayString
	ACCESS  read-only
	STATUS  mandatory
	DESCRIPTION
		"&<caiUxOs.585>The absolute value used for threshold calculation based on the configured critical value."
	::= { uxsStatusIPCMQEntry 12 }

uxsStatusIPCMQBytesWarn OBJECT-TYPE
	SYNTAX  DisplayString
	ACCESS  read-write
	STATUS  mandatory
	DESCRIPTION
		"&<caiUxOs.586>The value for used message queue bytes, either as a percentage or in kilobytes, that is considered a warning level for that resource. Valid ranges: Greater than 0, less than total queue size - 1, not greater than or equal to the critical threshold."
	::= { uxsStatusIPCMQEntry 13 }

uxsStatusIPCMQBytesCrit OBJECT-TYPE
	SYNTAX  DisplayString
	ACCESS  read-write
	STATUS  mandatory
	DESCRIPTION
		"&<caiUxOs.587>The value for used message queue bytes, either as a percentage or in kilobytes, that is considered a critical level for that resource. Valid ranges: Greater than 1, less than total Queue size, not less than or equal to the warning threshold."
	::= { uxsStatusIPCMQEntry 14 }

uxsStatusIPCMQBytesMonitor OBJECT-TYPE
	SYNTAX  INTEGER {
		do-not-monitor(1),
		warning-only(2),
		critical-only(3),
		both(4)
	}
	ACCESS  read-write
	STATUS  mandatory
	DESCRIPTION
		"&<caiUxOs.588>Defines the level of monitoring for the resource's status. Valid values: do-not-monitor(1), warning-only(2), critical-only(3) or both(4)."
	::= { uxsStatusIPCMQEntry 15 }

uxsStatusIPCMQBytesStatus OBJECT-TYPE
	SYNTAX  INTEGER {
		unknown(1),
		ok(2),
		warning(3),
		critical(4)
	}
	ACCESS  read-only
	STATUS  mandatory
	DESCRIPTION
		"&<caiUxOs.589>The current status of the resource: unknown(1) - An error occurred during data collection, ok(2) - The resource is within the defined limits, warning(3) - The resource has breached the warning threshold, critical(4) - The resource has breached the critical threshold."
	::= { uxsStatusIPCMQEntry 16 }

uxsStatusIPCMQCallBackRef OBJECT-TYPE
	SYNTAX DisplayString
	ACCESS read-only
	STATUS mandatory
	DESCRIPTION
		"&<caiUxOs.731>The name of the Call-Back reference that should be invoked in case of a status change."
	::= { uxsStatusIPCMQEntry 17 }

--
-- uxsAvailFSysTable
--
uxsAvailFSysEntry OBJECT-TYPE
	SYNTAX	UxsAvailFSysSequence
	ACCESS  not-accessible
	STATUS  mandatory
	DESCRIPTION
		"&<caiUxOs.590>"
	INDEX   { uxsAvailFSysName }
	::= { uxsAvailFSysTable 1 }

UxsAvailFSysSequence ::=
	SEQUENCE {
		uxsAvailFSysName		DisplayString,
		uxsAvailFSysRelatedTo		DisplayString,
		uxsAvailFSysType		DisplayString
	}

uxsAvailFSysName OBJECT-TYPE
	SYNTAX  DisplayString
	ACCESS  read-only
	STATUS  mandatory
	DESCRIPTION
		"&<caiUxOs.591>The file system name."
	::= { uxsAvailFSysEntry 1 }

uxsAvailFSysRelatedTo OBJECT-TYPE
	SYNTAX  DisplayString
	ACCESS  read-only
	STATUS  mandatory
	DESCRIPTION
		"&<caiUxOs.592>The device to which the file system is related."
	::= { uxsAvailFSysEntry 2 }

uxsAvailFSysType OBJECT-TYPE
	SYNTAX  DisplayString
	ACCESS  read-only
	STATUS  mandatory
	DESCRIPTION
        "&<caiUxOs.593>The type of the file system. Values are platform dependent, for example: UFS, CDROM, or NFS. File systems mounted temporarily are not recorded in the fstab file but only in the mnttab file. In this case the character string 'Not in fstab' will be appended to the displayed file system type."
	::= { uxsAvailFSysEntry 3 }

--
-- uxsAvailDiskTable
--
uxsAvailDiskEntry OBJECT-TYPE
	SYNTAX	UxsAvailDiskSequence
	ACCESS  not-accessible
	STATUS  mandatory
	DESCRIPTION
		"&<caiUxOs.594>"
	INDEX   { uxsAvailDiskName }
	::= { uxsAvailDiskTable 1 }

UxsAvailDiskSequence ::=
	SEQUENCE {
		uxsAvailDiskName		DisplayString
	}

uxsAvailDiskName OBJECT-TYPE
	SYNTAX  DisplayString
	ACCESS  read-only
	STATUS  mandatory
	DESCRIPTION
		"&<caiUxOs.595>The device name."
	::= { uxsAvailDiskEntry 1 }

--
-- uxsAvailPrnTable
--
uxsAvailPrnEntry OBJECT-TYPE
	SYNTAX	UxsAvailPrnSequence
	ACCESS  not-accessible
	STATUS  mandatory
	DESCRIPTION
		"&<caiUxOs.596>"
	INDEX   { uxsAvailPrnName }
	::= { uxsAvailPrnTable 1 }

UxsAvailPrnSequence ::=
	SEQUENCE {
		uxsAvailPrnName			DisplayString
	}

uxsAvailPrnName OBJECT-TYPE
	SYNTAX  DisplayString
	ACCESS  read-only
	STATUS  mandatory
	DESCRIPTION
		"&<caiUxOs.597>The local printer queue name."
	::= { uxsAvailPrnEntry 1 }

--
-- uxsPollNetGroup
--
uxsPollNetTable OBJECT-TYPE
	SYNTAX  SEQUENCE OF UxsPollNetSequence
	ACCESS  not-accessible
	STATUS  mandatory
	DESCRIPTION
		"&<caiUxOs.598>The table of raw network statistics."
	::= { uxsPollNetGroup 1 }

--
-- uxsPollNetTable
--
uxsPollNetEntry OBJECT-TYPE
	SYNTAX  UxsPollNetSequence
	ACCESS  not-accessible
	STATUS  mandatory
	DESCRIPTION
		"&<caiUxOs.599>"
	INDEX   { uxsPollNetName }
	::= { uxsPollNetTable 1 }

UxsPollNetSequence ::=
	SEQUENCE {
		uxsPollNetName		DisplayString,
		uxsPollNetIP		DisplayString,
		uxsPollNetIPktValue	INTEGER,
		uxsPollNetIErrValue	INTEGER,
		uxsPollNetOPktValue	INTEGER,
		uxsPollNetOErrValue	INTEGER,
		uxsPollNetCollValue	INTEGER
	}

uxsPollNetName OBJECT-TYPE
	SYNTAX  DisplayString
	ACCESS  read-only
	STATUS  mandatory
	DESCRIPTION
		"&<caiUxOs.600>The name by which the network interface is known."
	::= { uxsPollNetEntry 1 }

uxsPollNetIP OBJECT-TYPE
	SYNTAX  DisplayString
	ACCESS  read-only
	STATUS  mandatory
	DESCRIPTION
		"&<caiUxOs.601>The IP address of the interface."
	::= { uxsPollNetEntry 2 }

uxsPollNetIPktValue OBJECT-TYPE
	SYNTAX  INTEGER
	ACCESS  read-only
	STATUS  mandatory
	DESCRIPTION
		"&<caiUxOs.602>The number of input packets since the machine started."
	::= { uxsPollNetEntry 3 }

uxsPollNetIErrValue OBJECT-TYPE
	SYNTAX  INTEGER
	ACCESS  read-only
	STATUS  mandatory
	DESCRIPTION
		"&<caiUxOs.603>The number of input errors since the machine started."
	::= { uxsPollNetEntry 4 }

uxsPollNetOPktValue OBJECT-TYPE
	SYNTAX  INTEGER
	ACCESS  read-only
	STATUS  mandatory
	DESCRIPTION
		"&<caiUxOs.604>The number of output packets since the machine started."
	::= { uxsPollNetEntry 5 }

uxsPollNetOErrValue OBJECT-TYPE
	SYNTAX  INTEGER
	ACCESS  read-only
	STATUS  mandatory
	DESCRIPTION
		"&<caiUxOs.605>The number of output errors since the machine started."
	::= { uxsPollNetEntry 6 }

uxsPollNetCollValue OBJECT-TYPE
	SYNTAX  INTEGER
	ACCESS  read-only
	STATUS  mandatory
	DESCRIPTION
		"&<caiUxOs.606>The number of collisions since the machine started."
	::= { uxsPollNetEntry 7 }

--
-- uxsPollIPCGroup
--
uxsPollIPCSHMMonitor OBJECT-TYPE
	SYNTAX  INTEGER {
		do-not-monitor(1),
		monitor(2)
	}
	ACCESS  read-write
	STATUS  mandatory
	DESCRIPTION
		"&<caiUxOs.607>Defines the level of monitoring for the resource's status. Valid values: do-not-monitor(1) or monitor(2)."
	::= { uxsPollIPCGroup 1 }

uxsPollIPCSHMCount OBJECT-TYPE
	SYNTAX  INTEGER
	ACCESS  read-only
	STATUS  mandatory
	DESCRIPTION
		"&<caiUxOs.608>The number of shared memory segments in the table."
	::= { uxsPollIPCGroup 2 }

uxsPollIPCSHMTable OBJECT-TYPE
	SYNTAX  SEQUENCE OF UxsPollIPCSHMSequence
	ACCESS  not-accessible
	STATUS  mandatory
	DESCRIPTION
		"&<caiUxOs.609>The table of shared memory segments."
	::= { uxsPollIPCGroup 3 }

uxsPollIPCSEMMonitor OBJECT-TYPE
	SYNTAX  INTEGER {
		do-not-monitor(1),
		monitor(2)
	}
	ACCESS  read-write
	STATUS  mandatory
	DESCRIPTION
		"&<caiUxOs.610>Defines the level of monitoring for the resource's status. Valid values: do-not-monitor(1) or monitor(2)."
	::= { uxsPollIPCGroup 4 }

uxsPollIPCSEMCount OBJECT-TYPE
	SYNTAX  INTEGER
	ACCESS  read-only
	STATUS  mandatory
	DESCRIPTION
		"&<caiUxOs.611>The number of semaphores in the table."
	::= { uxsPollIPCGroup 5 }

uxsPollIPCSEMTable OBJECT-TYPE
	SYNTAX  SEQUENCE OF UxsPollIPCSEMSequence
	ACCESS  not-accessible
	STATUS  mandatory
	DESCRIPTION
		"&<caiUxOs.612>The table of semaphore information."
	::= { uxsPollIPCGroup 6 }

--
-- uxsPollIPCSHMTable
--
uxsPollIPCSHMEntry OBJECT-TYPE
	SYNTAX  UxsPollIPCSHMSequence
	ACCESS  not-accessible
	STATUS  mandatory
	DESCRIPTION
		"&<caiUxOs.613>"
	INDEX   { uxsPollIPCSHMID }
	::= { uxsPollIPCSHMTable 1 }

UxsPollIPCSHMSequence ::=
	SEQUENCE {
		uxsPollIPCSHMID		DisplayString,
		uxsPollIPCSHMKey	DisplayString,
		uxsPollIPCSHMMode	DisplayString,
		uxsPollIPCSHMOwner	DisplayString,
		uxsPollIPCSHMGroup	DisplayString,
		uxsPollIPCSHMMaxSize	INTEGER,
		uxsPollIPCSHMAttached	INTEGER
	}

uxsPollIPCSHMID OBJECT-TYPE
	SYNTAX  DisplayString
	ACCESS  read-only
	STATUS  mandatory
	DESCRIPTION
		"&<caiUxOs.614>The shared memory ID."
	::= { uxsPollIPCSHMEntry 1 }

uxsPollIPCSHMKey OBJECT-TYPE
	SYNTAX  DisplayString
	ACCESS  read-only
	STATUS  mandatory
	DESCRIPTION
		"&<caiUxOs.615>The shared memory key."
	::= { uxsPollIPCSHMEntry 2 }

uxsPollIPCSHMMode OBJECT-TYPE
	SYNTAX  DisplayString
	ACCESS  read-only
	STATUS  mandatory
	DESCRIPTION
		"&<caiUxOs.616>The shared memory access rights."
	::= { uxsPollIPCSHMEntry 3 }

uxsPollIPCSHMOwner OBJECT-TYPE
	SYNTAX  DisplayString
	ACCESS  read-only
	STATUS  mandatory
	DESCRIPTION
		"&<caiUxOs.617>The shared memory segment owner."
	::= { uxsPollIPCSHMEntry 4 }

uxsPollIPCSHMGroup OBJECT-TYPE
	SYNTAX  DisplayString
	ACCESS  read-only
	STATUS  mandatory
	DESCRIPTION
		"&<caiUxOs.618>The shared memory segments group."
	::= { uxsPollIPCSHMEntry 5 }

uxsPollIPCSHMMaxSize OBJECT-TYPE
	SYNTAX  INTEGER
	ACCESS  read-only
	STATUS  mandatory
	DESCRIPTION
		"&<caiUxOs.619>The shared memory segment size."
	::= { uxsPollIPCSHMEntry 6 }

uxsPollIPCSHMAttached OBJECT-TYPE
	SYNTAX  INTEGER
	ACCESS  read-only
	STATUS  mandatory
	DESCRIPTION
		"&<caiUxOs.620>The number of processes using the shared memory segment."
	::= { uxsPollIPCSHMEntry 7 }

--
-- uxsPollIPCSEMTable
--
uxsPollIPCSEMEntry OBJECT-TYPE
	SYNTAX  UxsPollIPCSEMSequence
	ACCESS  not-accessible
	STATUS  mandatory
	DESCRIPTION
		"&<caiUxOs.621>"
	INDEX   { uxsPollIPCSEMID }
	::= { uxsPollIPCSEMTable 1 }

UxsPollIPCSEMSequence ::=
	SEQUENCE {
		uxsPollIPCSEMID		DisplayString,
		uxsPollIPCSEMKey	DisplayString,
		uxsPollIPCSEMMode	DisplayString,
		uxsPollIPCSEMOwner	DisplayString,
		uxsPollIPCSEMGroup	DisplayString,
		uxsPollIPCSEMMaxNums	INTEGER
	}

uxsPollIPCSEMID OBJECT-TYPE
	SYNTAX  DisplayString
	ACCESS  read-only
	STATUS  mandatory
	DESCRIPTION
		"&<caiUxOs.622>The semaphore ID."
	::= { uxsPollIPCSEMEntry 1 }

uxsPollIPCSEMKey OBJECT-TYPE
	SYNTAX  DisplayString
	ACCESS  read-only
	STATUS  mandatory
	DESCRIPTION
		"&<caiUxOs.623>The semaphore key."
	::= { uxsPollIPCSEMEntry 2 }

uxsPollIPCSEMMode OBJECT-TYPE
	SYNTAX  DisplayString
	ACCESS  read-only
	STATUS  mandatory
	DESCRIPTION
		"&<caiUxOs.624>The semaphore access rights."
	::= { uxsPollIPCSEMEntry 3 }

uxsPollIPCSEMOwner OBJECT-TYPE
	SYNTAX  DisplayString
	ACCESS  read-only
	STATUS  mandatory
	DESCRIPTION
		"&<caiUxOs.625>The semaphore owner."
	::= { uxsPollIPCSEMEntry 4 }

uxsPollIPCSEMGroup OBJECT-TYPE
	SYNTAX  DisplayString
	ACCESS  read-only
	STATUS  mandatory
	DESCRIPTION
		"&<caiUxOs.626>The semaphore group."
	::= { uxsPollIPCSEMEntry 5 }

uxsPollIPCSEMMaxNums OBJECT-TYPE
	SYNTAX  INTEGER
	ACCESS  read-only
	STATUS  mandatory
	DESCRIPTION
		"&<caiUxOs.627>The number of semaphores."
	::= { uxsPollIPCSEMEntry 6 }

--
-- Traps
--

uxsCPUTotalUnknown TRAP-TYPE
	ENTERPRISE caiUxOs
	DESCRIPTION
		"&<caiUxOs.628>"
	::= 10000

uxsCPUTotalOK TRAP-TYPE
	ENTERPRISE caiUxOs
	DESCRIPTION
		"&<caiUxOs.629>"
	::= 10001

uxsCPUTotalWarning TRAP-TYPE
	ENTERPRISE caiUxOs
	DESCRIPTION
		"&<caiUxOs.630>"
	::= 10002

uxsCPUTotalCritical TRAP-TYPE
	ENTERPRISE caiUxOs
	DESCRIPTION
		"&<caiUxOs.631>"
	::= 10003

uxsCPUUnknown TRAP-TYPE
	ENTERPRISE caiUxOs
	DESCRIPTION
		"&<caiUxOs.632>"
	::= 10990

uxsCPUOK TRAP-TYPE
	ENTERPRISE caiUxOs
	DESCRIPTION
		"&<caiUxOs.633>"
	::= 10991

uxsCPUWarning TRAP-TYPE
	ENTERPRISE caiUxOs
	DESCRIPTION
		"&<caiUxOs.634>"
	::= 10992

uxsCPUCritical TRAP-TYPE
	ENTERPRISE caiUxOs
	DESCRIPTION
		"&<caiUxOs.635>"
	::= 10993

uxsCPUDown TRAP-TYPE
	ENTERPRISE caiUxOs
	DESCRIPTION
		"&<caiUxOs.636>"
	::= 10995

uxsCPUAdded TRAP-TYPE
	ENTERPRISE caiUxOs
	DESCRIPTION
		"&<caiUxOs.637>"
	::= 10996

uxsCPUDeleted TRAP-TYPE
	ENTERPRISE caiUxOs
	DESCRIPTION
		"&<caiUxOs.638>"
	::= 10997

uxsLoad1Unknown TRAP-TYPE
	ENTERPRISE caiUxOs
	DESCRIPTION
		"&<caiUxOs.639>"
	::= 11010

uxsLoad1OK TRAP-TYPE
	ENTERPRISE caiUxOs
	DESCRIPTION
		"&<caiUxOs.640>"
	::= 11011

uxsLoad1Warning TRAP-TYPE
	ENTERPRISE caiUxOs
	DESCRIPTION
		"&<caiUxOs.641>"
	::= 11012

uxsLoad1Critical TRAP-TYPE
	ENTERPRISE caiUxOs
	DESCRIPTION
		"&<caiUxOs.642>"
	::= 11013

uxsLoad5Unknown TRAP-TYPE
	ENTERPRISE caiUxOs
	DESCRIPTION
		"&<caiUxOs.643>"
	::= 11050

uxsLoad5OK TRAP-TYPE
	ENTERPRISE caiUxOs
	DESCRIPTION
		"&<caiUxOs.644>"
	::= 11051

uxsLoad5Warning TRAP-TYPE
	ENTERPRISE caiUxOs
	DESCRIPTION
		"&<caiUxOs.645>"
	::= 11052

uxsLoad5Critical TRAP-TYPE
	ENTERPRISE caiUxOs
	DESCRIPTION
		"&<caiUxOs.646>"
	::= 11053

uxsLoad15Unknown TRAP-TYPE
	ENTERPRISE caiUxOs
	DESCRIPTION
		"&<caiUxOs.647>"
	::= 11150

uxsLoad15OK TRAP-TYPE
	ENTERPRISE caiUxOs
	DESCRIPTION
		"&<caiUxOs.648>"
	::= 11151

uxsLoad15Warning TRAP-TYPE
	ENTERPRISE caiUxOs
	DESCRIPTION
		"&<caiUxOs.649>"
	::= 11152

uxsLoad15Critical TRAP-TYPE
	ENTERPRISE caiUxOs
	DESCRIPTION
		"&<caiUxOs.650>"
	::= 11153

uxsMemUnknown TRAP-TYPE
	ENTERPRISE caiUxOs
	DESCRIPTION
		"&<caiUxOs.651>"
	::= 12010

uxsMemOK TRAP-TYPE
	ENTERPRISE caiUxOs
	DESCRIPTION
		"&<caiUxOs.652>"
	::= 12011

uxsMemWarning TRAP-TYPE
	ENTERPRISE caiUxOs
	DESCRIPTION
		"&<caiUxOs.653>"
	::= 12012

uxsMemCritical TRAP-TYPE
	ENTERPRISE caiUxOs
	DESCRIPTION
		"&<caiUxOs.654>"
	::= 12013

uxsSwapTotalUnknown TRAP-TYPE
	ENTERPRISE caiUxOs
	DESCRIPTION
		"&<caiUxOs.655>"
	::= 13000

uxsSwapTotalOK TRAP-TYPE
	ENTERPRISE caiUxOs
	DESCRIPTION
		"&<caiUxOs.656>"
	::= 13001

uxsSwapTotalWarning TRAP-TYPE
	ENTERPRISE caiUxOs
	DESCRIPTION
		"&<caiUxOs.657>"
	::= 13002

uxsSwapTotalCritical TRAP-TYPE
	ENTERPRISE caiUxOs
	DESCRIPTION
		"&<caiUxOs.658>"
	::= 13003

uxsSwapUnknown TRAP-TYPE
	ENTERPRISE caiUxOs
	DESCRIPTION
		"&<caiUxOs.659>"
	::= 13990

uxsSwapOK TRAP-TYPE
	ENTERPRISE caiUxOs
	DESCRIPTION
		"&<caiUxOs.660>"
	::= 13991

uxsSwapWarning TRAP-TYPE
	ENTERPRISE caiUxOs
	DESCRIPTION
		"&<caiUxOs.661>"
	::= 13992

uxsSwapCritical TRAP-TYPE
	ENTERPRISE caiUxOs
	DESCRIPTION
		"&<caiUxOs.662>"
	::= 13993

uxsSwapDown TRAP-TYPE
	ENTERPRISE caiUxOs
	DESCRIPTION
		"&<caiUxOs.663>"
	::= 13995

uxsSwapAdded TRAP-TYPE
	ENTERPRISE caiUxOs
	DESCRIPTION
		"&<caiUxOs.664>"
	::= 13996

uxsSwapDeleted TRAP-TYPE
	ENTERPRISE caiUxOs
	DESCRIPTION
		"&<caiUxOs.665>"
	::= 13997

uxsFSysUnknown TRAP-TYPE
	ENTERPRISE caiUxOs
	DESCRIPTION
		"&<caiUxOs.666>"
	::= 14980

uxsFSysOK TRAP-TYPE
	ENTERPRISE caiUxOs
	DESCRIPTION
		"&<caiUxOs.667>"
	::= 14981

uxsFSysWarning TRAP-TYPE
	ENTERPRISE caiUxOs
	DESCRIPTION
		"&<caiUxOs.668>"
	::= 14982

uxsFSysCritical TRAP-TYPE
	ENTERPRISE caiUxOs
	DESCRIPTION
		"&<caiUxOs.669>"
	::= 14983

uxsFSysDown TRAP-TYPE
	ENTERPRISE caiUxOs
	DESCRIPTION
		"&<caiUxOs.670>"
	::= 14985

uxsFSysAdded TRAP-TYPE
	ENTERPRISE caiUxOs
	DESCRIPTION
		"&<caiUxOs.671>"
	::= 14986

uxsFSysDeleted TRAP-TYPE
	ENTERPRISE caiUxOs
	DESCRIPTION
		"&<caiUxOs.672>"
	::= 14987

uxsDiskUnknown TRAP-TYPE
	ENTERPRISE caiUxOs
	DESCRIPTION
		"&<caiUxOs.673>"
	::= 15980

uxsDiskOK TRAP-TYPE
	ENTERPRISE caiUxOs
	DESCRIPTION
		"&<caiUxOs.674>"
	::= 15981

uxsDiskWarning TRAP-TYPE
	ENTERPRISE caiUxOs
	DESCRIPTION
		"&<caiUxOs.675>"
	::= 15982

uxsDiskCritical TRAP-TYPE
	ENTERPRISE caiUxOs
	DESCRIPTION
		"&<caiUxOs.676>"
	::= 15983

uxsDiskDown TRAP-TYPE
	ENTERPRISE caiUxOs
	DESCRIPTION
		"&<caiUxOs.677>"
	::= 15985

uxsDiskAdded TRAP-TYPE
	ENTERPRISE caiUxOs
	DESCRIPTION
		"&<caiUxOs.678>"
	::= 15986

uxsDiskDeleted TRAP-TYPE
	ENTERPRISE caiUxOs
	DESCRIPTION
		"&<caiUxOs.679>"
	::= 15987

uxsProcUnknown TRAP-TYPE
	ENTERPRISE caiUxOs
	DESCRIPTION
		"&<caiUxOs.680>"
	::= 16980

uxsProcOK TRAP-TYPE
	ENTERPRISE caiUxOs
	DESCRIPTION
		"&<caiUxOs.681>"
	::= 16981

uxsProcWarning TRAP-TYPE
	ENTERPRISE caiUxOs
	DESCRIPTION
		"&<caiUxOs.682>"
	::= 16982

uxsProcCritical TRAP-TYPE
	ENTERPRISE caiUxOs
	DESCRIPTION
		"&<caiUxOs.683>"
	::= 16983

uxsProcDown TRAP-TYPE
	ENTERPRISE caiUxOs
	DESCRIPTION
		"&<caiUxOs.684>"
	::= 16985

uxsProcAdded TRAP-TYPE
	ENTERPRISE caiUxOs
	DESCRIPTION
		"&<caiUxOs.685>"
	::= 16986

uxsProcDeleted TRAP-TYPE
	ENTERPRISE caiUxOs
	DESCRIPTION
		"&<caiUxOs.686>"
	::= 16987

uxsFilesUnknown TRAP-TYPE
	ENTERPRISE caiUxOs
	DESCRIPTION
		"&<caiUxOs.687>"
	::= 17980

uxsFilesOK TRAP-TYPE
	ENTERPRISE caiUxOs
	DESCRIPTION
		"&<caiUxOs.688>"
	::= 17981

uxsFilesWarning TRAP-TYPE
	ENTERPRISE caiUxOs
	DESCRIPTION
		"&<caiUxOs.689>"
	::= 17982

uxsFilesCritical TRAP-TYPE
	ENTERPRISE caiUxOs
	DESCRIPTION
		"&<caiUxOs.690>"
	::= 17983

uxsFilesDown TRAP-TYPE
	ENTERPRISE caiUxOs
	DESCRIPTION
		"&<caiUxOs.691>"
	::= 17985

uxsFilesAdded TRAP-TYPE
	ENTERPRISE caiUxOs
	DESCRIPTION
		"&<caiUxOs.692>"
	::= 17986

uxsFilesDeleted TRAP-TYPE
	ENTERPRISE caiUxOs
	DESCRIPTION
		"&<caiUxOs.693>"
	::= 17987

uxsPrnUnknown TRAP-TYPE
	ENTERPRISE caiUxOs
	DESCRIPTION
		"&<caiUxOs.694>"
	::= 18980

uxsPrnOK TRAP-TYPE
	ENTERPRISE caiUxOs
	DESCRIPTION
		"&<caiUxOs.695>"
	::= 18981

uxsPrnWarning TRAP-TYPE
	ENTERPRISE caiUxOs
	DESCRIPTION
		"&<caiUxOs.696>"
	::= 18982

uxsPrnCritical TRAP-TYPE
	ENTERPRISE caiUxOs
	DESCRIPTION
		"&<caiUxOs.697>"
	::= 18983

uxsPrnDown TRAP-TYPE
	ENTERPRISE caiUxOs
	DESCRIPTION
		"&<caiUxOs.698>"
	::= 18985

uxsPrnAdded TRAP-TYPE
	ENTERPRISE caiUxOs
	DESCRIPTION
		"&<caiUxOs.699>"
	::= 18986

uxsPrnDeleted TRAP-TYPE
	ENTERPRISE caiUxOs
	DESCRIPTION
		"&<caiUxOs.700>"
	::= 18987

uxsNetTotalUnknown TRAP-TYPE
	ENTERPRISE caiUxOs
	DESCRIPTION
		"&<caiUxOs.701>"
	::= 19000

uxsNetTotalOK TRAP-TYPE
	ENTERPRISE caiUxOs
	DESCRIPTION
		"&<caiUxOs.702>"
	::= 19001

uxsNetTotalWarning TRAP-TYPE
	ENTERPRISE caiUxOs
	DESCRIPTION
		"&<caiUxOs.703>"
	::= 19002

uxsNetTotalCritical TRAP-TYPE
	ENTERPRISE caiUxOs
	DESCRIPTION
		"&<caiUxOs.704>"
	::= 19003

uxsNetUnknown TRAP-TYPE
	ENTERPRISE caiUxOs
	DESCRIPTION
		"&<caiUxOs.705>"
	::= 19990

uxsNetOK TRAP-TYPE
	ENTERPRISE caiUxOs
	DESCRIPTION
		"&<caiUxOs.706>"
	::= 19991

uxsNetWarning TRAP-TYPE
	ENTERPRISE caiUxOs
	DESCRIPTION
		"&<caiUxOs.707>"
	::= 19992

uxsNetCritical TRAP-TYPE
	ENTERPRISE caiUxOs
	DESCRIPTION
		"&<caiUxOs.708>"
	::= 19993

uxsNetDown TRAP-TYPE
	ENTERPRISE caiUxOs
	DESCRIPTION
		"&<caiUxOs.709>"
	::= 19995

uxsNetAdded TRAP-TYPE
	ENTERPRISE caiUxOs
	DESCRIPTION
		"&<caiUxOs.710>"
	::= 19996

uxsNetDeleted TRAP-TYPE
	ENTERPRISE caiUxOs
	DESCRIPTION
		"&<caiUxOs.711>"
	::= 19997


uxsIPCSHMUnknown TRAP-TYPE
	ENTERPRISE caiUxOs
	DESCRIPTION
		"&<caiUxOs.712>"
	::= 20010

uxsIPCSHMOK TRAP-TYPE
	ENTERPRISE caiUxOs
	DESCRIPTION
		"&<caiUxOs.713>"
	::= 20011

uxsIPCSHMWarning TRAP-TYPE
	ENTERPRISE caiUxOs
	DESCRIPTION
		"&<caiUxOs.714>"
	::= 20012

uxsIPCSHMCritical TRAP-TYPE
	ENTERPRISE caiUxOs
	DESCRIPTION
		"&<caiUxOs.715>"
	::= 20013

uxsIPCSEMUnknown TRAP-TYPE
	ENTERPRISE caiUxOs
	DESCRIPTION
		"&<caiUxOs.716>"
	::= 20020

uxsIPCSEMOK TRAP-TYPE
	ENTERPRISE caiUxOs
	DESCRIPTION
		"&<caiUxOs.717>"
	::= 20021

uxsIPCSEMWarning TRAP-TYPE
	ENTERPRISE caiUxOs
	DESCRIPTION
		"&<caiUxOs.718>"
	::= 20022

uxsIPCSEMCritical TRAP-TYPE
	ENTERPRISE caiUxOs
	DESCRIPTION
		"&<caiUxOs.719>"
	::= 20023

uxsIPCMQUnknown TRAP-TYPE
	ENTERPRISE caiUxOs
	DESCRIPTION
		"&<caiUxOs.720>"
	::= 20030

uxsIPCMQOK TRAP-TYPE
	ENTERPRISE caiUxOs
	DESCRIPTION
		"&<caiUxOs.721>"
	::= 20031

uxsIPCMQWarning TRAP-TYPE
	ENTERPRISE caiUxOs
	DESCRIPTION
		"&<caiUxOs.722>"
	::= 20032

uxsIPCMQCritical TRAP-TYPE
	ENTERPRISE caiUxOs
	DESCRIPTION
		"&<caiUxOs.723>"
	::= 20033

uxsIPCMQSUnknown TRAP-TYPE
	ENTERPRISE caiUxOs
	DESCRIPTION
		"&<caiUxOs.724>"
	::= 20980

uxsIPCMQSOK TRAP-TYPE
	ENTERPRISE caiUxOs
	DESCRIPTION
		"&<caiUxOs.725>"
	::= 20981

uxsIPCMQSWarning TRAP-TYPE
	ENTERPRISE caiUxOs
	DESCRIPTION
		"&<caiUxOs.726>"
	::= 20982

uxsIPCMQSCritical TRAP-TYPE
	ENTERPRISE caiUxOs
	DESCRIPTION
		"&<caiUxOs.727>"
	::= 20983

uxsIPCMQSDown TRAP-TYPE
	ENTERPRISE caiUxOs
	DESCRIPTION
		"&<caiUxOs.728>"
	::= 20985

uxsIPCMQSAdded TRAP-TYPE
	ENTERPRISE caiUxOs
	DESCRIPTION
		"&<caiUxOs.729>"
	::= 20986

uxsIPCMQSDeleted TRAP-TYPE
	ENTERPRISE caiUxOs
	DESCRIPTION
		"&<caiUxOs.730>"
	::= 20987

--  ========================================================================
--
--  Extension groups of caiUxOs MIB:
--  ---------------------------------
--  ux3EHGroup added to support reports for Concord eHealth
--
--  ========================================================================
ux3A2ExtensionGroup OBJECT IDENTIFIER ::= { caiUxOs 5 }

ux3EHGroup OBJECT IDENTIFIER ::= { ux3A2ExtensionGroup 1 }


--  ---------------------------------
--  Poll information
--  ---------------------------------
ux3EHPollMethod OBJECT-TYPE
	SYNTAX INTEGER {
		disabled(1),
		enabled(2)
	}
	ACCESS read-write
	STATUS mandatory
	DESCRIPTION "The poll method for the eHealth group. If set to disabled, polling of this group is not possible."
	DEFVAL { 2 }
	::= { ux3EHGroup 1 }

ux3EHLastPoll OBJECT-TYPE
	SYNTAX TimeTicks
	ACCESS read-only
	STATUS mandatory
	DESCRIPTION "The value of ux3EHSrvSystemUpTime at the point in time the ux3EHSrvGroup group (and all ux3EH tables) was last polled."
	::= { ux3EHGroup 2 }


--  ---------------------------------
--  Server group
--  ---------------------------------
ux3EHSrvGroup OBJECT IDENTIFIER ::= { ux3EHGroup 3 }

ux3EHSrvSystemUpTime OBJECT-TYPE
	SYNTAX TimeTicks
	ACCESS read-only
	STATUS mandatory
	DESCRIPTION "The time (in hundredths of a second) since the system was last started."
	::= { ux3EHSrvGroup 1 }

ux3EHSrvSystemNumUsers OBJECT-TYPE
	SYNTAX Gauge
	ACCESS read-only
	STATUS mandatory
	DESCRIPTION "The number of users."
	::= { ux3EHSrvGroup 2 }

ux3EHSrvSystemProcesses OBJECT-TYPE
	SYNTAX Gauge
	ACCESS read-only
	STATUS mandatory
	DESCRIPTION "The number of processes."
	::= { ux3EHSrvGroup 3 }

ux3EHSrvMemorySize OBJECT-TYPE
	SYNTAX KBytes
	ACCESS read-only
	STATUS mandatory
	DESCRIPTION "The amount of physical main memory contained by the host."
	::= { ux3EHSrvGroup 4 }

ux3EHSrvMemInUse OBJECT-TYPE
	SYNTAX Gauge
	ACCESS read-only
	STATUS mandatory
	DESCRIPTION "The total real KBytes of memory in use."
	::= { ux3EHSrvGroup 5 }

ux3EHSrvTotalSwapSpace OBJECT-TYPE
	SYNTAX INTEGER
	ACCESS read-only
	STATUS mandatory
	DESCRIPTION "Total system swap space in KBytes."
	::= { ux3EHSrvGroup 6 }

ux3EHSrvSwapInUse OBJECT-TYPE
	SYNTAX Gauge
	ACCESS read-only
	STATUS mandatory
	DESCRIPTION "The amount of swap space in KBytes currently in use by the system."
	::= { ux3EHSrvGroup 7 }

ux3EHSrvLoadAverage5Min OBJECT-TYPE
	SYNTAX INTEGER
	ACCESS read-only
	STATUS mandatory
	DESCRIPTION "The load average over the last 5 minutes. The load average represents the average number of jobs in the run queue over the specified time range. The value reported is the load average multiplied by 100."
	::= { ux3EHSrvGroup 8 }

ux3EHSrvNumBreadRequests OBJECT-TYPE
	SYNTAX Counter
	ACCESS read-only
	STATUS mandatory
	DESCRIPTION "The total number of calls to the kernel's bread() function."
	::= { ux3EHSrvGroup 9 }

ux3EHSrvNumBreadHits OBJECT-TYPE
	SYNTAX Counter
	ACCESS read-only
	STATUS mandatory
	DESCRIPTION "The number of kernel buffer cache 'hits'."
	::= { ux3EHSrvGroup 10 }

ux3EHSrvSystemCalls OBJECT-TYPE
	SYNTAX Counter
	ACCESS read-only
	STATUS mandatory
	DESCRIPTION "The number of calls to system service routines."
	::= { ux3EHSrvGroup 11 }

ux3EHSrvInterrupts OBJECT-TYPE
	SYNTAX Counter
	ACCESS read-only
	STATUS mandatory
	DESCRIPTION "The number of hardware interrupts that have occurred."
	::= { ux3EHSrvGroup 12 }

ux3EHSrvPageFaults OBJECT-TYPE
	SYNTAX Counter
	ACCESS read-only
	STATUS mandatory
	DESCRIPTION "Number of page faults in the processor."
	::= { ux3EHSrvGroup 13 }

ux3EHSrvPageSwapIns OBJECT-TYPE
	SYNTAX Counter
	ACCESS read-only
	STATUS mandatory
	DESCRIPTION "The total number of pages that have been swapped in since the kernel was last initialized."
	::= { ux3EHSrvGroup 14 }

ux3EHSrvPageSwapOuts OBJECT-TYPE
	SYNTAX Counter
	ACCESS read-only
	STATUS mandatory
	DESCRIPTION "The total number of pages that have been swapped out since the kernel was last initialized."
	::= { ux3EHSrvGroup 15 }

ux3EHSrvPageIns OBJECT-TYPE
	SYNTAX Counter
	ACCESS read-only
	STATUS mandatory
	DESCRIPTION "The total number of processes that have been swapped in since the kernel was last initialized."
	::= { ux3EHSrvGroup 16 }

ux3EHSrvPageOuts OBJECT-TYPE
	SYNTAX Counter
	ACCESS read-only
	STATUS mandatory
	DESCRIPTION "The total number of processes that have been swapped out since the kernel was last initialized."
	::= { ux3EHSrvGroup 17 }

ux3EHSrvPageScans OBJECT-TYPE
	SYNTAX Counter
	ACCESS read-only
	STATUS mandatory
	DESCRIPTION "Total number of pages examined by pageout daemon."
	::= { ux3EHSrvGroup 18 }

ux3EHSrvIfNumber OBJECT-TYPE
	SYNTAX INTEGER
	ACCESS read-only
	STATUS mandatory
	DESCRIPTION "The number of network interfaces."
	::= { ux3EHSrvGroup 19 }

--  ---------------------------------
--  Cpu table
--  ---------------------------------
ux3EHCpuTable OBJECT-TYPE
	SYNTAX SEQUENCE OF Ux3EHCpuEntry
	ACCESS not-accessible
	STATUS mandatory
	DESCRIPTION ""
	::= { ux3EHGroup 4 }

ux3EHCpuEntry OBJECT-TYPE
	SYNTAX Ux3EHCpuEntry
	ACCESS not-accessible
	STATUS mandatory
	DESCRIPTION ""
	INDEX { ux3EHCpuIndex }
	::= { ux3EHCpuTable 1 }

Ux3EHCpuEntry ::= SEQUENCE {
	ux3EHCpuIndex INTEGER,
	ux3EHCpuName DisplayString,
	ux3EHCpuIdle Counter,
	ux3EHCpuUser Counter,
	ux3EHCpuSys Counter,
	ux3EHCpuWait Counter
}

ux3EHCpuIndex OBJECT-TYPE
	SYNTAX INTEGER (1..2147483647)
	ACCESS read-only
	STATUS mandatory
	DESCRIPTION "The unique index of this table entry."
	::= { ux3EHCpuEntry 1 }

ux3EHCpuName OBJECT-TYPE
	SYNTAX DisplayString
	ACCESS read-only
	STATUS mandatory
	DESCRIPTION "The name of the CPU (in the format 'Cpu-N')."
	::= { ux3EHCpuEntry 2 }

ux3EHCpuIdle OBJECT-TYPE
	SYNTAX Counter
	ACCESS read-only
	STATUS mandatory
	DESCRIPTION "The total number of 'ticks' spent by this CPU in Idle mode."
	::= { ux3EHCpuEntry 3 }

ux3EHCpuUser OBJECT-TYPE
	SYNTAX Counter
	ACCESS read-only
	STATUS mandatory
	DESCRIPTION "The total number of 'ticks' spent by this CPU in User mode."
	::= { ux3EHCpuEntry 4 }

ux3EHCpuSys OBJECT-TYPE
	SYNTAX Counter
	ACCESS read-only
	STATUS mandatory
	DESCRIPTION "The total number of 'ticks' spent by this CPU in System mode."
	::= { ux3EHCpuEntry 5 }

ux3EHCpuWait OBJECT-TYPE
	SYNTAX Counter
	ACCESS read-only
	STATUS mandatory
	DESCRIPTION "The total number of 'ticks' spent by this CPU in Wait mode."
	::= { ux3EHCpuEntry 6 }


--  ---------------------------------
--  Disk table
--  ---------------------------------
ux3EHDiskTable OBJECT-TYPE
	SYNTAX SEQUENCE OF Ux3EHDiskEntry
	ACCESS not-accessible
	STATUS mandatory
	DESCRIPTION ""
	::= { ux3EHGroup 5 }

ux3EHDiskEntry OBJECT-TYPE
	SYNTAX Ux3EHDiskEntry
	ACCESS not-accessible
	STATUS mandatory
	DESCRIPTION ""
	INDEX { ux3EHDiskIndex }
	::= { ux3EHDiskTable 1 }

Ux3EHDiskEntry ::= SEQUENCE {
	ux3EHDiskIndex INTEGER,
	ux3EHDiskName DisplayString,
	ux3EHDiskDeviceErrors Counter,
	ux3EHDiskStorageCapacity INTEGER,
	ux3EHDiskQueueLength Gauge,
	ux3EHDiskUtilization INTEGER,
	ux3EHDiskKBytesTransferred Counter,
	ux3EHDiskReads Counter,
	ux3EHDiskWrites Counter
}

ux3EHDiskIndex OBJECT-TYPE
	SYNTAX INTEGER (1..2147483647)
	ACCESS read-only
	STATUS mandatory
	DESCRIPTION "The unique index of this table entry."
	::= { ux3EHDiskEntry 1 }

ux3EHDiskName OBJECT-TYPE
	SYNTAX DisplayString
	ACCESS read-only
	STATUS mandatory
	DESCRIPTION "The name of the disk (in the format 'HarddiskN')."
	::= { ux3EHDiskEntry 2 }

ux3EHDiskDeviceErrors OBJECT-TYPE
	SYNTAX Counter
	ACCESS read-only
	STATUS mandatory
	DESCRIPTION "The number of errors detected on this disk."
	::= { ux3EHDiskEntry 3 }

ux3EHDiskStorageCapacity OBJECT-TYPE
	SYNTAX INTEGER (0..2147483647)
	ACCESS read-only
	STATUS mandatory
	DESCRIPTION "Disk capacity in KB."
	::= { ux3EHDiskEntry 4 }

ux3EHDiskQueueLength OBJECT-TYPE
	SYNTAX Gauge
	ACCESS read-only
	STATUS mandatory
	DESCRIPTION "The average number of operations waiting in the disk's service queue over the last measurement period."
	::= { ux3EHDiskEntry 5 }

ux3EHDiskUtilization OBJECT-TYPE
	SYNTAX INTEGER (0..100)
	ACCESS read-only
	STATUS mandatory
	DESCRIPTION "The utilization rate (percentage) for this disk over the last measurement period."
	::= { ux3EHDiskEntry 6 }

ux3EHDiskKBytesTransferred OBJECT-TYPE
	SYNTAX Counter
	ACCESS read-only
	STATUS mandatory
	DESCRIPTION "The number of KBytes transferred to/from this disk."
	::= { ux3EHDiskEntry 7}

ux3EHDiskReads OBJECT-TYPE
	SYNTAX Counter
	ACCESS read-only
	STATUS mandatory
	DESCRIPTION "The number of read operations from this disk."
	::= { ux3EHDiskEntry 8 }

ux3EHDiskWrites OBJECT-TYPE
	SYNTAX Counter
	ACCESS read-only
	STATUS mandatory
	DESCRIPTION "The number of write operations to this disk."
	::= { ux3EHDiskEntry 9 }


--  ---------------------------------
--  Device (partition) table
--  ---------------------------------
ux3EHDevTable OBJECT-TYPE
	SYNTAX SEQUENCE OF Ux3EHDevEntry
	ACCESS not-accessible
	STATUS mandatory
	DESCRIPTION ""
	::= { ux3EHGroup 6 }

ux3EHDevEntry OBJECT-TYPE
	SYNTAX Ux3EHDevEntry
	ACCESS not-accessible
	STATUS mandatory
	DESCRIPTION ""
	INDEX { ux3EHDevIndex }
	::= { ux3EHDevTable 1 }

Ux3EHDevEntry ::= SEQUENCE {
	ux3EHDevIndex INTEGER,
	ux3EHDevName DisplayString,
	ux3EHDevBsize INTEGER,
	ux3EHDevTblks INTEGER,
	ux3EHDevCapacity INTEGER,
	ux3EHDevInodeCapacity INTEGER,
	ux3EHDevStorageAllocationFailures Counter
}

ux3EHDevIndex OBJECT-TYPE
	SYNTAX INTEGER (1..2147483647)
	ACCESS read-only
	STATUS mandatory
	DESCRIPTION "The unique index of this table entry."
	::= { ux3EHDevEntry 1 }

ux3EHDevName OBJECT-TYPE
	SYNTAX DisplayString
	ACCESS read-only
	STATUS mandatory
	DESCRIPTION "The name of the device (partition)."
	::= { ux3EHDevEntry 2 }

ux3EHDevBsize OBJECT-TYPE
	SYNTAX INTEGER
	ACCESS read-only
	STATUS mandatory
	DESCRIPTION "The block size of the mounted device in bytes."
	::= { ux3EHDevEntry 3 }

ux3EHDevTblks OBJECT-TYPE
	SYNTAX INTEGER
	ACCESS read-only
	STATUS mandatory
	DESCRIPTION "The total number of blocks contained in the mounted device."
	::= { ux3EHDevEntry 4 }

ux3EHDevCapacity OBJECT-TYPE
	SYNTAX INTEGER (0..100)
	ACCESS read-only
	STATUS mandatory
	DESCRIPTION "The percentage of the device's total capacity in use."
	::= { ux3EHDevEntry 5 }

ux3EHDevInodeCapacity OBJECT-TYPE
	SYNTAX INTEGER (0..100)
	ACCESS read-only
	STATUS mandatory
	DESCRIPTION "The percentage of the device's total file capacity (inodes) in use."
	::= { ux3EHDevEntry 6 }

ux3EHDevStorageAllocationFailures OBJECT-TYPE
	SYNTAX Counter
	ACCESS read-only
	STATUS mandatory
	DESCRIPTION "The number of requests for storage represented by this entry that could not be honored due to not enough storage."
	::= { ux3EHDevEntry 7 }


--  ---------------------------------
--  Network interface table
--  ---------------------------------
ux3EHIfTable OBJECT-TYPE
	SYNTAX SEQUENCE OF Ux3EHIfEntry
	ACCESS not-accessible
	STATUS mandatory
	DESCRIPTION ""
	::= { ux3EHGroup 7 }

ux3EHIfEntry OBJECT-TYPE
	SYNTAX Ux3EHIfEntry
	ACCESS not-accessible
	STATUS mandatory
	DESCRIPTION ""
	INDEX { ux3EHIfIndex }
	::= { ux3EHIfTable 1 }

Ux3EHIfEntry ::= SEQUENCE {
	ux3EHIfIndex INTEGER,
	ux3EHIfDescr DisplayString,
	ux3EHIfType INTEGER,
	ux3EHIfSpeed Gauge,
	ux3EHIfPhysAddress PhysAddress,
	ux3EHIfAdminStatus INTEGER,
	ux3EHIfOperStatus INTEGER,
	ux3EHIfLastChange TimeTicks,
	ux3EHIfInOctets Counter,
	ux3EHIfInUcastPkts Counter,
	ux3EHIfInNUcastPkts Counter,
	ux3EHIfInDiscards Counter,
	ux3EHIfInErrors Counter,
	ux3EHIfInUnknownProtos Counter,
	ux3EHIfOutOctets Counter,
	ux3EHIfOutUcastPkts Counter,
	ux3EHIfOutNUcastPkts Counter,
	ux3EHIfOutDiscards Counter,
	ux3EHIfOutErrors Counter,
	ux3EHIfIpAdEntAddr IpAddress
}

ux3EHIfIndex OBJECT-TYPE
	SYNTAX INTEGER (1..2147483647)
	ACCESS read-only
	STATUS mandatory
	DESCRIPTION "The unique index of this table entry."
	::= { ux3EHIfEntry 1 }

ux3EHIfDescr OBJECT-TYPE
	SYNTAX DisplayString
	ACCESS read-only
	STATUS mandatory
	DESCRIPTION "The description of the network interface."
	::= { ux3EHIfEntry 2 }

ux3EHIfType OBJECT-TYPE
	SYNTAX INTEGER
	ACCESS read-only
	STATUS mandatory
	DESCRIPTION "The type of interface."
	::= { ux3EHIfEntry 3 }

ux3EHIfSpeed OBJECT-TYPE
	SYNTAX Gauge
	ACCESS read-only
	STATUS mandatory
	DESCRIPTION "An estimate of the interface's current bandwidth in bits per second."
	::= { ux3EHIfEntry 4 }

ux3EHIfPhysAddress OBJECT-TYPE
	SYNTAX PhysAddress
	ACCESS read-only
	STATUS mandatory
	DESCRIPTION "The interface's address at the protocol layer."
	::= { ux3EHIfEntry 5 }

ux3EHIfAdminStatus OBJECT-TYPE
	SYNTAX INTEGER {
		up(1),
		down(2),
		testing(3),
		unknown(4),
		dormant(5)
	}
	ACCESS read-only
	STATUS mandatory
	DESCRIPTION "The desired state of the interface."
	::= { ux3EHIfEntry 6 }

ux3EHIfOperStatus OBJECT-TYPE
	SYNTAX INTEGER {
		up(1),
		down(2),
		testing(3),
		unknown(4),
		dormant(5)
	}
	ACCESS read-only
	STATUS mandatory
	DESCRIPTION "The current operational state of the interface."
	::= { ux3EHIfEntry 7 }

ux3EHIfLastChange OBJECT-TYPE
	SYNTAX TimeTicks
	ACCESS read-only
	STATUS mandatory
	DESCRIPTION "The value of sysUpTime at the time the interface entered its current operational state."
	::= { ux3EHIfEntry 8 }

ux3EHIfInOctets OBJECT-TYPE
	SYNTAX Counter
	ACCESS read-only
	STATUS mandatory
	DESCRIPTION "The total number of octets received on the interface, including framing characters."
	::= { ux3EHIfEntry 9 }

ux3EHIfInUcastPkts OBJECT-TYPE
	SYNTAX Counter
	ACCESS read-only
	STATUS mandatory
	DESCRIPTION "The number of subnetwork-unicast packets delivered to a higher-layer protocol."
	::= { ux3EHIfEntry 10 }

ux3EHIfInNUcastPkts OBJECT-TYPE
	SYNTAX Counter
	ACCESS read-only
	STATUS mandatory
	DESCRIPTION "The number of non-unicast (i.e., subnetwork-broadcast or subnetwork-multicast) packets delivered to a higher-layer protocol."
	::= { ux3EHIfEntry 11 }

ux3EHIfInDiscards OBJECT-TYPE
	SYNTAX Counter
	ACCESS read-only
	STATUS mandatory
	DESCRIPTION "The number of inbound packets which were chosen to be discarded even though no errors had been detected to prevent their being deliverable to a higher-layer protocol."
	::= { ux3EHIfEntry 12 }

ux3EHIfInErrors OBJECT-TYPE
	SYNTAX Counter
	ACCESS read-only
	STATUS mandatory
	DESCRIPTION "The number of inbound packets that contained errors preventing them from being deliverable to a higher-layer protocol."
	::= { ux3EHIfEntry 13 }

ux3EHIfInUnknownProtos OBJECT-TYPE
	SYNTAX Counter
	ACCESS read-only
	STATUS mandatory
	DESCRIPTION "The number of packets received via the interface which were discarded because of an unknown or unsupported protocol."
	::= { ux3EHIfEntry 14 }

ux3EHIfOutOctets OBJECT-TYPE
	SYNTAX Counter
	ACCESS read-only
	STATUS mandatory
	DESCRIPTION "The total number of octets transmitted out of the interface, including framing characters."
	::= { ux3EHIfEntry 15 }

ux3EHIfOutUcastPkts OBJECT-TYPE
	SYNTAX Counter
	ACCESS read-only
	STATUS mandatory
	DESCRIPTION "The total number of packets that higher-level protocols requested be transmitted to a subnetwork-unicast address, including those that were discarded or not sent."
	::= { ux3EHIfEntry 16 }

ux3EHIfOutNUcastPkts OBJECT-TYPE
	SYNTAX Counter
	ACCESS read-only
	STATUS mandatory
	DESCRIPTION "The total number of packets that higher-level protocols requested be transmitted to a non-unicast (i.e., a subnetwork-broadcast or subnetwork-multicast) address, including those that were discarded or not sent."
	::= { ux3EHIfEntry 17 }

ux3EHIfOutDiscards OBJECT-TYPE
	SYNTAX Counter
	ACCESS read-only
	STATUS mandatory
	DESCRIPTION "The number of outbound packets which were chosen to be discarded even though no errors had been detected to prevent their being transmitted."
	::= { ux3EHIfEntry 18 }

ux3EHIfOutErrors OBJECT-TYPE
	SYNTAX Counter
	ACCESS read-only
	STATUS mandatory
	DESCRIPTION "The number of outbound packets that could not be transmitted because of errors."
	::= { ux3EHIfEntry 19 }

ux3EHIfIpAdEntAddr OBJECT-TYPE
	SYNTAX IpAddress
	ACCESS read-only
	STATUS mandatory
	DESCRIPTION "The IP address."
	::= { ux3EHIfEntry 20 }


--  ---------------------------------
--  Process table
--  ---------------------------------
ux3EHProcTable OBJECT-TYPE
	SYNTAX SEQUENCE OF Ux3EHProcEntry
	ACCESS not-accessible
	STATUS mandatory
	DESCRIPTION ""
	::= { ux3EHGroup 8 }

ux3EHProcEntry OBJECT-TYPE
	SYNTAX Ux3EHProcEntry
	ACCESS not-accessible
	STATUS mandatory
	DESCRIPTION ""
	INDEX { ux3EHProcName }
	::= { ux3EHProcTable 1 }

Ux3EHProcEntry ::= SEQUENCE {
	ux3EHProcName DisplayString,
	ux3EHProcNumber INTEGER,
	ux3EHProcPid DisplayString,
	ux3EHProcState INTEGER,
	ux3EHProcSize Gauge,
	ux3EHProcRSS Gauge,
	ux3EHProcTime INTEGER,
	ux3EHProcMinorPgFlts Counter,
	ux3EHProcMajorPgFlts Counter
}

ux3EHProcName OBJECT-TYPE
	SYNTAX DisplayString
	ACCESS read-only
	STATUS mandatory
	DESCRIPTION "The unique index (process name) of this table entry. This name is case-sensitive."
	::= { ux3EHProcEntry 1 }

ux3EHProcNumber OBJECT-TYPE
	SYNTAX INTEGER
	ACCESS read-only
	STATUS mandatory
	DESCRIPTION "The number of processes with this name."
	::= { ux3EHProcEntry 2 }

ux3EHProcPid OBJECT-TYPE
	SYNTAX DisplayString
	ACCESS read-only
	STATUS mandatory
	DESCRIPTION "The process identifier (PID). If ux3EHProcNumber is greater one, this attribute lists all PIDs, delimited by a pipe sign."
	::= { ux3EHProcEntry 3 }

ux3EHProcState OBJECT-TYPE
	SYNTAX INTEGER {
		starting(1),
		runnable(2),
		active(3),
		wait(4),
		sleeping(5),
		swapped(6),
		sleep(7),
		stop(8),
		other(9),
		zombie(10)
	}
	ACCESS read-only
	STATUS deprecated
	DESCRIPTION "The process state. Not all states are supported on all platforms. If ux3EHProcNumber is greater one, this attribute is set to other(9)."
	::= { ux3EHProcEntry 4 }

ux3EHProcSize OBJECT-TYPE
	SYNTAX Gauge
	ACCESS read-only
	STATUS mandatory
	DESCRIPTION "The combined size of the text, data and stack segments in KBytes. If ux3EHProcNumber is greater one, this attribute is the accumulated value."
::= { ux3EHProcEntry 5 }

ux3EHProcRSS OBJECT-TYPE
	SYNTAX Gauge
	ACCESS read-only
	STATUS mandatory
	DESCRIPTION "Real memory (resident set) size of the process in KBytes. If ux3EHProcNumber is greater one, this attribute is the accumulated value."
::= { ux3EHProcEntry 6 }

ux3EHProcTime OBJECT-TYPE
	SYNTAX INTEGER
	ACCESS read-only
	STATUS mandatory
	DESCRIPTION "This process' accumulated CPU time in seconds. If ux3EHProcNumber is greater one, this attribute is the accumulated value."
::= { ux3EHProcEntry 7 }

ux3EHProcMinorPgFlts OBJECT-TYPE
	SYNTAX Counter
	ACCESS read-only
	STATUS mandatory
	DESCRIPTION "The number of minor page faults incurred by this process. Minor faults do not require I/O to retrieve the page. If ux3EHProcNumber is greater one, this attribute is the accumulated value."
::= { ux3EHProcEntry 8 }

ux3EHProcMajorPgFlts OBJECT-TYPE
	SYNTAX Counter
	ACCESS read-only
	STATUS mandatory
	DESCRIPTION "The number of major page faults incurred by this process. Major faults require I/O to retrieve the page. If ux3EHProcNumber is greater one, this attribute is the accumulated value."
::= { ux3EHProcEntry 9 }


END
