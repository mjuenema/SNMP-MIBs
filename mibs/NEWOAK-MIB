--
        NEWOAK-MIB DEFINITIONS ::= BEGIN
                
        IMPORTS
                enterprises							FROM RFC1155-SMI
				MODULE-IDENTITY				 		FROM SNMPv2-SMI;

      newoak    OBJECT IDENTIFIER ::= { enterprises 2505 }

-- The following MODULE-IDENTITY definition can be commented out if the MIB parser
-- you are using has trouble parsing it. If you do comment it out, then uncomment 
-- the following object identifier defintion. 
--    contivity OBJECT IDENTIFIER ::= {newoak 1}
--
	  contivity  MODULE-IDENTITY
			LAST-UPDATED "0004252130Z"  -- April 25, 2000 7:30pm EST
			ORGANIZATION "Nortel Networks,Inc."
			CONTACT-INFO
				   "support@nortelnetworks.com
            Postal: Nortel Networks,Inc.
                    80 Central St.
                    Boxboro, MA 01719
            Tel:    +1 978 264 7100
            E-Mail: support@nortelnetworks.com"

			DESCRIPTION
				"This MIB defines the sysObjectIDs for different variations
				 of the Convitiy Extranet Switch."
			REVISION     "0005122045Z"   -- May 12, 2000 4:45pm EST
			DESCRIPTION
                "Reversed the 1600 and 2600 ids."
			::= { newoak 1 }

-- Wish we could do this BUT, its already taken	  contivityExtranetSwitch4000 OBJECT IDENTIFIER ::= {newoak 1}
	  contivityExtranetSwitch2000 OBJECT IDENTIFIER ::= {newoak 2}
	  contivityExtranetSwitch1000 OBJECT IDENTIFIER ::= {newoak 3}
	  contivityExtranetSwitch4500 OBJECT IDENTIFIER ::= {newoak 4}
	  contivityExtranetSwitch15XX OBJECT IDENTIFIER ::= {newoak 5}
	  contivityExtranetSwitch2500 OBJECT IDENTIFIER ::= {newoak 6}
	  contivityExtranetSwitch1600 OBJECT IDENTIFIER ::= {newoak 7}
	  contivityExtranetSwitch2600 OBJECT IDENTIFIER ::= {newoak 8}
	  contivityExtranetSwitch4600 OBJECT IDENTIFIER ::= {newoak 9} 
	  contivityExtranetSwitch1700 OBJECT IDENTIFIER ::= {newoak 1700}
	  contivityExtranetSwitch1740 OBJECT IDENTIFIER ::= {newoak 1740}
	  contivityExtranetSwitch1750 OBJECT IDENTIFIER ::= {newoak 1750}
	  contivityExtranetSwitch2700 OBJECT IDENTIFIER ::= {newoak 2700}
	  contivityExtranetSwitch1010 OBJECT IDENTIFIER ::= {newoak 1010}
	  contivityExtranetSwitch1050 OBJECT IDENTIFIER ::= {newoak 1050}
	  contivityExtranetSwitch1100 OBJECT IDENTIFIER ::= {newoak 1100}
	  contivityExtranetSwitch600 OBJECT IDENTIFIER ::= {newoak 600}  
	  contivityExtranetSwitch5000 OBJECT IDENTIFIER ::= {newoak 5000} 

      END
