--
--
-- ACMEPACKET-TC-MIB: Acme Packet Environmental Monitor MIB file
--
-- May 2012
--
-- Copyright (c) by Acme Packet, Inc.
-- All rights reserved.
----------------------------------------------------------------------

ACMEPACKET-TC DEFINITIONS ::= BEGIN

IMPORTS
        MODULE-IDENTITY
                FROM SNMPv2-SMI
        TEXTUAL-CONVENTION, DisplayString, TruthValue
                FROM SNMPv2-TC
        acmepacket
                FROM ACMEPACKET-SMI
        MODULE-COMPLIANCE, OBJECT-GROUP, NOTIFICATION-GROUP
                FROM SNMPv2-CONF;

apTextualConventions MODULE-IDENTITY
        LAST-UPDATED "201205082305Z"
        ORGANIZATION "Acme Packet, Inc."
	CONTACT-INFO
		"	Customer Service
		Postal: Acme Packet, Inc
			100 Crosby Drive
			Bedford, MA 01730
			US
		Tel:	1-781-328-4400
		E-mail:	support@acmepacket.com"
        DESCRIPTION  "This module contains common textual convention
                     definitons used by various Acme Packet MIB modules."
        REVISION     "201202062305Z"
        DESCRIPTION  "Initial revision."
        REVISION     "201205052305Z"
        DESCRIPTION  "Expanded ApHardwareModuleFamily with niu10g."
        ::= { acmepacket 0 }


ApHardwareModuleFamily ::= TEXTUAL-CONVENTION
        STATUS          current
        DESCRIPTION
               "The hardware module types."
        SYNTAX INTEGER {
	                unknown(0),
			spu(17),
			npu(18),
			tcu(19),
			niuCopper(24),
			niuFiber(25),
			miu(26),
			fanTray(240),
			powerSupply(241),
			niu10g(242)
		       }

ApRedundancyState ::= TEXTUAL-CONVENTION
        STATUS          current
        DESCRIPTION
               "The redundancy states that system or card can be in."
        SYNTAX INTEGER {
                unknown(0),             -- unrecognised state
                initial(1),             -- initial stage
                active(2),              -- active state
                standby(3),             -- standby state
                outOfService(4),        -- out of service
                unassigned(5),          -- unassigned state
                activePending(6),       -- becoming active
                standbyPending(7),      -- becoming standby
                outOfServicePending(8), -- becoming OOS
                recovery(9)             -- recovey state
                }


ApPhyPortType ::= TEXTUAL-CONVENTION
        STATUS          current
        DESCRIPTION
               "The physical port type."
        SYNTAX INTEGER {
	                unknown(0),
			sfp(1)
		       }

ApPresence ::= TEXTUAL-CONVENTION
        STATUS          current
        DESCRIPTION
               "The Presence of the physical entity."
        SYNTAX INTEGER {
	                unknown(0),
			inserted(1),
			removed(2)
		       }

ApTransportType ::= TEXTUAL-CONVENTION
        STATUS          current
        DESCRIPTION
               "The transport type."
        SYNTAX INTEGER {
	                unknown(0),
			tcp(1),
			sctp(2)
		       }

ApServerStatus ::= TEXTUAL-CONVENTION
        STATUS          current
        DESCRIPTION
               "The server status ."
        SYNTAX INTEGER { 	
	                inservice(0),
			lowerpriority(1),
			oosunreachable(2)
		       }

ApDiamResultCode ::= TEXTUAL-CONVENTION
       STATUS                current
       DESCRIPTION
              "The Result-Code AVP (268) value 
               RFC 3588, 7.1. Result-Code AVP"
       SYNTAX  INTEGER {
                    diameterMultiRoundAuth(1001),
                    diameterSuccess(2001),
                    diameterLimitedSuccess(2002),
                    diameterCommandUnsupported(3001),
                    diameterUnableToDeliver(3002),
                    diameterRealmNotServed(3003),
                    diameterTooBusy(3004),
                    diameterLoopDetected(3005),
                    diameterRedirectIndicatoion(3006),
                    diameterApplicationUnsupported(3007),
                    diameterInvalidHdrBits(3008),
                    diameterInvalidAvpBits(3009),
                    diameterUnknownPeer(3010),
                    diameterAuthenticationRejected(4001),
                    diameterOutOfSpace(4002),
                    electionLost(4003),
                    diameterAvpUnsupported(5001),
                    diameterUnknownSessionId(5002),
                    diameterAuthoriszationRejected(5003),
                    diameterInvalidAvpValue(5004),
                    diameterMissingAvp(5005),
                    diameterResourcesExceeded(5006),
                    diameterContradictingAvps(5007),
                    diameterAvpNotAllowed(5008),
                    diameterAvpTooManyTimes(5009),
                    diameterNoCommonApplication(5010),
                    diameterUnsupportedVersion(5011),
                    diameterUnableToComply(5012),
                    diameterInvalidBitInHeader(5013),
                    diameterInvalidAvpLength(5014),
                    diameterInvalidMessageLength(5015),
                    diameterInvalidAvpBitCombo(5016),
                    diameterNoCommonSecurity(5017)
               }
       
ApPercentage ::= TEXTUAL-CONVENTION
--	DISPLAY_HINT "d"
	STATUS		 current
	DESCRIPTION
		"This value is percentage. For example, if the value from 
		GETs is 15, which means 15%, or 0.15."
	SYNTAX         INTEGER (0..100)


END
