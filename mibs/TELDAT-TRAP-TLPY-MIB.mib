-- file automatically created


TELDAT-TRAP-TLPY-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tlpyTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TLPY event subsystem."
    REVISION "201401200930Z"
    DESCRIPTION "Initial implementation"
        ::= { telEventTraps 184 }


tlpyEventsGroup	OBJECT IDENTIFIER	::= { tlpyTrapsMIB 1 }

tlpyNotifications	OBJECT IDENTIFIER	::= { tlpyTrapsMIB 2 }
tlpyNotificationsPrefix	OBJECT IDENTIFIER	::= { tlpyNotifications 0 }

tlpyEventObjects1 OBJECT-IDENTITY
    STATUS current
    DESCRIPTION
        "Event TLPY.1
        Call events."
    ::= { tlpyEventsGroup 1 }

tlpy1_event OBJECT-TYPE
    SYNTAX DisplayString
    MAX-ACCESS accessible-for-notify
    STATUS current
    DESCRIPTION
        "Parameter 'event' in event TLPY.1"
    ::= { tlpyEventObjects1 1 }

tlpy1_caller OBJECT-TYPE
    SYNTAX DisplayString
    MAX-ACCESS accessible-for-notify
    STATUS current
    DESCRIPTION
        "Parameter 'caller' in event TLPY.1"
    ::= { tlpyEventObjects1 2 }

tlpy1_indp OBJECT-TYPE
    SYNTAX Integer32
    MAX-ACCESS accessible-for-notify
    STATUS current
    DESCRIPTION
        "Parameter 'indp' in event TLPY.1"
    ::= { tlpyEventObjects1 3 }

tlpy1_called OBJECT-TYPE
    SYNTAX DisplayString
    MAX-ACCESS accessible-for-notify
    STATUS current
    DESCRIPTION
        "Parameter 'called' in event TLPY.1"
    ::= { tlpyEventObjects1 4 }

tlpy1_outdp OBJECT-TYPE
    SYNTAX Integer32
    MAX-ACCESS accessible-for-notify
    STATUS current
    DESCRIPTION
        "Parameter 'outdp' in event TLPY.1"
    ::= { tlpyEventObjects1 5 }

tlpy1_cdr OBJECT-TYPE
    SYNTAX Integer32
    MAX-ACCESS accessible-for-notify
    STATUS current
    DESCRIPTION
        "Parameter 'cdr' in event TLPY.1"
    ::= { tlpyEventObjects1 6 }

tlpyEventObjects2 OBJECT-IDENTITY
    STATUS current
    DESCRIPTION
        "Event TLPY.2
        Call transfer event."
    ::= { tlpyEventsGroup 2 }

tlpy2_call1 OBJECT-TYPE
    SYNTAX DisplayString
    MAX-ACCESS accessible-for-notify
    STATUS current
    DESCRIPTION
        "Parameter 'call1' in event TLPY.2"
    ::= { tlpyEventObjects2 1 }

tlpy2_call2 OBJECT-TYPE
    SYNTAX DisplayString
    MAX-ACCESS accessible-for-notify
    STATUS current
    DESCRIPTION
        "Parameter 'call2' in event TLPY.2"
    ::= { tlpyEventObjects2 2 }

tlpyEventObjects3 OBJECT-IDENTITY
    STATUS current
    DESCRIPTION
        "Event TLPY.3
        NSLA changed."
    ::= { tlpyEventsGroup 3 }

tlpy3_dialpeer OBJECT-TYPE
    SYNTAX Integer32
    MAX-ACCESS accessible-for-notify
    STATUS current
    DESCRIPTION
        "Parameter 'dialpeer' in event TLPY.3"
    ::= { tlpyEventObjects3 1 }

tlpy3_status OBJECT-TYPE
    SYNTAX DisplayString
    MAX-ACCESS accessible-for-notify
    STATUS current
    DESCRIPTION
        "Parameter 'status' in event TLPY.3"
    ::= { tlpyEventObjects3 2 }

tlpyEventObjects4 OBJECT-IDENTITY
    STATUS current
    DESCRIPTION
        "Event TLPY.4
        Control status changed."
    ::= { tlpyEventsGroup 4 }

tlpy4_calltype OBJECT-TYPE
    SYNTAX DisplayString
    MAX-ACCESS accessible-for-notify
    STATUS current
    DESCRIPTION
        "Parameter 'calltype' in event TLPY.4"
    ::= { tlpyEventObjects4 1 }

tlpy4_status OBJECT-TYPE
    SYNTAX DisplayString
    MAX-ACCESS accessible-for-notify
    STATUS current
    DESCRIPTION
        "Parameter 'status' in event TLPY.4"
    ::= { tlpyEventObjects4 2 }

tlpyEventObjects5 OBJECT-IDENTITY
    STATUS current
    DESCRIPTION
        "Event TLPY.5
        Found dial-peer."
    ::= { tlpyEventsGroup 5 }

tlpy5_dialpeer OBJECT-TYPE
    SYNTAX Integer32
    MAX-ACCESS accessible-for-notify
    STATUS current
    DESCRIPTION
        "Parameter 'dialpeer' in event TLPY.5"
    ::= { tlpyEventObjects5 1 }

tlpy5_called-number OBJECT-TYPE
    SYNTAX DisplayString
    MAX-ACCESS accessible-for-notify
    STATUS current
    DESCRIPTION
        "Parameter 'called-number' in event TLPY.5"
    ::= { tlpyEventObjects5 2 }

tlpy5_calling-number OBJECT-TYPE
    SYNTAX DisplayString
    MAX-ACCESS accessible-for-notify
    STATUS current
    DESCRIPTION
        "Parameter 'calling-number' in event TLPY.5"
    ::= { tlpyEventObjects5 3 }

tlpyEventObjects6 OBJECT-IDENTITY
    STATUS current
    DESCRIPTION
        "Event TLPY.6
        Found dial-peer."
    ::= { tlpyEventsGroup 6 }

tlpy6_dialpeer OBJECT-TYPE
    SYNTAX Integer32
    MAX-ACCESS accessible-for-notify
    STATUS current
    DESCRIPTION
        "Parameter 'dialpeer' in event TLPY.6"
    ::= { tlpyEventObjects6 1 }

tlpy6_called-number OBJECT-TYPE
    SYNTAX DisplayString
    MAX-ACCESS accessible-for-notify
    STATUS current
    DESCRIPTION
        "Parameter 'called-number' in event TLPY.6"
    ::= { tlpyEventObjects6 2 }

tlpyEventObjects7 OBJECT-IDENTITY
    STATUS current
    DESCRIPTION
        "Event TLPY.7
        Dial-peer not found."
    ::= { tlpyEventsGroup 7 }

tlpy7_direction OBJECT-TYPE
    SYNTAX DisplayString
    MAX-ACCESS accessible-for-notify
    STATUS current
    DESCRIPTION
        "Parameter 'direction' in event TLPY.7"
    ::= { tlpyEventObjects7 1 }

tlpy7_called-number OBJECT-TYPE
    SYNTAX DisplayString
    MAX-ACCESS accessible-for-notify
    STATUS current
    DESCRIPTION
        "Parameter 'called-number' in event TLPY.7"
    ::= { tlpyEventObjects7 2 }

tlpy7_calling-number OBJECT-TYPE
    SYNTAX DisplayString
    MAX-ACCESS accessible-for-notify
    STATUS current
    DESCRIPTION
        "Parameter 'calling-number' in event TLPY.7"
    ::= { tlpyEventObjects7 3 }

tlpyEventObjects8 OBJECT-IDENTITY
    STATUS current
    DESCRIPTION
        "Event TLPY.8
        This message shows the percentage of lost frames in the last second."
    ::= { tlpyEventsGroup 8 }

tlpy8_num OBJECT-TYPE
    SYNTAX Integer32
    MAX-ACCESS accessible-for-notify
    STATUS current
    DESCRIPTION
        "Parameter 'num' in event TLPY.8"
    ::= { tlpyEventObjects8 1 }

tlpy8_per OBJECT-TYPE
    SYNTAX Integer32
    MAX-ACCESS accessible-for-notify
    STATUS current
    DESCRIPTION
        "Parameter 'per' in event TLPY.8"
    ::= { tlpyEventObjects8 2 }

tlpy8_id OBJECT-TYPE
    SYNTAX DisplayString
    MAX-ACCESS accessible-for-notify
    STATUS current
    DESCRIPTION
        "Parameter 'id' in event TLPY.8"
    ::= { tlpyEventObjects8 3 }

tlpy8_cdr OBJECT-TYPE
    SYNTAX Integer32
    MAX-ACCESS accessible-for-notify
    STATUS current
    DESCRIPTION
        "Parameter 'cdr' in event TLPY.8"
    ::= { tlpyEventObjects8 4 }

tlpyEventObjects9 OBJECT-IDENTITY
    STATUS current
    DESCRIPTION
        "Event TLPY.9
        Display several statistical values for current delay computation."
    ::= { tlpyEventsGroup 9 }

tlpy9_text OBJECT-TYPE
    SYNTAX DisplayString
    MAX-ACCESS accessible-for-notify
    STATUS current
    DESCRIPTION
        "Parameter 'text' in event TLPY.9"
    ::= { tlpyEventObjects9 1 }

tlpy9_id OBJECT-TYPE
    SYNTAX DisplayString
    MAX-ACCESS accessible-for-notify
    STATUS current
    DESCRIPTION
        "Parameter 'id' in event TLPY.9"
    ::= { tlpyEventObjects9 2 }

tlpy9_cdr OBJECT-TYPE
    SYNTAX Integer32
    MAX-ACCESS accessible-for-notify
    STATUS current
    DESCRIPTION
        "Parameter 'cdr' in event TLPY.9"
    ::= { tlpyEventObjects9 3 }

tlpyEventObjects10 OBJECT-IDENTITY
    STATUS current
    DESCRIPTION
        "Event TLPY.10
        This message gives information about the delay and variance measured in
        a communication."
    ::= { tlpyEventsGroup 10 }

tlpy10_delay OBJECT-TYPE
    SYNTAX Integer32
    MAX-ACCESS accessible-for-notify
    STATUS current
    DESCRIPTION
        "Parameter 'delay' in event TLPY.10"
    ::= { tlpyEventObjects10 1 }

tlpy10_jitter OBJECT-TYPE
    SYNTAX Integer32
    MAX-ACCESS accessible-for-notify
    STATUS current
    DESCRIPTION
        "Parameter 'jitter' in event TLPY.10"
    ::= { tlpyEventObjects10 2 }

tlpy10_id OBJECT-TYPE
    SYNTAX DisplayString
    MAX-ACCESS accessible-for-notify
    STATUS current
    DESCRIPTION
        "Parameter 'id' in event TLPY.10"
    ::= { tlpyEventObjects10 3 }

tlpy10_cdr OBJECT-TYPE
    SYNTAX Integer32
    MAX-ACCESS accessible-for-notify
    STATUS current
    DESCRIPTION
        "Parameter 'cdr' in event TLPY.10"
    ::= { tlpyEventObjects10 4 }

tlpyEventObjects11 OBJECT-IDENTITY
    STATUS current
    DESCRIPTION
        "Event TLPY.11
        RTP mean delay out."
    ::= { tlpyEventsGroup 11 }

tlpy11_delay OBJECT-TYPE
    SYNTAX Integer32
    MAX-ACCESS accessible-for-notify
    STATUS current
    DESCRIPTION
        "Parameter 'delay' in event TLPY.11"
    ::= { tlpyEventObjects11 1 }

tlpy11_id OBJECT-TYPE
    SYNTAX DisplayString
    MAX-ACCESS accessible-for-notify
    STATUS current
    DESCRIPTION
        "Parameter 'id' in event TLPY.11"
    ::= { tlpyEventObjects11 2 }

tlpy11_cdr OBJECT-TYPE
    SYNTAX Integer32
    MAX-ACCESS accessible-for-notify
    STATUS current
    DESCRIPTION
        "Parameter 'cdr' in event TLPY.11"
    ::= { tlpyEventObjects11 3 }

tlpyEventObjects12 OBJECT-IDENTITY
    STATUS current
    DESCRIPTION
        "Event TLPY.12
        RTP synchronize."
    ::= { tlpyEventsGroup 12 }

tlpy12_id OBJECT-TYPE
    SYNTAX DisplayString
    MAX-ACCESS accessible-for-notify
    STATUS current
    DESCRIPTION
        "Parameter 'id' in event TLPY.12"
    ::= { tlpyEventObjects12 1 }

tlpy12_cdr OBJECT-TYPE
    SYNTAX Integer32
    MAX-ACCESS accessible-for-notify
    STATUS current
    DESCRIPTION
        "Parameter 'cdr' in event TLPY.12"
    ::= { tlpyEventObjects12 2 }

tlpyEventObjects13 OBJECT-IDENTITY
    STATUS current
    DESCRIPTION
        "Event TLPY.13
        Lost a too delayed frame."
    ::= { tlpyEventsGroup 13 }

tlpy13_CurrDelay OBJECT-TYPE
    SYNTAX Integer32
    MAX-ACCESS accessible-for-notify
    STATUS current
    DESCRIPTION
        "Parameter 'CurrDelay' in event TLPY.13"
    ::= { tlpyEventObjects13 1 }

tlpy13_PlyDelay OBJECT-TYPE
    SYNTAX Integer32
    MAX-ACCESS accessible-for-notify
    STATUS current
    DESCRIPTION
        "Parameter 'PlyDelay' in event TLPY.13"
    ::= { tlpyEventObjects13 2 }

tlpy13_id OBJECT-TYPE
    SYNTAX DisplayString
    MAX-ACCESS accessible-for-notify
    STATUS current
    DESCRIPTION
        "Parameter 'id' in event TLPY.13"
    ::= { tlpyEventObjects13 3 }

tlpy13_cdr OBJECT-TYPE
    SYNTAX Integer32
    MAX-ACCESS accessible-for-notify
    STATUS current
    DESCRIPTION
        "Parameter 'cdr' in event TLPY.13"
    ::= { tlpyEventObjects13 4 }

tlpyEventObjects14 OBJECT-IDENTITY
    STATUS current
    DESCRIPTION
        "Event TLPY.14
        Codec added or removed from call."
    ::= { tlpyEventsGroup 14 }

tlpy14_action OBJECT-TYPE
    SYNTAX DisplayString
    MAX-ACCESS accessible-for-notify
    STATUS current
    DESCRIPTION
        "Parameter 'action' in event TLPY.14"
    ::= { tlpyEventObjects14 1 }

tlpy14_called-number OBJECT-TYPE
    SYNTAX DisplayString
    MAX-ACCESS accessible-for-notify
    STATUS current
    DESCRIPTION
        "Parameter 'called-number' in event TLPY.14"
    ::= { tlpyEventObjects14 2 }

tlpy14_calling-number OBJECT-TYPE
    SYNTAX DisplayString
    MAX-ACCESS accessible-for-notify
    STATUS current
    DESCRIPTION
        "Parameter 'calling-number' in event TLPY.14"
    ::= { tlpyEventObjects14 3 }

tlpy14_codec_str OBJECT-TYPE
    SYNTAX DisplayString
    MAX-ACCESS accessible-for-notify
    STATUS current
    DESCRIPTION
        "Parameter 'codec_str' in event TLPY.14"
    ::= { tlpyEventObjects14 4 }

tlpy14_nob OBJECT-TYPE
    SYNTAX Integer32
    MAX-ACCESS accessible-for-notify
    STATUS current
    DESCRIPTION
        "Parameter 'nob' in event TLPY.14"
    ::= { tlpyEventObjects14 5 }

tlpy14_vad OBJECT-TYPE
    SYNTAX DisplayString
    MAX-ACCESS accessible-for-notify
    STATUS current
    DESCRIPTION
        "Parameter 'vad' in event TLPY.14"
    ::= { tlpyEventObjects14 6 }

tlpy14_cdr OBJECT-TYPE
    SYNTAX Integer32
    MAX-ACCESS accessible-for-notify
    STATUS current
    DESCRIPTION
        "Parameter 'cdr' in event TLPY.14"
    ::= { tlpyEventObjects14 7 }

tlpyEventObjects15 OBJECT-IDENTITY
    STATUS current
    DESCRIPTION
        "Event TLPY.15
        Call jump event."
    ::= { tlpyEventsGroup 15 }

tlpy15_type OBJECT-TYPE
    SYNTAX DisplayString
    MAX-ACCESS accessible-for-notify
    STATUS current
    DESCRIPTION
        "Parameter 'type' in event TLPY.15"
    ::= { tlpyEventObjects15 1 }

tlpy15_peergroup OBJECT-TYPE
    SYNTAX Integer32
    MAX-ACCESS accessible-for-notify
    STATUS current
    DESCRIPTION
        "Parameter 'peergroup' in event TLPY.15"
    ::= { tlpyEventObjects15 2 }

tlpy15_dial-peer OBJECT-TYPE
    SYNTAX Integer32
    MAX-ACCESS accessible-for-notify
    STATUS current
    DESCRIPTION
        "Parameter 'dial-peer' in event TLPY.15"
    ::= { tlpyEventObjects15 3 }

tlpy15_telephone OBJECT-TYPE
    SYNTAX DisplayString
    MAX-ACCESS accessible-for-notify
    STATUS current
    DESCRIPTION
        "Parameter 'telephone' in event TLPY.15"
    ::= { tlpyEventObjects15 4 }

tlpy15_cdr OBJECT-TYPE
    SYNTAX Integer32
    MAX-ACCESS accessible-for-notify
    STATUS current
    DESCRIPTION
        "Parameter 'cdr' in event TLPY.15"
    ::= { tlpyEventObjects15 5 }

tlpyEventObjects16 OBJECT-IDENTITY
    STATUS current
    DESCRIPTION
        "Event TLPY.16
        CDR file information."
    ::= { tlpyEventsGroup 16 }

tlpy16_file OBJECT-TYPE
    SYNTAX DisplayString
    MAX-ACCESS accessible-for-notify
    STATUS current
    DESCRIPTION
        "Parameter 'file' in event TLPY.16"
    ::= { tlpyEventObjects16 1 }

tlpy16_state OBJECT-TYPE
    SYNTAX DisplayString
    MAX-ACCESS accessible-for-notify
    STATUS current
    DESCRIPTION
        "Parameter 'state' in event TLPY.16"
    ::= { tlpyEventObjects16 2 }

tlpy16_size OBJECT-TYPE
    SYNTAX Integer32
    MAX-ACCESS accessible-for-notify
    STATUS current
    DESCRIPTION
        "Parameter 'size' in event TLPY.16"
    ::= { tlpyEventObjects16 3 }

tlpyEventObjects17 OBJECT-IDENTITY
    STATUS current
    DESCRIPTION
        "Event TLPY.17
        Warning, too many consecutive errors."
    ::= { tlpyEventsGroup 17 }

tlpy17_errors OBJECT-TYPE
    SYNTAX Integer32
    MAX-ACCESS accessible-for-notify
    STATUS current
    DESCRIPTION
        "Parameter 'errors' in event TLPY.17"
    ::= { tlpyEventObjects17 1 }

tlpy17_dial-peer OBJECT-TYPE
    SYNTAX Integer32
    MAX-ACCESS accessible-for-notify
    STATUS current
    DESCRIPTION
        "Parameter 'dial-peer' in event TLPY.17"
    ::= { tlpyEventObjects17 2 }

tlpyEventObjects18 OBJECT-IDENTITY
    STATUS current
    DESCRIPTION
        "Event TLPY.18
        Fax detected in this call, switching to fax mode"
    ::= { tlpyEventsGroup 18 }

tlpy18_cdr OBJECT-TYPE
    SYNTAX Integer32
    MAX-ACCESS accessible-for-notify
    STATUS current
    DESCRIPTION
        "Parameter 'cdr' in event TLPY.18"
    ::= { tlpyEventObjects18 1 }

tlpy18_mode OBJECT-TYPE
    SYNTAX DisplayString
    MAX-ACCESS accessible-for-notify
    STATUS current
    DESCRIPTION
        "Parameter 'mode' in event TLPY.18"
    ::= { tlpyEventObjects18 2 }

tlpyEventObjects19 OBJECT-IDENTITY
    STATUS current
    DESCRIPTION
        "Event TLPY.19
        Hold or unhold event"
    ::= { tlpyEventsGroup 19 }

tlpy19_event OBJECT-TYPE
    SYNTAX DisplayString
    MAX-ACCESS accessible-for-notify
    STATUS current
    DESCRIPTION
        "Parameter 'event' in event TLPY.19"
    ::= { tlpyEventObjects19 1 }

tlpy19_peer_name OBJECT-TYPE
    SYNTAX DisplayString
    MAX-ACCESS accessible-for-notify
    STATUS current
    DESCRIPTION
        "Parameter 'peer_name' in event TLPY.19"
    ::= { tlpyEventObjects19 2 }

tlpy19_peer_line OBJECT-TYPE
    SYNTAX Integer32
    MAX-ACCESS accessible-for-notify
    STATUS current
    DESCRIPTION
        "Parameter 'peer_line' in event TLPY.19"
    ::= { tlpyEventObjects19 3 }

tlpy19_called OBJECT-TYPE
    SYNTAX DisplayString
    MAX-ACCESS accessible-for-notify
    STATUS current
    DESCRIPTION
        "Parameter 'called' in event TLPY.19"
    ::= { tlpyEventObjects19 4 }

tlpy19_calling OBJECT-TYPE
    SYNTAX DisplayString
    MAX-ACCESS accessible-for-notify
    STATUS current
    DESCRIPTION
        "Parameter 'calling' in event TLPY.19"
    ::= { tlpyEventObjects19 5 }

tlpy19_cdr OBJECT-TYPE
    SYNTAX Integer32
    MAX-ACCESS accessible-for-notify
    STATUS current
    DESCRIPTION
        "Parameter 'cdr' in event TLPY.19"
    ::= { tlpyEventObjects19 6 }

tlpyEventObjects20 OBJECT-IDENTITY
    STATUS current
    DESCRIPTION
        "Event TLPY.20
        Call error event."
    ::= { tlpyEventsGroup 20 }

tlpy20_description OBJECT-TYPE
    SYNTAX DisplayString
    MAX-ACCESS accessible-for-notify
    STATUS current
    DESCRIPTION
        "Parameter 'description' in event TLPY.20"
    ::= { tlpyEventObjects20 1 }

tlpy20_incoming-dialpeer OBJECT-TYPE
    SYNTAX Integer32
    MAX-ACCESS accessible-for-notify
    STATUS current
    DESCRIPTION
        "Parameter 'incoming-dialpeer' in event TLPY.20"
    ::= { tlpyEventObjects20 2 }

tlpy20_outging-dialpeer OBJECT-TYPE
    SYNTAX Integer32
    MAX-ACCESS accessible-for-notify
    STATUS current
    DESCRIPTION
        "Parameter 'outging-dialpeer' in event TLPY.20"
    ::= { tlpyEventObjects20 3 }

tlpy20_cdr OBJECT-TYPE
    SYNTAX Integer32
    MAX-ACCESS accessible-for-notify
    STATUS current
    DESCRIPTION
        "Parameter 'cdr' in event TLPY.20"
    ::= { tlpyEventObjects20 4 }

tlpyEventObjects21 OBJECT-IDENTITY
    STATUS current
    DESCRIPTION
        "Event TLPY.21
        RTP VAD detected/undetected"
    ::= { tlpyEventsGroup 21 }

tlpy21_vad OBJECT-TYPE
    SYNTAX DisplayString
    MAX-ACCESS accessible-for-notify
    STATUS current
    DESCRIPTION
        "Parameter 'vad' in event TLPY.21"
    ::= { tlpyEventObjects21 1 }

tlpy21_id OBJECT-TYPE
    SYNTAX DisplayString
    MAX-ACCESS accessible-for-notify
    STATUS current
    DESCRIPTION
        "Parameter 'id' in event TLPY.21"
    ::= { tlpyEventObjects21 2 }

tlpy21_cdr OBJECT-TYPE
    SYNTAX Integer32
    MAX-ACCESS accessible-for-notify
    STATUS current
    DESCRIPTION
        "Parameter 'cdr' in event TLPY.21"
    ::= { tlpyEventObjects21 3 }

tlpyEventObjects22 OBJECT-IDENTITY
    STATUS current
    DESCRIPTION
        "Event TLPY.22
        RTP collection session detected/undetected"
    ::= { tlpyEventsGroup 22 }

tlpy22_action OBJECT-TYPE
    SYNTAX DisplayString
    MAX-ACCESS accessible-for-notify
    STATUS current
    DESCRIPTION
        "Parameter 'action' in event TLPY.22"
    ::= { tlpyEventObjects22 1 }

tlpy22_remote-ip OBJECT-TYPE
    SYNTAX IpAddress
    MAX-ACCESS accessible-for-notify
    STATUS current
    DESCRIPTION
        "Parameter 'remote-ip' in event TLPY.22"
    ::= { tlpyEventObjects22 2 }

tlpy22_remote-port OBJECT-TYPE
    SYNTAX Integer32
    MAX-ACCESS accessible-for-notify
    STATUS current
    DESCRIPTION
        "Parameter 'remote-port' in event TLPY.22"
    ::= { tlpyEventObjects22 3 }

tlpy22_ssrc OBJECT-TYPE
    SYNTAX Integer32
    MAX-ACCESS accessible-for-notify
    STATUS current
    DESCRIPTION
        "Parameter 'ssrc' in event TLPY.22"
    ::= { tlpyEventObjects22 4 }

tlpy22_id OBJECT-TYPE
    SYNTAX DisplayString
    MAX-ACCESS accessible-for-notify
    STATUS current
    DESCRIPTION
        "Parameter 'id' in event TLPY.22"
    ::= { tlpyEventObjects22 5 }

tlpy22_cdr OBJECT-TYPE
    SYNTAX Integer32
    MAX-ACCESS accessible-for-notify
    STATUS current
    DESCRIPTION
        "Parameter 'cdr' in event TLPY.22"
    ::= { tlpyEventObjects22 6 }

tlpyEventObjects23 OBJECT-IDENTITY
    STATUS current
    DESCRIPTION
        "Event TLPY.23
        Call transfer event."
    ::= { tlpyEventsGroup 23 }

tlpy23_original-call OBJECT-TYPE
    SYNTAX Integer32
    MAX-ACCESS accessible-for-notify
    STATUS current
    DESCRIPTION
        "Parameter 'original-call' in event TLPY.23"
    ::= { tlpyEventObjects23 1 }

tlpy23_consult-call OBJECT-TYPE
    SYNTAX Integer32
    MAX-ACCESS accessible-for-notify
    STATUS current
    DESCRIPTION
        "Parameter 'consult-call' in event TLPY.23"
    ::= { tlpyEventObjects23 2 }

tlpy23_new-call OBJECT-TYPE
    SYNTAX Integer32
    MAX-ACCESS accessible-for-notify
    STATUS current
    DESCRIPTION
        "Parameter 'new-call' in event TLPY.23"
    ::= { tlpyEventObjects23 3 }

tlpyEventObjects24 OBJECT-IDENTITY
    STATUS current
    DESCRIPTION
        "Event TLPY.24
        Outgoing type of peers allowed for incoming call."
    ::= { tlpyEventsGroup 24 }

tlpy24_allowed-peers OBJECT-TYPE
    SYNTAX DisplayString
    MAX-ACCESS accessible-for-notify
    STATUS current
    DESCRIPTION
        "Parameter 'allowed-peers' in event TLPY.24"
    ::= { tlpyEventObjects24 1 }

tlpyEventObjects25 OBJECT-IDENTITY
    STATUS current
    DESCRIPTION
        "Event TLPY.25
        Keeping old incoming dial-peer in a call transfer."
    ::= { tlpyEventsGroup 25 }

tlpy25_dialpeer OBJECT-TYPE
    SYNTAX Integer32
    MAX-ACCESS accessible-for-notify
    STATUS current
    DESCRIPTION
        "Parameter 'dialpeer' in event TLPY.25"
    ::= { tlpyEventObjects25 1 }

tlpy25_called-number OBJECT-TYPE
    SYNTAX DisplayString
    MAX-ACCESS accessible-for-notify
    STATUS current
    DESCRIPTION
        "Parameter 'called-number' in event TLPY.25"
    ::= { tlpyEventObjects25 2 }

tlpy25_calling-number OBJECT-TYPE
    SYNTAX DisplayString
    MAX-ACCESS accessible-for-notify
    STATUS current
    DESCRIPTION
        "Parameter 'calling-number' in event TLPY.25"
    ::= { tlpyEventObjects25 3 }

tlpyEventObjects26 OBJECT-IDENTITY
    STATUS current
    DESCRIPTION
        "Event TLPY.26
        Change in max calls alowed for call limit control."
    ::= { tlpyEventsGroup 26 }

tlpy26_id1 OBJECT-TYPE
    SYNTAX DisplayString
    MAX-ACCESS accessible-for-notify
    STATUS current
    DESCRIPTION
        "Parameter 'id1' in event TLPY.26"
    ::= { tlpyEventObjects26 1 }

tlpy26_id2 OBJECT-TYPE
    SYNTAX DisplayString
    MAX-ACCESS accessible-for-notify
    STATUS current
    DESCRIPTION
        "Parameter 'id2' in event TLPY.26"
    ::= { tlpyEventObjects26 2 }

tlpy26_max-calls OBJECT-TYPE
    SYNTAX Integer32
    MAX-ACCESS accessible-for-notify
    STATUS current
    DESCRIPTION
        "Parameter 'max-calls' in event TLPY.26"
    ::= { tlpyEventObjects26 3 }

tlpyEventObjects27 OBJECT-IDENTITY
    STATUS current
    DESCRIPTION
        "Event TLPY.27
        Telephony facility event."
    ::= { tlpyEventsGroup 27 }

tlpy27_event OBJECT-TYPE
    SYNTAX DisplayString
    MAX-ACCESS accessible-for-notify
    STATUS current
    DESCRIPTION
        "Parameter 'event' in event TLPY.27"
    ::= { tlpyEventObjects27 1 }

tlpy27_number OBJECT-TYPE
    SYNTAX DisplayString
    MAX-ACCESS accessible-for-notify
    STATUS current
    DESCRIPTION
        "Parameter 'number' in event TLPY.27"
    ::= { tlpyEventObjects27 2 }

tlpy27_in-dialpeer OBJECT-TYPE
    SYNTAX Integer32
    MAX-ACCESS accessible-for-notify
    STATUS current
    DESCRIPTION
        "Parameter 'in-dialpeer' in event TLPY.27"
    ::= { tlpyEventObjects27 3 }

tlpy27_out-dialpeer OBJECT-TYPE
    SYNTAX Integer32
    MAX-ACCESS accessible-for-notify
    STATUS current
    DESCRIPTION
        "Parameter 'out-dialpeer' in event TLPY.27"
    ::= { tlpyEventObjects27 4 }

tlpy27_call-cdr OBJECT-TYPE
    SYNTAX Integer32
    MAX-ACCESS accessible-for-notify
    STATUS current
    DESCRIPTION
        "Parameter 'call-cdr' in event TLPY.27"
    ::= { tlpyEventObjects27 5 }

tlpyEventObjects28 OBJECT-IDENTITY
    STATUS current
    DESCRIPTION
        "Event TLPY.28
        SRTP engine event"
    ::= { tlpyEventsGroup 28 }

tlpy28_event OBJECT-TYPE
    SYNTAX DisplayString
    MAX-ACCESS accessible-for-notify
    STATUS current
    DESCRIPTION
        "Parameter 'event' in event TLPY.28"
    ::= { tlpyEventObjects28 1 }

tlpyEventObjects29 OBJECT-IDENTITY
    STATUS current
    DESCRIPTION
        "Event TLPY.29
        Report events related to voice messages"
    ::= { tlpyEventsGroup 29 }

tlpy29_loc-index OBJECT-TYPE
    SYNTAX Integer32
    MAX-ACCESS accessible-for-notify
    STATUS current
    DESCRIPTION
        "Parameter 'loc-index' in event TLPY.29"
    ::= { tlpyEventObjects29 1 }

tlpy29_event OBJECT-TYPE
    SYNTAX DisplayString
    MAX-ACCESS accessible-for-notify
    STATUS current
    DESCRIPTION
        "Parameter 'event' in event TLPY.29"
    ::= { tlpyEventObjects29 2 }

tlpyEventObjects30 OBJECT-IDENTITY
    STATUS current
    DESCRIPTION
        "Event TLPY.30
        Report events related to no-answer timer"
    ::= { tlpyEventsGroup 30 }

tlpy30_event OBJECT-TYPE
    SYNTAX DisplayString
    MAX-ACCESS accessible-for-notify
    STATUS current
    DESCRIPTION
        "Parameter 'event' in event TLPY.30"
    ::= { tlpyEventObjects30 1 }

tlpy30_out_dp OBJECT-TYPE
    SYNTAX Integer32
    MAX-ACCESS accessible-for-notify
    STATUS current
    DESCRIPTION
        "Parameter 'out_dp' in event TLPY.30"
    ::= { tlpyEventObjects30 2 }

tlpyEventObjects31 OBJECT-IDENTITY
    STATUS current
    DESCRIPTION
        "Event TLPY.31
        RTP timeout reached event"
    ::= { tlpyEventsGroup 31 }

tlpy31_local-ip OBJECT-TYPE
    SYNTAX DisplayString
    MAX-ACCESS accessible-for-notify
    STATUS current
    DESCRIPTION
        "Parameter 'local-ip' in event TLPY.31"
    ::= { tlpyEventObjects31 1 }

tlpy31_local-port OBJECT-TYPE
    SYNTAX Integer32
    MAX-ACCESS accessible-for-notify
    STATUS current
    DESCRIPTION
        "Parameter 'local-port' in event TLPY.31"
    ::= { tlpyEventObjects31 2 }

tlpy31_cdr OBJECT-TYPE
    SYNTAX Integer32
    MAX-ACCESS accessible-for-notify
    STATUS current
    DESCRIPTION
        "Parameter 'cdr' in event TLPY.31"
    ::= { tlpyEventObjects31 3 }

tlpyEventObjects32 OBJECT-IDENTITY
    STATUS current
    DESCRIPTION
        "Event TLPY.32
        RTP reception started event"
    ::= { tlpyEventsGroup 32 }

tlpy32_local-ip OBJECT-TYPE
    SYNTAX DisplayString
    MAX-ACCESS accessible-for-notify
    STATUS current
    DESCRIPTION
        "Parameter 'local-ip' in event TLPY.32"
    ::= { tlpyEventObjects32 1 }

tlpy32_local-port OBJECT-TYPE
    SYNTAX Integer32
    MAX-ACCESS accessible-for-notify
    STATUS current
    DESCRIPTION
        "Parameter 'local-port' in event TLPY.32"
    ::= { tlpyEventObjects32 2 }

tlpy32_cdr OBJECT-TYPE
    SYNTAX Integer32
    MAX-ACCESS accessible-for-notify
    STATUS current
    DESCRIPTION
        "Parameter 'cdr' in event TLPY.32"
    ::= { tlpyEventObjects32 3 }

tlpyEventObjects33 OBJECT-IDENTITY
    STATUS current
    DESCRIPTION
        "Event TLPY.33
        The OOD (Out of Dialog) OPTIONS keepalive process for the given
        dial-peer switched to the specified status."
    ::= { tlpyEventsGroup 33 }

tlpy33_dialpeer OBJECT-TYPE
    SYNTAX Integer32
    MAX-ACCESS accessible-for-notify
    STATUS current
    DESCRIPTION
        "Parameter 'dialpeer' in event TLPY.33"
    ::= { tlpyEventObjects33 1 }

tlpy33_status OBJECT-TYPE
    SYNTAX DisplayString
    MAX-ACCESS accessible-for-notify
    STATUS current
    DESCRIPTION
        "Parameter 'status' in event TLPY.33"
    ::= { tlpyEventObjects33 2 }


tlpyNotification1 NOTIFICATION-TYPE
    OBJECTS { 
              tlpy1_event, 
              tlpy1_caller,
              tlpy1_indp,
              tlpy1_called,
              tlpy1_outdp,
              tlpy1_cdr 
            }
    STATUS current
    DESCRIPTION
        "Notification of Event TLPY.1

        Message: 'Call $1 in $2(dp $3) out $4(dp $5) cdr $6'

        Parameters list:
              $1: tlpy1_event
              $2: tlpy1_caller
              $3: tlpy1_indp
              $4: tlpy1_called
              $5: tlpy1_outdp
              $6: tlpy1_cdr

        Call events."
    ::= { tlpyNotificationsPrefix 1 }

tlpyNotification2 NOTIFICATION-TYPE
    OBJECTS { 
              tlpy2_call1, 
              tlpy2_call2 
            }
    STATUS current
    DESCRIPTION
        "Notification of Event TLPY.2

        Message: 'Call transfer $1->$2'

        Parameters list:
              $1: tlpy2_call1
              $2: tlpy2_call2

        Call transfer event."
    ::= { tlpyNotificationsPrefix 2 }

tlpyNotification3 NOTIFICATION-TYPE
    OBJECTS { 
              tlpy3_dialpeer, 
              tlpy3_status 
            }
    STATUS current
    DESCRIPTION
        "Notification of Event TLPY.3

        Message: 'NSLA dial-peer $1 status changed to $2'

        Parameters list:
              $1: tlpy3_dialpeer
              $2: tlpy3_status

        NSLA changed."
    ::= { tlpyNotificationsPrefix 3 }

tlpyNotification4 NOTIFICATION-TYPE
    OBJECTS { 
              tlpy4_calltype, 
              tlpy4_status 
            }
    STATUS current
    DESCRIPTION
        "Notification of Event TLPY.4

        Message: '$1 calls control status changed to $2'

        Parameters list:
              $1: tlpy4_calltype
              $2: tlpy4_status

        Control status changed."
    ::= { tlpyNotificationsPrefix 4 }

tlpyNotification5 NOTIFICATION-TYPE
    OBJECTS { 
              tlpy5_dialpeer, 
              tlpy5_called-number,
              tlpy5_calling-number 
            }
    STATUS current
    DESCRIPTION
        "Notification of Event TLPY.5

        Message: 'Incoming dial-peer found $1 called $2 calling $3'

        Parameters list:
              $1: tlpy5_dialpeer
              $2: tlpy5_called-number
              $3: tlpy5_calling-number

        Found dial-peer."
    ::= { tlpyNotificationsPrefix 5 }

tlpyNotification6 NOTIFICATION-TYPE
    OBJECTS { 
              tlpy6_dialpeer, 
              tlpy6_called-number 
            }
    STATUS current
    DESCRIPTION
        "Notification of Event TLPY.6

        Message: 'Outgoing dial-peer found $1 called $2'

        Parameters list:
              $1: tlpy6_dialpeer
              $2: tlpy6_called-number

        Found dial-peer."
    ::= { tlpyNotificationsPrefix 6 }

tlpyNotification7 NOTIFICATION-TYPE
    OBJECTS { 
              tlpy7_direction, 
              tlpy7_called-number,
              tlpy7_calling-number 
            }
    STATUS current
    DESCRIPTION
        "Notification of Event TLPY.7

        Message: '$1 dial-peer not found called $2 calling $3'

        Parameters list:
              $1: tlpy7_direction
              $2: tlpy7_called-number
              $3: tlpy7_calling-number

        Dial-peer not found."
    ::= { tlpyNotificationsPrefix 7 }

tlpyNotification8 NOTIFICATION-TYPE
    OBJECTS { 
              tlpy8_num, 
              tlpy8_per,
              tlpy8_id,
              tlpy8_cdr 
            }
    STATUS current
    DESCRIPTION
        "Notification of Event TLPY.8

        Message: 'RTP lost frames $1 percentage $2$3 call cdr $4'

        Parameters list:
              $1: tlpy8_num
              $2: tlpy8_per
              $3: tlpy8_id
              $4: tlpy8_cdr

        This message shows the percentage of lost frames in the last second."
    ::= { tlpyNotificationsPrefix 8 }

tlpyNotification9 NOTIFICATION-TYPE
    OBJECTS { 
              tlpy9_text, 
              tlpy9_id,
              tlpy9_cdr 
            }
    STATUS current
    DESCRIPTION
        "Notification of Event TLPY.9

        Message: 'RTP:$1 $2 call cdr $3'

        Parameters list:
              $1: tlpy9_text
              $2: tlpy9_id
              $3: tlpy9_cdr

        Display several statistical values for current delay computation."
    ::= { tlpyNotificationsPrefix 9 }

tlpyNotification10 NOTIFICATION-TYPE
    OBJECTS { 
              tlpy10_delay, 
              tlpy10_jitter,
              tlpy10_id,
              tlpy10_cdr 
            }
    STATUS current
    DESCRIPTION
        "Notification of Event TLPY.10

        Message: 'Delay $1 ms Var $2 ms $3 call cdr $4'

        Parameters list:
              $1: tlpy10_delay
              $2: tlpy10_jitter
              $3: tlpy10_id
              $4: tlpy10_cdr

        This message gives information about the delay and variance measured in
        a communication."
    ::= { tlpyNotificationsPrefix 10 }

tlpyNotification11 NOTIFICATION-TYPE
    OBJECTS { 
              tlpy11_delay, 
              tlpy11_id,
              tlpy11_cdr 
            }
    STATUS current
    DESCRIPTION
        "Notification of Event TLPY.11

        Message: 'Mn-Dly Out: dly $1 $2 call cdr $3'

        Parameters list:
              $1: tlpy11_delay
              $2: tlpy11_id
              $3: tlpy11_cdr

        RTP mean delay out."
    ::= { tlpyNotificationsPrefix 11 }

tlpyNotification12 NOTIFICATION-TYPE
    OBJECTS { 
              tlpy12_id, 
              tlpy12_cdr 
            }
    STATUS current
    DESCRIPTION
        "Notification of Event TLPY.12

        Message: 'Sync Tmstamp $1 call cdr $2'

        Parameters list:
              $1: tlpy12_id
              $2: tlpy12_cdr

        RTP synchronize."
    ::= { tlpyNotificationsPrefix 12 }

tlpyNotification13 NOTIFICATION-TYPE
    OBJECTS { 
              tlpy13_CurrDelay, 
              tlpy13_PlyDelay,
              tlpy13_id,
              tlpy13_cdr 
            }
    STATUS current
    DESCRIPTION
        "Notification of Event TLPY.13

        Message: 'Lost Frame current delay $1 Playing delay $2 $3 call cdr $4'

        Parameters list:
              $1: tlpy13_CurrDelay
              $2: tlpy13_PlyDelay
              $3: tlpy13_id
              $4: tlpy13_cdr

        Lost a too delayed frame."
    ::= { tlpyNotificationsPrefix 13 }

tlpyNotification14 NOTIFICATION-TYPE
    OBJECTS { 
              tlpy14_action, 
              tlpy14_called-number,
              tlpy14_calling-number,
              tlpy14_codec_str,
              tlpy14_nob,
              tlpy14_vad,
              tlpy14_cdr 
            }
    STATUS current
    DESCRIPTION
        "Notification of Event TLPY.14

        Message: 'Codec $1 Call: $2/$3 (called/calling), codec $4, nob $5, vad $6, cdr $7'

        Parameters list:
              $1: tlpy14_action
              $2: tlpy14_called-number
              $3: tlpy14_calling-number
              $4: tlpy14_codec_str
              $5: tlpy14_nob
              $6: tlpy14_vad
              $7: tlpy14_cdr

        Codec added or removed from call."
    ::= { tlpyNotificationsPrefix 14 }

tlpyNotification15 NOTIFICATION-TYPE
    OBJECTS { 
              tlpy15_type, 
              tlpy15_peergroup,
              tlpy15_dial-peer,
              tlpy15_telephone,
              tlpy15_cdr 
            }
    STATUS current
    DESCRIPTION
        "Notification of Event TLPY.15

        Message: 'Call forward ($1): $2/$3 (group/dp), phone $4, cdr $5'

        Parameters list:
              $1: tlpy15_type
              $2: tlpy15_peergroup
              $3: tlpy15_dial-peer
              $4: tlpy15_telephone
              $5: tlpy15_cdr

        Call jump event."
    ::= { tlpyNotificationsPrefix 15 }

tlpyNotification16 NOTIFICATION-TYPE
    OBJECTS { 
              tlpy16_file, 
              tlpy16_state,
              tlpy16_size 
            }
    STATUS current
    DESCRIPTION
        "Notification of Event TLPY.16

        Message: 'CDR file $1 state $2 size $3'

        Parameters list:
              $1: tlpy16_file
              $2: tlpy16_state
              $3: tlpy16_size

        CDR file information."
    ::= { tlpyNotificationsPrefix 16 }

tlpyNotification17 NOTIFICATION-TYPE
    OBJECTS { 
              tlpy17_errors, 
              tlpy17_dial-peer 
            }
    STATUS current
    DESCRIPTION
        "Notification of Event TLPY.17

        Message: 'Warning: $1 consecutive errors in dial-peer $2'

        Parameters list:
              $1: tlpy17_errors
              $2: tlpy17_dial-peer

        Warning, too many consecutive errors."
    ::= { tlpyNotificationsPrefix 17 }

tlpyNotification18 NOTIFICATION-TYPE
    OBJECTS { 
              tlpy18_cdr, 
              tlpy18_mode 
            }
    STATUS current
    DESCRIPTION
        "Notification of Event TLPY.18

        Message: 'Fax detected in call $1, switching to $2'

        Parameters list:
              $1: tlpy18_cdr
              $2: tlpy18_mode

        Fax detected in this call, switching to fax mode"
    ::= { tlpyNotificationsPrefix 18 }

tlpyNotification19 NOTIFICATION-TYPE
    OBJECTS { 
              tlpy19_event, 
              tlpy19_peer_name,
              tlpy19_peer_line,
              tlpy19_called,
              tlpy19_calling,
              tlpy19_cdr 
            }
    STATUS current
    DESCRIPTION
        "Notification of Event TLPY.19

        Message: 'Event: $1 Peer: $2/$3 Call: $4/$5 (called/calling) cdr $6'

        Parameters list:
              $1: tlpy19_event
              $2: tlpy19_peer_name
              $3: tlpy19_peer_line
              $4: tlpy19_called
              $5: tlpy19_calling
              $6: tlpy19_cdr

        Hold or unhold event"
    ::= { tlpyNotificationsPrefix 19 }

tlpyNotification20 NOTIFICATION-TYPE
    OBJECTS { 
              tlpy20_description, 
              tlpy20_incoming-dialpeer,
              tlpy20_outging-dialpeer,
              tlpy20_cdr 
            }
    STATUS current
    DESCRIPTION
        "Notification of Event TLPY.20

        Message: 'Error $1. in dp $2 out dp $3 cdr $4'

        Parameters list:
              $1: tlpy20_description
              $2: tlpy20_incoming-dialpeer
              $3: tlpy20_outging-dialpeer
              $4: tlpy20_cdr

        Call error event."
    ::= { tlpyNotificationsPrefix 20 }

tlpyNotification21 NOTIFICATION-TYPE
    OBJECTS { 
              tlpy21_vad, 
              tlpy21_id,
              tlpy21_cdr 
            }
    STATUS current
    DESCRIPTION
        "Notification of Event TLPY.21

        Message: 'VAD $1 in $2 cdr $3'

        Parameters list:
              $1: tlpy21_vad
              $2: tlpy21_id
              $3: tlpy21_cdr

        RTP VAD detected/undetected"
    ::= { tlpyNotificationsPrefix 21 }

tlpyNotification22 NOTIFICATION-TYPE
    OBJECTS { 
              tlpy22_action, 
              tlpy22_remote-ip,
              tlpy22_remote-port,
              tlpy22_ssrc,
              tlpy22_id,
              tlpy22_cdr 
            }
    STATUS current
    DESCRIPTION
        "Notification of Event TLPY.22

        Message: 'Rtp source $1 from $2:$3 ssrc $4 in $5 cdr $6'

        Parameters list:
              $1: tlpy22_action
              $2: tlpy22_remote-ip
              $3: tlpy22_remote-port
              $4: tlpy22_ssrc
              $5: tlpy22_id
              $6: tlpy22_cdr

        RTP collection session detected/undetected"
    ::= { tlpyNotificationsPrefix 22 }

tlpyNotification23 NOTIFICATION-TYPE
    OBJECTS { 
              tlpy23_original-call, 
              tlpy23_consult-call,
              tlpy23_new-call 
            }
    STATUS current
    DESCRIPTION
        "Notification of Event TLPY.23

        Message: 'Call transfer: orig $1 cnsl $2 new $3'

        Parameters list:
              $1: tlpy23_original-call
              $2: tlpy23_consult-call
              $3: tlpy23_new-call

        Call transfer event."
    ::= { tlpyNotificationsPrefix 23 }

tlpyNotification24 NOTIFICATION-TYPE
    OBJECTS { 
              tlpy24_allowed-peers 
            }
    STATUS current
    DESCRIPTION
        "Notification of Event TLPY.24

        Message: 'Out peers allowed: $1'

        Parameters list:
              $1: tlpy24_allowed-peers

        Outgoing type of peers allowed for incoming call."
    ::= { tlpyNotificationsPrefix 24 }

tlpyNotification25 NOTIFICATION-TYPE
    OBJECTS { 
              tlpy25_dialpeer, 
              tlpy25_called-number,
              tlpy25_calling-number 
            }
    STATUS current
    DESCRIPTION
        "Notification of Event TLPY.25

        Message: 'Keeping old incoming dial-peer $1 called $2 calling $3'

        Parameters list:
              $1: tlpy25_dialpeer
              $2: tlpy25_called-number
              $3: tlpy25_calling-number

        Keeping old incoming dial-peer in a call transfer."
    ::= { tlpyNotificationsPrefix 25 }

tlpyNotification26 NOTIFICATION-TYPE
    OBJECTS { 
              tlpy26_id1, 
              tlpy26_id2,
              tlpy26_max-calls 
            }
    STATUS current
    DESCRIPTION
        "Notification of Event TLPY.26

        Message: 'CAC change Id1: $1, Id2: $2, Max Calls: $3'

        Parameters list:
              $1: tlpy26_id1
              $2: tlpy26_id2
              $3: tlpy26_max-calls

        Change in max calls alowed for call limit control."
    ::= { tlpyNotificationsPrefix 26 }

tlpyNotification27 NOTIFICATION-TYPE
    OBJECTS { 
              tlpy27_event, 
              tlpy27_number,
              tlpy27_in-dialpeer,
              tlpy27_out-dialpeer,
              tlpy27_call-cdr 
            }
    STATUS current
    DESCRIPTION
        "Notification of Event TLPY.27

        Message: 'Tlphy facility: $1, tlph $2, in $3, out $4, cdr $5'

        Parameters list:
              $1: tlpy27_event
              $2: tlpy27_number
              $3: tlpy27_in-dialpeer
              $4: tlpy27_out-dialpeer
              $5: tlpy27_call-cdr

        Telephony facility event."
    ::= { tlpyNotificationsPrefix 27 }

tlpyNotification28 NOTIFICATION-TYPE
    OBJECTS { 
              tlpy28_event 
            }
    STATUS current
    DESCRIPTION
        "Notification of Event TLPY.28

        Message: 'SRTP: $1'

        Parameters list:
              $1: tlpy28_event

        SRTP engine event"
    ::= { tlpyNotificationsPrefix 28 }

tlpyNotification29 NOTIFICATION-TYPE
    OBJECTS { 
              tlpy29_loc-index, 
              tlpy29_event 
            }
    STATUS current
    DESCRIPTION
        "Notification of Event TLPY.29

        Message: 'Voice message $1: $2'

        Parameters list:
              $1: tlpy29_loc-index
              $2: tlpy29_event

        Report events related to voice messages"
    ::= { tlpyNotificationsPrefix 29 }

tlpyNotification30 NOTIFICATION-TYPE
    OBJECTS { 
              tlpy30_event, 
              tlpy30_out_dp 
            }
    STATUS current
    DESCRIPTION
        "Notification of Event TLPY.30

        Message: 'No-answer timer $1 for dp $2'

        Parameters list:
              $1: tlpy30_event
              $2: tlpy30_out_dp

        Report events related to no-answer timer"
    ::= { tlpyNotificationsPrefix 30 }

tlpyNotification31 NOTIFICATION-TYPE
    OBJECTS { 
              tlpy31_local-ip, 
              tlpy31_local-port,
              tlpy31_cdr 
            }
    STATUS current
    DESCRIPTION
        "Notification of Event TLPY.31

        Message: 'RTP timeout reached, no RTP received at $1:$2, call cdr $3'

        Parameters list:
              $1: tlpy31_local-ip
              $2: tlpy31_local-port
              $3: tlpy31_cdr

        RTP timeout reached event"
    ::= { tlpyNotificationsPrefix 31 }

tlpyNotification32 NOTIFICATION-TYPE
    OBJECTS { 
              tlpy32_local-ip, 
              tlpy32_local-port,
              tlpy32_cdr 
            }
    STATUS current
    DESCRIPTION
        "Notification of Event TLPY.32

        Message: 'RTP reception started at $1:$2, call cdr $3'

        Parameters list:
              $1: tlpy32_local-ip
              $2: tlpy32_local-port
              $3: tlpy32_cdr

        RTP reception started event"
    ::= { tlpyNotificationsPrefix 32 }

tlpyNotification33 NOTIFICATION-TYPE
    OBJECTS { 
              tlpy33_dialpeer, 
              tlpy33_status 
            }
    STATUS current
    DESCRIPTION
        "Notification of Event TLPY.33

        Message: 'OPTIONS keepalive dial-peer $1 status changed to $2'

        Parameters list:
              $1: tlpy33_dialpeer
              $2: tlpy33_status

        The OOD (Out of Dialog) OPTIONS keepalive process for the given
        dial-peer switched to the specified status."
    ::= { tlpyNotificationsPrefix 33 }


END
