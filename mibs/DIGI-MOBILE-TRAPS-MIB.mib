-- =====================================================================
-- == DIGI-MOBILE-TRAPS-MIB :                                         ==
-- ==  DIGI Mobile Traps Management Information Base                  ==
-- ==                                                                 ==
-- ==   Digi International Part Number: 4000xxxx_A                    ==
-- ==                                                                 ==
-- == (c) Copyright 2001-2007 Digi International, Inc.                ==
-- =====================================================================

DIGI-MOBILE-TRAPS-MIB DEFINITIONS ::= BEGIN

IMPORTS digiMobileTraps FROM DIGI-SMI
TRAP-TYPE FROM RFC-1215
OBJECT-TYPE FROM RFC-1212;

--   digiMobileTraps MODULE-IDENTITY
--       LAST-UPDATED "0308120100Z"
--       ORGANIZATION "Digi International Inc."
--       CONTACT-INFO
--               "
--                Postal: Digi International Inc.
--                        11001 Bren Road East
--                        Minnetonka, MN 55343
--
--               "
--       DESCRIPTION
--               "Mobile Traps MIB"
--       ::= { digiFeatures 24 }

-- === + Textual Conventions + =========================================

DisplayString ::= OCTET STRING

-- =====================================================================
-- =====================================================================
-- === + Variables + ===================================================
-- =====================================================================
-- =====================================================================

mobileInfoInterface OBJECT-TYPE
    SYNTAX INTEGER
    ACCESS read-write
    STATUS mandatory
    DESCRIPTION
  "A unique value for each interface.  Its value
  ranges between 1 and the maximum interface number.  The
  value for each interface must remain constant at
  least from one re-initialization of the entity's
  network management system to the next re-
  initialization. The interface identified
  by a particular value of this index is the same
  interface as identified by the same value of
  ifIndex."
::= { digiMobileTraps 11 }

mobileInfoName OBJECT-TYPE
    SYNTAX DisplayString
    ACCESS read-write
    STATUS mandatory
    DESCRIPTION
     "The name portion of this information name/value pair"
::= { digiMobileTraps 12 }

mobileInfoValue OBJECT-TYPE
    SYNTAX DisplayString
    ACCESS read-write
    STATUS mandatory
    DESCRIPTION
     "The value portion of this information name/value pair"
::= { digiMobileTraps 13 }

-- =====================================================================
-- =====================================================================
-- === + Traps + =======================================================
-- =====================================================================
-- =====================================================================

-- === + SNMPv1 Trap + =================================================
mobileSuboptimal TRAP-TYPE
    ENTERPRISE  digiMobileTraps
    VARIABLES { mobileInfoInterface, mobileInfoName, mobileInfoValue }
    DESCRIPTION
		  "A mobileSuboptimal trap signifies that a
		  device has transitioned to a sub-optimal operating
		  condition from an optimal operating condition. The
                  mobileInfoName and mobileInfoValue will describe 
                  what has changed."
::= 1

mobileOptimal TRAP-TYPE
    ENTERPRISE  digiMobileTraps
    VARIABLES { mobileInfoInterface, mobileInfoName, mobileInfoValue }
    DESCRIPTION
		  "A mobileOptimal trap signifies that a
		  device has transitioned to an optimal operating
		  condition from a sub-optimal operating condition. The
                  mobileInfoName and mobileInfoValue will describe 
                  what has changed."
::= 2

mobileConfigurationChange TRAP-TYPE
    ENTERPRISE  digiMobileTraps
    VARIABLES { mobileInfoInterface }
    DESCRIPTION
        "A mobileConfigurationChange trap signifies that the
        mobile PPP parameters or mobile provisioning (manual
        or IOTA) has changed."
::= 3

-- === + SNMPv2 Notification + =========================================
mobileSuboptimalNotification NOTIFICATION-TYPE
	OBJECTS { mobileInfoInterface, mobileInfoName, mobileInfoValue }
	STATUS  current
	DESCRIPTION
		  "A mobileSuboptimal trap signifies that a
		  device has transitioned to a sub-optimal operating
		  condition from an optimal operating condition. The
                  mobileInfoName and mobileInfoValue will describe 
                  what has changed."
	::= { digiMobileTraps 1 }
	
mobileOptimalNotification NOTIFICATION-TYPE
	OBJECTS { mobileInfoInterface, mobileInfoName, mobileInfoValue }
	STATUS  current
	DESCRIPTION
		  "A mobileOptimal trap signifies that a
		  device has transitioned to an optimal operating
		  condition from a sub-optimal operating condition. The
                  mobileInfoName and mobileInfoValue will describe 
                  what has changed."
	::= { digiMobileTraps 2 }
	
mobileConfigurationChangeNotification NOTIFICATION-TYPE
	OBJECTS { mobileInfoInterface }
	STATUS  current
	DESCRIPTION
        "A mobileConfigurationChange trap signifies that the
        mobile PPP parameters or mobile provisioning (manual
        or IOTA) has changed."
	::= { digiMobileTraps 3 }

END
