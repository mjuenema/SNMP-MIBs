-- =====================================================================
-- == DIGI-SERIAL-ALARM-TRAPS-MIB :                                   ==
-- ==   DIGI Serial Alarm Traps Management Information Base           ==
-- ==                                                                 ==
-- ==   Digi International Part Number: 40002411_A                    ==
-- ==                                                                 ==
-- == (c) Copyright 2001-2004 Digi International, Inc.                ==
-- =====================================================================

DIGI-SERIAL-ALARM-TRAPS-MIB DEFINITIONS ::= BEGIN

IMPORTS digiSerialAlarmTraps FROM DIGI-SMI
TRAP-TYPE FROM RFC-1215
OBJECT-TYPE FROM RFC-1212;

--   digiSerialAlarmTraps MODULE-IDENTITY
--       LAST-UPDATED "0308120100Z"
--       ORGANIZATION "Digi International Inc."
--       CONTACT-INFO
--               "
--                Postal: Digi International Inc.
--                        11001 Bren Road East
--                        Minnetonka, MN 55343
--
--               "
--       DESCRIPTION
--               "Serial Alarm Traps MIB"
--       ::= { digiFeatures 19 }

-- === + Textual Conventions + ===========================================

DisplayString ::= OCTET STRING

-- =======================================================================
-- =======================================================================
-- === + Variables + =====================================================
-- =======================================================================
-- =======================================================================

serialAlarmSubject OBJECT-TYPE
    SYNTAX DisplayString
    ACCESS read-write
    STATUS mandatory
    DESCRIPTION
	    "A message describing the serial alarm"
::= { digiSerialAlarmTraps 11 }

-- =======================================================================
-- =======================================================================
-- === + Traps + =========================================================
-- =======================================================================
-- =======================================================================

serialAlarmDataPattern TRAP-TYPE
    ENTERPRISE  digiSerialAlarmTraps
    VARIABLES { serialAlarmSubject }
    DESCRIPTION
		  "A serialAlarmDataPattern trap signifies that
		  a data pattern match was made on a serial port
		  on the Digi device."
::= 1

serialAlarmTransition TRAP-TYPE
    ENTERPRISE  digiSerialAlarmTraps
    VARIABLES { serialAlarmSubject }
    DESCRIPTION
		  "A serialAlarmTransition trap signifies that a
		  set of GPIO pins has transitioned to an alarm
		  defined state on the Digi device."
::= 2

serialAlarmReminder TRAP-TYPE
    ENTERPRISE  digiSerialAlarmTraps
    VARIABLES { serialAlarmSubject }
    DESCRIPTION
		  "A serialAlarmReminder trap signifies that a
		  set of GPIO pins has continued to be in an alarm
		  defined state for some defined amount of time 
		  on the Digi device."
::= 3

END
