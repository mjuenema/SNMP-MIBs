--*****************************************************************
-- ADC-FWU-IRS-TC-MIB.mib : MIB file name
--
-- March 29 12:00:00 PDT 2011
--
-- Copyright (c) 2010 by ADC Telecommunications, Inc.,
--               2011 by Tyco Electronics Corporation
-- All rights reserved.
--
--*****************************************************************

ADC-FWU-IRS-TC-MIB DEFINITIONS ::= BEGIN

IMPORTS
    Integer32
        FROM SNMPv2-SMI
    TEXTUAL-CONVENTION
        FROM SNMPv2-TC;

-- TEXTUAL-CONVENTIONS

UnitId1 ::= TEXTUAL-CONVENTION
    STATUS current
    DESCRIPTION
       "The first portion of a unit id, indicating the Host Unit ID."
    SYNTAX Integer32 (1..15)

UnitId2 ::= TEXTUAL-CONVENTION
    STATUS current
    DESCRIPTION
       "The second portion of a unit id consisting of 1 to 8 digits
        indicating the node address of a DART Remote Unit (DRU).  Each
        digit represents the first port in the parent unit to which a
        child unit is connected.  For example, a DRU conected to ports
        5-8 of its parent DRU which is connected to ports 1-4 of a host
        would have a node address of 15."
    SYNTAX Integer32 (1..88888888)

UnitId3 ::= TEXTUAL-CONVENTION
    STATUS current
    DESCRIPTION
       "The third portion of a unit id, indicating the layered address
        of an IF expansion unit (IFEU), a main remote antenna unit
        (MRAU), or a secondary remote antenna unit (SRAU).  Each of the
        4 digits represents the port in the parent unit to which a child
        unit is connected.  The first digit, with the value 1,
        represents an IFEU connected to a DART Remote Unit.  The second
        digit, with a value of 1 through 8, represents the IFEU port to
        which an MRAU is connected.  The third digit, with a value of 1
        through 3, represents the MRAU port to which an SRAU is
        connected.  The fourth digit is reserved as 0.  Examples are
        1000 for an IFEU, 1500 for an MRAU connected to port 5 of an
        IFEU, and 1830 for an SRAU connected to port 3 of an MRAU
        connected to port 8 of an IFEU."
    SYNTAX Integer32 (1000..1830)

UnitType ::= TEXTUAL-CONVENTION
    STATUS current
    DESCRIPTION
       "Type of unit."
    SYNTAX INTEGER {
        unknown(-1),
        hostUnit(1),
        urhRemoteUnit(2),
        prismRemoteUnit(3),
        dartRemoteUnit(4),
        ifeu(5),            -- IF Expansion Unit
        mRau(6),            -- main RAU
        sRau(7)             -- secondary RAU
    }

LatAndLong ::= TEXTUAL-CONVENTION
    DISPLAY-HINT "15a"
    STATUS current
    DESCRIPTION
       "The RAU's latitude / longitude reading.  It is of the format
           ['N/S' | 'E/W'] (+|-)ddd.dddddd where
        'N/S' or 'E/W' speak to latitude or longitude.
        If the data is not present to the decimal then zeros must be
        inserted.  i.e.
        N/S +001.100000 and E/W 001.123000 are valid while
        E/W 1.1230000 and N/S 1.123456 are not."
    SYNTAX OCTET STRING (SIZE (14..15))

RauIntPath ::= TEXTUAL-CONVENTION
    STATUS current
    DESCRIPTION
       "An RAU internal component path used to handle one or more RF
        bands."
    SYNTAX INTEGER {
        unknown(-1),
        path1A(1),
        path2A(2),
        path3A(3),
        path1B(4),
        path2B(5),
        path3B(6)
    }

RauIntPathDir ::= TEXTUAL-CONVENTION
    STATUS current
    DESCRIPTION
       "The portion of an RAU internal component path used to handle one
        or more RF bands in the forward or reverse direction."
    SYNTAX INTEGER {
        unknown(-1),
        path1AFwd(1),
        path1ARev(2),
        path2AFwd(3),
        path2ARev(4),
        path3AFwd(5),
        path3ARev(6),
        path1BFwd(7),
        path1BRev(8),
        path2BFwd(9),
        path2BRev(10),
        path3BFwd(11),
        path3BRev(12)
    }

END
