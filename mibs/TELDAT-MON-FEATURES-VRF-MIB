-- Teldat, S.A.

                -- Parque Tecnolgico de Madrid

                -- 28760, Tres Cantos (Madrid)

                -- Tlf: +34-918076565

                -- Fax: +34-918076521

                -- e-mail: id@teldat.com


            -- MIB privada de Teldat

            -- Monitorizacin de VRFs


    -- Historial:
    -- 1.0  07-04-14    F. Hernßndez        Implementacin inicial
--------------------------------------------------------------------------------

TELDAT-MON-FEATURES-VRF-MIB DEFINITIONS ::= BEGIN

    IMPORTS
        Counter
            FROM RFC1155-SMI
        OBJECT-TYPE
            FROM RFC-1212
        DisplayString
            FROM RFC1213-MIB
        telProdNpMonFeatures
            FROM TELDAT-SW-STRUCTURE-MIB;


-- Monitorizacin privada de VRFs

telProdNpMonFeatVrf OBJECT IDENTIFIER ::= { telProdNpMonFeatures 10 }

-- Tabla que recoge las VRFs asociadas a los interfaces

telProdNpMonFeatVrfTable OBJECT-TYPE
    SYNTAX SEQUENCE OF TelProdNpMonFeatVrfEntry
    ACCESS not-accessible
    STATUS mandatory
    DESCRIPTION
    "Displays the VRF names associated to the interface."
    ::= { telProdNpMonFeatVrf 1 }

telProdNpMonFeatVrfEntry OBJECT-TYPE
    SYNTAX TelProdNpMonFeatVrfEntry
    ACCESS not-accessible
    STATUS mandatory
    DESCRIPTION
    "The table index is the interface number"
    INDEX { telProdNpMonFeatVrfIfc }
    ::= { telProdNpMonFeatVrfTable 1 }

TelProdNpMonFeatVrfEntry ::=
    SEQUENCE{
        telProdNpMonFeatVrfIfc
            INTEGER,
        telProdNpMonFeatVrfIfcDesc
        		DisplayString,
        telProdNpMonFeatVrfName
            DisplayString
        }

telProdNpMonFeatVrfIfc OBJECT-TYPE
    SYNTAX INTEGER
    ACCESS read-only
    STATUS mandatory
    DESCRIPTION
    "Index: interface number"
    ::= { telProdNpMonFeatVrfEntry 1 }
    
telProdNpMonFeatVrfIfcDesc OBJECT-TYPE
    SYNTAX      DisplayString (SIZE (0..255))
    ACCESS  	  read-only
    STATUS      mandatory
    DESCRIPTION
            "A textual string containing information about the
            interface.  This string should include the name of the
            manufacturer, the product name and the version of the
            interface hardware/software."
    ::= { telProdNpMonFeatVrfEntry 2 }

telProdNpMonFeatVrfName OBJECT-TYPE
    SYNTAX DisplayString(SIZE(0..79))
    ACCESS read-only
    STATUS mandatory
    DESCRIPTION
    "Name of the VRF associate to the interface"
    ::= { telProdNpMonFeatVrfEntry 3 }

END
