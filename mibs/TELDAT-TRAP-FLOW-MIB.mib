-- file automatically created


TELDAT-TRAP-FLOW-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


flowTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the FLOW event subsystem."
    REVISION "201401200930Z"
    DESCRIPTION "Initial implementation"
        ::= { telEventTraps 218 }


flowEventsGroup	OBJECT IDENTIFIER	::= { flowTrapsMIB 1 }

flowNotifications	OBJECT IDENTIFIER	::= { flowTrapsMIB 2 }
flowNotificationsPrefix	OBJECT IDENTIFIER	::= { flowNotifications 0 }

flowEventObjects1 OBJECT-IDENTITY
    STATUS current
    DESCRIPTION
        "Event FLOW.1
        client state changed"
    ::= { flowEventsGroup 1 }

flow1_state OBJECT-TYPE
    SYNTAX DisplayString
    MAX-ACCESS accessible-for-notify
    STATUS current
    DESCRIPTION
        "Parameter 'state' in event FLOW.1"
    ::= { flowEventObjects1 1 }

flowEventObjects2 OBJECT-IDENTITY
    STATUS current
    DESCRIPTION
        "Event FLOW.2
        new flow created"
    ::= { flowEventsGroup 2 }

flow2_source-ip OBJECT-TYPE
    SYNTAX IpAddress
    MAX-ACCESS accessible-for-notify
    STATUS current
    DESCRIPTION
        "Parameter 'source-ip' in event FLOW.2"
    ::= { flowEventObjects2 1 }

flow2_destination-ip OBJECT-TYPE
    SYNTAX IpAddress
    MAX-ACCESS accessible-for-notify
    STATUS current
    DESCRIPTION
        "Parameter 'destination-ip' in event FLOW.2"
    ::= { flowEventObjects2 2 }

flow2_protocol OBJECT-TYPE
    SYNTAX DisplayString
    MAX-ACCESS accessible-for-notify
    STATUS current
    DESCRIPTION
        "Parameter 'protocol' in event FLOW.2"
    ::= { flowEventObjects2 3 }

flow2_expiry OBJECT-TYPE
    SYNTAX Integer32
    MAX-ACCESS accessible-for-notify
    STATUS current
    DESCRIPTION
        "Parameter 'expiry' in event FLOW.2"
    ::= { flowEventObjects2 4 }

flowEventObjects3 OBJECT-IDENTITY
    STATUS current
    DESCRIPTION
        "Event FLOW.3
        flow matched"
    ::= { flowEventsGroup 3 }

flow3_source-ip OBJECT-TYPE
    SYNTAX IpAddress
    MAX-ACCESS accessible-for-notify
    STATUS current
    DESCRIPTION
        "Parameter 'source-ip' in event FLOW.3"
    ::= { flowEventObjects3 1 }

flow3_destination-ip OBJECT-TYPE
    SYNTAX IpAddress
    MAX-ACCESS accessible-for-notify
    STATUS current
    DESCRIPTION
        "Parameter 'destination-ip' in event FLOW.3"
    ::= { flowEventObjects3 2 }

flow3_protocol OBJECT-TYPE
    SYNTAX DisplayString
    MAX-ACCESS accessible-for-notify
    STATUS current
    DESCRIPTION
        "Parameter 'protocol' in event FLOW.3"
    ::= { flowEventObjects3 3 }

flow3_expiry OBJECT-TYPE
    SYNTAX Integer32
    MAX-ACCESS accessible-for-notify
    STATUS current
    DESCRIPTION
        "Parameter 'expiry' in event FLOW.3"
    ::= { flowEventObjects3 4 }

flowEventObjects4 OBJECT-IDENTITY
    STATUS current
    DESCRIPTION
        "Event FLOW.4
        netflow v9 packet sent"
    ::= { flowEventsGroup 4 }

flow4_srvr_ip OBJECT-TYPE
    SYNTAX IpAddress
    MAX-ACCESS accessible-for-notify
    STATUS current
    DESCRIPTION
        "Parameter 'srvr_ip' in event FLOW.4"
    ::= { flowEventObjects4 1 }

flow4_srvr_port OBJECT-TYPE
    SYNTAX Integer32
    MAX-ACCESS accessible-for-notify
    STATUS current
    DESCRIPTION
        "Parameter 'srvr_port' in event FLOW.4"
    ::= { flowEventObjects4 2 }

flow4_length OBJECT-TYPE
    SYNTAX Integer32
    MAX-ACCESS accessible-for-notify
    STATUS current
    DESCRIPTION
        "Parameter 'length' in event FLOW.4"
    ::= { flowEventObjects4 3 }

flow4_flows OBJECT-TYPE
    SYNTAX Integer32
    MAX-ACCESS accessible-for-notify
    STATUS current
    DESCRIPTION
        "Parameter 'flows' in event FLOW.4"
    ::= { flowEventObjects4 4 }

flow4_template OBJECT-TYPE
    SYNTAX DisplayString
    MAX-ACCESS accessible-for-notify
    STATUS current
    DESCRIPTION
        "Parameter 'template' in event FLOW.4"
    ::= { flowEventObjects4 5 }

flowEventObjects5 OBJECT-IDENTITY
    STATUS current
    DESCRIPTION
        "Event FLOW.5
        netflow v5 packet sent"
    ::= { flowEventsGroup 5 }

flow5_srvr_ip OBJECT-TYPE
    SYNTAX IpAddress
    MAX-ACCESS accessible-for-notify
    STATUS current
    DESCRIPTION
        "Parameter 'srvr_ip' in event FLOW.5"
    ::= { flowEventObjects5 1 }

flow5_srvr_port OBJECT-TYPE
    SYNTAX Integer32
    MAX-ACCESS accessible-for-notify
    STATUS current
    DESCRIPTION
        "Parameter 'srvr_port' in event FLOW.5"
    ::= { flowEventObjects5 2 }

flow5_length OBJECT-TYPE
    SYNTAX Integer32
    MAX-ACCESS accessible-for-notify
    STATUS current
    DESCRIPTION
        "Parameter 'length' in event FLOW.5"
    ::= { flowEventObjects5 3 }

flow5_flows OBJECT-TYPE
    SYNTAX Integer32
    MAX-ACCESS accessible-for-notify
    STATUS current
    DESCRIPTION
        "Parameter 'flows' in event FLOW.5"
    ::= { flowEventObjects5 4 }

flowEventObjects6 OBJECT-IDENTITY
    STATUS current
    DESCRIPTION
        "Event FLOW.6
        flow deleted"
    ::= { flowEventsGroup 6 }

flow6_source-ip OBJECT-TYPE
    SYNTAX IpAddress
    MAX-ACCESS accessible-for-notify
    STATUS current
    DESCRIPTION
        "Parameter 'source-ip' in event FLOW.6"
    ::= { flowEventObjects6 1 }

flow6_destination-ip OBJECT-TYPE
    SYNTAX IpAddress
    MAX-ACCESS accessible-for-notify
    STATUS current
    DESCRIPTION
        "Parameter 'destination-ip' in event FLOW.6"
    ::= { flowEventObjects6 2 }

flow6_protocol OBJECT-TYPE
    SYNTAX DisplayString
    MAX-ACCESS accessible-for-notify
    STATUS current
    DESCRIPTION
        "Parameter 'protocol' in event FLOW.6"
    ::= { flowEventObjects6 3 }

flowEventObjects7 OBJECT-IDENTITY
    STATUS current
    DESCRIPTION
        "Event FLOW.7
        an ip fragment has been ignored"
    ::= { flowEventsGroup 7 }

flow7_source-ip OBJECT-TYPE
    SYNTAX IpAddress
    MAX-ACCESS accessible-for-notify
    STATUS current
    DESCRIPTION
        "Parameter 'source-ip' in event FLOW.7"
    ::= { flowEventObjects7 1 }

flow7_destination-ip OBJECT-TYPE
    SYNTAX IpAddress
    MAX-ACCESS accessible-for-notify
    STATUS current
    DESCRIPTION
        "Parameter 'destination-ip' in event FLOW.7"
    ::= { flowEventObjects7 2 }

flow7_protocol OBJECT-TYPE
    SYNTAX DisplayString
    MAX-ACCESS accessible-for-notify
    STATUS current
    DESCRIPTION
        "Parameter 'protocol' in event FLOW.7"
    ::= { flowEventObjects7 3 }

flowEventObjects8 OBJECT-IDENTITY
    STATUS current
    DESCRIPTION
        "Event FLOW.8
        an ipsec packet has been ignored"
    ::= { flowEventsGroup 8 }

flow8_source-ip OBJECT-TYPE
    SYNTAX IpAddress
    MAX-ACCESS accessible-for-notify
    STATUS current
    DESCRIPTION
        "Parameter 'source-ip' in event FLOW.8"
    ::= { flowEventObjects8 1 }

flow8_destination-ip OBJECT-TYPE
    SYNTAX IpAddress
    MAX-ACCESS accessible-for-notify
    STATUS current
    DESCRIPTION
        "Parameter 'destination-ip' in event FLOW.8"
    ::= { flowEventObjects8 2 }

flow8_protocol OBJECT-TYPE
    SYNTAX DisplayString
    MAX-ACCESS accessible-for-notify
    STATUS current
    DESCRIPTION
        "Parameter 'protocol' in event FLOW.8"
    ::= { flowEventObjects8 3 }

flowEventObjects9 OBJECT-IDENTITY
    STATUS current
    DESCRIPTION
        "Event FLOW.9
        ip packtet ignored due to sampling"
    ::= { flowEventsGroup 9 }

flow9_source-ip OBJECT-TYPE
    SYNTAX IpAddress
    MAX-ACCESS accessible-for-notify
    STATUS current
    DESCRIPTION
        "Parameter 'source-ip' in event FLOW.9"
    ::= { flowEventObjects9 1 }

flow9_destination-ip OBJECT-TYPE
    SYNTAX IpAddress
    MAX-ACCESS accessible-for-notify
    STATUS current
    DESCRIPTION
        "Parameter 'destination-ip' in event FLOW.9"
    ::= { flowEventObjects9 2 }

flow9_protocol OBJECT-TYPE
    SYNTAX DisplayString
    MAX-ACCESS accessible-for-notify
    STATUS current
    DESCRIPTION
        "Parameter 'protocol' in event FLOW.9"
    ::= { flowEventObjects9 3 }

flow9_sampling-factor OBJECT-TYPE
    SYNTAX Integer32
    MAX-ACCESS accessible-for-notify
    STATUS current
    DESCRIPTION
        "Parameter 'sampling-factor' in event FLOW.9"
    ::= { flowEventObjects9 4 }


flowNotification1 NOTIFICATION-TYPE
    OBJECTS { 
              flow1_state 
            }
    STATUS current
    DESCRIPTION
        "Notification of Event FLOW.1

        Message: 'Client $1'

        Parameters list:
              $1: flow1_state

        client state changed"
    ::= { flowNotificationsPrefix 1 }

flowNotification2 NOTIFICATION-TYPE
    OBJECTS { 
              flow2_source-ip, 
              flow2_destination-ip,
              flow2_protocol,
              flow2_expiry 
            }
    STATUS current
    DESCRIPTION
        "Notification of Event FLOW.2

        Message: 'New flow created $1->$2 protocol $3 expiry $4'

        Parameters list:
              $1: flow2_source-ip
              $2: flow2_destination-ip
              $3: flow2_protocol
              $4: flow2_expiry

        new flow created"
    ::= { flowNotificationsPrefix 2 }

flowNotification3 NOTIFICATION-TYPE
    OBJECTS { 
              flow3_source-ip, 
              flow3_destination-ip,
              flow3_protocol,
              flow3_expiry 
            }
    STATUS current
    DESCRIPTION
        "Notification of Event FLOW.3

        Message: 'Flow matched $1->$2 protocol $3 expiry $4'

        Parameters list:
              $1: flow3_source-ip
              $2: flow3_destination-ip
              $3: flow3_protocol
              $4: flow3_expiry

        flow matched"
    ::= { flowNotificationsPrefix 3 }

flowNotification4 NOTIFICATION-TYPE
    OBJECTS { 
              flow4_srvr_ip, 
              flow4_srvr_port,
              flow4_length,
              flow4_flows,
              flow4_template 
            }
    STATUS current
    DESCRIPTION
        "Notification of Event FLOW.4

        Message: 'NetflowV9 packet sent to $1:$2 length $3 number of flows $4 template $5'

        Parameters list:
              $1: flow4_srvr_ip
              $2: flow4_srvr_port
              $3: flow4_length
              $4: flow4_flows
              $5: flow4_template

        netflow v9 packet sent"
    ::= { flowNotificationsPrefix 4 }

flowNotification5 NOTIFICATION-TYPE
    OBJECTS { 
              flow5_srvr_ip, 
              flow5_srvr_port,
              flow5_length,
              flow5_flows 
            }
    STATUS current
    DESCRIPTION
        "Notification of Event FLOW.5

        Message: 'NetflowV5 packet sent to $1:$2 length $3 number of flows $4'

        Parameters list:
              $1: flow5_srvr_ip
              $2: flow5_srvr_port
              $3: flow5_length
              $4: flow5_flows

        netflow v5 packet sent"
    ::= { flowNotificationsPrefix 5 }

flowNotification6 NOTIFICATION-TYPE
    OBJECTS { 
              flow6_source-ip, 
              flow6_destination-ip,
              flow6_protocol 
            }
    STATUS current
    DESCRIPTION
        "Notification of Event FLOW.6

        Message: 'Flow deleted $1->$2 protocol $3'

        Parameters list:
              $1: flow6_source-ip
              $2: flow6_destination-ip
              $3: flow6_protocol

        flow deleted"
    ::= { flowNotificationsPrefix 6 }

flowNotification7 NOTIFICATION-TYPE
    OBJECTS { 
              flow7_source-ip, 
              flow7_destination-ip,
              flow7_protocol 
            }
    STATUS current
    DESCRIPTION
        "Notification of Event FLOW.7

        Message: 'IP fragment ignored $1->$2 protocol $3'

        Parameters list:
              $1: flow7_source-ip
              $2: flow7_destination-ip
              $3: flow7_protocol

        an ip fragment has been ignored"
    ::= { flowNotificationsPrefix 7 }

flowNotification8 NOTIFICATION-TYPE
    OBJECTS { 
              flow8_source-ip, 
              flow8_destination-ip,
              flow8_protocol 
            }
    STATUS current
    DESCRIPTION
        "Notification of Event FLOW.8

        Message: 'Ipsec packet ignored $1->$2 protocol $3'

        Parameters list:
              $1: flow8_source-ip
              $2: flow8_destination-ip
              $3: flow8_protocol

        an ipsec packet has been ignored"
    ::= { flowNotificationsPrefix 8 }

flowNotification9 NOTIFICATION-TYPE
    OBJECTS { 
              flow9_source-ip, 
              flow9_destination-ip,
              flow9_protocol,
              flow9_sampling-factor 
            }
    STATUS current
    DESCRIPTION
        "Notification of Event FLOW.9

        Message: 'IP packet sampled $1->$2 protocol $3 factor $4'

        Parameters list:
              $1: flow9_source-ip
              $2: flow9_destination-ip
              $3: flow9_protocol
              $4: flow9_sampling-factor

        ip packtet ignored due to sampling"
    ::= { flowNotificationsPrefix 9 }

flowNotification10 NOTIFICATION-TYPE
    STATUS current
    DESCRIPTION
        "Notification of Event FLOW.10

        Message: 'IP packet procesing error'

        ip packtet processing error"
    ::= { flowNotificationsPrefix 10 }


END
