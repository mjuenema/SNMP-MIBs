-- file automatically created


TELDAT-TRAP-SCFW-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


scfwTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SCFW event subsystem."
    REVISION "201401200930Z"
    DESCRIPTION "Initial implementation"
        ::= { telEventTraps 189 }


scfwEventsGroup	OBJECT IDENTIFIER	::= { scfwTrapsMIB 1 }

scfwNotifications	OBJECT IDENTIFIER	::= { scfwTrapsMIB 2 }
scfwNotificationsPrefix	OBJECT IDENTIFIER	::= { scfwNotifications 0 }

scfwEventObjects1 OBJECT-IDENTITY
    STATUS current
    DESCRIPTION
        "Event SCFW.1
        TCP listen for incoming RTU's connections has not been make."
    ::= { scfwEventsGroup 1 }

scfw1_tcp_port OBJECT-TYPE
    SYNTAX Integer32
    MAX-ACCESS accessible-for-notify
    STATUS current
    DESCRIPTION
        "Parameter 'tcp_port' in event SCFW.1"
    ::= { scfwEventObjects1 1 }

scfwEventObjects2 OBJECT-IDENTITY
    STATUS current
    DESCRIPTION
        "Event SCFW.2
        TCP listen for incoming Control Centers connections has not been make."
    ::= { scfwEventsGroup 2 }

scfw2_tcp_port OBJECT-TYPE
    SYNTAX Integer32
    MAX-ACCESS accessible-for-notify
    STATUS current
    DESCRIPTION
        "Parameter 'tcp_port' in event SCFW.2"
    ::= { scfwEventObjects2 1 }

scfwEventObjects3 OBJECT-IDENTITY
    STATUS current
    DESCRIPTION
        "Event SCFW.3
        A message with LRC/CRC error has been received from Control Center."
    ::= { scfwEventsGroup 3 }

scfw3_data_leng OBJECT-TYPE
    SYNTAX Integer32
    MAX-ACCESS accessible-for-notify
    STATUS current
    DESCRIPTION
        "Parameter 'data_leng' in event SCFW.3"
    ::= { scfwEventObjects3 1 }

scfw3_cent_ip OBJECT-TYPE
    SYNTAX IpAddress
    MAX-ACCESS accessible-for-notify
    STATUS current
    DESCRIPTION
        "Parameter 'cent_ip' in event SCFW.3"
    ::= { scfwEventObjects3 2 }

scfw3_cent_port OBJECT-TYPE
    SYNTAX Integer32
    MAX-ACCESS accessible-for-notify
    STATUS current
    DESCRIPTION
        "Parameter 'cent_port' in event SCFW.3"
    ::= { scfwEventObjects3 3 }

scfwEventObjects4 OBJECT-IDENTITY
    STATUS current
    DESCRIPTION
        "Event SCFW.4
        A message with LRC/CRC error has been received from RTU."
    ::= { scfwEventsGroup 4 }

scfw4_data_leng OBJECT-TYPE
    SYNTAX Integer32
    MAX-ACCESS accessible-for-notify
    STATUS current
    DESCRIPTION
        "Parameter 'data_leng' in event SCFW.4"
    ::= { scfwEventObjects4 1 }

scfw4_rtu_ip OBJECT-TYPE
    SYNTAX IpAddress
    MAX-ACCESS accessible-for-notify
    STATUS current
    DESCRIPTION
        "Parameter 'rtu_ip' in event SCFW.4"
    ::= { scfwEventObjects4 2 }

scfw4_rtu_port OBJECT-TYPE
    SYNTAX Integer32
    MAX-ACCESS accessible-for-notify
    STATUS current
    DESCRIPTION
        "Parameter 'rtu_port' in event SCFW.4"
    ::= { scfwEventObjects4 3 }

scfwEventObjects5 OBJECT-IDENTITY
    STATUS current
    DESCRIPTION
        "Event SCFW.5
        TCP session to direcction especified not found when an event occur."
    ::= { scfwEventsGroup 5 }

scfw5_directon OBJECT-TYPE
    SYNTAX DisplayString
    MAX-ACCESS accessible-for-notify
    STATUS current
    DESCRIPTION
        "Parameter 'directon' in event SCFW.5"
    ::= { scfwEventObjects5 1 }

scfw5_event_load OBJECT-TYPE
    SYNTAX Integer32
    MAX-ACCESS accessible-for-notify
    STATUS current
    DESCRIPTION
        "Parameter 'event_load' in event SCFW.5"
    ::= { scfwEventObjects5 2 }

scfwEventObjects6 OBJECT-IDENTITY
    STATUS current
    DESCRIPTION
        "Event SCFW.6
        Addres received from Control Center is not included in configuration
        registers list."
    ::= { scfwEventsGroup 6 }

scfw6_serial_address OBJECT-TYPE
    SYNTAX Integer32
    MAX-ACCESS accessible-for-notify
    STATUS current
    DESCRIPTION
        "Parameter 'serial_address' in event SCFW.6"
    ::= { scfwEventObjects6 1 }

scfw6_center_addr OBJECT-TYPE
    SYNTAX IpAddress
    MAX-ACCESS accessible-for-notify
    STATUS current
    DESCRIPTION
        "Parameter 'center_addr' in event SCFW.6"
    ::= { scfwEventObjects6 2 }

scfw6_tcp_port OBJECT-TYPE
    SYNTAX Integer32
    MAX-ACCESS accessible-for-notify
    STATUS current
    DESCRIPTION
        "Parameter 'tcp_port' in event SCFW.6"
    ::= { scfwEventObjects6 3 }

scfwEventObjects7 OBJECT-IDENTITY
    STATUS current
    DESCRIPTION
        "Event SCFW.7
        It's trying the connection against remote IP and P port."
    ::= { scfwEventsGroup 7 }

scfw7_serial_address OBJECT-TYPE
    SYNTAX Integer32
    MAX-ACCESS accessible-for-notify
    STATUS current
    DESCRIPTION
        "Parameter 'serial_address' in event SCFW.7"
    ::= { scfwEventObjects7 1 }

scfw7_rtu_ip_address OBJECT-TYPE
    SYNTAX IpAddress
    MAX-ACCESS accessible-for-notify
    STATUS current
    DESCRIPTION
        "Parameter 'rtu_ip_address' in event SCFW.7"
    ::= { scfwEventObjects7 2 }

scfw7_port OBJECT-TYPE
    SYNTAX Integer32
    MAX-ACCESS accessible-for-notify
    STATUS current
    DESCRIPTION
        "Parameter 'port' in event SCFW.7"
    ::= { scfwEventObjects7 3 }

scfwEventObjects8 OBJECT-IDENTITY
    STATUS current
    DESCRIPTION
        "Event SCFW.8
        Trying to send message to a RTU."
    ::= { scfwEventsGroup 8 }

scfw8_bytes OBJECT-TYPE
    SYNTAX Integer32
    MAX-ACCESS accessible-for-notify
    STATUS current
    DESCRIPTION
        "Parameter 'bytes' in event SCFW.8"
    ::= { scfwEventObjects8 1 }

scfw8_rem_ip_addr OBJECT-TYPE
    SYNTAX IpAddress
    MAX-ACCESS accessible-for-notify
    STATUS current
    DESCRIPTION
        "Parameter 'rem_ip_addr' in event SCFW.8"
    ::= { scfwEventObjects8 2 }

scfw8_rem_tcp_port OBJECT-TYPE
    SYNTAX Integer32
    MAX-ACCESS accessible-for-notify
    STATUS current
    DESCRIPTION
        "Parameter 'rem_tcp_port' in event SCFW.8"
    ::= { scfwEventObjects8 3 }

scfwEventObjects9 OBJECT-IDENTITY
    STATUS current
    DESCRIPTION
        "Event SCFW.9
        Trying to send message to Remote end."
    ::= { scfwEventsGroup 9 }

scfw9_bytes OBJECT-TYPE
    SYNTAX Integer32
    MAX-ACCESS accessible-for-notify
    STATUS current
    DESCRIPTION
        "Parameter 'bytes' in event SCFW.9"
    ::= { scfwEventObjects9 1 }

scfw9_rem_ip_addr OBJECT-TYPE
    SYNTAX IpAddress
    MAX-ACCESS accessible-for-notify
    STATUS current
    DESCRIPTION
        "Parameter 'rem_ip_addr' in event SCFW.9"
    ::= { scfwEventObjects9 2 }

scfw9_rem_tcp_port OBJECT-TYPE
    SYNTAX Integer32
    MAX-ACCESS accessible-for-notify
    STATUS current
    DESCRIPTION
        "Parameter 'rem_tcp_port' in event SCFW.9"
    ::= { scfwEventObjects9 3 }

scfwEventObjects10 OBJECT-IDENTITY
    STATUS current
    DESCRIPTION
        "Event SCFW.10
        A TCP Packet has been received from Control Center."
    ::= { scfwEventsGroup 10 }

scfw10_message_type OBJECT-TYPE
    SYNTAX DisplayString
    MAX-ACCESS accessible-for-notify
    STATUS current
    DESCRIPTION
        "Parameter 'message_type' in event SCFW.10"
    ::= { scfwEventObjects10 1 }

scfw10_bytes OBJECT-TYPE
    SYNTAX Integer32
    MAX-ACCESS accessible-for-notify
    STATUS current
    DESCRIPTION
        "Parameter 'bytes' in event SCFW.10"
    ::= { scfwEventObjects10 2 }

scfw10_foreign_host OBJECT-TYPE
    SYNTAX IpAddress
    MAX-ACCESS accessible-for-notify
    STATUS current
    DESCRIPTION
        "Parameter 'foreign_host' in event SCFW.10"
    ::= { scfwEventObjects10 3 }

scfw10_remote_port OBJECT-TYPE
    SYNTAX Integer32
    MAX-ACCESS accessible-for-notify
    STATUS current
    DESCRIPTION
        "Parameter 'remote_port' in event SCFW.10"
    ::= { scfwEventObjects10 4 }

scfwEventObjects11 OBJECT-IDENTITY
    STATUS current
    DESCRIPTION
        "Event SCFW.11
        A TCP Packet has been received from RTU."
    ::= { scfwEventsGroup 11 }

scfw11_message_type OBJECT-TYPE
    SYNTAX DisplayString
    MAX-ACCESS accessible-for-notify
    STATUS current
    DESCRIPTION
        "Parameter 'message_type' in event SCFW.11"
    ::= { scfwEventObjects11 1 }

scfw11_bytes OBJECT-TYPE
    SYNTAX Integer32
    MAX-ACCESS accessible-for-notify
    STATUS current
    DESCRIPTION
        "Parameter 'bytes' in event SCFW.11"
    ::= { scfwEventObjects11 2 }

scfw11_foreign_host OBJECT-TYPE
    SYNTAX IpAddress
    MAX-ACCESS accessible-for-notify
    STATUS current
    DESCRIPTION
        "Parameter 'foreign_host' in event SCFW.11"
    ::= { scfwEventObjects11 3 }

scfw11_remote_port OBJECT-TYPE
    SYNTAX Integer32
    MAX-ACCESS accessible-for-notify
    STATUS current
    DESCRIPTION
        "Parameter 'remote_port' in event SCFW.11"
    ::= { scfwEventObjects11 4 }

scfwEventObjects12 OBJECT-IDENTITY
    STATUS current
    DESCRIPTION
        "Event SCFW.12
        A TCP Packet has been received from RTU."
    ::= { scfwEventsGroup 12 }

scfw12_message_type OBJECT-TYPE
    SYNTAX DisplayString
    MAX-ACCESS accessible-for-notify
    STATUS current
    DESCRIPTION
        "Parameter 'message_type' in event SCFW.12"
    ::= { scfwEventObjects12 1 }

scfw12_bytes OBJECT-TYPE
    SYNTAX Integer32
    MAX-ACCESS accessible-for-notify
    STATUS current
    DESCRIPTION
        "Parameter 'bytes' in event SCFW.12"
    ::= { scfwEventObjects12 2 }

scfw12_foreign_host OBJECT-TYPE
    SYNTAX IpAddress
    MAX-ACCESS accessible-for-notify
    STATUS current
    DESCRIPTION
        "Parameter 'foreign_host' in event SCFW.12"
    ::= { scfwEventObjects12 3 }

scfw12_remote_port OBJECT-TYPE
    SYNTAX Integer32
    MAX-ACCESS accessible-for-notify
    STATUS current
    DESCRIPTION
        "Parameter 'remote_port' in event SCFW.12"
    ::= { scfwEventObjects12 4 }

scfwEventObjects13 OBJECT-IDENTITY
    STATUS current
    DESCRIPTION
        "Event SCFW.13
        The TCP session to RTU/Control Center has been closed."
    ::= { scfwEventsGroup 13 }

scfw13_type_host OBJECT-TYPE
    SYNTAX DisplayString
    MAX-ACCESS accessible-for-notify
    STATUS current
    DESCRIPTION
        "Parameter 'type_host' in event SCFW.13"
    ::= { scfwEventObjects13 1 }

scfw13_foreign_host OBJECT-TYPE
    SYNTAX IpAddress
    MAX-ACCESS accessible-for-notify
    STATUS current
    DESCRIPTION
        "Parameter 'foreign_host' in event SCFW.13"
    ::= { scfwEventObjects13 2 }

scfw13_remote_port OBJECT-TYPE
    SYNTAX Integer32
    MAX-ACCESS accessible-for-notify
    STATUS current
    DESCRIPTION
        "Parameter 'remote_port' in event SCFW.13"
    ::= { scfwEventObjects13 3 }

scfwEventObjects14 OBJECT-IDENTITY
    STATUS current
    DESCRIPTION
        "Event SCFW.14
        The TCP session has been closed by the Remote end."
    ::= { scfwEventsGroup 14 }

scfw14_foreign_host OBJECT-TYPE
    SYNTAX IpAddress
    MAX-ACCESS accessible-for-notify
    STATUS current
    DESCRIPTION
        "Parameter 'foreign_host' in event SCFW.14"
    ::= { scfwEventObjects14 1 }

scfw14_remote_port OBJECT-TYPE
    SYNTAX Integer32
    MAX-ACCESS accessible-for-notify
    STATUS current
    DESCRIPTION
        "Parameter 'remote_port' in event SCFW.14"
    ::= { scfwEventObjects14 2 }

scfwEventObjects15 OBJECT-IDENTITY
    STATUS current
    DESCRIPTION
        "Event SCFW.15
        The TCP session to RTU/Ctrl. Center has been opened."
    ::= { scfwEventsGroup 15 }

scfw15_type_host OBJECT-TYPE
    SYNTAX DisplayString
    MAX-ACCESS accessible-for-notify
    STATUS current
    DESCRIPTION
        "Parameter 'type_host' in event SCFW.15"
    ::= { scfwEventObjects15 1 }

scfw15_remote_ip OBJECT-TYPE
    SYNTAX IpAddress
    MAX-ACCESS accessible-for-notify
    STATUS current
    DESCRIPTION
        "Parameter 'remote_ip' in event SCFW.15"
    ::= { scfwEventObjects15 2 }

scfw15_remote_port OBJECT-TYPE
    SYNTAX Integer32
    MAX-ACCESS accessible-for-notify
    STATUS current
    DESCRIPTION
        "Parameter 'remote_port' in event SCFW.15"
    ::= { scfwEventObjects15 3 }

scfwEventObjects16 OBJECT-IDENTITY
    STATUS current
    DESCRIPTION
        "Event SCFW.16
        A packet was lost, due TCP Tx overrun error."
    ::= { scfwEventsGroup 16 }

scfw16_type_host OBJECT-TYPE
    SYNTAX DisplayString
    MAX-ACCESS accessible-for-notify
    STATUS current
    DESCRIPTION
        "Parameter 'type_host' in event SCFW.16"
    ::= { scfwEventObjects16 1 }

scfw16_rem_ip OBJECT-TYPE
    SYNTAX IpAddress
    MAX-ACCESS accessible-for-notify
    STATUS current
    DESCRIPTION
        "Parameter 'rem_ip' in event SCFW.16"
    ::= { scfwEventObjects16 2 }

scfw16_remp_tcp_port OBJECT-TYPE
    SYNTAX Integer32
    MAX-ACCESS accessible-for-notify
    STATUS current
    DESCRIPTION
        "Parameter 'remp_tcp_port' in event SCFW.16"
    ::= { scfwEventObjects16 3 }

scfwEventObjects17 OBJECT-IDENTITY
    STATUS current
    DESCRIPTION
        "Event SCFW.17
        TCP generic event was occurred."
    ::= { scfwEventsGroup 17 }

scfw17_event OBJECT-TYPE
    SYNTAX DisplayString
    MAX-ACCESS accessible-for-notify
    STATUS current
    DESCRIPTION
        "Parameter 'event' in event SCFW.17"
    ::= { scfwEventObjects17 1 }

scfw17_ip OBJECT-TYPE
    SYNTAX IpAddress
    MAX-ACCESS accessible-for-notify
    STATUS current
    DESCRIPTION
        "Parameter 'ip' in event SCFW.17"
    ::= { scfwEventObjects17 2 }

scfw17_port OBJECT-TYPE
    SYNTAX Integer32
    MAX-ACCESS accessible-for-notify
    STATUS current
    DESCRIPTION
        "Parameter 'port' in event SCFW.17"
    ::= { scfwEventObjects17 3 }

scfwEventObjects18 OBJECT-IDENTITY
    STATUS current
    DESCRIPTION
        "Event SCFW.18
        TCP Listen to Control Center has been closed, due max session number has been reached."
    ::= { scfwEventsGroup 18 }

scfw18_port OBJECT-TYPE
    SYNTAX Integer32
    MAX-ACCESS accessible-for-notify
    STATUS current
    DESCRIPTION
        "Parameter 'port' in event SCFW.18"
    ::= { scfwEventObjects18 1 }

scfwEventObjects19 OBJECT-IDENTITY
    STATUS current
    DESCRIPTION
        "Event SCFW.19
        TCP Listen to RTUs has been closed, due max session number has been reached."
    ::= { scfwEventsGroup 19 }

scfw19_port OBJECT-TYPE
    SYNTAX Integer32
    MAX-ACCESS accessible-for-notify
    STATUS current
    DESCRIPTION
        "Parameter 'port' in event SCFW.19"
    ::= { scfwEventObjects19 1 }

scfwEventObjects20 OBJECT-IDENTITY
    STATUS current
    DESCRIPTION
        "Event SCFW.20
        An input TCP session has been rejet."
    ::= { scfwEventsGroup 20 }

scfw20_event OBJECT-TYPE
    SYNTAX DisplayString
    MAX-ACCESS accessible-for-notify
    STATUS current
    DESCRIPTION
        "Parameter 'event' in event SCFW.20"
    ::= { scfwEventObjects20 1 }

scfw20_ip OBJECT-TYPE
    SYNTAX IpAddress
    MAX-ACCESS accessible-for-notify
    STATUS current
    DESCRIPTION
        "Parameter 'ip' in event SCFW.20"
    ::= { scfwEventObjects20 2 }

scfw20_port OBJECT-TYPE
    SYNTAX Integer32
    MAX-ACCESS accessible-for-notify
    STATUS current
    DESCRIPTION
        "Parameter 'port' in event SCFW.20"
    ::= { scfwEventObjects20 3 }


scfwNotification1 NOTIFICATION-TYPE
    OBJECTS { 
              scfw1_tcp_port 
            }
    STATUS current
    DESCRIPTION
        "Notification of Event SCFW.1

        Message: 'Can't open TCP listen for RTU's connections. Port $1'

        Parameters list:
              $1: scfw1_tcp_port

        TCP listen for incoming RTU's connections has not been make."
    ::= { scfwNotificationsPrefix 1 }

scfwNotification2 NOTIFICATION-TYPE
    OBJECTS { 
              scfw2_tcp_port 
            }
    STATUS current
    DESCRIPTION
        "Notification of Event SCFW.2

        Message: 'Can't make TCP listen for Control Centers connections. Port $1'

        Parameters list:
              $1: scfw2_tcp_port

        TCP listen for incoming Control Centers connections has not been make."
    ::= { scfwNotificationsPrefix 2 }

scfwNotification3 NOTIFICATION-TYPE
    OBJECTS { 
              scfw3_data_leng, 
              scfw3_cent_ip,
              scfw3_cent_port 
            }
    STATUS current
    DESCRIPTION
        "Notification of Event SCFW.3

        Message: 'A block with LRC/CRC error has been received from Control Center. Data length:$1, IP Address:$2, Port: $3'

        Parameters list:
              $1: scfw3_data_leng
              $2: scfw3_cent_ip
              $3: scfw3_cent_port

        A message with LRC/CRC error has been received from Control Center."
    ::= { scfwNotificationsPrefix 3 }

scfwNotification4 NOTIFICATION-TYPE
    OBJECTS { 
              scfw4_data_leng, 
              scfw4_rtu_ip,
              scfw4_rtu_port 
            }
    STATUS current
    DESCRIPTION
        "Notification of Event SCFW.4

        Message: 'A block with LRC/CRC error has been received from RTU, Data length:$1, IP Address:$2, Port: $3'

        Parameters list:
              $1: scfw4_data_leng
              $2: scfw4_rtu_ip
              $3: scfw4_rtu_port

        A message with LRC/CRC error has been received from RTU."
    ::= { scfwNotificationsPrefix 4 }

scfwNotification5 NOTIFICATION-TYPE
    OBJECTS { 
              scfw5_directon, 
              scfw5_event_load 
            }
    STATUS current
    DESCRIPTION
        "Notification of Event SCFW.5

        Message: 'TCP session to $1 not found for eve.:$2'

        Parameters list:
              $1: scfw5_directon
              $2: scfw5_event_load

        TCP session to direcction especified not found when an event occur."
    ::= { scfwNotificationsPrefix 5 }

scfwNotification6 NOTIFICATION-TYPE
    OBJECTS { 
              scfw6_serial_address, 
              scfw6_center_addr,
              scfw6_tcp_port 
            }
    STATUS current
    DESCRIPTION
        "Notification of Event SCFW.6

        Message: 'Address $1 received from Serial Terminal is not included in config. regiters. Ctrl Center IP address: $2, port: $3'

        Parameters list:
              $1: scfw6_serial_address
              $2: scfw6_center_addr
              $3: scfw6_tcp_port

        Addres received from Control Center is not included in configuration
        registers list."
    ::= { scfwNotificationsPrefix 6 }

scfwNotification7 NOTIFICATION-TYPE
    OBJECTS { 
              scfw7_serial_address, 
              scfw7_rtu_ip_address,
              scfw7_port 
            }
    STATUS current
    DESCRIPTION
        "Notification of Event SCFW.7

        Message: 'Address $1 is trying the connection against IP $2, Port $3'

        Parameters list:
              $1: scfw7_serial_address
              $2: scfw7_rtu_ip_address
              $3: scfw7_port

        It's trying the connection against remote IP and P port."
    ::= { scfwNotificationsPrefix 7 }

scfwNotification8 NOTIFICATION-TYPE
    OBJECTS { 
              scfw8_bytes, 
              scfw8_rem_ip_addr,
              scfw8_rem_tcp_port 
            }
    STATUS current
    DESCRIPTION
        "Notification of Event SCFW.8

        Message: 'Trying to send a message to RTU with $1 bytes. IP $2, Port $3'

        Parameters list:
              $1: scfw8_bytes
              $2: scfw8_rem_ip_addr
              $3: scfw8_rem_tcp_port

        Trying to send message to a RTU."
    ::= { scfwNotificationsPrefix 8 }

scfwNotification9 NOTIFICATION-TYPE
    OBJECTS { 
              scfw9_bytes, 
              scfw9_rem_ip_addr,
              scfw9_rem_tcp_port 
            }
    STATUS current
    DESCRIPTION
        "Notification of Event SCFW.9

        Message: 'Trying to send a message to Control Center with $1 bytes. IP $2, Port $3'

        Parameters list:
              $1: scfw9_bytes
              $2: scfw9_rem_ip_addr
              $3: scfw9_rem_tcp_port

        Trying to send message to Remote end."
    ::= { scfwNotificationsPrefix 9 }

scfwNotification10 NOTIFICATION-TYPE
    OBJECTS { 
              scfw10_message_type, 
              scfw10_bytes,
              scfw10_foreign_host,
              scfw10_remote_port 
            }
    STATUS current
    DESCRIPTION
        "Notification of Event SCFW.10

        Message: 'A TCP packet $1 has been received from Cntrl. Center, $2 bytes. rem. IP: $3, Port: $4'

        Parameters list:
              $1: scfw10_message_type
              $2: scfw10_bytes
              $3: scfw10_foreign_host
              $4: scfw10_remote_port

        A TCP Packet has been received from Control Center."
    ::= { scfwNotificationsPrefix 10 }

scfwNotification11 NOTIFICATION-TYPE
    OBJECTS { 
              scfw11_message_type, 
              scfw11_bytes,
              scfw11_foreign_host,
              scfw11_remote_port 
            }
    STATUS current
    DESCRIPTION
        "Notification of Event SCFW.11

        Message: 'A TCP packet $1 has been received from RTU, $2 bytes. rem. IP: $3, Port: $4'

        Parameters list:
              $1: scfw11_message_type
              $2: scfw11_bytes
              $3: scfw11_foreign_host
              $4: scfw11_remote_port

        A TCP Packet has been received from RTU."
    ::= { scfwNotificationsPrefix 11 }

scfwNotification12 NOTIFICATION-TYPE
    OBJECTS { 
              scfw12_message_type, 
              scfw12_bytes,
              scfw12_foreign_host,
              scfw12_remote_port 
            }
    STATUS current
    DESCRIPTION
        "Notification of Event SCFW.12

        Message: 'A TCP packet $1 has been received from RTU, $2 bytes. rem. IP: $3, Port: $4'

        Parameters list:
              $1: scfw12_message_type
              $2: scfw12_bytes
              $3: scfw12_foreign_host
              $4: scfw12_remote_port

        A TCP Packet has been received from RTU."
    ::= { scfwNotificationsPrefix 12 }

scfwNotification13 NOTIFICATION-TYPE
    OBJECTS { 
              scfw13_type_host, 
              scfw13_foreign_host,
              scfw13_remote_port 
            }
    STATUS current
    DESCRIPTION
        "Notification of Event SCFW.13

        Message: 'The TCP session to $1 has been closed. rem. IP: $2, Port: $3'

        Parameters list:
              $1: scfw13_type_host
              $2: scfw13_foreign_host
              $3: scfw13_remote_port

        The TCP session to RTU/Control Center has been closed."
    ::= { scfwNotificationsPrefix 13 }

scfwNotification14 NOTIFICATION-TYPE
    OBJECTS { 
              scfw14_foreign_host, 
              scfw14_remote_port 
            }
    STATUS current
    DESCRIPTION
        "Notification of Event SCFW.14

        Message: 'The TCP session has been closed by the Remote end. rem. IP: $1, Port: $2'

        Parameters list:
              $1: scfw14_foreign_host
              $2: scfw14_remote_port

        The TCP session has been closed by the Remote end."
    ::= { scfwNotificationsPrefix 14 }

scfwNotification15 NOTIFICATION-TYPE
    OBJECTS { 
              scfw15_type_host, 
              scfw15_remote_ip,
              scfw15_remote_port 
            }
    STATUS current
    DESCRIPTION
        "Notification of Event SCFW.15

        Message: 'The TCP session has been opened to $1. Remote IP:$2 , Port: $3'

        Parameters list:
              $1: scfw15_type_host
              $2: scfw15_remote_ip
              $3: scfw15_remote_port

        The TCP session to RTU/Ctrl. Center has been opened."
    ::= { scfwNotificationsPrefix 15 }

scfwNotification16 NOTIFICATION-TYPE
    OBJECTS { 
              scfw16_type_host, 
              scfw16_rem_ip,
              scfw16_remp_tcp_port 
            }
    STATUS current
    DESCRIPTION
        "Notification of Event SCFW.16

        Message: 'Packet lost due TCP Tx overrun error to $1: rem. IP $2, Port $3'

        Parameters list:
              $1: scfw16_type_host
              $2: scfw16_rem_ip
              $3: scfw16_remp_tcp_port

        A packet was lost, due TCP Tx overrun error."
    ::= { scfwNotificationsPrefix 16 }

scfwNotification17 NOTIFICATION-TYPE
    OBJECTS { 
              scfw17_event, 
              scfw17_ip,
              scfw17_port 
            }
    STATUS current
    DESCRIPTION
        "Notification of Event SCFW.17

        Message: 'The TCP event: $1 . Rem. IP: $2, Port: $3'

        Parameters list:
              $1: scfw17_event
              $2: scfw17_ip
              $3: scfw17_port

        TCP generic event was occurred."
    ::= { scfwNotificationsPrefix 17 }

scfwNotification18 NOTIFICATION-TYPE
    OBJECTS { 
              scfw18_port 
            }
    STATUS current
    DESCRIPTION
        "Notification of Event SCFW.18

        Message: 'Max sessions number has been reached to Control Centers, port $1'

        Parameters list:
              $1: scfw18_port

        TCP Listen to Control Center has been closed, due max session number has been reached."
    ::= { scfwNotificationsPrefix 18 }

scfwNotification19 NOTIFICATION-TYPE
    OBJECTS { 
              scfw19_port 
            }
    STATUS current
    DESCRIPTION
        "Notification of Event SCFW.19

        Message: 'Max sessions number has been reached to RTUs, port $1'

        Parameters list:
              $1: scfw19_port

        TCP Listen to RTUs has been closed, due max session number has been reached."
    ::= { scfwNotificationsPrefix 19 }

scfwNotification20 NOTIFICATION-TYPE
    OBJECTS { 
              scfw20_event, 
              scfw20_ip,
              scfw20_port 
            }
    STATUS current
    DESCRIPTION
        "Notification of Event SCFW.20

        Message: 'TCP inout session rejet: $1 . Rem. IP: $2, Port: $3'

        Parameters list:
              $1: scfw20_event
              $2: scfw20_ip
              $3: scfw20_port

        An input TCP session has been rejet."
    ::= { scfwNotificationsPrefix 20 }


END
