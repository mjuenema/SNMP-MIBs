-- Teldat, S.A.

                -- Parque Tecnolgico de Madrid

                -- 28760, Tres Cantos (Madrid)

                -- Tlf: +34-918076565

                -- Fax: +34-918076521

                -- e-mail: id@teldat.com


                -- MIB privada de Teldat

                -- MIB de protocolo FTP


    -- Historial:
    --      07/02/14    M.A. Pastor     XH 3523. Errors with HP Openview 9.20
    -- 1.1  08/07/09    I. Mu±oz        Revisin de todas las MIB para evitar
    --                  M.A. Pastor     warnings y errores de compilacin
    -- 1.0  01/07/04    J. Molina       Fichero procedente de FtpMIB.mib

    -- Historial de FtpMIB.mib:
        -- 16-10-01  J. Roman           Se obsoleta variable de autenticacion
        -- ??-??-01  A. Guerrero        Implementacin inicial
    --------------------------------------------------------------------------

TELDAT-CFG-PROTOCOL-FTP-MIB DEFINITIONS ::= BEGIN

-- Tipos importados

    IMPORTS
            OBJECT-TYPE
        FROM RFC-1212
            telProdNpConfProtocol
        FROM TELDAT-SW-STRUCTURE-MIB;


-- telProdNpConfProtFtp group

    telProdNpConfProtFtp    OBJECT IDENTIFIER ::= { telProdNpConfProtocol 12}


    telProdNpConProtFtpOs       OBJECT-TYPE
        SYNTAX  INTEGER{
                msdos(0),
                unix(1)
            }
        ACCESS  read-write
        STATUS  mandatory
        DESCRIPTION
            "Identifies the operating system used by the FTP server."
        ::={ telProdNpConfProtFtp 1 }

    telProdNpConfProtFtpSyst    OBJECT-TYPE
        SYNTAX  INTEGER{
                nul(0),
                tst(1),
                mem(2),
                dsk(3),
                fco(4),
                fda(5),
                bio(6)
            }
        ACCESS  read-write
        STATUS  mandatory
        DESCRIPTION
            "File system used by the FTP server."
        ::={ telProdNpConfProtFtp 2 }

    telProdNpConfProtFtpCPort   OBJECT-TYPE
        SYNTAX  INTEGER(0..65535)
        ACCESS  read-write
        STATUS  mandatory
        DESCRIPTION
            "FTP protocol Control Port."
        ::={ telProdNpConfProtFtp 3 }

    telProdNpConfProtFtpDPort   OBJECT-TYPE
        SYNTAX  INTEGER(0..65535)
        ACCESS  read-write
        STATUS  mandatory
        DESCRIPTION
            "FTP protocol Data Port."
        ::={ telProdNpConfProtFtp 4 }

    telProdNpConfProtFtpTimer   OBJECT-TYPE
        SYNTAX  INTEGER
        ACCESS  read-write
        STATUS  mandatory
        DESCRIPTION
            "Inactivity Timer. Determines the time after what
             the FTP session finishes. Possible values: 0 or 360-3600."
        ::={ telProdNpConfProtFtp 5 }

    telProdNpConfProtFtpClients OBJECT-TYPE
        SYNTAX  INTEGER
        ACCESS  read-write
        STATUS  mandatory
        DESCRIPTION
            "Maximum number of clients simultaneously connected.
             Possible values: 0-10 or 50-100"
        ::={ telProdNpConfProtFtp 6 }

    telProdNpConfProtFtpPri     OBJECT-TYPE
        SYNTAX  INTEGER(0..255)
        ACCESS  read-write
        STATUS  mandatory
        DESCRIPTION
            "FTP protocol tasks priority"
        ::={ telProdNpConfProtFtp 7 }

    telProdNpConfProtFtpMss     OBJECT-TYPE
        SYNTAX  INTEGER(512..4096)
        ACCESS  read-write
        STATUS  mandatory
        DESCRIPTION
            "Maximum TCP segment size."
        ::={ telProdNpConfProtFtp 8 }

    telProdNpConfProtFtpRxBuff  OBJECT-TYPE
        SYNTAX  INTEGER(2048..16384)
        ACCESS  read-write
        STATUS  mandatory
        DESCRIPTION
            "Maximum Reception buffer size."
        ::={ telProdNpConfProtFtp 9 }

    telProdNpConfProtFtpTxBuff  OBJECT-TYPE
        SYNTAX  INTEGER(2048..16384)
        ACCESS  read-write
        STATUS  mandatory
        DESCRIPTION
        "Maximum Transmission buffer size."
        ::={ telProdNpConfProtFtp 10 }

    telProdNpConfProtFtpTmpBuff OBJECT-TYPE
        SYNTAX  INTEGER
        ACCESS  read-write
        STATUS  mandatory
        DESCRIPTION
        "Temporal buffer size. Must be a positive integer."
        ::={ telProdNpConfProtFtp 11 }

    telProdNpConfProtFtpReply   OBJECT-TYPE
        SYNTAX  INTEGER{
                disabled(0),
                enabled(1)
            }
        ACCESS  read-write
        STATUS  mandatory
        DESCRIPTION
            "Enables reply sending when a request takes long time to execute."
        ::={ telProdNpConfProtFtp 12 }

    telProdNpConfProtFtpKeepAl  OBJECT-TYPE
        SYNTAX  INTEGER{
                disabled(0),
                enabled(1)
            }
        ACCESS  read-write
        STATUS  mandatory
        DESCRIPTION
            "Enables data-link keepalive."
        ::={ telProdNpConfProtFtp 13 }

    telProdNpConfProtFtpImm OBJECT-TYPE
        SYNTAX  INTEGER{
                disabled(0),
                enabled(1)
            }
        ACCESS  read-write
        STATUS  mandatory
        DESCRIPTION
            "Enables TCP data reception by means of immediate indication."
        ::={ telProdNpConfProtFtp 14 }

    telProdNpConfProtFtpComp    OBJECT-TYPE
        SYNTAX  INTEGER{
                disabled(0),
                enabled(1)
            }
        ACCESS  read-write
        STATUS  mandatory
        DESCRIPTION
            "Enables compatibility with previous versions."
        ::={ telProdNpConfProtFtp 15 }

    telProdNpConfProtFtpDirect  OBJECT-TYPE
        SYNTAX  INTEGER{
                disabled(0),
                enabled(1)
            }
        ACCESS  read-write
        STATUS  mandatory
        DESCRIPTION
            "Enables saving the file received directly in
             the file system active for that session."
        ::={ telProdNpConfProtFtp 16 }

--  !!! Obsoleted !!!

--  telProdNpConfProtFtpAuth    OBJECT-TYPE
--      SYNTAX  INTEGER{
--              disabled(0),
--              enabled(1)
--          }
--      ACCESS  read-write
--      STATUS  mandatory
--      DESCRIPTION
--          "Enables user authentication through RADIUS server"
--      ::={ telProdNpConfProtFtp 17 }
--

END
