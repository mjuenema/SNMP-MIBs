-- Teldat, S.A.

        -- Parque Tecnolgico de Madrid

        -- 28760, Tres Cantos (Madrid)

        -- Tlf: +34-918076565

        -- Fax: +34-918076521

        -- e-mail: id@teldat.com


    -- MIB privada de Teldat

    -- Monitorizacin de la facilidad BRS (Band Reservation System)


    -- Historial:
    --      07/02/14    M.A. Pastor     XH 3523. Errors with HP Openview 9.20
    -- 1.7  11-01-13    E. Amorena      XH 2610. MIBs compilation.
    -- 1.6  08/07/09    I. Mu±oz        Revisin de todas las MIB para evitar
    --                  M.A. Pastor     warnings y errores de compilacin
    -- 1.5   19-06-09   I. Mu±oz        PMP 890. Implementacion del comando "traffic-shape-group"
    --                                  para las colas
    -- 1.4   02-03-09   P. Ortiz        Nuevas tablas para level-indicator
    -- 1.3   18-02-09   I. Mu±oz        WRED
    -- 1.2   01-09-04   M.A. Pastor     Nuevos estad�sticos
    -- 1.1   25/06/04   M.A. Pastor     Actualizacin de la MIB para que se
    --                                  corresponda con la informacin de
    --                                  monitorizacin disponible
    -- 1.0   01/07/04   J. Molina       Archivo procedente de BRS.mib


    -- Historial de BRS.mib:

    -- 02/10/01     N.Villase±or    Traduccin a ingl‰s
    -- 01/12/00     M.A. Pastor     Modificaciones para que pueda ser compilada
    --                              utilizando compiladores distintos del de Teldat
    -- 7/11/00      J. Alvarez      Implementacion inicial
--------------------------------------------------------------------------------

TELDAT-MON-FEATURES-BRS-MIB DEFINITIONS ::= BEGIN

    IMPORTS
        Counter, Gauge
            FROM RFC1155-SMI
        OBJECT-TYPE
            FROM RFC-1212
        DisplayString
            FROM RFC1213-MIB
        telProdNpMonFeatures
            FROM TELDAT-SW-STRUCTURE-MIB;


-- Facilidad de Reserva de Ancho de Banda (BRS)
telProdNpMonFeatBrs     OBJECT IDENTIFIER ::= { telProdNpMonFeatures 1 }


-- Tabla que recoge los estad�sticos que describen el trßfico de Reserva de
-- Ancho de Banda para el interfaz seleccionado.

telProdNpMonFeatBrsDevCountTable OBJECT-TYPE
    SYNTAX SEQUENCE OF TelProdNpMonFeatBrsDevCountEntry
    ACCESS not-accessible
    STATUS mandatory
    DESCRIPTION
    "Displays the last statistics describing bandwidth reservation traffic
    for the selected interface. For the Frame Relay interface displays the last
    statistics describing bandwidth reservation traffic for all circuit classes
    of the interface."
    ::= { telProdNpMonFeatBrs 1 }

telProdNpMonFeatBrsDevCountEntry OBJECT-TYPE
    SYNTAX TelProdNpMonFeatBrsDevCountEntry
    ACCESS not-accessible
    STATUS mandatory
    DESCRIPTION
    "The table index are: the interface number and the order of the selected
    class within the interface."
    INDEX { telProdNpMonFeatBrsDevCountIfc, telProdNpMonFeatBrsDevCountIndex }
    ::= { telProdNpMonFeatBrsDevCountTable 1 }

TelProdNpMonFeatBrsDevCountEntry ::=
    SEQUENCE{
        telProdNpMonFeatBrsDevCountIfc
            INTEGER,
        telProdNpMonFeatBrsDevCountIndex
            INTEGER,
        telProdNpMonFeatBrsDevCountClear
            INTEGER,
        telProdNpMonFeatBrsDevCountClass
            DisplayString,
        telProdNpMonFeatBrsDevCountTxPkt
            Counter,
        telProdNpMonFeatBrsDevCountTxByt
            Counter,
        telProdNpMonFeatBrsDevCountDiscByt
            Counter,
        telProdNpMonFeatBrsDevCountDiscPkt
            Counter,
        telProdNpMonFeatBrsDevCountInPkt
            Counter,
        telProdNpMonFeatBrsDevCountInByt
            Counter,
        telProdNpMonFeatBrsDevCountDiscRLPkt
            Counter,
        telProdNpMonFeatBrsDevCountDiscRLByt
            Counter,
        telProdNpMonFeatBrsDevCountRemarkPkt
            Counter,
        telProdNpMonFeatBrsDevCountRemarkByt
            Counter,
        telProdNpMonFeatBrsDevCountReassPkt
            Counter,
        telProdNpMonFeatBrsDevCountReassByt
            Counter,
        telProdNpMonFeatBrsDevCountLoopPkt
            Counter,
        telProdNpMonFeatBrsDevCountLoopByt
            Counter,
        telProdNpMonFeatBrsDevCountQueueOvflPkt
            Counter,
        telProdNpMonFeatBrsDevCountQueueOvflByt
            Counter,
    telProdNpMonFeatBrsDevCountWredPkt
        Counter,
    telProdNpMonFeatBrsDevCountWredByt
        Counter
        }

telProdNpMonFeatBrsDevCountIfc OBJECT-TYPE
    SYNTAX INTEGER
    ACCESS read-only
    STATUS mandatory
    DESCRIPTION
    "First index: interface number."
    ::= { telProdNpMonFeatBrsDevCountEntry 1 }

telProdNpMonFeatBrsDevCountIndex OBJECT-TYPE
    SYNTAX INTEGER
    ACCESS read-only
    STATUS mandatory
    DESCRIPTION
    "Second index: class order within the interface."
    ::= { telProdNpMonFeatBrsDevCountEntry 2 }

telProdNpMonFeatBrsDevCountClear OBJECT-TYPE
    SYNTAX INTEGER{
        delete(1),
        ok(2),
        error(3),
        undefined(4)
        }
    ACCESS read-write
    STATUS mandatory
    DESCRIPTION
    "Clear command to delete statistics. Enter 1 (delete) to clear
    the counters. In case the counters were correctly deleted, it will
    appear 2 (ok); otherwise it will appear 3 (error). Finally, if the
    counter has been never cleared it will appear 4 (undefined)."
    ::= { telProdNpMonFeatBrsDevCountEntry 3 }

telProdNpMonFeatBrsDevCountClass OBJECT-TYPE
    SYNTAX DisplayString(SIZE(0..9))
    ACCESS read-only
    STATUS mandatory
    DESCRIPTION
    "Class name."
    ::= { telProdNpMonFeatBrsDevCountEntry 4 }

telProdNpMonFeatBrsDevCountTxPkt OBJECT-TYPE
    SYNTAX Counter
    ACCESS read-only
    STATUS mandatory
    DESCRIPTION
    "Number of packets transmitted."
    ::= { telProdNpMonFeatBrsDevCountEntry 5 }

telProdNpMonFeatBrsDevCountTxByt OBJECT-TYPE
    SYNTAX Counter
    ACCESS read-only
    STATUS mandatory
    DESCRIPTION
    "Number of bytes transmitted."
    ::= { telProdNpMonFeatBrsDevCountEntry 6 }

telProdNpMonFeatBrsDevCountDiscByt OBJECT-TYPE
    SYNTAX Counter
    ACCESS read-only
    STATUS mandatory
    DESCRIPTION
    "Number of bytes lost due to overflow."
    ::= { telProdNpMonFeatBrsDevCountEntry 7 }

telProdNpMonFeatBrsDevCountDiscPkt OBJECT-TYPE
    SYNTAX Counter
    ACCESS read-only
    STATUS mandatory
    DESCRIPTION
    "Number of discarded packets."
    ::= { telProdNpMonFeatBrsDevCountEntry 8 }

telProdNpMonFeatBrsDevCountInPkt OBJECT-TYPE
    SYNTAX Counter
    ACCESS read-only
    STATUS mandatory
    DESCRIPTION
    "Number of input packets: packets offered to a class before the application
    of any QoS action."
    ::= { telProdNpMonFeatBrsDevCountEntry 9 }

telProdNpMonFeatBrsDevCountInByt OBJECT-TYPE
    SYNTAX Counter
    ACCESS read-only
    STATUS mandatory
    DESCRIPTION
    "Number of input bytes: bytes offered to a class before the application
    of any QoS action."
    ::= { telProdNpMonFeatBrsDevCountEntry 10 }

telProdNpMonFeatBrsDevCountDiscRLPkt OBJECT-TYPE
    SYNTAX Counter
    ACCESS read-only
    STATUS mandatory
    DESCRIPTION
    "Number of discarded packets due to rate-limit."
    ::= { telProdNpMonFeatBrsDevCountEntry 11 }

telProdNpMonFeatBrsDevCountDiscRLByt OBJECT-TYPE
    SYNTAX Counter
    ACCESS read-only
    STATUS mandatory
    DESCRIPTION
    "Number of discarded bytes due to rate-limit."
    ::= { telProdNpMonFeatBrsDevCountEntry 12 }

telProdNpMonFeatBrsDevCountRemarkPkt OBJECT-TYPE
    SYNTAX Counter
    ACCESS read-only
    STATUS mandatory
    DESCRIPTION
    "Number of exceeded packets which are dscp-marked."
    ::= { telProdNpMonFeatBrsDevCountEntry 13 }

telProdNpMonFeatBrsDevCountRemarkByt OBJECT-TYPE
    SYNTAX Counter
    ACCESS read-only
    STATUS mandatory
    DESCRIPTION
    "Number of exceeded bytes which are dscp-marked."
    ::= { telProdNpMonFeatBrsDevCountEntry 14 }

telProdNpMonFeatBrsDevCountReassPkt OBJECT-TYPE
    SYNTAX Counter
    ACCESS read-only
    STATUS mandatory
    DESCRIPTION
    "Number of exceeded packets which are re-classified (reassigned to another
    BRS class)."
    ::= { telProdNpMonFeatBrsDevCountEntry 15 }

telProdNpMonFeatBrsDevCountReassByt OBJECT-TYPE
    SYNTAX Counter
    ACCESS read-only
    STATUS mandatory
    DESCRIPTION
    "Number of exceeded bytes which are re-classified (reassigned to another
    BRS class)."
    ::= { telProdNpMonFeatBrsDevCountEntry 16 }

telProdNpMonFeatBrsDevCountLoopPkt OBJECT-TYPE
    SYNTAX Counter
    ACCESS read-only
    STATUS mandatory
    DESCRIPTION
    "Number of discarded packets because they were re-classified and reassigned
    to a class to which they were previously assigned."
    ::= { telProdNpMonFeatBrsDevCountEntry 17 }

telProdNpMonFeatBrsDevCountLoopByt OBJECT-TYPE
    SYNTAX Counter
    ACCESS read-only
    STATUS mandatory
    DESCRIPTION
    "Number of discarded bytes because they were re-classified and reassigned
    to a class to which they were previously assigned."
    ::= { telProdNpMonFeatBrsDevCountEntry 18 }

telProdNpMonFeatBrsDevCountQueueOvflPkt OBJECT-TYPE
    SYNTAX Counter
    ACCESS read-only
    STATUS mandatory
    DESCRIPTION
    "Number of discarded packets due to queue overflow."
    ::= { telProdNpMonFeatBrsDevCountEntry 19 }

telProdNpMonFeatBrsDevCountQueueOvflByt OBJECT-TYPE
    SYNTAX Counter
    ACCESS read-only
    STATUS mandatory
    DESCRIPTION
    "Number of discarded bytes due to queue overflow."
    ::= { telProdNpMonFeatBrsDevCountEntry 20 }

telProdNpMonFeatBrsDevCountWredPkt OBJECT-TYPE
    SYNTAX Counter
    ACCESS read-only
    STATUS mandatory
    DESCRIPTION
    "Number of discarded packets due to WRED."
    ::= { telProdNpMonFeatBrsDevCountEntry 21 }

telProdNpMonFeatBrsDevCountWredByt OBJECT-TYPE
    SYNTAX Counter
    ACCESS read-only
    STATUS mandatory
    DESCRIPTION
    "Number of discarded bytes due to WRED."
    ::= { telProdNpMonFeatBrsDevCountEntry 22 }

-- Tabla que muestra las ”ltimas estad�sticas de Reserva de Ancho de Banda
-- salvadas de los interfaces.

telProdNpMonFeatBrsDevLastTable OBJECT-TYPE
    SYNTAX SEQUENCE OF TelProdNpMonFeatBrsDevLastEntry
    ACCESS not-accessible
    STATUS mandatory
    DESCRIPTION
    "Displays the last statistics of bandwidth reservation saved for
    the interfaces."
    ::= { telProdNpMonFeatBrs 2 }

telProdNpMonFeatBrsDevLastEntry OBJECT-TYPE
    SYNTAX TelProdNpMonFeatBrsDevLastEntry
    ACCESS not-accessible
    STATUS mandatory
    DESCRIPTION
    "The table index are: the interface number and the order of the selected
    class within the interface."
    INDEX { telProdNpMonFeatBrsDevLastIfc, telProdNpMonFeatBrsDevLastIndex }
    ::= { telProdNpMonFeatBrsDevLastTable 1 }

TelProdNpMonFeatBrsDevLastEntry ::=
    SEQUENCE{
        telProdNpMonFeatBrsDevLastIfc
            INTEGER,
        telProdNpMonFeatBrsDevLastIndex
            INTEGER,
        telProdNpMonFeatBrsDevLastClass
            DisplayString,
        telProdNpMonFeatBrsDevLastTxPkt
            Counter,
        telProdNpMonFeatBrsDevLastTxByt
            Counter,
        telProdNpMonFeatBrsDevLastDiscByt
            Counter,
        telProdNpMonFeatBrsDevLastDiscPkt
            Counter,
        telProdNpMonFeatBrsDevLastInPkt
            Counter,
        telProdNpMonFeatBrsDevLastInByt
            Counter,
        telProdNpMonFeatBrsDevLastDiscRLPkt
            Counter,
        telProdNpMonFeatBrsDevLastDiscRLByt
            Counter,
        telProdNpMonFeatBrsDevLastRemarkPkt
            Counter,
        telProdNpMonFeatBrsDevLastRemarkByt
            Counter,
        telProdNpMonFeatBrsDevLastReassPkt
            Counter,
        telProdNpMonFeatBrsDevLastReassByt
            Counter,
        telProdNpMonFeatBrsDevLastLoopPkt
            Counter,
        telProdNpMonFeatBrsDevLastLoopByt
            Counter,
        telProdNpMonFeatBrsDevLastQueueOvflPkt
            Counter,
        telProdNpMonFeatBrsDevLastQueueOvflByt
            Counter,
        telProdNpMonFeatBrsDevLastWredPkt
            Counter,
        telProdNpMonFeatBrsDevLastWredByt
            Counter
        }

telProdNpMonFeatBrsDevLastIfc OBJECT-TYPE
    SYNTAX INTEGER
    ACCESS read-only
    STATUS mandatory
    DESCRIPTION
    "First index: interface number."
    ::= { telProdNpMonFeatBrsDevLastEntry 1 }

telProdNpMonFeatBrsDevLastIndex OBJECT-TYPE
    SYNTAX INTEGER
    ACCESS read-only
    STATUS mandatory
    DESCRIPTION
    "Second index: class order within the interface."
    ::= { telProdNpMonFeatBrsDevLastEntry 2 }

telProdNpMonFeatBrsDevLastClass OBJECT-TYPE
    SYNTAX DisplayString(SIZE(0..9))
    ACCESS read-only
    STATUS mandatory
    DESCRIPTION
    "Class name."
    ::= { telProdNpMonFeatBrsDevLastEntry 3 }

telProdNpMonFeatBrsDevLastTxPkt OBJECT-TYPE
    SYNTAX Counter
    ACCESS read-only
    STATUS mandatory
    DESCRIPTION
    "Number of packets transmitted."
    ::= { telProdNpMonFeatBrsDevLastEntry 4 }

telProdNpMonFeatBrsDevLastTxByt OBJECT-TYPE
    SYNTAX Counter
    ACCESS read-only
    STATUS mandatory
    DESCRIPTION
    "Number of bytes transmitted."
    ::= { telProdNpMonFeatBrsDevLastEntry 5 }

telProdNpMonFeatBrsDevLastDiscByt OBJECT-TYPE
    SYNTAX Counter
    ACCESS read-only
    STATUS mandatory
    DESCRIPTION
    "Number of bytes lost due to overflow."
    ::= { telProdNpMonFeatBrsDevLastEntry 6 }

telProdNpMonFeatBrsDevLastDiscPkt OBJECT-TYPE
    SYNTAX Counter
    ACCESS read-only
    STATUS mandatory
    DESCRIPTION
    "Number of discarded packets."
    ::= { telProdNpMonFeatBrsDevLastEntry 7 }

telProdNpMonFeatBrsDevLastInPkt OBJECT-TYPE
    SYNTAX Counter
    ACCESS read-only
    STATUS mandatory
    DESCRIPTION
    "Number of input packets: packets offered to a class before the application
    of any QoS action."
    ::= { telProdNpMonFeatBrsDevLastEntry 8 }

telProdNpMonFeatBrsDevLastInByt OBJECT-TYPE
    SYNTAX Counter
    ACCESS read-only
    STATUS mandatory
    DESCRIPTION
    "Number of input bytes: bytes offered to a class before the application
    of any QoS action."
    ::= { telProdNpMonFeatBrsDevLastEntry 9 }

telProdNpMonFeatBrsDevLastDiscRLPkt OBJECT-TYPE
    SYNTAX Counter
    ACCESS read-only
    STATUS mandatory
    DESCRIPTION
    "Number of discarded packets due to rate-limit."
    ::= { telProdNpMonFeatBrsDevLastEntry 10 }

telProdNpMonFeatBrsDevLastDiscRLByt OBJECT-TYPE
    SYNTAX Counter
    ACCESS read-only
    STATUS mandatory
    DESCRIPTION
    "Number of discarded bytes due to rate-limit."
    ::= { telProdNpMonFeatBrsDevLastEntry 11 }

telProdNpMonFeatBrsDevLastRemarkPkt OBJECT-TYPE
    SYNTAX Counter
    ACCESS read-only
    STATUS mandatory
    DESCRIPTION
    "Number of exceeded packets which are dscp-marked."
    ::= { telProdNpMonFeatBrsDevLastEntry 12 }

telProdNpMonFeatBrsDevLastRemarkByt OBJECT-TYPE
    SYNTAX Counter
    ACCESS read-only
    STATUS mandatory
    DESCRIPTION
    "Number of exceeded bytes which are dscp-marked."
    ::= { telProdNpMonFeatBrsDevLastEntry 13 }

telProdNpMonFeatBrsDevLastReassPkt OBJECT-TYPE
    SYNTAX Counter
    ACCESS read-only
    STATUS mandatory
    DESCRIPTION
    "Number of exceeded packets which are re-classified (reassigned to another
    BRS class)."
    ::= { telProdNpMonFeatBrsDevLastEntry 14 }

telProdNpMonFeatBrsDevLastReassByt OBJECT-TYPE
    SYNTAX Counter
    ACCESS read-only
    STATUS mandatory
    DESCRIPTION
    "Number of exceeded bytes which are re-classified (reassigned to another
    BRS class)."
    ::= { telProdNpMonFeatBrsDevLastEntry 15 }

telProdNpMonFeatBrsDevLastLoopPkt OBJECT-TYPE
    SYNTAX Counter
    ACCESS read-only
    STATUS mandatory
    DESCRIPTION
    "Number of discarded packets because they were re-classified and reassigned
    to a class to which they were previously assigned."
    ::= { telProdNpMonFeatBrsDevLastEntry 16 }

telProdNpMonFeatBrsDevLastLoopByt OBJECT-TYPE
    SYNTAX Counter
    ACCESS read-only
    STATUS mandatory
    DESCRIPTION
    "Number of discarded bytes because they were re-classified and reassigned
    to a class to which they were previously assigned."
    ::= { telProdNpMonFeatBrsDevLastEntry 17 }

telProdNpMonFeatBrsDevLastQueueOvflPkt OBJECT-TYPE
    SYNTAX Counter
    ACCESS read-only
    STATUS mandatory
    DESCRIPTION
    "Number of discarded packets due to queue overflow."
    ::= { telProdNpMonFeatBrsDevLastEntry 18 }

telProdNpMonFeatBrsDevLastQueueOvflByt OBJECT-TYPE
    SYNTAX Counter
    ACCESS read-only
    STATUS mandatory
    DESCRIPTION
    "Number of discarded bytes due to queue overflow."
    ::= { telProdNpMonFeatBrsDevLastEntry 19 }

telProdNpMonFeatBrsDevLastWredPkt OBJECT-TYPE
    SYNTAX Counter
    ACCESS read-only
    STATUS mandatory
    DESCRIPTION
    "Number of discarded packets due to WRED."
    ::= { telProdNpMonFeatBrsDevLastEntry 20 }

telProdNpMonFeatBrsDevLastWredByt OBJECT-TYPE
    SYNTAX Counter
    ACCESS read-only
    STATUS mandatory
    DESCRIPTION
    "Number of discarded bytes due to WRED."
    ::= { telProdNpMonFeatBrsDevLastEntry 21 }

-- Tabla que muestra los estad�sticos que describen el trßfico de Reserva de
-- Ancho de Banda para el interfaz FR y circuito.

telProdNpMonFeatBrsFrCirCountTable OBJECT-TYPE
    SYNTAX SEQUENCE OF TelProdNpMonFeatBrsFrCirCountEntry
    ACCESS not-accessible
    STATUS mandatory
    DESCRIPTION
    "Displays statistics describing bandwidth reservation traffic for the
    selected Frame Relay interface and circuit."
    ::= { telProdNpMonFeatBrs 3 }

telProdNpMonFeatBrsFrCirCountEntry OBJECT-TYPE
    SYNTAX TelProdNpMonFeatBrsFrCirCountEntry
    ACCESS not-accessible
    STATUS mandatory
    DESCRIPTION
    "Each entry contains statistics describing bandwidth reservation traffic for
    the selected Frame Relay interface and circuit. The table index are: the
    interface number, the Frame Relay circuit number (DLCI) and the class order
    within that circuit in this Frame Relay interface."
    INDEX { telProdNpMonFeatBrsFrCirCountIfc,
            telProdNpMonFeatBrsFrCirCountCir,
            telProdNpMonFeatBrsFrCirCountIndex }
    ::= { telProdNpMonFeatBrsFrCirCountTable 1 }

TelProdNpMonFeatBrsFrCirCountEntry ::=
    SEQUENCE{
        telProdNpMonFeatBrsFrCirCountIfc
            INTEGER,
        telProdNpMonFeatBrsFrCirCountCir
            INTEGER,
        telProdNpMonFeatBrsFrCirCountIndex
            INTEGER,
        telProdNpMonFeatBrsFrCirCountClear
            INTEGER,
        telProdNpMonFeatBrsFrCirCountClass
            DisplayString,
        telProdNpMonFeatBrsFrCirCountTxPkt
            Counter,
        telProdNpMonFeatBrsFrCirCountTxByt
            Counter,
        telProdNpMonFeatBrsFrCirCountDiscByt
            Counter,
        telProdNpMonFeatBrsFrCirCountDiscPkt
            Counter,
        telProdNpMonFeatBrsFrCirCountInPkt
            Counter,
        telProdNpMonFeatBrsFrCirCountInByt
            Counter,
        telProdNpMonFeatBrsFrCirCountDiscRLPkt
            Counter,
        telProdNpMonFeatBrsFrCirCountDiscRLByt
            Counter,
        telProdNpMonFeatBrsFrCirCountRemarkPkt
            Counter,
        telProdNpMonFeatBrsFrCirCountRemarkByt
            Counter,
        telProdNpMonFeatBrsFrCirCountReassPkt
            Counter,
        telProdNpMonFeatBrsFrCirCountReassByt
            Counter,
        telProdNpMonFeatBrsFrCirCountLoopPkt
            Counter,
        telProdNpMonFeatBrsFrCirCountLoopByt
            Counter,
        telProdNpMonFeatBrsFrCirCountQueueOvflPkt
            Counter,
        telProdNpMonFeatBrsFrCirCountQueueOvflByt
            Counter,
        telProdNpMonFeatBrsFrCirCountWredPkt
            Counter,
        telProdNpMonFeatBrsFrCirCountWredByt
            Counter
        }

telProdNpMonFeatBrsFrCirCountIfc OBJECT-TYPE
    SYNTAX INTEGER
    ACCESS read-only
    STATUS mandatory
    DESCRIPTION
    "First index: interface number."
    ::= { telProdNpMonFeatBrsFrCirCountEntry 1 }

telProdNpMonFeatBrsFrCirCountCir OBJECT-TYPE
    SYNTAX INTEGER(16..1007)
    ACCESS read-only
    STATUS mandatory
    DESCRIPTION
    "Second index: Frame Relay circuit number (DLCI)."
    ::= { telProdNpMonFeatBrsFrCirCountEntry 2 }

telProdNpMonFeatBrsFrCirCountIndex OBJECT-TYPE
    SYNTAX INTEGER
    ACCESS read-only
    STATUS mandatory
    DESCRIPTION
    "Third index: class order within that circuit in this Frame Relay
    interface."
    ::= { telProdNpMonFeatBrsFrCirCountEntry 3 }

telProdNpMonFeatBrsFrCirCountClear OBJECT-TYPE
    SYNTAX INTEGER{
        delete(1),
        ok(2),
        error(3),
        undefined(4)
        }
    ACCESS read-write
    STATUS mandatory
    DESCRIPTION
    "Clear command to delete statistics. Enter 1 (delete) to clear
    the counters. In case the counters were correctly deleted, it will
    appear 2 (ok); otherwise it will appear 3 (error). Finally, if the
    counter has been never cleared it will appear 4 (undefined)."
    ::= { telProdNpMonFeatBrsFrCirCountEntry 4 }

telProdNpMonFeatBrsFrCirCountClass OBJECT-TYPE
    SYNTAX DisplayString(SIZE(0..9))
    ACCESS read-only
    STATUS mandatory
    DESCRIPTION
    "Class name."
    ::= { telProdNpMonFeatBrsFrCirCountEntry 5 }

telProdNpMonFeatBrsFrCirCountTxPkt OBJECT-TYPE
    SYNTAX Counter
    ACCESS read-only
    STATUS mandatory
    DESCRIPTION
    "Number of packets transmitted."
    ::= { telProdNpMonFeatBrsFrCirCountEntry 6 }

telProdNpMonFeatBrsFrCirCountTxByt OBJECT-TYPE
    SYNTAX Counter
    ACCESS read-only
    STATUS mandatory
    DESCRIPTION
    "Number of bytes transmitted."
    ::= { telProdNpMonFeatBrsFrCirCountEntry 7 }

telProdNpMonFeatBrsFrCirCountDiscByt OBJECT-TYPE
    SYNTAX Counter
    ACCESS read-only
    STATUS mandatory
    DESCRIPTION
    "Number of packets lost due to overflow."
    ::= { telProdNpMonFeatBrsFrCirCountEntry 8 }

telProdNpMonFeatBrsFrCirCountDiscPkt OBJECT-TYPE
    SYNTAX Counter
    ACCESS read-only
    STATUS mandatory
    DESCRIPTION
    "Number of discarded packets."
    ::= { telProdNpMonFeatBrsFrCirCountEntry 9 }

telProdNpMonFeatBrsFrCirCountInPkt OBJECT-TYPE
    SYNTAX Counter
    ACCESS read-only
    STATUS mandatory
    DESCRIPTION
    "Number of input packets: packets offered to a class before the application
    of any QoS action."
    ::= { telProdNpMonFeatBrsFrCirCountEntry 10 }

telProdNpMonFeatBrsFrCirCountInByt OBJECT-TYPE
    SYNTAX Counter
    ACCESS read-only
    STATUS mandatory
    DESCRIPTION
    "Number of input bytes: bytes offered to a class before the application
    of any QoS action."
    ::= { telProdNpMonFeatBrsFrCirCountEntry 11 }

telProdNpMonFeatBrsFrCirCountDiscRLPkt OBJECT-TYPE
    SYNTAX Counter
    ACCESS read-only
    STATUS mandatory
    DESCRIPTION
    "Number of discarded packets due to rate-limit."
    ::= { telProdNpMonFeatBrsFrCirCountEntry 12 }

telProdNpMonFeatBrsFrCirCountDiscRLByt OBJECT-TYPE
    SYNTAX Counter
    ACCESS read-only
    STATUS mandatory
    DESCRIPTION
    "Number of discarded bytes due to rate-limit."
    ::= { telProdNpMonFeatBrsFrCirCountEntry 13 }

telProdNpMonFeatBrsFrCirCountRemarkPkt OBJECT-TYPE
    SYNTAX Counter
    ACCESS read-only
    STATUS mandatory
    DESCRIPTION
    "Number of exceeded packets which are dscp-marked."
    ::= { telProdNpMonFeatBrsFrCirCountEntry 14 }

telProdNpMonFeatBrsFrCirCountRemarkByt OBJECT-TYPE
    SYNTAX Counter
    ACCESS read-only
    STATUS mandatory
    DESCRIPTION
    "Number of exceeded bytes which are dscp-marked."
    ::= { telProdNpMonFeatBrsFrCirCountEntry 15 }

telProdNpMonFeatBrsFrCirCountReassPkt OBJECT-TYPE
    SYNTAX Counter
    ACCESS read-only
    STATUS mandatory
    DESCRIPTION
    "Number of exceeded packets which are re-classified (reassigned to another
    BRS class)."
    ::= { telProdNpMonFeatBrsFrCirCountEntry 16 }

telProdNpMonFeatBrsFrCirCountReassByt OBJECT-TYPE
    SYNTAX Counter
    ACCESS read-only
    STATUS mandatory
    DESCRIPTION
    "Number of exceeded bytes which are re-classified (reassigned to another
    BRS class)."
    ::= { telProdNpMonFeatBrsFrCirCountEntry 17 }

telProdNpMonFeatBrsFrCirCountLoopPkt OBJECT-TYPE
    SYNTAX Counter
    ACCESS read-only
    STATUS mandatory
    DESCRIPTION
    "Number of discarded packets because they were re-classified and reassigned
    to a class to which they were previously assigned."
    ::= { telProdNpMonFeatBrsFrCirCountEntry 18 }

telProdNpMonFeatBrsFrCirCountLoopByt OBJECT-TYPE
    SYNTAX Counter
    ACCESS read-only
    STATUS mandatory
    DESCRIPTION
    "Number of discarded bytes because they were re-classified and reassigned
    to a class to which they were previously assigned."
    ::= { telProdNpMonFeatBrsFrCirCountEntry 19 }

telProdNpMonFeatBrsFrCirCountQueueOvflPkt OBJECT-TYPE
    SYNTAX Counter
    ACCESS read-only
    STATUS obsolete
    DESCRIPTION
    "Number of discarded packets due to queue overflow."
    ::= { telProdNpMonFeatBrsFrCirCountEntry 20 }

telProdNpMonFeatBrsFrCirCountQueueOvflByt OBJECT-TYPE
    SYNTAX Counter
    ACCESS read-only
    STATUS obsolete
    DESCRIPTION
    "Number of discarded bytes due to queue overflow."
    ::= { telProdNpMonFeatBrsFrCirCountEntry 21 }

telProdNpMonFeatBrsFrCirCountWredPkt OBJECT-TYPE
    SYNTAX Counter
    ACCESS read-only
    STATUS mandatory
    DESCRIPTION
    "Number of discarded packets due to WRED."
    ::= { telProdNpMonFeatBrsFrCirCountEntry 22 }

telProdNpMonFeatBrsFrCirCountWredByt OBJECT-TYPE
    SYNTAX Counter
    ACCESS read-only
    STATUS mandatory
    DESCRIPTION
    "Number of discarded bytes due to WRED."
    ::= { telProdNpMonFeatBrsFrCirCountEntry 23 }


-- Tabla que muestra los ”ltimos estad�sticos salvados de Reserva de Ancho de
-- Banda para el interfaz FR y circuito seleccionado.

telProdNpMonFeatBrsFrCirLastTable OBJECT-TYPE
    SYNTAX SEQUENCE OF TelProdNpMonFeatBrsFrCirLastEntry
    ACCESS not-accessible
    STATUS mandatory
    DESCRIPTION
    "Displays last statistics of bandwidth reservation saved for the
    selected Frame Relay interface and circuit."
    ::= { telProdNpMonFeatBrs 4 }

telProdNpMonFeatBrsFrCirLastEntry OBJECT-TYPE
    SYNTAX TelProdNpMonFeatBrsFrCirLastEntry
    ACCESS not-accessible
    STATUS mandatory
    DESCRIPTION
    "The table index are: the interface number, the Frame Relay circuit number
    (DLCI) and the class order within that circuit in this Frame Relay
    interface."
    INDEX { telProdNpMonFeatBrsFrCirLastIfc,
            telProdNpMonFeatBrsFrCirLastCir,
            telProdNpMonFeatBrsFrCirLastIndex }
    ::= { telProdNpMonFeatBrsFrCirLastTable 1 }

TelProdNpMonFeatBrsFrCirLastEntry ::=
    SEQUENCE{
        telProdNpMonFeatBrsFrCirLastIfc
            INTEGER,
        telProdNpMonFeatBrsFrCirLastCir
            INTEGER,
        telProdNpMonFeatBrsFrCirLastIndex
            INTEGER,
        telProdNpMonFeatBrsFrCirLastClass
            DisplayString,
        telProdNpMonFeatBrsFrCirLastTxPkt
            Counter,
        telProdNpMonFeatBrsFrCirLastTxByt
            Counter,
        telProdNpMonFeatBrsFrCirLastDiscByt
            Counter,
        telProdNpMonFeatBrsFrCirLastDiscByt
            Counter,
        telProdNpMonFeatBrsFrCirLastDiscPkt
            Counter,
        telProdNpMonFeatBrsFrCirLastInPkt
            Counter,
        telProdNpMonFeatBrsFrCirLastInByt
            Counter,
        telProdNpMonFeatBrsFrCirLastDiscRLPkt
            Counter,
        telProdNpMonFeatBrsFrCirLastDiscRLByt
            Counter,
        telProdNpMonFeatBrsFrCirLastRemarkPkt
            Counter,
        telProdNpMonFeatBrsFrCirLastRemarkByt
            Counter,
        telProdNpMonFeatBrsFrCirLastReassPkt
            Counter,
        telProdNpMonFeatBrsFrCirLastReassByt
            Counter,
        telProdNpMonFeatBrsFrCirLastLoopPkt
            Counter,
        telProdNpMonFeatBrsFrCirLastLoopByt
            Counter,
        telProdNpMonFeatBrsFrCirLastQueueOvflPkt
            Counter,
        telProdNpMonFeatBrsFrCirLastQueueOvflByt
            Counter,
        telProdNpMonFeatBrsFrCirLastWredPkt
            Counter,
        telProdNpMonFeatBrsFrCirLastWredByt
            Counter
        }

telProdNpMonFeatBrsFrCirLastIfc OBJECT-TYPE
    SYNTAX INTEGER
    ACCESS read-only
    STATUS mandatory
    DESCRIPTION
    "First index: interface number."
    ::= { telProdNpMonFeatBrsFrCirLastEntry 1 }

telProdNpMonFeatBrsFrCirLastCir OBJECT-TYPE
    SYNTAX INTEGER(16..1007)
    ACCESS read-only
    STATUS mandatory
    DESCRIPTION
    "Second index: Frame Relay circuit number (DLCI)."
    ::= { telProdNpMonFeatBrsFrCirLastEntry 2 }

telProdNpMonFeatBrsFrCirLastIndex OBJECT-TYPE
    SYNTAX INTEGER
    ACCESS read-only
    STATUS mandatory
    DESCRIPTION
    "Third index: class order within that circuit in this Frame Relay
    interface."
    ::= { telProdNpMonFeatBrsFrCirLastEntry 3 }

telProdNpMonFeatBrsFrCirLastClass OBJECT-TYPE
    SYNTAX DisplayString(SIZE(0..9))
    ACCESS read-only
    STATUS mandatory
    DESCRIPTION
    "Class name."
    ::= { telProdNpMonFeatBrsFrCirLastEntry 4 }

telProdNpMonFeatBrsFrCirLastTxPkt OBJECT-TYPE
    SYNTAX Counter
    ACCESS read-only
    STATUS mandatory
    DESCRIPTION
    "Number of packets transmitted."
    ::= { telProdNpMonFeatBrsFrCirLastEntry 5 }

telProdNpMonFeatBrsFrCirLastTxByt OBJECT-TYPE
    SYNTAX Counter
    ACCESS read-only
    STATUS mandatory
    DESCRIPTION
    "Number of bytes transmitted."
    ::= { telProdNpMonFeatBrsFrCirLastEntry 6 }

telProdNpMonFeatBrsFrCirLastDiscByt OBJECT-TYPE
    SYNTAX Counter
    ACCESS read-only
    STATUS mandatory
    DESCRIPTION
    "Number of bytes lost due to overflow."
    ::= { telProdNpMonFeatBrsFrCirLastEntry 7 }

telProdNpMonFeatBrsFrCirLastDiscPkt OBJECT-TYPE
    SYNTAX Counter
    ACCESS read-only
    STATUS mandatory
    DESCRIPTION
    "Number of discarded packets."
    ::= { telProdNpMonFeatBrsFrCirLastEntry 8 }

telProdNpMonFeatBrsFrCirLastInPkt OBJECT-TYPE
    SYNTAX Counter
    ACCESS read-only
    STATUS mandatory
    DESCRIPTION
    "Number of input packets: packets offered to a class before the application
    of any QoS action."
    ::= { telProdNpMonFeatBrsFrCirLastEntry 9 }

telProdNpMonFeatBrsFrCirLastInByt OBJECT-TYPE
    SYNTAX Counter
    ACCESS read-only
    STATUS mandatory
    DESCRIPTION
    "Number of input bytes: bytes offered to a class before the application
    of any QoS action."
    ::= { telProdNpMonFeatBrsFrCirLastEntry 10 }

telProdNpMonFeatBrsFrCirLastDiscRLPkt OBJECT-TYPE
    SYNTAX Counter
    ACCESS read-only
    STATUS mandatory
    DESCRIPTION
    "Number of discarded packets due to rate-limit."
    ::= { telProdNpMonFeatBrsFrCirLastEntry 11 }

telProdNpMonFeatBrsFrCirLastDiscRLByt OBJECT-TYPE
    SYNTAX Counter
    ACCESS read-only
    STATUS mandatory
    DESCRIPTION
    "Number of discarded bytes due to rate-limit."
    ::= { telProdNpMonFeatBrsFrCirLastEntry 12 }

telProdNpMonFeatBrsFrCirLastRemarkPkt OBJECT-TYPE
    SYNTAX Counter
    ACCESS read-only
    STATUS mandatory
    DESCRIPTION
    "Number of exceeded packets which are dscp-marked."
    ::= { telProdNpMonFeatBrsFrCirLastEntry 13 }

telProdNpMonFeatBrsFrCirLastRemarkByt OBJECT-TYPE
    SYNTAX Counter
    ACCESS read-only
    STATUS mandatory
    DESCRIPTION
    "Number of exceeded bytes which are dscp-marked."
    ::= { telProdNpMonFeatBrsFrCirLastEntry 14 }

telProdNpMonFeatBrsFrCirLastReassPkt OBJECT-TYPE
    SYNTAX Counter
    ACCESS read-only
    STATUS mandatory
    DESCRIPTION
    "Number of exceeded packets which are re-classified (reassigned to another
    BRS class)."
    ::= { telProdNpMonFeatBrsFrCirLastEntry 15 }

telProdNpMonFeatBrsFrCirLastReassByt OBJECT-TYPE
    SYNTAX Counter
    ACCESS read-only
    STATUS mandatory
    DESCRIPTION
    "Number of exceeded bytes which are re-classified (reassigned to another
    BRS class)."
    ::= { telProdNpMonFeatBrsFrCirLastEntry 16 }

telProdNpMonFeatBrsFrCirLastLoopPkt OBJECT-TYPE
    SYNTAX Counter
    ACCESS read-only
    STATUS mandatory
    DESCRIPTION
    "Number of discarded packets because they were re-classified and reassigned
    to a class to which they were previously assigned."
    ::= { telProdNpMonFeatBrsFrCirLastEntry 17 }

telProdNpMonFeatBrsFrCirLastLoopByt OBJECT-TYPE
    SYNTAX Counter
    ACCESS read-only
    STATUS mandatory
    DESCRIPTION
    "Number of discarded bytes because they were re-classified and reassigned
    to a class to which they were previously assigned."
    ::= { telProdNpMonFeatBrsFrCirLastEntry 18 }

telProdNpMonFeatBrsFrCirLastQueueOvflPkt OBJECT-TYPE
    SYNTAX Counter
    ACCESS read-only
    STATUS obsolete
    DESCRIPTION
    "Number of discarded packets due to queue overflow."
    ::= { telProdNpMonFeatBrsFrCirLastEntry 19 }

telProdNpMonFeatBrsFrCirLastQueueOvflByt OBJECT-TYPE
    SYNTAX Counter
    ACCESS read-only
    STATUS obsolete
    DESCRIPTION
    "Number of discarded bytes due to queue overflow."
    ::= { telProdNpMonFeatBrsFrCirLastEntry 20 }

telProdNpMonFeatBrsFrCirLastWredPkt OBJECT-TYPE
    SYNTAX Counter
    ACCESS read-only
    STATUS mandatory
    DESCRIPTION
    "Number of discarded packets due to WRED."
    ::= { telProdNpMonFeatBrsFrCirLastEntry 21 }

telProdNpMonFeatBrsFrCirLastWredByt OBJECT-TYPE
    SYNTAX Counter
    ACCESS read-only
    STATUS mandatory
    DESCRIPTION
    "Number of discarded bytes due to WRED."
    ::= { telProdNpMonFeatBrsFrCirLastEntry 22 }

-- Tabla que contiene los datos de las longitudes de las colas asociadas a cada
-- clase y prioridad, as� como su ocupacin, y esto para cada interfaz
-- configurado en el equipo con Reserva de Ancho de Banda.

telProdNpMonFeatBrsDevQueueTable OBJECT-TYPE
    SYNTAX SEQUENCE OF TelProdNpMonFeatBrsDevQueueEntry
    ACCESS not-accessible
    STATUS mandatory
    DESCRIPTION
    "This table contains information about the length and occupation of the BRS
    queues for each class and each priority in all interfaces with this
    facility enabled."
    ::= { telProdNpMonFeatBrs 5 }

telProdNpMonFeatBrsDevQueueEntry OBJECT-TYPE
    SYNTAX TelProdNpMonFeatBrsDevQueueEntry
    ACCESS not-accessible
    STATUS mandatory
    DESCRIPTION
    "Each entry in the table contains data about the length and occupation of
    the BRS queues for a class within an interface. The entry is comprised of
    several variables to store the current value and the maximum permitted
    value of the queues for each priority within a configured class in an
    interface. In cases of PPP interfaces with real-time traffic, the
    occupation of non-real-time traffic also appears."
    INDEX { telProdNpMonFeatBrsDevQueueIfc,
            telProdNpMonFeatBrsDevQueueClassNum }
    ::= { telProdNpMonFeatBrsDevQueueTable 1 }

TelProdNpMonFeatBrsDevQueueEntry ::=
    SEQUENCE{
        telProdNpMonFeatBrsDevQueueIfc
            INTEGER,
        telProdNpMonFeatBrsDevQueueClassNum
            INTEGER,
        telProdNpMonFeatBrsDevQueueClassName
            DisplayString,
        telProdNpMonFeatBrsDevQueueUrgNum
            Gauge,
        telProdNpMonFeatBrsDevQueueUrgLen
            INTEGER,
        telProdNpMonFeatBrsDevQueueHighNum
            Gauge,
        telProdNpMonFeatBrsDevQueueHighLen
            INTEGER,
        telProdNpMonFeatBrsDevQueueNormNum
            Gauge,
        telProdNpMonFeatBrsDevQueueNormLen
            INTEGER,
        telProdNpMonFeatBrsDevQueueLowNum
            Gauge,
        telProdNpMonFeatBrsDevQueueLowLen
            INTEGER,
        telProdNpMonFeatBrsDevQueueThroughput
            INTEGER
        }

telProdNpMonFeatBrsDevQueueIfc OBJECT-TYPE
    SYNTAX INTEGER
    ACCESS read-only
    STATUS mandatory
    DESCRIPTION
    "First index: interface number."
    ::= { telProdNpMonFeatBrsDevQueueEntry 1 }

telProdNpMonFeatBrsDevQueueClassNum OBJECT-TYPE
    SYNTAX INTEGER
    ACCESS read-only
    STATUS mandatory
    DESCRIPTION
    "Second index: class order within the interface."
    ::= { telProdNpMonFeatBrsDevQueueEntry 2 }

telProdNpMonFeatBrsDevQueueClassName OBJECT-TYPE
    SYNTAX DisplayString(SIZE(0..9))
    ACCESS read-only
    STATUS mandatory
    DESCRIPTION
    "Class name."
    ::= { telProdNpMonFeatBrsDevQueueEntry 3 }

telProdNpMonFeatBrsDevQueueUrgNum OBJECT-TYPE
    SYNTAX Gauge
    ACCESS read-only
    STATUS mandatory
    DESCRIPTION
    "Current value of the urgent priority queue."
    ::= { telProdNpMonFeatBrsDevQueueEntry 4 }

telProdNpMonFeatBrsDevQueueUrgLen OBJECT-TYPE
    SYNTAX INTEGER
    ACCESS read-only
    STATUS mandatory
    DESCRIPTION
    "Length of the urgent priority queue."
    ::= { telProdNpMonFeatBrsDevQueueEntry 5 }

telProdNpMonFeatBrsDevQueueHighNum OBJECT-TYPE
    SYNTAX Gauge
    ACCESS read-only
    STATUS mandatory
    DESCRIPTION
    "Current value of the high priority queue."
    ::= { telProdNpMonFeatBrsDevQueueEntry 6 }

telProdNpMonFeatBrsDevQueueHighLen OBJECT-TYPE
    SYNTAX INTEGER
    ACCESS read-only
    STATUS mandatory
    DESCRIPTION
    "Length of the high priority queue."
    ::= { telProdNpMonFeatBrsDevQueueEntry 7 }

telProdNpMonFeatBrsDevQueueNormNum OBJECT-TYPE
    SYNTAX Gauge
    ACCESS read-only
    STATUS mandatory
    DESCRIPTION
    "Current value of the normal priority queue."
    ::= { telProdNpMonFeatBrsDevQueueEntry 8 }

telProdNpMonFeatBrsDevQueueNormLen OBJECT-TYPE
    SYNTAX INTEGER
    ACCESS read-only
    STATUS mandatory
    DESCRIPTION
    "Length of the normal priority queue."
    ::= { telProdNpMonFeatBrsDevQueueEntry 9 }

telProdNpMonFeatBrsDevQueueLowNum OBJECT-TYPE
    SYNTAX Gauge
    ACCESS read-only
    STATUS mandatory
    DESCRIPTION
    "Current value of the low priority queue."
    ::= { telProdNpMonFeatBrsDevQueueEntry 10 }

telProdNpMonFeatBrsDevQueueLowLen OBJECT-TYPE
    SYNTAX INTEGER
    ACCESS read-only
    STATUS mandatory
    DESCRIPTION
    "Length of the low priority queue."
    ::= { telProdNpMonFeatBrsDevQueueEntry 11 }

telProdNpMonFeatBrsDevQueueThroughput OBJECT-TYPE
    SYNTAX INTEGER
    ACCESS read-only
    STATUS mandatory
    DESCRIPTION
    "Throughput of class."
    ::= { telProdNpMonFeatBrsDevQueueEntry 12 }

-- Tabla que contiene los datos de las longitudes de las colas asociadas a cada
-- clase y prioridad, as� como su ocupacin, y esto para cada uno de los DLCIs
-- de los interfaces Frame Relay configurados en el equipo con Reserva de Ancho
-- de Banda.

telProdNpMonFeatBrsFRCirQueueTable OBJECT-TYPE
    SYNTAX SEQUENCE OF TelProdNpMonFeatBrsFRCirQueueEntry
    ACCESS not-accessible
    STATUS mandatory
    DESCRIPTION
    "This table contains information about the length and occupation of the BRS
    queues for each class and each priority in all Frame Relay circuits with
    this facility enabled."
    ::= { telProdNpMonFeatBrs 6 }

telProdNpMonFeatBrsFRCirQueueEntry OBJECT-TYPE
    SYNTAX TelProdNpMonFeatBrsFRCirQueueEntry
    ACCESS not-accessible
    STATUS mandatory
    DESCRIPTION
    "Each entry in the table contains data about the length and occupation of
    the BRS queues for a class within a circuit in a Frame Relay interface.
    The entry is comprised of several variables to store the current value and
    the maximum permitted value of the queues for each priority within a
    configured class in an interface."
    INDEX { telProdNpMonFeatBrsFRCirQueueIfc,
            telProdNpMonFeatBrsFRCirQueueDlci,
            telProdNpMonFeatBrsFRCirQueueClassNum }
    ::= { telProdNpMonFeatBrsFRCirQueueTable 1 }

TelProdNpMonFeatBrsFRCirQueueEntry ::=
    SEQUENCE{
        telProdNpMonFeatBrsFRCirQueueIfc
            INTEGER,
        telProdNpMonFeatBrsFRCirQueueDlci
            INTEGER,
        telProdNpMonFeatBrsFRCirQueueClassNum
            INTEGER,
        telProdNpMonFeatBrsFRCirQueueClassName
            DisplayString,
        telProdNpMonFeatBrsFRCirQueueUrgNum
            Gauge,
        telProdNpMonFeatBrsFRCirQueueUrgLen
            INTEGER,
        telProdNpMonFeatBrsFRCirQueueHighNum
            Gauge,
        telProdNpMonFeatBrsFRCirQueueHighLen
            INTEGER,
        telProdNpMonFeatBrsFRCirQueueNormNum
            Gauge,
        telProdNpMonFeatBrsFRCirQueueNormLen
            INTEGER,
        telProdNpMonFeatBrsFRCirQueueLowNum
            Gauge,
        telProdNpMonFeatBrsFRCirQueueLowLen
            INTEGER,
        telProdNpMonFeatBrsFRCirQueueThroughput
            INTEGER
        }

telProdNpMonFeatBrsFRCirQueueIfc OBJECT-TYPE
    SYNTAX INTEGER
    ACCESS read-only
    STATUS mandatory
    DESCRIPTION
    "First index: interface number."
    ::= { telProdNpMonFeatBrsFRCirQueueEntry 1 }

telProdNpMonFeatBrsFRCirQueueDlci OBJECT-TYPE
    SYNTAX INTEGER(16..1007)
    ACCESS read-only
    STATUS mandatory
    DESCRIPTION
    "Second index: Frame Relay circuit number (DLCI)."
    ::= { telProdNpMonFeatBrsFRCirQueueEntry 2 }

telProdNpMonFeatBrsFRCirQueueClassNum OBJECT-TYPE
    SYNTAX INTEGER
    ACCESS read-only
    STATUS mandatory
    DESCRIPTION
    "Third index: class order within that circuit in this Frame Relay
    interface."
    ::= { telProdNpMonFeatBrsFRCirQueueEntry 3 }

telProdNpMonFeatBrsFRCirQueueClassName OBJECT-TYPE
    SYNTAX DisplayString(SIZE(0..9))
    ACCESS read-only
    STATUS mandatory
    DESCRIPTION
    "Class name."
    ::= { telProdNpMonFeatBrsFRCirQueueEntry 4 }

telProdNpMonFeatBrsFRCirQueueUrgNum OBJECT-TYPE
    SYNTAX Gauge
    ACCESS read-only
    STATUS mandatory
    DESCRIPTION
    "Current value of the urgent priority queue."
    ::= { telProdNpMonFeatBrsFRCirQueueEntry 5 }

telProdNpMonFeatBrsFRCirQueueUrgLen OBJECT-TYPE
    SYNTAX INTEGER
    ACCESS read-only
    STATUS mandatory
    DESCRIPTION
    "Length of the urgent priority queue."
    ::= { telProdNpMonFeatBrsFRCirQueueEntry 6 }

telProdNpMonFeatBrsFRCirQueueHighNum OBJECT-TYPE
    SYNTAX Gauge
    ACCESS read-only
    STATUS mandatory
    DESCRIPTION
    "Current value of the high priority queue."
    ::= { telProdNpMonFeatBrsFRCirQueueEntry 7 }

telProdNpMonFeatBrsFRCirQueueHighLen OBJECT-TYPE
    SYNTAX INTEGER
    ACCESS read-only
    STATUS mandatory
    DESCRIPTION
    "Length of the high priority queue."
    ::= { telProdNpMonFeatBrsFRCirQueueEntry 8 }

telProdNpMonFeatBrsFRCirQueueNormNum OBJECT-TYPE
    SYNTAX Gauge
    ACCESS read-only
    STATUS mandatory
    DESCRIPTION
    "Current value of the normal priority queue."
    ::= { telProdNpMonFeatBrsFRCirQueueEntry 9 }

telProdNpMonFeatBrsFRCirQueueNormLen OBJECT-TYPE
    SYNTAX INTEGER
    ACCESS read-only
    STATUS mandatory
    DESCRIPTION
    "Length of the normal priority queue."
    ::= { telProdNpMonFeatBrsFRCirQueueEntry 10 }

telProdNpMonFeatBrsFRCirQueueLowNum OBJECT-TYPE
    SYNTAX Gauge
    ACCESS read-only
    STATUS mandatory
    DESCRIPTION
    "Current value of the low priority queue."
    ::= { telProdNpMonFeatBrsFRCirQueueEntry 11 }

telProdNpMonFeatBrsFRCirQueueLowLen OBJECT-TYPE
    SYNTAX INTEGER
    ACCESS read-only
    STATUS mandatory
    DESCRIPTION
    "Length of the low priority queue."
    ::= { telProdNpMonFeatBrsFRCirQueueEntry 12 }

telProdNpMonFeatBrsFRCirQueueThroughput OBJECT-TYPE
    SYNTAX INTEGER
    ACCESS read-only
    STATUS mandatory
    DESCRIPTION
    "Throughput of class."
    ::= { telProdNpMonFeatBrsFRCirQueueEntry 13 }

-- Tabla que contiene la informacin relativa a traffic-shaping para cada clase
-- dentro de cada interfaz configurado en el equipo con Reserva de Ancho de
-- Banda.

telProdNpMonFeatBrsDevTSTable OBJECT-TYPE
    SYNTAX SEQUENCE OF TelProdNpMonFeatBrsDevTSEntry
    ACCESS not-accessible
    STATUS mandatory
    DESCRIPTION
    "This table contains information relative to traffic-shaping for each class
    and for the whole interface ('Global' row)."
    ::= { telProdNpMonFeatBrs 7 }

telProdNpMonFeatBrsDevTSEntry OBJECT-TYPE
    SYNTAX TelProdNpMonFeatBrsDevTSEntry
    ACCESS not-accessible
    STATUS mandatory
    DESCRIPTION
    "Each entry is comprised of several variables to store information relative
    to traffic-shaping for one class within an interface or for the whole
    interface ('Global' row)."
    INDEX { telProdNpMonFeatBrsDevTSIfc,
            telProdNpMonFeatBrsDevTSClassNum }
    ::= { telProdNpMonFeatBrsDevTSTable 1 }

TelProdNpMonFeatBrsDevTSEntry ::=
    SEQUENCE{
        telProdNpMonFeatBrsDevTSIfc
            INTEGER,
        telProdNpMonFeatBrsDevTSClassNum
            INTEGER,
        telProdNpMonFeatBrsDevTSClear
            INTEGER,
        telProdNpMonFeatBrsDevTSClassName
            DisplayString,
        telProdNpMonFeatBrsDevTSCir
            INTEGER,
        telProdNpMonFeatBrsDevTSBurst
            INTEGER,
        telProdNpMonFeatBrsDevTSState
            INTEGER,
        telProdNpMonFeatBrsDevTSQueued
            INTEGER,
        telProdNpMonFeatBrsDevTSLastTx
            INTEGER,
        telProdNpMonFeatBrsDevTSThroughput
            INTEGER
        }

telProdNpMonFeatBrsDevTSIfc OBJECT-TYPE
    SYNTAX INTEGER
    ACCESS read-only
    STATUS mandatory
    DESCRIPTION
    "First index: interface number."
    ::= { telProdNpMonFeatBrsDevTSEntry 1 }

telProdNpMonFeatBrsDevTSClassNum OBJECT-TYPE
    SYNTAX INTEGER
    ACCESS read-only
    STATUS mandatory
    DESCRIPTION
    "Second index: class order within the interface."
    ::= { telProdNpMonFeatBrsDevTSEntry 2 }

telProdNpMonFeatBrsDevTSClear OBJECT-TYPE
    SYNTAX INTEGER{
        delete(1),
        ok(2),
        error(3),
        undefined(4)
        }
    ACCESS read-write
    STATUS mandatory
    DESCRIPTION
    "This variable is used to make a clear operation: when it is set to 1
    (delete), a clear command is executed, starting the measure of the
    throughput in this moment. The throughput measuring will only take into
    account those packets which are transmitted after this instant.
    In reading operations (GET) this variable will show the result of last clear
    operation attempt: the value is 2 (ok) if clear operation was performed
    succesfully, 3 (error) if an error ocurred and 4 (undefined) if no clear
    operations have been made yet."
    ::= { telProdNpMonFeatBrsDevTSEntry 3 }

telProdNpMonFeatBrsDevTSClassName OBJECT-TYPE
    SYNTAX DisplayString(SIZE(0..9))
    ACCESS read-only
    STATUS mandatory
    DESCRIPTION
    "Class name."
    ::= { telProdNpMonFeatBrsDevTSEntry 4 }

telProdNpMonFeatBrsDevTSCir OBJECT-TYPE
    SYNTAX INTEGER
    ACCESS read-only
    STATUS mandatory
    DESCRIPTION
    "Maximum average permitted throughput (0 indicates there is no limit)."
    ::= { telProdNpMonFeatBrsDevTSEntry 5 }

telProdNpMonFeatBrsDevTSBurst OBJECT-TYPE
    SYNTAX INTEGER
    ACCESS read-only
    STATUS mandatory
    DESCRIPTION
    "Currently used burst size (in bits)."
    ::= { telProdNpMonFeatBrsDevTSEntry 6 }

telProdNpMonFeatBrsDevTSState OBJECT-TYPE
    SYNTAX INTEGER{
        congested(1),
        bursting(2),
        ready(3)
        }
    ACCESS read-only
    STATUS mandatory
    DESCRIPTION
    "There are three possible states:  (1) congested,  (2) bursting, (3) ready.
    Transmission cannot be executed when a class or an interface is congested;
    transmission is possible in any other state."
    ::= { telProdNpMonFeatBrsDevTSEntry 7 }

telProdNpMonFeatBrsDevTSQueued OBJECT-TYPE
    SYNTAX INTEGER{
        yes(1),
        no(2)
        }
    ACCESS read-only
    STATUS mandatory
    DESCRIPTION
    "Indicates if this class is queued: when a class is queued, there is
    traffic to be transmitted."
    ::= { telProdNpMonFeatBrsDevTSEntry 8 }

telProdNpMonFeatBrsDevTSLastTx OBJECT-TYPE
    SYNTAX INTEGER
    ACCESS read-only
    STATUS mandatory
    DESCRIPTION
    "Last instant where a packet for this class was transmitted.
    (This parameter is for Teldat personnel use only)."
    ::= { telProdNpMonFeatBrsDevTSEntry 9 }

telProdNpMonFeatBrsDevTSThroughput OBJECT-TYPE
    SYNTAX INTEGER
    ACCESS read-only
    STATUS mandatory
    DESCRIPTION
    "Average throughput for a class."
    ::= { telProdNpMonFeatBrsDevTSEntry 10 }

-- Tabla que contiene la informacin relativa a traffic-shaping para cada clase
-- dentro de cada uno de los DLCIs de los interfaces Frame Relay configurados
-- en el equipo con Reserva de Ancho de Banda.

telProdNpMonFeatBrsFRCirTSTable OBJECT-TYPE
    SYNTAX SEQUENCE OF TelProdNpMonFeatBrsFRCirTSEntry
    ACCESS not-accessible
    STATUS mandatory
    DESCRIPTION
    "This table contains information relative to traffic-shaping for each class
    within a Frame Relay circuit (DLCI) and for the whole circuit
    ('Global' row)."
    ::= { telProdNpMonFeatBrs 8 }

telProdNpMonFeatBrsFRCirTSEntry OBJECT-TYPE
    SYNTAX TelProdNpMonFeatBrsFRCirTSEntry
    ACCESS not-accessible
    STATUS mandatory
    DESCRIPTION
    "Each entry is comprised of several variables to store information relative
    to traffic-shaping for one class within a Frame Relay circuit (DLCI) or for
    the whole circuit ('Global' row)."
    INDEX { telProdNpMonFeatBrsFRCirTSIfc,
            telProdNpMonFeatBrsFRCirTSDlci,
            telProdNpMonFeatBrsFRCirTSClassNum }
    ::= { telProdNpMonFeatBrsFRCirTSTable 1 }

TelProdNpMonFeatBrsFRCirTSEntry ::=
    SEQUENCE{
        telProdNpMonFeatBrsFRCirTSIfc
            INTEGER,
        telProdNpMonFeatBrsFRCirTSDlci
            INTEGER,
        telProdNpMonFeatBrsFRCirTSClassNum
            INTEGER,
        telProdNpMonFeatBrsFRCirTSClear
            INTEGER,
        telProdNpMonFeatBrsFRCirTSClassName
            DisplayString,
        telProdNpMonFeatBrsFRCirTSCir
            INTEGER,
        telProdNpMonFeatBrsFRCirTSBurst
            INTEGER,
        telProdNpMonFeatBrsFRCirTSState
            INTEGER,
        telProdNpMonFeatBrsFRCirTSQueued
            INTEGER,
        telProdNpMonFeatBrsFRCirTSLastTx
            INTEGER,
        telProdNpMonFeatBrsFRCirTSThroughput
            INTEGER
        }

telProdNpMonFeatBrsFRCirTSIfc OBJECT-TYPE
    SYNTAX INTEGER
    ACCESS read-only
    STATUS mandatory
    DESCRIPTION
    "First index: interface number."
    ::= { telProdNpMonFeatBrsFRCirTSEntry 1 }

telProdNpMonFeatBrsFRCirTSDlci OBJECT-TYPE
    SYNTAX INTEGER(16..1007)
    ACCESS read-only
    STATUS mandatory
    DESCRIPTION
    "Second index: Frame Relay circuit number (DLCI)."
    ::= { telProdNpMonFeatBrsFRCirTSEntry 2 }

telProdNpMonFeatBrsFRCirTSClassNum OBJECT-TYPE
    SYNTAX INTEGER
    ACCESS read-only
    STATUS mandatory
    DESCRIPTION
    "Third index: class order within the Frame Relay circuit (DLCI)."
    ::= { telProdNpMonFeatBrsFRCirTSEntry 3 }

telProdNpMonFeatBrsFRCirTSClear OBJECT-TYPE
    SYNTAX INTEGER{
        delete(1),
        ok(2),
        error(3),
        undefined(4)
        }
    ACCESS read-write
    STATUS mandatory
    DESCRIPTION
    "This variable is used to make a clear operation: when it is set to 1
    (delete), a clear command is executed, starting the measure of the
    throughput in this moment. The throughput measuring will only take into
    account those packets which are transmitted after this instant.
    In reading operations (GET) this variable will show the result of last clear
    operation attempt: the value is 2 (ok) if clear operation was performed
    succesfully, 3 (error) if an error ocurred and 4 (undefined) if no clear
    operations have been made yet."
    ::= { telProdNpMonFeatBrsFRCirTSEntry 4 }

telProdNpMonFeatBrsFRCirTSClassName OBJECT-TYPE
    SYNTAX DisplayString(SIZE(0..9))
    ACCESS read-only
    STATUS mandatory
    DESCRIPTION
    "Class name."
    ::= { telProdNpMonFeatBrsFRCirTSEntry 5 }

telProdNpMonFeatBrsFRCirTSCir OBJECT-TYPE
    SYNTAX INTEGER
    ACCESS read-only
    STATUS mandatory
    DESCRIPTION
    "Maximum average permitted throughput (0 indicates there is no limit)."
    ::= { telProdNpMonFeatBrsFRCirTSEntry 6 }

telProdNpMonFeatBrsFRCirTSBurst OBJECT-TYPE
    SYNTAX INTEGER
    ACCESS read-only
    STATUS mandatory
    DESCRIPTION
    "Currently used burst size (in bits)."
    ::= { telProdNpMonFeatBrsFRCirTSEntry 7 }

telProdNpMonFeatBrsFRCirTSState OBJECT-TYPE
    SYNTAX INTEGER{
        congested(1),
        bursting(2),
        ready(3)
        }
    ACCESS read-only
    STATUS mandatory
    DESCRIPTION
    "There are three possible states:  (1) congested,  (2) bursting, (3) ready.
    Transmission cannot be executed when a class or an interface is congested;
    transmission is possible in any other state."
    ::= { telProdNpMonFeatBrsFRCirTSEntry 8 }

telProdNpMonFeatBrsFRCirTSQueued OBJECT-TYPE
    SYNTAX INTEGER{
        yes(1),
        no(2)
        }
    ACCESS read-only
    STATUS mandatory
    DESCRIPTION
    "Indicates if this class is queued: when a class is queued, there is
    traffic to be transmitted."
    ::= { telProdNpMonFeatBrsFRCirTSEntry 9 }

telProdNpMonFeatBrsFRCirTSLastTx OBJECT-TYPE
    SYNTAX INTEGER
    ACCESS read-only
    STATUS mandatory
    DESCRIPTION
    "Last instant where a packet for this class was transmitted.
    (This parameter is for Teldat personnel use only)."
    ::= { telProdNpMonFeatBrsFRCirTSEntry 10 }

telProdNpMonFeatBrsFRCirTSThroughput OBJECT-TYPE
    SYNTAX INTEGER
    ACCESS read-only
    STATUS mandatory
    DESCRIPTION
    "Average throughput for a class."
    ::= { telProdNpMonFeatBrsFRCirTSEntry 11 }

-- Tabla que contiene la informacin relativa a traffic-shaping usado para
-- level-indicator en cada clase o a nivel global dentro de cada interfaz
-- configurado en el equipo con Reserva de Ancho de Banda.

telProdNpMonFeatBrsDevTSLvlIndTable OBJECT-TYPE
    SYNTAX SEQUENCE OF TelProdNpMonFeatBrsDevTSLvlIndEntry
    ACCESS not-accessible
    STATUS mandatory
    DESCRIPTION
    "This table contains information relative to traffic-shaping used for
    level-indicator for each class and for the whole interface ('Global'
    row)."
    ::= { telProdNpMonFeatBrs 9 }

telProdNpMonFeatBrsDevTSLvlIndEntry OBJECT-TYPE
    SYNTAX TelProdNpMonFeatBrsDevTSLvlIndEntry
    ACCESS not-accessible
    STATUS mandatory
    DESCRIPTION
    "Each entry is comprised of several variables to store information relative
    to traffic-shaping for level-indicator for one class within an interface or
    for the whole interface ('Global' row)."
    INDEX { telProdNpMonFeatBrsDevTSLvlIndIfc,
            telProdNpMonFeatBrsDevTSLvlIndClassNum }
    ::= { telProdNpMonFeatBrsDevTSLvlIndTable 1 }

TelProdNpMonFeatBrsDevTSLvlIndEntry ::=
    SEQUENCE{
        telProdNpMonFeatBrsDevTSLvlIndIfc
            INTEGER,
        telProdNpMonFeatBrsDevTSLvlIndClassNum
            INTEGER,
        telProdNpMonFeatBrsDevTSLvlIndClear
            INTEGER,
        telProdNpMonFeatBrsDevTSLvlIndClassName
            DisplayString,
        telProdNpMonFeatBrsDevTSLvlIndCir
            INTEGER,
        telProdNpMonFeatBrsDevTSLvlIndBurst
            INTEGER,
        telProdNpMonFeatBrsDevTSLvlIndState
            INTEGER,
        telProdNpMonFeatBrsDevTSLvlIndQueued
            INTEGER,
        telProdNpMonFeatBrsDevTSLvlIndLastTx
            INTEGER,
        telProdNpMonFeatBrsDevTSLvlIndThroughput
            INTEGER
        }

telProdNpMonFeatBrsDevTSLvlIndIfc OBJECT-TYPE
    SYNTAX INTEGER
    ACCESS read-only
    STATUS mandatory
    DESCRIPTION
    "First index: interface number."
    ::= { telProdNpMonFeatBrsDevTSLvlIndEntry 1 }

telProdNpMonFeatBrsDevTSLvlIndClassNum OBJECT-TYPE
    SYNTAX INTEGER
    ACCESS read-only
    STATUS mandatory
    DESCRIPTION
    "Second index: class order within the interface."
    ::= { telProdNpMonFeatBrsDevTSLvlIndEntry 2 }

telProdNpMonFeatBrsDevTSLvlIndClear OBJECT-TYPE
    SYNTAX INTEGER{
        delete(1),
        ok(2),
        error(3),
        undefined(4)
        }
    ACCESS read-write
    STATUS mandatory
    DESCRIPTION
    "This variable is used to make a clear operation: when it is set to 1
    (delete), a clear command is executed, starting the measure of the
    throughput in this moment. The throughput measuring will only take into
    account those packets which are transmitted after this instant.
    In reading operations (GET) this variable will show the result of last clear
    operation attempt: the value is 2 (ok) if clear operation was performed
    succesfully, 3 (error) if an error ocurred and 4 (undefined) if no clear
    operations have been made yet."
    ::= { telProdNpMonFeatBrsDevTSLvlIndEntry 3 }

telProdNpMonFeatBrsDevTSLvlIndClassName OBJECT-TYPE
    SYNTAX DisplayString(SIZE(0..9))
    ACCESS read-only
    STATUS mandatory
    DESCRIPTION
    "Class name."
    ::= { telProdNpMonFeatBrsDevTSLvlIndEntry 4 }

telProdNpMonFeatBrsDevTSLvlIndCir OBJECT-TYPE
    SYNTAX INTEGER
    ACCESS read-only
    STATUS mandatory
    DESCRIPTION
    "Maximum average permitted throughput (0 indicates there is no limit)."
    ::= { telProdNpMonFeatBrsDevTSLvlIndEntry 5 }

telProdNpMonFeatBrsDevTSLvlIndBurst OBJECT-TYPE
    SYNTAX INTEGER
    ACCESS read-only
    STATUS mandatory
    DESCRIPTION
    "Currently used burst size (in bits)."
    ::= { telProdNpMonFeatBrsDevTSLvlIndEntry 6 }

telProdNpMonFeatBrsDevTSLvlIndState OBJECT-TYPE
    SYNTAX INTEGER{
        congested(1),
        bursting(2),
        ready(3)
        }
    ACCESS read-only
    STATUS mandatory
    DESCRIPTION
    "There are three possible states:  (1) congested,  (2) bursting, (3) ready.
    A level-indicator is updated when a class or an interface becomes
    congested; when congestion ends, it comes back to previous state."
    ::= { telProdNpMonFeatBrsDevTSLvlIndEntry 7 }

telProdNpMonFeatBrsDevTSLvlIndQueued OBJECT-TYPE
    SYNTAX INTEGER{
        yes(1),
        no(2)
        }
    ACCESS read-only
    STATUS mandatory
    DESCRIPTION
    "Indicates if this class is queued: when a class is queued, there is
    traffic to be transmitted."
    ::= { telProdNpMonFeatBrsDevTSLvlIndEntry 8 }

telProdNpMonFeatBrsDevTSLvlIndLastTx OBJECT-TYPE
    SYNTAX INTEGER
    ACCESS read-only
    STATUS mandatory
    DESCRIPTION
    "Last instant where a packet for this class was transmitted.
    (This parameter is for Teldat personnel use only)."
    ::= { telProdNpMonFeatBrsDevTSLvlIndEntry 9 }

telProdNpMonFeatBrsDevTSLvlIndThroughput OBJECT-TYPE
    SYNTAX INTEGER
    ACCESS read-only
    STATUS mandatory
    DESCRIPTION
    "Average throughput for a class."
    ::= { telProdNpMonFeatBrsDevTSLvlIndEntry 10 }

-- Tabla que contiene la informacin relativa a traffic-shaping usado para
-- level-indicator en cada clase o a nivel global dentro de cada uno de
-- los DLCIs de los interfaces Frame Relay configurados en el equipo con
-- Reserva de Ancho de Banda.

telProdNpMonFeatBrsFRCirTSLvlIndTable OBJECT-TYPE
    SYNTAX SEQUENCE OF TelProdNpMonFeatBrsFRCirTSLvlIndEntry
    ACCESS not-accessible
    STATUS mandatory
    DESCRIPTION
    "This table contains information relative to traffic-shaping used for
    level-indicator for each class within a Frame Relay circuit (DLCI) and
    for the whole circuit ('Global' row)."
    ::= { telProdNpMonFeatBrs 10 }

telProdNpMonFeatBrsFRCirTSLvlIndEntry OBJECT-TYPE
    SYNTAX TelProdNpMonFeatBrsFRCirTSLvlIndEntry
    ACCESS not-accessible
    STATUS mandatory
    DESCRIPTION
    "Each entry is comprised of several variables to store information relative
    to traffic-shaping used for level-indicator for one class within a Frame
    Relay circuit (DLCI) or for the whole circuit ('Global' row)."
    INDEX { telProdNpMonFeatBrsFRCirTSLvlIndIfc,
            telProdNpMonFeatBrsFRCirTSLvlIndDlci,
            telProdNpMonFeatBrsFRCirTSLvlIndClassNum }
    ::= { telProdNpMonFeatBrsFRCirTSLvlIndTable 1 }

TelProdNpMonFeatBrsFRCirTSLvlIndEntry ::=
    SEQUENCE{
        telProdNpMonFeatBrsFRCirTSLvlIndIfc
            INTEGER,
        telProdNpMonFeatBrsFRCirTSLvlIndDlci
            INTEGER,
        telProdNpMonFeatBrsFRCirTSLvlIndClassNum
            INTEGER,
        telProdNpMonFeatBrsFRCirTSLvlIndClear
            INTEGER,
        telProdNpMonFeatBrsFRCirTSLvlIndClassName
            DisplayString,
        telProdNpMonFeatBrsFRCirTSLvlIndCir
            INTEGER,
        telProdNpMonFeatBrsFRCirTSLvlIndBurst
            INTEGER,
        telProdNpMonFeatBrsFRCirTSLvlIndState
            INTEGER,
        telProdNpMonFeatBrsFRCirTSLvlIndQueued
            INTEGER,
        telProdNpMonFeatBrsFRCirTSLvlIndLastTx
            INTEGER,
        telProdNpMonFeatBrsFRCirTSLvlIndThroughput
            INTEGER
        }

telProdNpMonFeatBrsFRCirTSLvlIndIfc OBJECT-TYPE
    SYNTAX INTEGER
    ACCESS read-only
    STATUS mandatory
    DESCRIPTION
    "First index: interface number."
    ::= { telProdNpMonFeatBrsFRCirTSLvlIndEntry 1 }

telProdNpMonFeatBrsFRCirTSLvlIndDlci OBJECT-TYPE
    SYNTAX INTEGER(16..1007)
    ACCESS read-only
    STATUS mandatory
    DESCRIPTION
    "Second index: Frame Relay circuit number (DLCI)."
    ::= { telProdNpMonFeatBrsFRCirTSLvlIndEntry 2 }

telProdNpMonFeatBrsFRCirTSLvlIndClassNum OBJECT-TYPE
    SYNTAX INTEGER
    ACCESS read-only
    STATUS mandatory
    DESCRIPTION
    "Third index: class order within the Frame Relay circuit (DLCI)."
    ::= { telProdNpMonFeatBrsFRCirTSLvlIndEntry 3 }

telProdNpMonFeatBrsFRCirTSLvlIndClear OBJECT-TYPE
    SYNTAX INTEGER{
        delete(1),
        ok(2),
        error(3),
        undefined(4)
        }
    ACCESS read-write
    STATUS mandatory
    DESCRIPTION
    "This variable is used to make a clear operation: when it is set to 1
    (delete), a clear command is executed, starting the measure of the
    throughput in this moment. The throughput measuring will only take into
    account those packets which are transmitted after this instant.
    In reading operations (GET) this variable will show the result of last clear
    operation attempt: the value is 2 (ok) if clear operation was performed
    succesfully, 3 (error) if an error ocurred and 4 (undefined) if no clear
    operations have been made yet."
    ::= { telProdNpMonFeatBrsFRCirTSLvlIndEntry 4 }

telProdNpMonFeatBrsFRCirTSLvlIndClassName OBJECT-TYPE
    SYNTAX DisplayString(SIZE(0..9))
    ACCESS read-only
    STATUS mandatory
    DESCRIPTION
    "Class name."
    ::= { telProdNpMonFeatBrsFRCirTSLvlIndEntry 5 }

telProdNpMonFeatBrsFRCirTSLvlIndCir OBJECT-TYPE
    SYNTAX INTEGER
    ACCESS read-only
    STATUS mandatory
    DESCRIPTION
    "Maximum average permitted throughput (0 indicates there is no limit)."
    ::= { telProdNpMonFeatBrsFRCirTSLvlIndEntry 6 }

telProdNpMonFeatBrsFRCirTSLvlIndBurst OBJECT-TYPE
    SYNTAX INTEGER
    ACCESS read-only
    STATUS mandatory
    DESCRIPTION
    "Currently used burst size (in bits)."
    ::= { telProdNpMonFeatBrsFRCirTSLvlIndEntry 7 }

telProdNpMonFeatBrsFRCirTSLvlIndState OBJECT-TYPE
    SYNTAX INTEGER{
        congested(1),
        bursting(2),
        ready(3)
        }
    ACCESS read-only
    STATUS mandatory
    DESCRIPTION
    "There are three possible states:  (1) congested,  (2) bursting, (3) ready.
    A level-indicator is updated when a class or an interface becomes congested;
    when congestion ends, it comes back to previous state."
    ::= { telProdNpMonFeatBrsFRCirTSLvlIndEntry 8 }

telProdNpMonFeatBrsFRCirTSLvlIndQueued OBJECT-TYPE
    SYNTAX INTEGER{
        yes(1),
        no(2)
        }
    ACCESS read-only
    STATUS mandatory
    DESCRIPTION
    "Indicates if this class is queued: when a class is queued, there is
    traffic to be transmitted."
    ::= { telProdNpMonFeatBrsFRCirTSLvlIndEntry 9 }

telProdNpMonFeatBrsFRCirTSLvlIndLastTx OBJECT-TYPE
    SYNTAX INTEGER
    ACCESS read-only
    STATUS mandatory
    DESCRIPTION
    "Last instant where a packet for this class was transmitted.
    (This parameter is for Teldat personnel use only)."
    ::= { telProdNpMonFeatBrsFRCirTSLvlIndEntry 10 }

telProdNpMonFeatBrsFRCirTSLvlIndThroughput OBJECT-TYPE
    SYNTAX INTEGER
    ACCESS read-only
    STATUS mandatory
    DESCRIPTION
    "Average throughput for a class."
    ::= { telProdNpMonFeatBrsFRCirTSLvlIndEntry 11 }


END
