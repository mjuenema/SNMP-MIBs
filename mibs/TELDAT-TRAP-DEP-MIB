-- file automatically created


TELDAT-TRAP-DEP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


depTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the DEP event subsystem."
    REVISION "201401200930Z"
    DESCRIPTION "Initial implementation"
        ::= { telEventTraps 144 }


depEventsGroup	OBJECT IDENTIFIER	::= { depTrapsMIB 1 }

depNotifications	OBJECT IDENTIFIER	::= { depTrapsMIB 2 }
depNotificationsPrefix	OBJECT IDENTIFIER	::= { depNotifications 0 }

depEventObjects1 OBJECT-IDENTITY
    STATUS current
    DESCRIPTION
        "Event DEP.1
        A Test packet has been received."
    ::= { depEventsGroup 1 }

dep1_ip_address OBJECT-TYPE
    SYNTAX IpAddress
    MAX-ACCESS accessible-for-notify
    STATUS current
    DESCRIPTION
        "Parameter 'ip_address' in event DEP.1"
    ::= { depEventObjects1 1 }

dep1_session OBJECT-TYPE
    SYNTAX Integer32
    MAX-ACCESS accessible-for-notify
    STATUS current
    DESCRIPTION
        "Parameter 'session' in event DEP.1"
    ::= { depEventObjects1 2 }

dep1_index OBJECT-TYPE
    SYNTAX Integer32
    MAX-ACCESS accessible-for-notify
    STATUS current
    DESCRIPTION
        "Parameter 'index' in event DEP.1"
    ::= { depEventObjects1 3 }

depEventObjects2 OBJECT-IDENTITY
    STATUS current
    DESCRIPTION
        "Event DEP.2
        An S Message has been received."
    ::= { depEventsGroup 2 }

dep2_nri OBJECT-TYPE
    SYNTAX DisplayString
    MAX-ACCESS accessible-for-notify
    STATUS current
    DESCRIPTION
        "Parameter 'nri' in event DEP.2"
    ::= { depEventObjects2 1 }

dep2_ip_address OBJECT-TYPE
    SYNTAX IpAddress
    MAX-ACCESS accessible-for-notify
    STATUS current
    DESCRIPTION
        "Parameter 'ip_address' in event DEP.2"
    ::= { depEventObjects2 2 }

dep2_state OBJECT-TYPE
    SYNTAX Integer32
    MAX-ACCESS accessible-for-notify
    STATUS current
    DESCRIPTION
        "Parameter 'state' in event DEP.2"
    ::= { depEventObjects2 3 }

dep2_session OBJECT-TYPE
    SYNTAX Integer32
    MAX-ACCESS accessible-for-notify
    STATUS current
    DESCRIPTION
        "Parameter 'session' in event DEP.2"
    ::= { depEventObjects2 4 }

depEventObjects3 OBJECT-IDENTITY
    STATUS current
    DESCRIPTION
        "Event DEP.3
        An A Message has been transmitted."
    ::= { depEventsGroup 3 }

dep3_ip_address OBJECT-TYPE
    SYNTAX IpAddress
    MAX-ACCESS accessible-for-notify
    STATUS current
    DESCRIPTION
        "Parameter 'ip_address' in event DEP.3"
    ::= { depEventObjects3 1 }

dep3_state OBJECT-TYPE
    SYNTAX Integer32
    MAX-ACCESS accessible-for-notify
    STATUS current
    DESCRIPTION
        "Parameter 'state' in event DEP.3"
    ::= { depEventObjects3 2 }

dep3_session OBJECT-TYPE
    SYNTAX Integer32
    MAX-ACCESS accessible-for-notify
    STATUS current
    DESCRIPTION
        "Parameter 'session' in event DEP.3"
    ::= { depEventObjects3 3 }

depEventObjects4 OBJECT-IDENTITY
    STATUS current
    DESCRIPTION
        "Event DEP.4
        A Data Message has been received."
    ::= { depEventsGroup 4 }

dep4_type_msg OBJECT-TYPE
    SYNTAX DisplayString
    MAX-ACCESS accessible-for-notify
    STATUS current
    DESCRIPTION
        "Parameter 'type_msg' in event DEP.4"
    ::= { depEventObjects4 1 }

dep4_ip_address OBJECT-TYPE
    SYNTAX IpAddress
    MAX-ACCESS accessible-for-notify
    STATUS current
    DESCRIPTION
        "Parameter 'ip_address' in event DEP.4"
    ::= { depEventObjects4 2 }

dep4_state OBJECT-TYPE
    SYNTAX Integer32
    MAX-ACCESS accessible-for-notify
    STATUS current
    DESCRIPTION
        "Parameter 'state' in event DEP.4"
    ::= { depEventObjects4 3 }

dep4_session OBJECT-TYPE
    SYNTAX Integer32
    MAX-ACCESS accessible-for-notify
    STATUS current
    DESCRIPTION
        "Parameter 'session' in event DEP.4"
    ::= { depEventObjects4 4 }

depEventObjects5 OBJECT-IDENTITY
    STATUS current
    DESCRIPTION
        "Event DEP.5
        A Data Message has been transmitted."
    ::= { depEventsGroup 5 }

dep5_type_msg OBJECT-TYPE
    SYNTAX DisplayString
    MAX-ACCESS accessible-for-notify
    STATUS current
    DESCRIPTION
        "Parameter 'type_msg' in event DEP.5"
    ::= { depEventObjects5 1 }

dep5_ip_address OBJECT-TYPE
    SYNTAX IpAddress
    MAX-ACCESS accessible-for-notify
    STATUS current
    DESCRIPTION
        "Parameter 'ip_address' in event DEP.5"
    ::= { depEventObjects5 2 }

dep5_state OBJECT-TYPE
    SYNTAX Integer32
    MAX-ACCESS accessible-for-notify
    STATUS current
    DESCRIPTION
        "Parameter 'state' in event DEP.5"
    ::= { depEventObjects5 3 }

dep5_session OBJECT-TYPE
    SYNTAX Integer32
    MAX-ACCESS accessible-for-notify
    STATUS current
    DESCRIPTION
        "Parameter 'session' in event DEP.5"
    ::= { depEventObjects5 4 }

depEventObjects6 OBJECT-IDENTITY
    STATUS current
    DESCRIPTION
        "Event DEP.6
        A Release Message has been received."
    ::= { depEventsGroup 6 }

dep6_ip_address OBJECT-TYPE
    SYNTAX IpAddress
    MAX-ACCESS accessible-for-notify
    STATUS current
    DESCRIPTION
        "Parameter 'ip_address' in event DEP.6"
    ::= { depEventObjects6 1 }

dep6_state OBJECT-TYPE
    SYNTAX Integer32
    MAX-ACCESS accessible-for-notify
    STATUS current
    DESCRIPTION
        "Parameter 'state' in event DEP.6"
    ::= { depEventObjects6 2 }

dep6_session OBJECT-TYPE
    SYNTAX Integer32
    MAX-ACCESS accessible-for-notify
    STATUS current
    DESCRIPTION
        "Parameter 'session' in event DEP.6"
    ::= { depEventObjects6 3 }

depEventObjects7 OBJECT-IDENTITY
    STATUS current
    DESCRIPTION
        "Event DEP.7
        A Release Message has been transmitted."
    ::= { depEventsGroup 7 }

dep7_ip_address OBJECT-TYPE
    SYNTAX IpAddress
    MAX-ACCESS accessible-for-notify
    STATUS current
    DESCRIPTION
        "Parameter 'ip_address' in event DEP.7"
    ::= { depEventObjects7 1 }

dep7_state OBJECT-TYPE
    SYNTAX Integer32
    MAX-ACCESS accessible-for-notify
    STATUS current
    DESCRIPTION
        "Parameter 'state' in event DEP.7"
    ::= { depEventObjects7 2 }

dep7_session OBJECT-TYPE
    SYNTAX Integer32
    MAX-ACCESS accessible-for-notify
    STATUS current
    DESCRIPTION
        "Parameter 'session' in event DEP.7"
    ::= { depEventObjects7 3 }

depEventObjects8 OBJECT-IDENTITY
    STATUS current
    DESCRIPTION
        "Event DEP.8
        An EOT packet has been received."
    ::= { depEventsGroup 8 }

dep8_ip_address OBJECT-TYPE
    SYNTAX IpAddress
    MAX-ACCESS accessible-for-notify
    STATUS current
    DESCRIPTION
        "Parameter 'ip_address' in event DEP.8"
    ::= { depEventObjects8 1 }

dep8_state OBJECT-TYPE
    SYNTAX Integer32
    MAX-ACCESS accessible-for-notify
    STATUS current
    DESCRIPTION
        "Parameter 'state' in event DEP.8"
    ::= { depEventObjects8 2 }

dep8_session OBJECT-TYPE
    SYNTAX Integer32
    MAX-ACCESS accessible-for-notify
    STATUS current
    DESCRIPTION
        "Parameter 'session' in event DEP.8"
    ::= { depEventObjects8 3 }

depEventObjects9 OBJECT-IDENTITY
    STATUS current
    DESCRIPTION
        "Event DEP.9
        A T4 Indication has been received."
    ::= { depEventsGroup 9 }

dep9_state OBJECT-TYPE
    SYNTAX Integer32
    MAX-ACCESS accessible-for-notify
    STATUS current
    DESCRIPTION
        "Parameter 'state' in event DEP.9"
    ::= { depEventObjects9 1 }

dep9_session OBJECT-TYPE
    SYNTAX Integer32
    MAX-ACCESS accessible-for-notify
    STATUS current
    DESCRIPTION
        "Parameter 'session' in event DEP.9"
    ::= { depEventObjects9 2 }

depEventObjects11 OBJECT-IDENTITY
    STATUS current
    DESCRIPTION
        "Event DEP.11
        The TCP session has been opened by the remote HOST."
    ::= { depEventsGroup 11 }

dep11_ip_address OBJECT-TYPE
    SYNTAX IpAddress
    MAX-ACCESS accessible-for-notify
    STATUS current
    DESCRIPTION
        "Parameter 'ip_address' in event DEP.11"
    ::= { depEventObjects11 1 }

dep11_session OBJECT-TYPE
    SYNTAX Integer32
    MAX-ACCESS accessible-for-notify
    STATUS current
    DESCRIPTION
        "Parameter 'session' in event DEP.11"
    ::= { depEventObjects11 2 }

dep11_index OBJECT-TYPE
    SYNTAX Integer32
    MAX-ACCESS accessible-for-notify
    STATUS current
    DESCRIPTION
        "Parameter 'index' in event DEP.11"
    ::= { depEventObjects11 3 }

depEventObjects12 OBJECT-IDENTITY
    STATUS current
    DESCRIPTION
        "Event DEP.12
        The TCP session has been closed."
    ::= { depEventsGroup 12 }

dep12_state OBJECT-TYPE
    SYNTAX Integer32
    MAX-ACCESS accessible-for-notify
    STATUS current
    DESCRIPTION
        "Parameter 'state' in event DEP.12"
    ::= { depEventObjects12 1 }

dep12_session OBJECT-TYPE
    SYNTAX Integer32
    MAX-ACCESS accessible-for-notify
    STATUS current
    DESCRIPTION
        "Parameter 'session' in event DEP.12"
    ::= { depEventObjects12 2 }

depEventObjects13 OBJECT-IDENTITY
    STATUS current
    DESCRIPTION
        "Event DEP.13
        The TCP session has been closed by the remote HOST."
    ::= { depEventsGroup 13 }

dep13_state OBJECT-TYPE
    SYNTAX Integer32
    MAX-ACCESS accessible-for-notify
    STATUS current
    DESCRIPTION
        "Parameter 'state' in event DEP.13"
    ::= { depEventObjects13 1 }

dep13_session OBJECT-TYPE
    SYNTAX Integer32
    MAX-ACCESS accessible-for-notify
    STATUS current
    DESCRIPTION
        "Parameter 'session' in event DEP.13"
    ::= { depEventObjects13 2 }

depEventObjects14 OBJECT-IDENTITY
    STATUS current
    DESCRIPTION
        "Event DEP.14
        The max number of TCP sessions has been reached."
    ::= { depEventsGroup 14 }

dep14_access_type OBJECT-TYPE
    SYNTAX DisplayString
    MAX-ACCESS accessible-for-notify
    STATUS current
    DESCRIPTION
        "Parameter 'access_type' in event DEP.14"
    ::= { depEventObjects14 1 }

depEventObjects15 OBJECT-IDENTITY
    STATUS current
    DESCRIPTION
        "Event DEP.15
        A X25 event has been received."
    ::= { depEventsGroup 15 }

dep15_type OBJECT-TYPE
    SYNTAX DisplayString
    MAX-ACCESS accessible-for-notify
    STATUS current
    DESCRIPTION
        "Parameter 'type' in event DEP.15"
    ::= { depEventObjects15 1 }

dep15_session OBJECT-TYPE
    SYNTAX Integer32
    MAX-ACCESS accessible-for-notify
    STATUS current
    DESCRIPTION
        "Parameter 'session' in event DEP.15"
    ::= { depEventObjects15 2 }

dep15_state OBJECT-TYPE
    SYNTAX Integer32
    MAX-ACCESS accessible-for-notify
    STATUS current
    DESCRIPTION
        "Parameter 'state' in event DEP.15"
    ::= { depEventObjects15 3 }

depEventObjects16 OBJECT-IDENTITY
    STATUS current
    DESCRIPTION
        "Event DEP.16
        A Data Message has been received from POS."
    ::= { depEventsGroup 16 }

dep16_msg_type OBJECT-TYPE
    SYNTAX DisplayString
    MAX-ACCESS accessible-for-notify
    STATUS current
    DESCRIPTION
        "Parameter 'msg_type' in event DEP.16"
    ::= { depEventObjects16 1 }

dep16_msg_leng OBJECT-TYPE
    SYNTAX Integer32
    MAX-ACCESS accessible-for-notify
    STATUS current
    DESCRIPTION
        "Parameter 'msg_leng' in event DEP.16"
    ::= { depEventObjects16 2 }

dep16_state OBJECT-TYPE
    SYNTAX Integer32
    MAX-ACCESS accessible-for-notify
    STATUS current
    DESCRIPTION
        "Parameter 'state' in event DEP.16"
    ::= { depEventObjects16 3 }

dep16_session OBJECT-TYPE
    SYNTAX Integer32
    MAX-ACCESS accessible-for-notify
    STATUS current
    DESCRIPTION
        "Parameter 'session' in event DEP.16"
    ::= { depEventObjects16 4 }

depEventObjects17 OBJECT-IDENTITY
    STATUS current
    DESCRIPTION
        "Event DEP.17
        A Data Message has been transmitted to POS."
    ::= { depEventsGroup 17 }

dep17_msg_type OBJECT-TYPE
    SYNTAX DisplayString
    MAX-ACCESS accessible-for-notify
    STATUS current
    DESCRIPTION
        "Parameter 'msg_type' in event DEP.17"
    ::= { depEventObjects17 1 }

dep17_msg_leng OBJECT-TYPE
    SYNTAX Integer32
    MAX-ACCESS accessible-for-notify
    STATUS current
    DESCRIPTION
        "Parameter 'msg_leng' in event DEP.17"
    ::= { depEventObjects17 2 }

dep17_state OBJECT-TYPE
    SYNTAX Integer32
    MAX-ACCESS accessible-for-notify
    STATUS current
    DESCRIPTION
        "Parameter 'state' in event DEP.17"
    ::= { depEventObjects17 3 }

dep17_session OBJECT-TYPE
    SYNTAX Integer32
    MAX-ACCESS accessible-for-notify
    STATUS current
    DESCRIPTION
        "Parameter 'session' in event DEP.17"
    ::= { depEventObjects17 4 }

depEventObjects18 OBJECT-IDENTITY
    STATUS current
    DESCRIPTION
        "Event DEP.18
        A control character has been received from POS."
    ::= { depEventsGroup 18 }

dep18_msg_type OBJECT-TYPE
    SYNTAX DisplayString
    MAX-ACCESS accessible-for-notify
    STATUS current
    DESCRIPTION
        "Parameter 'msg_type' in event DEP.18"
    ::= { depEventObjects18 1 }

dep18_state OBJECT-TYPE
    SYNTAX Integer32
    MAX-ACCESS accessible-for-notify
    STATUS current
    DESCRIPTION
        "Parameter 'state' in event DEP.18"
    ::= { depEventObjects18 2 }

dep18_session OBJECT-TYPE
    SYNTAX Integer32
    MAX-ACCESS accessible-for-notify
    STATUS current
    DESCRIPTION
        "Parameter 'session' in event DEP.18"
    ::= { depEventObjects18 3 }

depEventObjects19 OBJECT-IDENTITY
    STATUS current
    DESCRIPTION
        "Event DEP.19
        A control character has been transmitted to POS."
    ::= { depEventsGroup 19 }

dep19_msg_type OBJECT-TYPE
    SYNTAX DisplayString
    MAX-ACCESS accessible-for-notify
    STATUS current
    DESCRIPTION
        "Parameter 'msg_type' in event DEP.19"
    ::= { depEventObjects19 1 }

dep19_state OBJECT-TYPE
    SYNTAX Integer32
    MAX-ACCESS accessible-for-notify
    STATUS current
    DESCRIPTION
        "Parameter 'state' in event DEP.19"
    ::= { depEventObjects19 2 }

dep19_session OBJECT-TYPE
    SYNTAX Integer32
    MAX-ACCESS accessible-for-notify
    STATUS current
    DESCRIPTION
        "Parameter 'session' in event DEP.19"
    ::= { depEventObjects19 3 }

depEventObjects20 OBJECT-IDENTITY
    STATUS current
    DESCRIPTION
        "Event DEP.20
        Bad Message has been received from POS side."
    ::= { depEventsGroup 20 }

dep20_source OBJECT-TYPE
    SYNTAX DisplayString
    MAX-ACCESS accessible-for-notify
    STATUS current
    DESCRIPTION
        "Parameter 'source' in event DEP.20"
    ::= { depEventObjects20 1 }

dep20_state OBJECT-TYPE
    SYNTAX Integer32
    MAX-ACCESS accessible-for-notify
    STATUS current
    DESCRIPTION
        "Parameter 'state' in event DEP.20"
    ::= { depEventObjects20 2 }

dep20_session OBJECT-TYPE
    SYNTAX Integer32
    MAX-ACCESS accessible-for-notify
    STATUS current
    DESCRIPTION
        "Parameter 'session' in event DEP.20"
    ::= { depEventObjects20 3 }

depEventObjects21 OBJECT-IDENTITY
    STATUS current
    DESCRIPTION
        "Event DEP.21
        A block with parity error has been received from POS."
    ::= { depEventsGroup 21 }

dep21_state OBJECT-TYPE
    SYNTAX Integer32
    MAX-ACCESS accessible-for-notify
    STATUS current
    DESCRIPTION
        "Parameter 'state' in event DEP.21"
    ::= { depEventObjects21 1 }

dep21_session OBJECT-TYPE
    SYNTAX Integer32
    MAX-ACCESS accessible-for-notify
    STATUS current
    DESCRIPTION
        "Parameter 'session' in event DEP.21"
    ::= { depEventObjects21 2 }

depEventObjects22 OBJECT-IDENTITY
    STATUS current
    DESCRIPTION
        "Event DEP.22
        The transaction has been completed successfully."
    ::= { depEventsGroup 22 }

dep22_ip_address OBJECT-TYPE
    SYNTAX IpAddress
    MAX-ACCESS accessible-for-notify
    STATUS current
    DESCRIPTION
        "Parameter 'ip_address' in event DEP.22"
    ::= { depEventObjects22 1 }

dep22_state OBJECT-TYPE
    SYNTAX Integer32
    MAX-ACCESS accessible-for-notify
    STATUS current
    DESCRIPTION
        "Parameter 'state' in event DEP.22"
    ::= { depEventObjects22 2 }

dep22_session OBJECT-TYPE
    SYNTAX Integer32
    MAX-ACCESS accessible-for-notify
    STATUS current
    DESCRIPTION
        "Parameter 'session' in event DEP.22"
    ::= { depEventObjects22 3 }

depEventObjects23 OBJECT-IDENTITY
    STATUS current
    DESCRIPTION
        "Event DEP.23
        The transaction has been wrong against NA %s, IP addr %I."
    ::= { depEventsGroup 23 }

dep23_nua OBJECT-TYPE
    SYNTAX DisplayString
    MAX-ACCESS accessible-for-notify
    STATUS current
    DESCRIPTION
        "Parameter 'nua' in event DEP.23"
    ::= { depEventObjects23 1 }

dep23_ip_host_address OBJECT-TYPE
    SYNTAX IpAddress
    MAX-ACCESS accessible-for-notify
    STATUS current
    DESCRIPTION
        "Parameter 'ip_host_address' in event DEP.23"
    ::= { depEventObjects23 2 }

dep23_cause OBJECT-TYPE
    SYNTAX Integer32
    MAX-ACCESS accessible-for-notify
    STATUS current
    DESCRIPTION
        "Parameter 'cause' in event DEP.23"
    ::= { depEventObjects23 3 }

dep23_state OBJECT-TYPE
    SYNTAX Integer32
    MAX-ACCESS accessible-for-notify
    STATUS current
    DESCRIPTION
        "Parameter 'state' in event DEP.23"
    ::= { depEventObjects23 4 }

dep23_session OBJECT-TYPE
    SYNTAX Integer32
    MAX-ACCESS accessible-for-notify
    STATUS current
    DESCRIPTION
        "Parameter 'session' in event DEP.23"
    ::= { depEventObjects23 5 }

depEventObjects24 OBJECT-IDENTITY
    STATUS current
    DESCRIPTION
        "Event DEP.24
        Trying connection to TCP HOST with regiter NA found."
    ::= { depEventsGroup 24 }

dep24_nua OBJECT-TYPE
    SYNTAX DisplayString
    MAX-ACCESS accessible-for-notify
    STATUS current
    DESCRIPTION
        "Parameter 'nua' in event DEP.24"
    ::= { depEventObjects24 1 }

dep24_ip_host_address OBJECT-TYPE
    SYNTAX IpAddress
    MAX-ACCESS accessible-for-notify
    STATUS current
    DESCRIPTION
        "Parameter 'ip_host_address' in event DEP.24"
    ::= { depEventObjects24 2 }

dep24_port OBJECT-TYPE
    SYNTAX Integer32
    MAX-ACCESS accessible-for-notify
    STATUS current
    DESCRIPTION
        "Parameter 'port' in event DEP.24"
    ::= { depEventObjects24 3 }

dep24_session OBJECT-TYPE
    SYNTAX Integer32
    MAX-ACCESS accessible-for-notify
    STATUS current
    DESCRIPTION
        "Parameter 'session' in event DEP.24"
    ::= { depEventObjects24 4 }

depEventObjects25 OBJECT-IDENTITY
    STATUS current
    DESCRIPTION
        "Event DEP.25
        Host session signed event."
    ::= { depEventsGroup 25 }

dep25_host_type OBJECT-TYPE
    SYNTAX DisplayString
    MAX-ACCESS accessible-for-notify
    STATUS current
    DESCRIPTION
        "Parameter 'host_type' in event DEP.25"
    ::= { depEventObjects25 1 }

dep25_event OBJECT-TYPE
    SYNTAX DisplayString
    MAX-ACCESS accessible-for-notify
    STATUS current
    DESCRIPTION
        "Parameter 'event' in event DEP.25"
    ::= { depEventObjects25 2 }

dep25_state OBJECT-TYPE
    SYNTAX Integer32
    MAX-ACCESS accessible-for-notify
    STATUS current
    DESCRIPTION
        "Parameter 'state' in event DEP.25"
    ::= { depEventObjects25 3 }

dep25_session OBJECT-TYPE
    SYNTAX Integer32
    MAX-ACCESS accessible-for-notify
    STATUS current
    DESCRIPTION
        "Parameter 'session' in event DEP.25"
    ::= { depEventObjects25 4 }

depEventObjects26 OBJECT-IDENTITY
    STATUS current
    DESCRIPTION
        "Event DEP.26
        A TCP Packet has been received from Host."
    ::= { depEventsGroup 26 }

dep26_message_type OBJECT-TYPE
    SYNTAX DisplayString
    MAX-ACCESS accessible-for-notify
    STATUS current
    DESCRIPTION
        "Parameter 'message_type' in event DEP.26"
    ::= { depEventObjects26 1 }

dep26_bytes OBJECT-TYPE
    SYNTAX Integer32
    MAX-ACCESS accessible-for-notify
    STATUS current
    DESCRIPTION
        "Parameter 'bytes' in event DEP.26"
    ::= { depEventObjects26 2 }

dep26_state OBJECT-TYPE
    SYNTAX Integer32
    MAX-ACCESS accessible-for-notify
    STATUS current
    DESCRIPTION
        "Parameter 'state' in event DEP.26"
    ::= { depEventObjects26 3 }

dep26_session OBJECT-TYPE
    SYNTAX Integer32
    MAX-ACCESS accessible-for-notify
    STATUS current
    DESCRIPTION
        "Parameter 'session' in event DEP.26"
    ::= { depEventObjects26 4 }

depEventObjects27 OBJECT-IDENTITY
    STATUS current
    DESCRIPTION
        "Event DEP.27
        Trying to send message to TCP Host"
    ::= { depEventsGroup 27 }

dep27_bytes OBJECT-TYPE
    SYNTAX Integer32
    MAX-ACCESS accessible-for-notify
    STATUS current
    DESCRIPTION
        "Parameter 'bytes' in event DEP.27"
    ::= { depEventObjects27 1 }

dep27_state OBJECT-TYPE
    SYNTAX Integer32
    MAX-ACCESS accessible-for-notify
    STATUS current
    DESCRIPTION
        "Parameter 'state' in event DEP.27"
    ::= { depEventObjects27 2 }

dep27_session OBJECT-TYPE
    SYNTAX Integer32
    MAX-ACCESS accessible-for-notify
    STATUS current
    DESCRIPTION
        "Parameter 'session' in event DEP.27"
    ::= { depEventObjects27 3 }

depEventObjects28 OBJECT-IDENTITY
    STATUS current
    DESCRIPTION
        "Event DEP.28
        Trying connection to X25 HOST."
    ::= { depEventsGroup 28 }

dep28_nua OBJECT-TYPE
    SYNTAX DisplayString
    MAX-ACCESS accessible-for-notify
    STATUS current
    DESCRIPTION
        "Parameter 'nua' in event DEP.28"
    ::= { depEventObjects28 1 }

dep28_session OBJECT-TYPE
    SYNTAX Integer32
    MAX-ACCESS accessible-for-notify
    STATUS current
    DESCRIPTION
        "Parameter 'session' in event DEP.28"
    ::= { depEventObjects28 2 }

depEventObjects29 OBJECT-IDENTITY
    STATUS current
    DESCRIPTION
        "Event DEP.29
        X25 Warning indication."
    ::= { depEventsGroup 29 }

dep29_indication OBJECT-TYPE
    SYNTAX DisplayString
    MAX-ACCESS accessible-for-notify
    STATUS current
    DESCRIPTION
        "Parameter 'indication' in event DEP.29"
    ::= { depEventObjects29 1 }

dep29_state OBJECT-TYPE
    SYNTAX Integer32
    MAX-ACCESS accessible-for-notify
    STATUS current
    DESCRIPTION
        "Parameter 'state' in event DEP.29"
    ::= { depEventObjects29 2 }

dep29_session OBJECT-TYPE
    SYNTAX Integer32
    MAX-ACCESS accessible-for-notify
    STATUS current
    DESCRIPTION
        "Parameter 'session' in event DEP.29"
    ::= { depEventObjects29 3 }

depEventObjects30 OBJECT-IDENTITY
    STATUS current
    DESCRIPTION
        "Event DEP.30
        Generic Warning indication."
    ::= { depEventsGroup 30 }

dep30_indication OBJECT-TYPE
    SYNTAX DisplayString
    MAX-ACCESS accessible-for-notify
    STATUS current
    DESCRIPTION
        "Parameter 'indication' in event DEP.30"
    ::= { depEventObjects30 1 }

dep30_state OBJECT-TYPE
    SYNTAX Integer32
    MAX-ACCESS accessible-for-notify
    STATUS current
    DESCRIPTION
        "Parameter 'state' in event DEP.30"
    ::= { depEventObjects30 2 }

dep30_session OBJECT-TYPE
    SYNTAX Integer32
    MAX-ACCESS accessible-for-notify
    STATUS current
    DESCRIPTION
        "Parameter 'session' in event DEP.30"
    ::= { depEventObjects30 3 }


depNotification1 NOTIFICATION-TYPE
    OBJECTS { 
              dep1_ip_address, 
              dep1_session,
              dep1_index 
            }
    STATUS current
    DESCRIPTION
        "Notification of Event DEP.1

        Message: 'Rx TST packet from $1 address. Create new SES: $2 with Hash Index: $3'

        Parameters list:
              $1: dep1_ip_address
              $2: dep1_session
              $3: dep1_index

        A Test packet has been received."
    ::= { depNotificationsPrefix 1 }

depNotification2 NOTIFICATION-TYPE
    OBJECTS { 
              dep2_nri, 
              dep2_ip_address,
              dep2_state,
              dep2_session 
            }
    STATUS current
    DESCRIPTION
        "Notification of Event DEP.2

        Message: 'Rx S Message with NRI:$1 from $2 address in state $3, ses: $4'

        Parameters list:
              $1: dep2_nri
              $2: dep2_ip_address
              $3: dep2_state
              $4: dep2_session

        An S Message has been received."
    ::= { depNotificationsPrefix 2 }

depNotification3 NOTIFICATION-TYPE
    OBJECTS { 
              dep3_ip_address, 
              dep3_state,
              dep3_session 
            }
    STATUS current
    DESCRIPTION
        "Notification of Event DEP.3

        Message: 'Tx Accept Message to $1 address in state $2, ses: $3'

        Parameters list:
              $1: dep3_ip_address
              $2: dep3_state
              $3: dep3_session

        An A Message has been transmitted."
    ::= { depNotificationsPrefix 3 }

depNotification4 NOTIFICATION-TYPE
    OBJECTS { 
              dep4_type_msg, 
              dep4_ip_address,
              dep4_state,
              dep4_session 
            }
    STATUS current
    DESCRIPTION
        "Notification of Event DEP.4

        Message: 'Rx $1 Message from $2 address in state $3, ses: $4'

        Parameters list:
              $1: dep4_type_msg
              $2: dep4_ip_address
              $3: dep4_state
              $4: dep4_session

        A Data Message has been received."
    ::= { depNotificationsPrefix 4 }

depNotification5 NOTIFICATION-TYPE
    OBJECTS { 
              dep5_type_msg, 
              dep5_ip_address,
              dep5_state,
              dep5_session 
            }
    STATUS current
    DESCRIPTION
        "Notification of Event DEP.5

        Message: 'Tx $1 Message to $2 address in state $3, ses: $4'

        Parameters list:
              $1: dep5_type_msg
              $2: dep5_ip_address
              $3: dep5_state
              $4: dep5_session

        A Data Message has been transmitted."
    ::= { depNotificationsPrefix 5 }

depNotification6 NOTIFICATION-TYPE
    OBJECTS { 
              dep6_ip_address, 
              dep6_state,
              dep6_session 
            }
    STATUS current
    DESCRIPTION
        "Notification of Event DEP.6

        Message: 'Rx Release from $1 address in state $2, ses: $3'

        Parameters list:
              $1: dep6_ip_address
              $2: dep6_state
              $3: dep6_session

        A Release Message has been received."
    ::= { depNotificationsPrefix 6 }

depNotification7 NOTIFICATION-TYPE
    OBJECTS { 
              dep7_ip_address, 
              dep7_state,
              dep7_session 
            }
    STATUS current
    DESCRIPTION
        "Notification of Event DEP.7

        Message: 'Tx Release to $1 address in state $2, ses: $3'

        Parameters list:
              $1: dep7_ip_address
              $2: dep7_state
              $3: dep7_session

        A Release Message has been transmitted."
    ::= { depNotificationsPrefix 7 }

depNotification8 NOTIFICATION-TYPE
    OBJECTS { 
              dep8_ip_address, 
              dep8_state,
              dep8_session 
            }
    STATUS current
    DESCRIPTION
        "Notification of Event DEP.8

        Message: 'Rx EOT from $1 address in state $2, ses: $3. Session closed'

        Parameters list:
              $1: dep8_ip_address
              $2: dep8_state
              $3: dep8_session

        An EOT packet has been received."
    ::= { depNotificationsPrefix 8 }

depNotification9 NOTIFICATION-TYPE
    OBJECTS { 
              dep9_state, 
              dep9_session 
            }
    STATUS current
    DESCRIPTION
        "Notification of Event DEP.9

        Message: 'Rx T4 Ind in state $1, ses: $2. Session closed abnormally'

        Parameters list:
              $1: dep9_state
              $2: dep9_session

        A T4 Indication has been received."
    ::= { depNotificationsPrefix 9 }

depNotification10 NOTIFICATION-TYPE
    STATUS current
    DESCRIPTION
        "Notification of Event DEP.10

        Message: 'Error: Handler couldn't be created'

        Handler couldn't be created."
    ::= { depNotificationsPrefix 10 }

depNotification11 NOTIFICATION-TYPE
    OBJECTS { 
              dep11_ip_address, 
              dep11_session,
              dep11_index 
            }
    STATUS current
    DESCRIPTION
        "Notification of Event DEP.11

        Message: 'HOST $1 has opened the $2 TCP session with Hash Index: $3'

        Parameters list:
              $1: dep11_ip_address
              $2: dep11_session
              $3: dep11_index

        The TCP session has been opened by the remote HOST."
    ::= { depNotificationsPrefix 11 }

depNotification12 NOTIFICATION-TYPE
    OBJECTS { 
              dep12_state, 
              dep12_session 
            }
    STATUS current
    DESCRIPTION
        "Notification of Event DEP.12

        Message: 'The TCP session has been closed. State $1, ses $2'

        Parameters list:
              $1: dep12_state
              $2: dep12_session

        The TCP session has been closed."
    ::= { depNotificationsPrefix 12 }

depNotification13 NOTIFICATION-TYPE
    OBJECTS { 
              dep13_state, 
              dep13_session 
            }
    STATUS current
    DESCRIPTION
        "Notification of Event DEP.13

        Message: 'The TCP session has been closed by the remote HOST. State $1, ses $2'

        Parameters list:
              $1: dep13_state
              $2: dep13_session

        The TCP session has been closed by the remote HOST."
    ::= { depNotificationsPrefix 13 }

depNotification14 NOTIFICATION-TYPE
    OBJECTS { 
              dep14_access_type 
            }
    STATUS current
    DESCRIPTION
        "Notification of Event DEP.14

        Message: 'WARNING: The max number of $1 sessions has been reached'

        Parameters list:
              $1: dep14_access_type

        The max number of TCP sessions has been reached."
    ::= { depNotificationsPrefix 14 }

depNotification15 NOTIFICATION-TYPE
    OBJECTS { 
              dep15_type, 
              dep15_session,
              dep15_state 
            }
    STATUS current
    DESCRIPTION
        "Notification of Event DEP.15

        Message: 'X25 event received $1, ses: $2, state:$3'

        Parameters list:
              $1: dep15_type
              $2: dep15_session
              $3: dep15_state

        A X25 event has been received."
    ::= { depNotificationsPrefix 15 }

depNotification16 NOTIFICATION-TYPE
    OBJECTS { 
              dep16_msg_type, 
              dep16_msg_leng,
              dep16_state,
              dep16_session 
            }
    STATUS current
    DESCRIPTION
        "Notification of Event DEP.16

        Message: 'Rx $1 Message from POS, $2 Rx Bytes, in state $3, ses: $4'

        Parameters list:
              $1: dep16_msg_type
              $2: dep16_msg_leng
              $3: dep16_state
              $4: dep16_session

        A Data Message has been received from POS."
    ::= { depNotificationsPrefix 16 }

depNotification17 NOTIFICATION-TYPE
    OBJECTS { 
              dep17_msg_type, 
              dep17_msg_leng,
              dep17_state,
              dep17_session 
            }
    STATUS current
    DESCRIPTION
        "Notification of Event DEP.17

        Message: 'Tx $1 Message to POS, $2 Tx Bytes, in state $3, ses: $4'

        Parameters list:
              $1: dep17_msg_type
              $2: dep17_msg_leng
              $3: dep17_state
              $4: dep17_session

        A Data Message has been transmitted to POS."
    ::= { depNotificationsPrefix 17 }

depNotification18 NOTIFICATION-TYPE
    OBJECTS { 
              dep18_msg_type, 
              dep18_state,
              dep18_session 
            }
    STATUS current
    DESCRIPTION
        "Notification of Event DEP.18

        Message: 'Rx $1 character from POS, in state $2, ses: $3'

        Parameters list:
              $1: dep18_msg_type
              $2: dep18_state
              $3: dep18_session

        A control character has been received from POS."
    ::= { depNotificationsPrefix 18 }

depNotification19 NOTIFICATION-TYPE
    OBJECTS { 
              dep19_msg_type, 
              dep19_state,
              dep19_session 
            }
    STATUS current
    DESCRIPTION
        "Notification of Event DEP.19

        Message: 'Tx $1 Control character to POS, in state $2, ses: $3'

        Parameters list:
              $1: dep19_msg_type
              $2: dep19_state
              $3: dep19_session

        A control character has been transmitted to POS."
    ::= { depNotificationsPrefix 19 }

depNotification20 NOTIFICATION-TYPE
    OBJECTS { 
              dep20_source, 
              dep20_state,
              dep20_session 
            }
    STATUS current
    DESCRIPTION
        "Notification of Event DEP.20

        Message: 'Rx Bad Message from $1, in state $2, ses: $3'

        Parameters list:
              $1: dep20_source
              $2: dep20_state
              $3: dep20_session

        Bad Message has been received from POS side."
    ::= { depNotificationsPrefix 20 }

depNotification21 NOTIFICATION-TYPE
    OBJECTS { 
              dep21_state, 
              dep21_session 
            }
    STATUS current
    DESCRIPTION
        "Notification of Event DEP.21

        Message: 'A block with LRC/CRC error has been received from POS, State: $1 ses: $2'

        Parameters list:
              $1: dep21_state
              $2: dep21_session

        A block with parity error has been received from POS."
    ::= { depNotificationsPrefix 21 }

depNotification22 NOTIFICATION-TYPE
    OBJECTS { 
              dep22_ip_address, 
              dep22_state,
              dep22_session 
            }
    STATUS current
    DESCRIPTION
        "Notification of Event DEP.22

        Message: 'The transaction has been completed successfully. $1 IP address in state $2, ses: $3'

        Parameters list:
              $1: dep22_ip_address
              $2: dep22_state
              $3: dep22_session

        The transaction has been completed successfully."
    ::= { depNotificationsPrefix 22 }

depNotification23 NOTIFICATION-TYPE
    OBJECTS { 
              dep23_nua, 
              dep23_ip_host_address,
              dep23_cause,
              dep23_state,
              dep23_session 
            }
    STATUS current
    DESCRIPTION
        "Notification of Event DEP.23

        Message: 'The transaction has been wrong, against NA $1, IP $2, Cause $3, State: $4, ses: $5'

        Parameters list:
              $1: dep23_nua
              $2: dep23_ip_host_address
              $3: dep23_cause
              $4: dep23_state
              $5: dep23_session

        The transaction has been wrong against NA %s, IP addr %I."
    ::= { depNotificationsPrefix 23 }

depNotification24 NOTIFICATION-TYPE
    OBJECTS { 
              dep24_nua, 
              dep24_ip_host_address,
              dep24_port,
              dep24_session 
            }
    STATUS current
    DESCRIPTION
        "Notification of Event DEP.24

        Message: 'Trying connection to TCP HOST with reg. NA $1 in IP addr. $2, port $3, ses. $4'

        Parameters list:
              $1: dep24_nua
              $2: dep24_ip_host_address
              $3: dep24_port
              $4: dep24_session

        Trying connection to TCP HOST with regiter NA found."
    ::= { depNotificationsPrefix 24 }

depNotification25 NOTIFICATION-TYPE
    OBJECTS { 
              dep25_host_type, 
              dep25_event,
              dep25_state,
              dep25_session 
            }
    STATUS current
    DESCRIPTION
        "Notification of Event DEP.25

        Message: '$1 type Host session $2. State $3, Session $4'

        Parameters list:
              $1: dep25_host_type
              $2: dep25_event
              $3: dep25_state
              $4: dep25_session

        Host session signed event."
    ::= { depNotificationsPrefix 25 }

depNotification26 NOTIFICATION-TYPE
    OBJECTS { 
              dep26_message_type, 
              dep26_bytes,
              dep26_state,
              dep26_session 
            }
    STATUS current
    DESCRIPTION
        "Notification of Event DEP.26

        Message: 'A TCP Packet of $1 type has been received from Host,$2 bytes. State $3, Session $4'

        Parameters list:
              $1: dep26_message_type
              $2: dep26_bytes
              $3: dep26_state
              $4: dep26_session

        A TCP Packet has been received from Host."
    ::= { depNotificationsPrefix 26 }

depNotification27 NOTIFICATION-TYPE
    OBJECTS { 
              dep27_bytes, 
              dep27_state,
              dep27_session 
            }
    STATUS current
    DESCRIPTION
        "Notification of Event DEP.27

        Message: 'Trying to send packet to TCP Host with $1 bytes.State $2, Session $3'

        Parameters list:
              $1: dep27_bytes
              $2: dep27_state
              $3: dep27_session

        Trying to send message to TCP Host"
    ::= { depNotificationsPrefix 27 }

depNotification28 NOTIFICATION-TYPE
    OBJECTS { 
              dep28_nua, 
              dep28_session 
            }
    STATUS current
    DESCRIPTION
        "Notification of Event DEP.28

        Message: 'Trying connection to X25 HOST, with NA $1, ses. $2'

        Parameters list:
              $1: dep28_nua
              $2: dep28_session

        Trying connection to X25 HOST."
    ::= { depNotificationsPrefix 28 }

depNotification29 NOTIFICATION-TYPE
    OBJECTS { 
              dep29_indication, 
              dep29_state,
              dep29_session 
            }
    STATUS current
    DESCRIPTION
        "Notification of Event DEP.29

        Message: 'X25 Warning indication: $1. State $2, Session $3'

        Parameters list:
              $1: dep29_indication
              $2: dep29_state
              $3: dep29_session

        X25 Warning indication."
    ::= { depNotificationsPrefix 29 }

depNotification30 NOTIFICATION-TYPE
    OBJECTS { 
              dep30_indication, 
              dep30_state,
              dep30_session 
            }
    STATUS current
    DESCRIPTION
        "Notification of Event DEP.30

        Message: 'Warning indication: $1. State $2, Session $3'

        Parameters list:
              $1: dep30_indication
              $2: dep30_state
              $3: dep30_session

        Generic Warning indication."
    ::= { depNotificationsPrefix 30 }


END
