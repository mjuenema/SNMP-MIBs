-- file automatically created


TELDAT-TRAP-X252-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


x252TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the X252 event subsystem."
    REVISION "201401200930Z"
    DESCRIPTION "Initial implementation"
        ::= { telEventTraps 97 }


x252EventsGroup	OBJECT IDENTIFIER	::= { x252TrapsMIB 1 }

x252Notifications	OBJECT IDENTIFIER	::= { x252TrapsMIB 2 }
x252NotificationsPrefix	OBJECT IDENTIFIER	::= { x252Notifications 0 }

x252EventObjects1 OBJECT-IDENTITY
    STATUS current
    DESCRIPTION
        "Event X252.1
        Unnumbered control frame transmitted."
    ::= { x252EventsGroup 1 }

x2521_address OBJECT-TYPE
    SYNTAX Integer32
    MAX-ACCESS accessible-for-notify
    STATUS current
    DESCRIPTION
        "Parameter 'address' in event X252.1"
    ::= { x252EventObjects1 1 }

x2521_frame OBJECT-TYPE
    SYNTAX DisplayString
    MAX-ACCESS accessible-for-notify
    STATUS current
    DESCRIPTION
        "Parameter 'frame' in event X252.1"
    ::= { x252EventObjects1 2 }

x2521_bit_pf OBJECT-TYPE
    SYNTAX Integer32
    MAX-ACCESS accessible-for-notify
    STATUS current
    DESCRIPTION
        "Parameter 'bit_pf' in event X252.1"
    ::= { x252EventObjects1 3 }

x2521_port OBJECT-TYPE
    SYNTAX DisplayString
    MAX-ACCESS accessible-for-notify
    STATUS current
    DESCRIPTION
        "Parameter 'port' in event X252.1"
    ::= { x252EventObjects1 4 }

x252EventObjects2 OBJECT-IDENTITY
    STATUS current
    DESCRIPTION
        "Event X252.2
        Supervisory frame RR transmitted."
    ::= { x252EventsGroup 2 }

x2522_address OBJECT-TYPE
    SYNTAX Integer32
    MAX-ACCESS accessible-for-notify
    STATUS current
    DESCRIPTION
        "Parameter 'address' in event X252.2"
    ::= { x252EventObjects2 1 }

x2522_frame OBJECT-TYPE
    SYNTAX DisplayString
    MAX-ACCESS accessible-for-notify
    STATUS current
    DESCRIPTION
        "Parameter 'frame' in event X252.2"
    ::= { x252EventObjects2 2 }

x2522_bit_pf OBJECT-TYPE
    SYNTAX Integer32
    MAX-ACCESS accessible-for-notify
    STATUS current
    DESCRIPTION
        "Parameter 'bit_pf' in event X252.2"
    ::= { x252EventObjects2 3 }

x2522_nr OBJECT-TYPE
    SYNTAX Integer32
    MAX-ACCESS accessible-for-notify
    STATUS current
    DESCRIPTION
        "Parameter 'nr' in event X252.2"
    ::= { x252EventObjects2 4 }

x2522_port OBJECT-TYPE
    SYNTAX DisplayString
    MAX-ACCESS accessible-for-notify
    STATUS current
    DESCRIPTION
        "Parameter 'port' in event X252.2"
    ::= { x252EventObjects2 5 }

x252EventObjects3 OBJECT-IDENTITY
    STATUS current
    DESCRIPTION
        "Event X252.3
        Supervisory frame RNR or REJ transmitted."
    ::= { x252EventsGroup 3 }

x2523_address OBJECT-TYPE
    SYNTAX Integer32
    MAX-ACCESS accessible-for-notify
    STATUS current
    DESCRIPTION
        "Parameter 'address' in event X252.3"
    ::= { x252EventObjects3 1 }

x2523_frame OBJECT-TYPE
    SYNTAX DisplayString
    MAX-ACCESS accessible-for-notify
    STATUS current
    DESCRIPTION
        "Parameter 'frame' in event X252.3"
    ::= { x252EventObjects3 2 }

x2523_bit_pf OBJECT-TYPE
    SYNTAX Integer32
    MAX-ACCESS accessible-for-notify
    STATUS current
    DESCRIPTION
        "Parameter 'bit_pf' in event X252.3"
    ::= { x252EventObjects3 3 }

x2523_nr OBJECT-TYPE
    SYNTAX Integer32
    MAX-ACCESS accessible-for-notify
    STATUS current
    DESCRIPTION
        "Parameter 'nr' in event X252.3"
    ::= { x252EventObjects3 4 }

x2523_port OBJECT-TYPE
    SYNTAX DisplayString
    MAX-ACCESS accessible-for-notify
    STATUS current
    DESCRIPTION
        "Parameter 'port' in event X252.3"
    ::= { x252EventObjects3 5 }

x252EventObjects4 OBJECT-IDENTITY
    STATUS current
    DESCRIPTION
        "Event X252.4
        Information frame transmitted."
    ::= { x252EventsGroup 4 }

x2524_address OBJECT-TYPE
    SYNTAX Integer32
    MAX-ACCESS accessible-for-notify
    STATUS current
    DESCRIPTION
        "Parameter 'address' in event X252.4"
    ::= { x252EventObjects4 1 }

x2524_frame OBJECT-TYPE
    SYNTAX DisplayString
    MAX-ACCESS accessible-for-notify
    STATUS current
    DESCRIPTION
        "Parameter 'frame' in event X252.4"
    ::= { x252EventObjects4 2 }

x2524_bit_pf OBJECT-TYPE
    SYNTAX Integer32
    MAX-ACCESS accessible-for-notify
    STATUS current
    DESCRIPTION
        "Parameter 'bit_pf' in event X252.4"
    ::= { x252EventObjects4 3 }

x2524_ns OBJECT-TYPE
    SYNTAX Integer32
    MAX-ACCESS accessible-for-notify
    STATUS current
    DESCRIPTION
        "Parameter 'ns' in event X252.4"
    ::= { x252EventObjects4 4 }

x2524_nr OBJECT-TYPE
    SYNTAX Integer32
    MAX-ACCESS accessible-for-notify
    STATUS current
    DESCRIPTION
        "Parameter 'nr' in event X252.4"
    ::= { x252EventObjects4 5 }

x2524_port OBJECT-TYPE
    SYNTAX DisplayString
    MAX-ACCESS accessible-for-notify
    STATUS current
    DESCRIPTION
        "Parameter 'port' in event X252.4"
    ::= { x252EventObjects4 6 }

x252EventObjects5 OBJECT-IDENTITY
    STATUS current
    DESCRIPTION
        "Event X252.5
        Unnumbered control frame received."
    ::= { x252EventsGroup 5 }

x2525_address OBJECT-TYPE
    SYNTAX Integer32
    MAX-ACCESS accessible-for-notify
    STATUS current
    DESCRIPTION
        "Parameter 'address' in event X252.5"
    ::= { x252EventObjects5 1 }

x2525_frame OBJECT-TYPE
    SYNTAX DisplayString
    MAX-ACCESS accessible-for-notify
    STATUS current
    DESCRIPTION
        "Parameter 'frame' in event X252.5"
    ::= { x252EventObjects5 2 }

x2525_bit_pf OBJECT-TYPE
    SYNTAX Integer32
    MAX-ACCESS accessible-for-notify
    STATUS current
    DESCRIPTION
        "Parameter 'bit_pf' in event X252.5"
    ::= { x252EventObjects5 3 }

x2525_port OBJECT-TYPE
    SYNTAX DisplayString
    MAX-ACCESS accessible-for-notify
    STATUS current
    DESCRIPTION
        "Parameter 'port' in event X252.5"
    ::= { x252EventObjects5 4 }

x252EventObjects6 OBJECT-IDENTITY
    STATUS current
    DESCRIPTION
        "Event X252.6
        Supervisory frame RR received."
    ::= { x252EventsGroup 6 }

x2526_address OBJECT-TYPE
    SYNTAX Integer32
    MAX-ACCESS accessible-for-notify
    STATUS current
    DESCRIPTION
        "Parameter 'address' in event X252.6"
    ::= { x252EventObjects6 1 }

x2526_frame OBJECT-TYPE
    SYNTAX DisplayString
    MAX-ACCESS accessible-for-notify
    STATUS current
    DESCRIPTION
        "Parameter 'frame' in event X252.6"
    ::= { x252EventObjects6 2 }

x2526_bit_pf OBJECT-TYPE
    SYNTAX Integer32
    MAX-ACCESS accessible-for-notify
    STATUS current
    DESCRIPTION
        "Parameter 'bit_pf' in event X252.6"
    ::= { x252EventObjects6 3 }

x2526_nr OBJECT-TYPE
    SYNTAX Integer32
    MAX-ACCESS accessible-for-notify
    STATUS current
    DESCRIPTION
        "Parameter 'nr' in event X252.6"
    ::= { x252EventObjects6 4 }

x2526_port OBJECT-TYPE
    SYNTAX DisplayString
    MAX-ACCESS accessible-for-notify
    STATUS current
    DESCRIPTION
        "Parameter 'port' in event X252.6"
    ::= { x252EventObjects6 5 }

x252EventObjects7 OBJECT-IDENTITY
    STATUS current
    DESCRIPTION
        "Event X252.7
        Supervisory frame RNR or REJ received."
    ::= { x252EventsGroup 7 }

x2527_address OBJECT-TYPE
    SYNTAX Integer32
    MAX-ACCESS accessible-for-notify
    STATUS current
    DESCRIPTION
        "Parameter 'address' in event X252.7"
    ::= { x252EventObjects7 1 }

x2527_frame OBJECT-TYPE
    SYNTAX DisplayString
    MAX-ACCESS accessible-for-notify
    STATUS current
    DESCRIPTION
        "Parameter 'frame' in event X252.7"
    ::= { x252EventObjects7 2 }

x2527_bit_pf OBJECT-TYPE
    SYNTAX Integer32
    MAX-ACCESS accessible-for-notify
    STATUS current
    DESCRIPTION
        "Parameter 'bit_pf' in event X252.7"
    ::= { x252EventObjects7 3 }

x2527_nr OBJECT-TYPE
    SYNTAX Integer32
    MAX-ACCESS accessible-for-notify
    STATUS current
    DESCRIPTION
        "Parameter 'nr' in event X252.7"
    ::= { x252EventObjects7 4 }

x2527_port OBJECT-TYPE
    SYNTAX DisplayString
    MAX-ACCESS accessible-for-notify
    STATUS current
    DESCRIPTION
        "Parameter 'port' in event X252.7"
    ::= { x252EventObjects7 5 }

x252EventObjects8 OBJECT-IDENTITY
    STATUS current
    DESCRIPTION
        "Event X252.8
        Information frame received."
    ::= { x252EventsGroup 8 }

x2528_address OBJECT-TYPE
    SYNTAX Integer32
    MAX-ACCESS accessible-for-notify
    STATUS current
    DESCRIPTION
        "Parameter 'address' in event X252.8"
    ::= { x252EventObjects8 1 }

x2528_frame OBJECT-TYPE
    SYNTAX DisplayString
    MAX-ACCESS accessible-for-notify
    STATUS current
    DESCRIPTION
        "Parameter 'frame' in event X252.8"
    ::= { x252EventObjects8 2 }

x2528_bit_pf OBJECT-TYPE
    SYNTAX Integer32
    MAX-ACCESS accessible-for-notify
    STATUS current
    DESCRIPTION
        "Parameter 'bit_pf' in event X252.8"
    ::= { x252EventObjects8 3 }

x2528_ns OBJECT-TYPE
    SYNTAX Integer32
    MAX-ACCESS accessible-for-notify
    STATUS current
    DESCRIPTION
        "Parameter 'ns' in event X252.8"
    ::= { x252EventObjects8 4 }

x2528_nr OBJECT-TYPE
    SYNTAX Integer32
    MAX-ACCESS accessible-for-notify
    STATUS current
    DESCRIPTION
        "Parameter 'nr' in event X252.8"
    ::= { x252EventObjects8 5 }

x2528_port OBJECT-TYPE
    SYNTAX DisplayString
    MAX-ACCESS accessible-for-notify
    STATUS current
    DESCRIPTION
        "Parameter 'port' in event X252.8"
    ::= { x252EventObjects8 6 }

x252EventObjects9 OBJECT-IDENTITY
    STATUS current
    DESCRIPTION
        "Event X252.9
        N2 Counter runout."
    ::= { x252EventsGroup 9 }

x2529_port OBJECT-TYPE
    SYNTAX DisplayString
    MAX-ACCESS accessible-for-notify
    STATUS current
    DESCRIPTION
        "Parameter 'port' in event X252.9"
    ::= { x252EventObjects9 1 }

x252EventObjects10 OBJECT-IDENTITY
    STATUS current
    DESCRIPTION
        "Event X252.10
        Information or RR frame received with n(R) error."
    ::= { x252EventsGroup 10 }

x25210_port OBJECT-TYPE
    SYNTAX DisplayString
    MAX-ACCESS accessible-for-notify
    STATUS current
    DESCRIPTION
        "Parameter 'port' in event X252.10"
    ::= { x252EventObjects10 1 }

x252EventObjects11 OBJECT-IDENTITY
    STATUS current
    DESCRIPTION
        "Event X252.11
        FRMR frame received."
    ::= { x252EventsGroup 11 }

x25211_cause OBJECT-TYPE
    SYNTAX Integer32
    MAX-ACCESS accessible-for-notify
    STATUS current
    DESCRIPTION
        "Parameter 'cause' in event X252.11"
    ::= { x252EventObjects11 1 }

x25211_control OBJECT-TYPE
    SYNTAX Integer32
    MAX-ACCESS accessible-for-notify
    STATUS current
    DESCRIPTION
        "Parameter 'control' in event X252.11"
    ::= { x252EventObjects11 2 }

x25211_vs OBJECT-TYPE
    SYNTAX Integer32
    MAX-ACCESS accessible-for-notify
    STATUS current
    DESCRIPTION
        "Parameter 'vs' in event X252.11"
    ::= { x252EventObjects11 3 }

x25211_vr OBJECT-TYPE
    SYNTAX Integer32
    MAX-ACCESS accessible-for-notify
    STATUS current
    DESCRIPTION
        "Parameter 'vr' in event X252.11"
    ::= { x252EventObjects11 4 }

x25211_port OBJECT-TYPE
    SYNTAX DisplayString
    MAX-ACCESS accessible-for-notify
    STATUS current
    DESCRIPTION
        "Parameter 'port' in event X252.11"
    ::= { x252EventObjects11 5 }

x252EventObjects12 OBJECT-IDENTITY
    STATUS current
    DESCRIPTION
        "Event X252.12
        Frame received with undefined or unplemented control field."
    ::= { x252EventsGroup 12 }

x25212_port OBJECT-TYPE
    SYNTAX DisplayString
    MAX-ACCESS accessible-for-notify
    STATUS current
    DESCRIPTION
        "Parameter 'port' in event X252.12"
    ::= { x252EventObjects12 1 }

x252EventObjects13 OBJECT-IDENTITY
    STATUS current
    DESCRIPTION
        "Event X252.13
        Frame received with not permitted information field."
    ::= { x252EventsGroup 13 }

x25213_port OBJECT-TYPE
    SYNTAX DisplayString
    MAX-ACCESS accessible-for-notify
    STATUS current
    DESCRIPTION
        "Parameter 'port' in event X252.13"
    ::= { x252EventObjects13 1 }

x252EventObjects14 OBJECT-IDENTITY
    STATUS current
    DESCRIPTION
        "Event X252.14
        Frame received with wrong size."
    ::= { x252EventsGroup 14 }

x25214_port OBJECT-TYPE
    SYNTAX DisplayString
    MAX-ACCESS accessible-for-notify
    STATUS current
    DESCRIPTION
        "Parameter 'port' in event X252.14"
    ::= { x252EventObjects14 1 }

x252EventObjects15 OBJECT-IDENTITY
    STATUS current
    DESCRIPTION
        "Event X252.15
        Information frame received with N1 error."
    ::= { x252EventsGroup 15 }

x25215_port OBJECT-TYPE
    SYNTAX DisplayString
    MAX-ACCESS accessible-for-notify
    STATUS current
    DESCRIPTION
        "Parameter 'port' in event X252.15"
    ::= { x252EventObjects15 1 }

x252EventObjects16 OBJECT-IDENTITY
    STATUS current
    DESCRIPTION
        "Event X252.16
        Information frame received with N(S) error."
    ::= { x252EventsGroup 16 }

x25216_port OBJECT-TYPE
    SYNTAX DisplayString
    MAX-ACCESS accessible-for-notify
    STATUS current
    DESCRIPTION
        "Parameter 'port' in event X252.16"
    ::= { x252EventObjects16 1 }

x252EventObjects17 OBJECT-IDENTITY
    STATUS current
    DESCRIPTION
        "Event X252.17
        Frame received with unexpected P/F bit."
    ::= { x252EventsGroup 17 }

x25217_port OBJECT-TYPE
    SYNTAX DisplayString
    MAX-ACCESS accessible-for-notify
    STATUS current
    DESCRIPTION
        "Parameter 'port' in event X252.17"
    ::= { x252EventObjects17 1 }

x252EventObjects18 OBJECT-IDENTITY
    STATUS current
    DESCRIPTION
        "Event X252.18
        Frame received without lapb header."
    ::= { x252EventsGroup 18 }

x25218_port OBJECT-TYPE
    SYNTAX DisplayString
    MAX-ACCESS accessible-for-notify
    STATUS current
    DESCRIPTION
        "Parameter 'port' in event X252.18"
    ::= { x252EventObjects18 1 }

x252EventObjects19 OBJECT-IDENTITY
    STATUS current
    DESCRIPTION
        "Event X252.19
        FRMR frame module 8 transmitted."
    ::= { x252EventsGroup 19 }

x25219_cause OBJECT-TYPE
    SYNTAX Integer32
    MAX-ACCESS accessible-for-notify
    STATUS current
    DESCRIPTION
        "Parameter 'cause' in event X252.19"
    ::= { x252EventObjects19 1 }

x25219_control OBJECT-TYPE
    SYNTAX Integer32
    MAX-ACCESS accessible-for-notify
    STATUS current
    DESCRIPTION
        "Parameter 'control' in event X252.19"
    ::= { x252EventObjects19 2 }

x25219_vr OBJECT-TYPE
    SYNTAX Integer32
    MAX-ACCESS accessible-for-notify
    STATUS current
    DESCRIPTION
        "Parameter 'vr' in event X252.19"
    ::= { x252EventObjects19 3 }

x25219_vs OBJECT-TYPE
    SYNTAX Integer32
    MAX-ACCESS accessible-for-notify
    STATUS current
    DESCRIPTION
        "Parameter 'vs' in event X252.19"
    ::= { x252EventObjects19 4 }

x25219_port OBJECT-TYPE
    SYNTAX DisplayString
    MAX-ACCESS accessible-for-notify
    STATUS current
    DESCRIPTION
        "Parameter 'port' in event X252.19"
    ::= { x252EventObjects19 5 }

x252EventObjects20 OBJECT-IDENTITY
    STATUS current
    DESCRIPTION
        "Event X252.20
        FRMR frame module 128 transmitted."
    ::= { x252EventsGroup 20 }

x25220_cause OBJECT-TYPE
    SYNTAX Integer32
    MAX-ACCESS accessible-for-notify
    STATUS current
    DESCRIPTION
        "Parameter 'cause' in event X252.20"
    ::= { x252EventObjects20 1 }

x25220_control OBJECT-TYPE
    SYNTAX Integer32
    MAX-ACCESS accessible-for-notify
    STATUS current
    DESCRIPTION
        "Parameter 'control' in event X252.20"
    ::= { x252EventObjects20 2 }

x25220_vr OBJECT-TYPE
    SYNTAX Integer32
    MAX-ACCESS accessible-for-notify
    STATUS current
    DESCRIPTION
        "Parameter 'vr' in event X252.20"
    ::= { x252EventObjects20 3 }

x25220_vs OBJECT-TYPE
    SYNTAX Integer32
    MAX-ACCESS accessible-for-notify
    STATUS current
    DESCRIPTION
        "Parameter 'vs' in event X252.20"
    ::= { x252EventObjects20 4 }

x25220_port OBJECT-TYPE
    SYNTAX DisplayString
    MAX-ACCESS accessible-for-notify
    STATUS current
    DESCRIPTION
        "Parameter 'port' in event X252.20"
    ::= { x252EventObjects20 5 }

x252EventObjects21 OBJECT-IDENTITY
    STATUS current
    DESCRIPTION
        "Event X252.21
        FRMR frame module 8 received."
    ::= { x252EventsGroup 21 }

x25221_cause OBJECT-TYPE
    SYNTAX Integer32
    MAX-ACCESS accessible-for-notify
    STATUS current
    DESCRIPTION
        "Parameter 'cause' in event X252.21"
    ::= { x252EventObjects21 1 }

x25221_control OBJECT-TYPE
    SYNTAX Integer32
    MAX-ACCESS accessible-for-notify
    STATUS current
    DESCRIPTION
        "Parameter 'control' in event X252.21"
    ::= { x252EventObjects21 2 }

x25221_vs OBJECT-TYPE
    SYNTAX Integer32
    MAX-ACCESS accessible-for-notify
    STATUS current
    DESCRIPTION
        "Parameter 'vs' in event X252.21"
    ::= { x252EventObjects21 3 }

x25221_vr OBJECT-TYPE
    SYNTAX Integer32
    MAX-ACCESS accessible-for-notify
    STATUS current
    DESCRIPTION
        "Parameter 'vr' in event X252.21"
    ::= { x252EventObjects21 4 }

x25221_port OBJECT-TYPE
    SYNTAX DisplayString
    MAX-ACCESS accessible-for-notify
    STATUS current
    DESCRIPTION
        "Parameter 'port' in event X252.21"
    ::= { x252EventObjects21 5 }

x252EventObjects22 OBJECT-IDENTITY
    STATUS current
    DESCRIPTION
        "Event X252.22
        FRMR frame module 128 received."
    ::= { x252EventsGroup 22 }

x25222_cause OBJECT-TYPE
    SYNTAX Integer32
    MAX-ACCESS accessible-for-notify
    STATUS current
    DESCRIPTION
        "Parameter 'cause' in event X252.22"
    ::= { x252EventObjects22 1 }

x25222_control OBJECT-TYPE
    SYNTAX Integer32
    MAX-ACCESS accessible-for-notify
    STATUS current
    DESCRIPTION
        "Parameter 'control' in event X252.22"
    ::= { x252EventObjects22 2 }

x25222_vs OBJECT-TYPE
    SYNTAX Integer32
    MAX-ACCESS accessible-for-notify
    STATUS current
    DESCRIPTION
        "Parameter 'vs' in event X252.22"
    ::= { x252EventObjects22 3 }

x25222_vr OBJECT-TYPE
    SYNTAX Integer32
    MAX-ACCESS accessible-for-notify
    STATUS current
    DESCRIPTION
        "Parameter 'vr' in event X252.22"
    ::= { x252EventObjects22 4 }

x25222_port OBJECT-TYPE
    SYNTAX DisplayString
    MAX-ACCESS accessible-for-notify
    STATUS current
    DESCRIPTION
        "Parameter 'port' in event X252.22"
    ::= { x252EventObjects22 5 }

x252EventObjects23 OBJECT-IDENTITY
    STATUS current
    DESCRIPTION
        "Event X252.23
        Lapb error. Error codes:
        0x01 Receipt of an unsolicited supervisory frame (F=1)
        0x02 Receipt of an unsolicited DM response frame (F=1)
        0x03 Receipt of an unsolicited UA response (F=1)
        0x04 Receipt of an unsolicited UA response (F=0)
        0x05 Receipt of an unsolicited DM response (F=0)
        0x06 Peer initiated link re-establishment
        0x07 Retry limit reached N2 transmitting a SABM(E) command
        0x08 Retry limit reached N2 transmitting a DISC command
        0x09 Retry limit reached during status enquiry
        0x0A Receipt of an I o S frame with a N(R) error
        0x0B Receipt of a FRMR response
        0x0C Receipt of an undefined o not inplemented control field
        0x0D Receipt of an information field not permitted
        0x0E Receipt of a frame with wrong size
        0x0F Receipt of an I frame with N1 error
        0x10 An I-frame was received with a N(S) sequence error
        0x17 Unexpected Poll/Final bit
        0x18 Received frame does not contain the whole LAPB header in the first
        buffer."
    ::= { x252EventsGroup 23 }

x25223_cause OBJECT-TYPE
    SYNTAX Integer32
    MAX-ACCESS accessible-for-notify
    STATUS current
    DESCRIPTION
        "Parameter 'cause' in event X252.23"
    ::= { x252EventObjects23 1 }

x25223_port OBJECT-TYPE
    SYNTAX DisplayString
    MAX-ACCESS accessible-for-notify
    STATUS current
    DESCRIPTION
        "Parameter 'port' in event X252.23"
    ::= { x252EventObjects23 2 }


x252Notification1 NOTIFICATION-TYPE
    OBJECTS { 
              x2521_address, 
              x2521_frame,
              x2521_bit_pf,
              x2521_port 
            }
    STATUS current
    DESCRIPTION
        "Notification of Event X252.1

        Message: 'Tx -> Address [$1] Ctrl-type [$2] P/F bit [$3] port $4'

        Parameters list:
              $1: x2521_address
              $2: x2521_frame
              $3: x2521_bit_pf
              $4: x2521_port

        Unnumbered control frame transmitted."
    ::= { x252NotificationsPrefix 1 }

x252Notification2 NOTIFICATION-TYPE
    OBJECTS { 
              x2522_address, 
              x2522_frame,
              x2522_bit_pf,
              x2522_nr,
              x2522_port 
            }
    STATUS current
    DESCRIPTION
        "Notification of Event X252.2

        Message: 'Tx -> Address [$1] Ctrl-type [$2] P/F bit [$3] N(R) sequence [$4] port $5'

        Parameters list:
              $1: x2522_address
              $2: x2522_frame
              $3: x2522_bit_pf
              $4: x2522_nr
              $5: x2522_port

        Supervisory frame RR transmitted."
    ::= { x252NotificationsPrefix 2 }

x252Notification3 NOTIFICATION-TYPE
    OBJECTS { 
              x2523_address, 
              x2523_frame,
              x2523_bit_pf,
              x2523_nr,
              x2523_port 
            }
    STATUS current
    DESCRIPTION
        "Notification of Event X252.3

        Message: 'Tx -> Address [$1] Ctrl-type [$2] P/F bit [$3] N(R) sequence [$4] port $5'

        Parameters list:
              $1: x2523_address
              $2: x2523_frame
              $3: x2523_bit_pf
              $4: x2523_nr
              $5: x2523_port

        Supervisory frame RNR or REJ transmitted."
    ::= { x252NotificationsPrefix 3 }

x252Notification4 NOTIFICATION-TYPE
    OBJECTS { 
              x2524_address, 
              x2524_frame,
              x2524_bit_pf,
              x2524_ns,
              x2524_nr,
              x2524_port 
            }
    STATUS current
    DESCRIPTION
        "Notification of Event X252.4

        Message: 'Tx -> Address [$1] Ctrl-type [$2] P/F bit [$3] N(R) sequence [$4] N(S) sequence [$5] port $6'

        Parameters list:
              $1: x2524_address
              $2: x2524_frame
              $3: x2524_bit_pf
              $4: x2524_ns
              $5: x2524_nr
              $6: x2524_port

        Information frame transmitted."
    ::= { x252NotificationsPrefix 4 }

x252Notification5 NOTIFICATION-TYPE
    OBJECTS { 
              x2525_address, 
              x2525_frame,
              x2525_bit_pf,
              x2525_port 
            }
    STATUS current
    DESCRIPTION
        "Notification of Event X252.5

        Message: 'Rx <- Address [$1] Ctrl-type [$2] P/F bit [$3] port $4'

        Parameters list:
              $1: x2525_address
              $2: x2525_frame
              $3: x2525_bit_pf
              $4: x2525_port

        Unnumbered control frame received."
    ::= { x252NotificationsPrefix 5 }

x252Notification6 NOTIFICATION-TYPE
    OBJECTS { 
              x2526_address, 
              x2526_frame,
              x2526_bit_pf,
              x2526_nr,
              x2526_port 
            }
    STATUS current
    DESCRIPTION
        "Notification of Event X252.6

        Message: 'Rx <- Address [$1] Ctrl-type [$2] P/F bit [$3] N(R) sequence [$4] port $5'

        Parameters list:
              $1: x2526_address
              $2: x2526_frame
              $3: x2526_bit_pf
              $4: x2526_nr
              $5: x2526_port

        Supervisory frame RR received."
    ::= { x252NotificationsPrefix 6 }

x252Notification7 NOTIFICATION-TYPE
    OBJECTS { 
              x2527_address, 
              x2527_frame,
              x2527_bit_pf,
              x2527_nr,
              x2527_port 
            }
    STATUS current
    DESCRIPTION
        "Notification of Event X252.7

        Message: 'Rx <- Address [$1] Ctrl-type [$2] P/F bit [$3] N(R) sequence [$4] port $5'

        Parameters list:
              $1: x2527_address
              $2: x2527_frame
              $3: x2527_bit_pf
              $4: x2527_nr
              $5: x2527_port

        Supervisory frame RNR or REJ received."
    ::= { x252NotificationsPrefix 7 }

x252Notification8 NOTIFICATION-TYPE
    OBJECTS { 
              x2528_address, 
              x2528_frame,
              x2528_bit_pf,
              x2528_ns,
              x2528_nr,
              x2528_port 
            }
    STATUS current
    DESCRIPTION
        "Notification of Event X252.8

        Message: 'Rx <- Address [$1] Ctrl-type [$2] P/F bit [$3] N(R) sequence [$4] N(S) sequence [$5] port $6'

        Parameters list:
              $1: x2528_address
              $2: x2528_frame
              $3: x2528_bit_pf
              $4: x2528_ns
              $5: x2528_nr
              $6: x2528_port

        Information frame received."
    ::= { x252NotificationsPrefix 8 }

x252Notification9 NOTIFICATION-TYPE
    OBJECTS { 
              x2529_port 
            }
    STATUS current
    DESCRIPTION
        "Notification of Event X252.9

        Message: 'N2 RR frames sent port $1'

        Parameters list:
              $1: x2529_port

        N2 Counter runout."
    ::= { x252NotificationsPrefix 9 }

x252Notification10 NOTIFICATION-TYPE
    OBJECTS { 
              x25210_port 
            }
    STATUS current
    DESCRIPTION
        "Notification of Event X252.10

        Message: 'Rx I or RR frame with erroneus n(R) port $1'

        Parameters list:
              $1: x25210_port

        Information or RR frame received with n(R) error."
    ::= { x252NotificationsPrefix 10 }

x252Notification11 NOTIFICATION-TYPE
    OBJECTS { 
              x25211_cause, 
              x25211_control,
              x25211_vs,
              x25211_vr,
              x25211_port 
            }
    STATUS current
    DESCRIPTION
        "Notification of Event X252.11

        Message: 'Rx FRMR frame Cause:$1 C.Control:$2 v(s):$3 v(r):$4 port $5'

        Parameters list:
              $1: x25211_cause
              $2: x25211_control
              $3: x25211_vs
              $4: x25211_vr
              $5: x25211_port

        FRMR frame received."
    ::= { x252NotificationsPrefix 11 }

x252Notification12 NOTIFICATION-TYPE
    OBJECTS { 
              x25212_port 
            }
    STATUS current
    DESCRIPTION
        "Notification of Event X252.12

        Message: 'Rx frame with undefined or unplemented control field port $1'

        Parameters list:
              $1: x25212_port

        Frame received with undefined or unplemented control field."
    ::= { x252NotificationsPrefix 12 }

x252Notification13 NOTIFICATION-TYPE
    OBJECTS { 
              x25213_port 
            }
    STATUS current
    DESCRIPTION
        "Notification of Event X252.13

        Message: 'Rx frame with not permitted information field port $1'

        Parameters list:
              $1: x25213_port

        Frame received with not permitted information field."
    ::= { x252NotificationsPrefix 13 }

x252Notification14 NOTIFICATION-TYPE
    OBJECTS { 
              x25214_port 
            }
    STATUS current
    DESCRIPTION
        "Notification of Event X252.14

        Message: 'Rx frame with wrong size port $1'

        Parameters list:
              $1: x25214_port

        Frame received with wrong size."
    ::= { x252NotificationsPrefix 14 }

x252Notification15 NOTIFICATION-TYPE
    OBJECTS { 
              x25215_port 
            }
    STATUS current
    DESCRIPTION
        "Notification of Event X252.15

        Message: 'Rx Information frame with N1 error port $1'

        Parameters list:
              $1: x25215_port

        Information frame received with N1 error."
    ::= { x252NotificationsPrefix 15 }

x252Notification16 NOTIFICATION-TYPE
    OBJECTS { 
              x25216_port 
            }
    STATUS current
    DESCRIPTION
        "Notification of Event X252.16

        Message: 'Rx Information frame with erroneous N(S) port $1'

        Parameters list:
              $1: x25216_port

        Information frame received with N(S) error."
    ::= { x252NotificationsPrefix 16 }

x252Notification17 NOTIFICATION-TYPE
    OBJECTS { 
              x25217_port 
            }
    STATUS current
    DESCRIPTION
        "Notification of Event X252.17

        Message: 'Rx Unexpected P/F bit port $1'

        Parameters list:
              $1: x25217_port

        Frame received with unexpected P/F bit."
    ::= { x252NotificationsPrefix 17 }

x252Notification18 NOTIFICATION-TYPE
    OBJECTS { 
              x25218_port 
            }
    STATUS current
    DESCRIPTION
        "Notification of Event X252.18

        Message: 'Rx frame without lapb header port $1'

        Parameters list:
              $1: x25218_port

        Frame received without lapb header."
    ::= { x252NotificationsPrefix 18 }

x252Notification19 NOTIFICATION-TYPE
    OBJECTS { 
              x25219_cause, 
              x25219_control,
              x25219_vr,
              x25219_vs,
              x25219_port 
            }
    STATUS current
    DESCRIPTION
        "Notification of Event X252.19

        Message: 'Tx    FRMR frame Cause:$1 Control:$2 V(R):$3 V(S):$4 port $5'

        Parameters list:
              $1: x25219_cause
              $2: x25219_control
              $3: x25219_vr
              $4: x25219_vs
              $5: x25219_port

        FRMR frame module 8 transmitted."
    ::= { x252NotificationsPrefix 19 }

x252Notification20 NOTIFICATION-TYPE
    OBJECTS { 
              x25220_cause, 
              x25220_control,
              x25220_vr,
              x25220_vs,
              x25220_port 
            }
    STATUS current
    DESCRIPTION
        "Notification of Event X252.20

        Message: 'Tx    FRMR frame Cause:$1 Control:$2 V(R):$3 V(S):$4 port $5'

        Parameters list:
              $1: x25220_cause
              $2: x25220_control
              $3: x25220_vr
              $4: x25220_vs
              $5: x25220_port

        FRMR frame module 128 transmitted."
    ::= { x252NotificationsPrefix 20 }

x252Notification21 NOTIFICATION-TYPE
    OBJECTS { 
              x25221_cause, 
              x25221_control,
              x25221_vs,
              x25221_vr,
              x25221_port 
            }
    STATUS current
    DESCRIPTION
        "Notification of Event X252.21

        Message: 'Rx FRMR frame Cause:$1 C.Control:$2 v(s):$3 v(r):$4 port $5'

        Parameters list:
              $1: x25221_cause
              $2: x25221_control
              $3: x25221_vs
              $4: x25221_vr
              $5: x25221_port

        FRMR frame module 8 received."
    ::= { x252NotificationsPrefix 21 }

x252Notification22 NOTIFICATION-TYPE
    OBJECTS { 
              x25222_cause, 
              x25222_control,
              x25222_vs,
              x25222_vr,
              x25222_port 
            }
    STATUS current
    DESCRIPTION
        "Notification of Event X252.22

        Message: 'Rx frame FRMR Cause:$1 C.Control:$2 v(s):$3 v(r):$4 port $5'

        Parameters list:
              $1: x25222_cause
              $2: x25222_control
              $3: x25222_vs
              $4: x25222_vr
              $5: x25222_port

        FRMR frame module 128 received."
    ::= { x252NotificationsPrefix 22 }

x252Notification23 NOTIFICATION-TYPE
    OBJECTS { 
              x25223_cause, 
              x25223_port 
            }
    STATUS current
    DESCRIPTION
        "Notification of Event X252.23

        Message: 'Lapb error cause $1 port $2'

        Parameters list:
              $1: x25223_cause
              $2: x25223_port

        Lapb error. Error codes:
        0x01 Receipt of an unsolicited supervisory frame (F=1)
        0x02 Receipt of an unsolicited DM response frame (F=1)
        0x03 Receipt of an unsolicited UA response (F=1)
        0x04 Receipt of an unsolicited UA response (F=0)
        0x05 Receipt of an unsolicited DM response (F=0)
        0x06 Peer initiated link re-establishment
        0x07 Retry limit reached N2 transmitting a SABM(E) command
        0x08 Retry limit reached N2 transmitting a DISC command
        0x09 Retry limit reached during status enquiry
        0x0A Receipt of an I o S frame with a N(R) error
        0x0B Receipt of a FRMR response
        0x0C Receipt of an undefined o not inplemented control field
        0x0D Receipt of an information field not permitted
        0x0E Receipt of a frame with wrong size
        0x0F Receipt of an I frame with N1 error
        0x10 An I-frame was received with a N(S) sequence error
        0x17 Unexpected Poll/Final bit
        0x18 Received frame does not contain the whole LAPB header in the first
        buffer."
    ::= { x252NotificationsPrefix 23 }


END
