XEDIA-REG DEFINITIONS ::= BEGIN

IMPORTS
    MODULE-IDENTITY, enterprises, OBJECT-IDENTITY
        FROM SNMPv2-SMI
    TEXTUAL-CONVENTION
        FROM SNMPv2-TC
    ;

xedia OBJECT-IDENTITY
    STATUS      current
    DESCRIPTION
        "Xedia's node in the naming hierarchy as assigned by the
        Internet Assigned Numbers Authority (IANA)."
    ::= { enterprises 838 }

xediaRegistrations MODULE-IDENTITY
    LAST-UPDATED "9612202155Z" -- December 20, 1996
    ORGANIZATION "Xedia Corp."
    CONTACT-INFO
        "support@xedia.com"
    DESCRIPTION
        "This module defines the enterprises OID of Xedia and other
        company-wide definitions. The resulting top-level name space
        under the xedia branch looks like this:

        xedia
            (agentConfig       - an older MIB defined for MADswitch)
            xediaRegistrations - this module
            xediaMibs          - MIB modules defined in .mi2 files
            xediaClasses       - CLASS modules defined .mo files
            xediaProducts      - AGENT-CAPABILITIES modules defined 
                                 in .mi2 files

        This is where you reserve an OIDs for a MIB module. The values
        are defined in the appropriate .mi2/.mo files but are in
        comments here so that we can have one document under source
        control to reserve and catalog values."
    ::= { xedia 2 }

-- This is a MIB module defined for Xedia's first product, the MADswitch
-- agentConfig          OBJECT IDENTIFIER ::= { xedia 1 }

xediaMibs OBJECT-IDENTITY
    STATUS      current
    DESCRIPTION
        "A registration point under which all (new) Xedia MIB modules
        are defined."
    ::= { xedia 3 }

-- xediaSystemMIB           ::= { xediaMibs 1 }
-- xediaTrafficMgmtMIB      ::= { xediaMibs 2 }
-- xediaEthernetMIB         ::= { xediaMibs 3 }
-- xediaIpMIB               ::= { xediaMibs 4 }
-- xediaRipMIB              ::= { xediaMibs 5 }
-- xediaDriverMIB           ::= { xediaMibs 6 }
-- xediaHdlcMIB             ::= { xediaMibs 7 }
-- xediaSecurityMIB         ::= { xediaMibs 8 }
-- xediaBgpMIB              ::= { xediaMibs 9 }
-- xediaPolicyMIB           ::= { xediaMibs 10 }
-- xediaDs3MIB              ::= { xediaMibs 11 }
-- xediaAtmMIB              ::= { xediaMibs 12 }
-- xediaCronMib             ::= { xediaMibs 13 }
-- xediaIpsecMIB            ::= { xediaMibs 14 }
-- xediaIpBackupMIB         ::= { xediaMibs 15 }
-- xediaRadiusMib           ::= { xediaMibs 16 }
-- xediaAuthenticationMib   ::= { xediaMibs 17 }
-- xediaDs1MIB              ::= { xediaMibs 18 }
-- xediaFrameRelayMIB       ::= { xediaMibs 19 }
-- xediaPppSecMIB           ::= { xediaMibs 20 }
-- xediaPppMpMIB            ::= { xediaMibs 21 }
-- xediaSmdsMIB             ::= { xediaMibs 22 }
-- xediaNatMIB              ::= { xediaMibs 23 }
-- xediaPkiMIB              ::= { xediaMibs 24 }
-- xediaSonetMIB            ::= { xediaMibs 25 }
-- xediaNtpMIB              ::= { xediaMibs 26 }
-- xediaSlaMonitorMIB       ::= { xediaMibs 27 }
-- xediaDhcpMIB             ::= { xediaMibs 28 }
-- xediaIpMrouteMIB         ::= { xediaMibs 29 }
-- xediaL2DialMIB           ::= { xediaMibs 30 }
-- xediaPimMIB              ::= { xediaMibs 31 }
-- xediaDvmrpMIB            ::= { xediaMibs 32 }

xediaClasses OBJECT-IDENTITY
    STATUS      current
    DESCRIPTION
        "A registration point under which all Xedia CLASS definition
        modules are defined."
    ::= { xedia 4 }

-- xediaSystemClasses       ::= { xediaClasses 1 }
-- systemClasses            ::= { xediaClasses 2 }
-- raptorClasses            ::= { xediaClasses 3 }
-- ifClasses                ::= { xediaClasses 4 }
-- ipClasses                ::= { xediaClasses 5 }
-- udpClasses               ::= { xediaClasses 6 }
-- tcpClasses               ::= { xediaClasses 7 }
-- snmpClasses              ::= { xediaClasses 8 }
-- madSwitchClasses         ::= { xediaClasses 9 }
-- genAgentClasses          ::= { xediaClasses 10 }
-- rptrClasses              ::= { xediaClasses 11 }
-- bridgeClasses            ::= { xediaClasses 12 }
-- ethClasses               ::= { xediaClasses 13 }
-- xediaSystemClasses       ::= { xediaClasses 14 }
-- ipRouteClasses           ::= { xediaClasses 15 }
-- xediaSnmpCommClasses     ::= { xediaClasses 16 }
-- xediaTrafficMgmtClasses  ::= { xediaClasses 17 }
-- ripv2Classes             ::= { xediaClasses 18 }
-- ospfClasses              ::= { xediaClasses 19 }
-- ipAddrClasses            ::= { xediaClasses 20 }
-- frameRelayDteClasses     ::= { xediaClasses 21 }
-- ds3Classes               ::= { xediaClasses 22 }
-- usrHistoryClasses        ::= { xediaClasses 23 }
-- xediaDriverClasses       ::= { xediaClasses 24 }
-- xediaHdlcClasses         ::= { xediaClasses 25 }
-- bgp4Classes              ::= { xediaClasses 26 }
-- xediaSecurityClasses     ::= { xediaClasses 27 }
-- pppClasses               ::= { xediaClasses 28 }
-- xediaPolicyClasses       ::= { xediaClasses 29 }
-- t3Ds3Classes             ::= { xediaClasses 30 }
-- atmClasses               ::= { xediaClasses 31 }
-- ipoaClasses              ::= { xediaClasses 32 }
-- atmDs3Classes            ::= { xediaClasses 33 }
-- atmSonetClasses          ::= { xediaClasses 34 }
-- xediaCronClasses         ::= { xediaClasses 35 }
-- dnsResolverClasses       ::= { xediaClasses 36 }
-- xediaIpsecClasses        ::= { xediaClasses 37 }
-- xipbackupClasses         ::= { xediaClasses 38 }
-- xediaRadiusClasses       ::= { xediaClasses 39 }
-- xediaAuthenticationClasses ::= { xediaClasses 40 }
-- ds1Classes               ::= { xediaClasses 41 }
-- t1ds1Classes             ::= { xediaClasses 42 }
-- xediaFrameRelayClasses   ::= { xediaClasses 43 }
-- smdsClasses              ::= { xediaClasses 44 }
-- xediaPppSecClasses       ::= { xediaClasses 45 }
-- xediaPppMpClasses        ::= { xediaClasses 46 }
-- xediaNatClasses          ::= { xediaClasses 47 }
-- xediaPkiClasses          ::= { xediaClasses 48 }
-- xediaSonetClasses        ::= { xediaClasses 49 }
-- igmpClasses              ::= { xediaClasses 50 }
-- iptnlClasses             ::= { xediaClasses 51 }
-- xediaNtpClasses          ::= { xediaClasses 52 }
-- slaMonitorClasses        ::= { xediaClasses 53 }
-- xdhcpClasses             ::= { xediaClasses 54 }
-- ipMrouteClasses	        ::= { xediaClasses 55 }
-- l2tpClasses  	        ::= { xediaClasses 56 }
-- XediaMssiClasses  	    ::= { xediaClasses 57 }
-- dvmrpClasses  	    ::= { xediaClasses 58 }
-- xipMrouteClasses  	    ::= { xediaClasses 59 }
-- l2DialClasses            ::= { xediaClasses 60 }
-- pimClasses		    ::= { xediaClasses 61 }
-- xediPimClasses	    ::= { xediaClasses 62 }

xediaProducts OBJECT-IDENTITY
    STATUS      current
    DESCRIPTION
        "A registration point under which all Xedia AGENT-CAPABILITIES
        definitions (and therefore values of sysObjectId) are
        defined."
    ::= { xedia 5 }

-- xediaVelociraptor        ::= { xediaProducts 1 }
-- xediaVelociraptorMaj1    ::= { xediaVelociraptor 1 }
-- xediaVelociraptorMin0    ::= { xediaVelociraptorMaj1 0 }
-- xediaVelociraptorMin1    ::= { xediaVelociraptorMaj1 1 }
-- xediaVelociraptorMin2    ::= { xediaVelociraptorMaj1 2 }
-- xediaVelociraptorMin3    ::= { xediaVelociraptorMaj1 3 }

LongDisplayString ::= TEXTUAL-CONVENTION
    STATUS      current
    DESCRIPTION
        "A string that has the same properties as a DisplayString
        except it can be up to 2048 characters long."
    SYNTAX      OCTET STRING (SIZE (0..2048))

END
