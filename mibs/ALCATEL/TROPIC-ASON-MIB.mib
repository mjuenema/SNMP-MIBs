TROPIC-ASON-MIB DEFINITIONS ::= BEGIN

-- (c) Copyright 2016 Nokia.  All rights reserved.
-- This software is the confidential and proprietary property of
-- Nokia and may only be used in accordance with the
-- terms of the license agreement provided with this software.

 IMPORTS
      SnmpAdminString                         FROM SNMP-FRAMEWORK-MIB
      OBJECT-TYPE, MODULE-IDENTITY,
      IpAddress,
      Unsigned32, Integer32                   FROM SNMPv2-SMI
      MODULE-COMPLIANCE, OBJECT-GROUP         FROM SNMPv2-CONF
      TEXTUAL-CONVENTION,
      RowStatus                               FROM SNMPv2-TC
      ifIndex                                 FROM IF-MIB
      TnCommand,
      AluWdmTransferProtocol,
      AluWdmFecMode                           FROM TROPIC-TC
      tnSystemModules, tnAsonMIB              FROM TROPIC-GLOBAL-REG;

  tnAsonMibModule MODULE-IDENTITY
      LAST-UPDATED    "201605181200Z"
      ORGANIZATION    "Nokia"
      CONTACT-INFO    "Nokia
                       Postal: 600 March Rd.
                       Kanata, Ontario
                       Canada K2K 2E6

                       Phone: +1 613 591 3600
                       Fax:   +1 613 591 3680"

      DESCRIPTION "ASON MIB types."

      REVISION    "201010121200Z"
      DESCRIPTION "Created MIB file for GMRE IP and CORBA IOR parameters."

      REVISION    "201103041200Z"
      DESCRIPTION "Added the following tables:
                   tnGmreOmsLineImpTable
                   tnGmreOptLineImpTable."

      REVISION    "201105051200Z"
      DESCRIPTION "Added the following table:
                   tnAsonTopoAlarmTable."

      REVISION    "201105311200Z"
      DESCRIPTION "Added the following to tnGmreOptLineImpCompModule:
                   txfp(5)   -- Tunable 10G Small Form Factor Pluggable."

      REVISION    "201106301200Z"
      DESCRIPTION "Added ranges to the SYNTAX of the following attributes:
                   tnGmreOmsLineImpMaxAlwCh, (1..96)
                   tnGmreOmsLineImpPMD, (0..10000)
                   tnGmreOptLineImpOSNR, (0..100000000)
                   tnGmreOptLineImpOSNRNP, (0..100000000)."

      REVISION    "201107251200Z"
      DESCRIPTION "Added the following to tnGmreOptLineImpCompModule:
                   hperf1(6),      -- 100G High Performance OT
                   variant1(7),    -- Variant 1
                   variant2(8),    -- Variant 2
                   variant3(9),    -- Variant 3
                   variant4(10),   -- Variant 4
                   variant5(11),   -- Variant 5
                   variant6(12),   -- Variant 6
                   variant7(13),   -- Variant 7
                   variant8(14),   -- Variant 8
                   variant9(15),   -- Variant 9
                   variant10(16)   -- Variant 10."

      REVISION    "201108031200Z"
      DESCRIPTION "Updated ranges for the following attributes:
                   tnGmreOptLineImpOSNR, (0..1000000000)
                   tnGmreOptLineImpOSNRNP, (0..1000000000)."

      REVISION    "201108081200Z"
      DESCRIPTION "Added the following Feasibility File Transfer scalars:
                   tnAsonFeasibilityCommand
                   tnAsonFeasibilityRemoteHostIp
                   tnAsonFeasibilityRemotePath
                   tnAsonFeasibilityStatus
                   tnAsonFeasibilityLastTransferredVersion
                   tnAsonFeasibilityProtocol
                   tnAsonFeasibilityUserId
                   tnAsonFeasibilityPassword."

      REVISION    "201108121200Z"
      DESCRIPTION "Added the following to tnGmreOptLineImpCompModule:
                   tcfp(17)       -- Tunable Compact Form Package."

      REVISION    "201201171200Z"
      DESCRIPTION "1) Added the following MIB table:
                      tnAsonMgracdTable.
                   2) Added the following define:
                      AluWdmAccessControlDevice."

      REVISION    "201201241200Z"
      DESCRIPTION "Added the following to tnGmreOptLineImpCompModule:
                   cr(18)          -- Cost Reduced."

      REVISION    "201206251200Z"
      DESCRIPTION "Added the following MIB table:
                   tnGmreOmsWavelengthSetTable."

      REVISION    "201208101200Z"
      DESCRIPTION "1) Added the following to tnGmreOmsLineImpTable:
                      tnGmreOmsLineImpCD
                      tnGmreOmsLineImpFiberType.
                   2) Added the following to tnGmreOptLineImpTable:
                      tnGmreOptLineImpPower."

      REVISION    "201210221200Z"
      DESCRIPTION "1) Added the following to tnGmreOptLineImpEncoding:
                      icohpmqpsk(6)  -- Time-interleaved Coherent Path
                                     -- Modulation Quad Phase Shift Keying
                   2) Added the following to tnGmreOptLineImpCompModule:
                      ctxfpwt(19)     -- 0-Chirp Tunable XFP with unused WT capability."

      REVISION    "201211051200Z"
      DESCRIPTION "Added the following to tnGmreOptLineImpCompModule:
                   sperf2(20)     -- 100G Standard Performance OT, 2nd Gen."

      REVISION    "201309201200Z"
      DESCRIPTION "1) Added the following scalars and table:
                      tnAsonSnapshotRemoteHostIp
                      tnAsonSnapshotProtocol
                      tnAsonSnapshotUserId
                      tnAsonSnapshotPassword
                      tnAsonSnapshotTable.
                   2) Added the following to tnGmreOptLineImpCompModule:
                      hperf2(21)      -- 100G High Performance OT, 2nd Gen."

      REVISION    "201311181200Z"
      DESCRIPTION "Added the following to tnAsonSnapshotGroup:
                   tnAsonSnapshotRootRemotePath."

      REVISION    "201311221200Z"
      DESCRIPTION "1) Added the following to tnGmreOptLineImpBitRate:
                      rate260G(5).
                   2) Added the following to tnGmreOptLineImpEncoding:
                      cohpm16qam(7)  -- Coherent Polarization Multiplexed
                                     -- 16-state Quadrature Amplitude Modulation."

      REVISION    "201402261200Z"
      DESCRIPTION "Added DEFVAL to attributes."

      REVISION    "201503261200Z"
      DESCRIPTION "Changed range values of following in tnGmreOptLineImpTable:
                   tnGmreOptLineImpNLP 
                   tnGmreOptLineImpNLPNP."
      
      REVISION    "201506021200Z"
      DESCRIPTION "Added the following to tnGmreOmsLineImpTable:
                   tnGmreOmsLineImpPDL."

      REVISION    "201506291200Z"
      DESCRIPTION "Changed the SYNTAX of tnGmreOmsLineImpPDL:
                    Modified the max range from 10000 to 500000"

      REVISION    "201601201200Z"
      DESCRIPTION "1) Added the following to tnGmreOptLineImpEncoding:
                      cohpm8qam(8)   -- Coherent Polarization Multiplexed
                                     -- 8-state Quadrature Amplitude Modulation
                   2) Added the following to tnGmreOptLineImpCompModule:
                      add(22)        -- >= 100G High Performace OT, 3rd Gen."

      REVISION    "201602191200Z"
      DESCRIPTION "Changed the value of following in tnGmreOptLineImpCompModule:
                   From add(22) to add3(22)." 

      REVISION    "201602241200Z"
      DESCRIPTION "1) Added the following to tnGmreOptLineImpBitRate:
                      rate50G(6),
                      rate200G(7),
                      rate250G(8),
                      rate400G(9).
                   2)Added the following to tnGmreOptLineImpEncoding:
                      cohspqpsk(9),  -- Coherent Set Partial Quad Phase 
                                     -- Shift Keying
                      cohpm64qam(10) -- Coherent Polarization Multiplexed 64-state 
                                     -- Quadrature Amplitude Modulation.
                   3) Added the following to tnGmreOptLineImpCompModule:
                      add2l(23),     -- >= 100G High Performace OT for metro, 2nd Generation
                      add2lh(24)     -- >= 100G High Performace OT for long haul, 2nd Generation."

      REVISION    "201603181200Z"
      DESCRIPTION "Added the following to TEXTUAL-CONVENTION:
                   TnGmreOptLineImpEncoding
                   TnGmreOptLineImpCompModule."         

      REVISION    "201604181200Z"
      DESCRIPTION "Added the following to tnGmreOptLineImpCompModule 
                   and TnGmreOptLineImpCompModule:
                   ovclk(25)        -- 200G High Performace OT."

      REVISION    "201605181200Z"
      DESCRIPTION "Added the following to tnGmreOptLineImpCompModule
                   and TnGmreOptLineImpCompModule:
                   cm2ac100(26)."
 
      ::= { tnSystemModules 10 }

  tnAsonConf             OBJECT IDENTIFIER ::= { tnAsonMIB 1 }
  tnAsonGroups           OBJECT IDENTIFIER ::= { tnAsonConf 1 }
  tnAsonCompliances      OBJECT IDENTIFIER ::= { tnAsonConf 2 }
  tnAsonObjs             OBJECT IDENTIFIER ::= { tnAsonMIB 2 }
  tnAsonGlobal           OBJECT IDENTIFIER ::= { tnAsonObjs 1 }
  tnAsonIorGlobal        OBJECT IDENTIFIER ::= { tnAsonObjs 2 }
  tnAsonOmsLineImp       OBJECT IDENTIFIER ::= { tnAsonObjs 3 }
  tnAsonOptLineImp       OBJECT IDENTIFIER ::= { tnAsonObjs 4 }
  tnAsonTopoAlarm        OBJECT IDENTIFIER ::= { tnAsonObjs 5 }
  tnAsonFeasibility      OBJECT IDENTIFIER ::= { tnAsonObjs 6 }
  tnAsonMgracdInfo       OBJECT IDENTIFIER ::= { tnAsonObjs 7 }
  tnAsonOmsWavelengthSet OBJECT IDENTIFIER ::= { tnAsonObjs 8 }
  tnAsonSnapshot         OBJECT IDENTIFIER ::= { tnAsonObjs 9 }

--------------------------------------------------------------------------------
-- Type Definitions
--------------------------------------------------------------------------------
    AluWdmAccessControlDevice ::= TEXTUAL-CONVENTION
        STATUS         current
        DESCRIPTION    "Indicates if an entity is managed by control
                        plane, management plane, shared by both, or free."
        SYNTAX         INTEGER {
                         null(1), -- Entity is free
                         cp(2),   -- Entity is owned by control plane
                         mp(3),   -- Entity is owned by management plane
                         cpMp(4)  -- Entity is shared by control and management planes
                       }

    TnGmreOptLineImpEncoding ::= TEXTUAL-CONVENTION
        STATUS         current
        DESCRIPTION    "GMRE optical line encoding or modulation."
        SYNTAX         INTEGER {
                         nrz(1),        -- Non-Return-to-Zero encoding
                         pdpsk(2),      -- Partial Differential Phase Shift Keying
                         dpsk(3),       -- Differential Phase-Shift Keying
                         cohpmbpsk(4),  -- Coherent Path Modulation Binary Phase
                                        -- Shift Keying
                         cohpmqpsk(5),  -- Coherent Path Modulation Quad Phase
                                        -- Shift Keying
                         icohpmqpsk(6), -- Time-interleaved Coherent Path
                                        -- Modulation Quad Phase Shift Keying
                         cohpm16qam(7), -- Coherent Polarization Multiplexed
                                        -- 16-state Quadrature Amplitude Modulation
                         cohpm8qam(8),  -- Coherent Polarization Multiplexed
                                        -- 8-state Quadrature Amplitude Modulation
                         cohspqpsk(9),  -- Coherent Set Partial Quad Phase
                                        -- Shift Keying
                         cohpm64qam(10) -- Coherent Polarization Multiplexed 64-state
                                        -- Quadrature Amplitude Modulation
                       }

    TnGmreOptLineImpCompModule ::= TEXTUAL-CONVENTION 
        STATUS         current
        DESCRIPTION    "GMRE Optical Line Compensation Module (on the OCH
                        transponder line side)."
        SYNTAX         INTEGER {
                         null(1),
                         pmdc(2),        -- Polarization Mode Dispersion Compensation
                         mlse(3),        -- Maximum-Likelihood Sequence
                         tdcm(4),        -- Tunable Dispersion Compensation Module
                         txfp(5),        -- Tunable 10G Small Form Factor Pluggable
                         hperf1(6),      -- 100G High Performance OT
                         variant1(7),    -- Variant 1
                         variant2(8),    -- Variant 2
                         variant3(9),    -- Variant 3
                         variant4(10),   -- Variant 4
                         variant5(11),   -- Variant 5
                         variant6(12),   -- Variant 6
                         variant7(13),   -- Variant 7
                         variant8(14),   -- Variant 8
                         variant9(15),   -- Variant 9
                         variant10(16),  -- Variant 10
                         tcfp(17),       -- Tunable Compact Form Package
                         cr(18),         -- Cost Reduced
                         ctxfpwt(19),    -- 0-Chirp Tunable XFP with unused WT capability
                         sperf2(20),     -- 100G Standard Performance OT, 2nd Gen
                         hperf2(21),     -- 100G High Performance OT, 2nd Gen
                         add3(22),       -- >= 100G High Performace OT, 3rd Gen
                         add2l(23),      -- >= 100G High Performace OT for metro, 2nd Generation
                         add2lh(24),     -- >= 100G High Performace OT for long haul, 2nd Generation
                         ovclk(25),      -- 200G High Performance OT
                         cm2ac100(26)    -- 100G High Performace OT for metro, 2nd Generation, pluggable
                       }

--------------------------------------------------------------------------------
-- GMRE IP parameters
--------------------------------------------------------------------------------
    tnGmreNodeIpAddr OBJECT-TYPE
        SYNTAX         IpAddress
        MAX-ACCESS     read-create
        STATUS         current
        DESCRIPTION    "This address is used for all GMPLS communication
                        protocols across the network."
        DEFVAL         { "0.0.0.0" }
        ::= { tnAsonGlobal 1 }

    tnGmreNodeSubMask OBJECT-TYPE
        SYNTAX         IpAddress
        MAX-ACCESS     read-create
        STATUS         current
        DESCRIPTION    "Subnet mask for tnGmreNodeIpAddr."
        DEFVAL         { "0.0.0.0" }
        ::= { tnAsonGlobal 2 }

    tnGmreNotifyIpAddr OBJECT-TYPE
        SYNTAX         IpAddress
        MAX-ACCESS     read-create
        STATUS         current
        DESCRIPTION    "This address is used by RSVP-TE for fast failure
                        notify message within the network."
        DEFVAL         { "0.0.0.0" }
        ::= { tnAsonGlobal 3 }

    tnGmreNotifySubMask OBJECT-TYPE
        SYNTAX         IpAddress
        MAX-ACCESS     read-create
        STATUS         current
        DESCRIPTION    "Subnet mask for tnGmreNotifyIpAddr."
        DEFVAL         { "0.0.0.0" }
        ::= { tnAsonGlobal 4 }

--------------------------------------------------------------------------------
-- GMRE CORBA IOR parameters
--------------------------------------------------------------------------------
    tnGmreCorbaName OBJECT-TYPE
        SYNTAX         SnmpAdminString (SIZE(0..64))
        MAX-ACCESS     read-only
        STATUS         current
        DESCRIPTION    "GMRE CORBA IOR Name: 1 to 64 alphaNumeric
                        characters."
        DEFVAL         { "" }
        ::= { tnAsonIorGlobal 1 }

    tnGmreCorbaHostIpAddress OBJECT-TYPE
        SYNTAX         IpAddress
        MAX-ACCESS     read-only
        STATUS         current
        DESCRIPTION    "GMRE CORBA Host IP Address.

                        Current range: {1-254}:{0-255}:{0-255}:{1-254}."
        DEFVAL         { "0.0.0.0" }
        ::= { tnAsonIorGlobal 2 }

    tnGmreCorbaIor OBJECT-TYPE
        SYNTAX         SnmpAdminString (SIZE(0..265))
        MAX-ACCESS     read-only
        STATUS         current
        DESCRIPTION    "GMRE CORBA Interoperable Object Reference (IOR).
                        It contains 1 to 265 characters and provides
                        initial reference for the CORBA connection over
                        IIOP protocol."
        DEFVAL         { "" }
        ::= { tnAsonIorGlobal 3 }

--------------------------------------------------------------------------------
-- GMRE OMS Line Optical Impairment Scalar
--------------------------------------------------------------------------------
    tnGmreOmsLineImpAttributeTotal OBJECT-TYPE
        SYNTAX         Integer32
        MAX-ACCESS     read-only
        STATUS         current
        DESCRIPTION    ""
        ::= { tnAsonOmsLineImp 1 }

--------------------------------------------------------------------------------
-- GMRE OMS Line Optical Impairment parameters
--------------------------------------------------------------------------------
    tnGmreOmsLineImpTable OBJECT-TYPE
        SYNTAX         SEQUENCE OF TnGmreOmsLineImpEntry
        MAX-ACCESS     not-accessible
        STATUS         current
        DESCRIPTION    ""
        ::= { tnAsonOmsLineImp 2 }

    tnGmreOmsLineImpEntry OBJECT-TYPE
        SYNTAX         TnGmreOmsLineImpEntry
        MAX-ACCESS     not-accessible
        STATUS         current
        DESCRIPTION    ""
        INDEX { ifIndex }
        ::= { tnGmreOmsLineImpTable 1 }

    TnGmreOmsLineImpEntry ::=
        SEQUENCE {
            tnGmreOmsLineImpMaxAlwCh   Unsigned32,
            tnGmreOmsLineImpPMD        Unsigned32,
            tnGmreOmsLineImpAlcMode    INTEGER,
            tnGmreOmsLineImpDcuFree    INTEGER,
            tnGmreOmsLineImpCD         Integer32,
            tnGmreOmsLineImpFiberType  INTEGER,
            tnGmreOmsLineImpPDL        Unsigned32
        }

    tnGmreOmsLineImpMaxAlwCh OBJECT-TYPE
        SYNTAX         Unsigned32 (1..96)
        MAX-ACCESS     read-create
        STATUS         current
        DESCRIPTION    "GMRE OMS maximum allowed channels (MAXALCH).

                        Current configurable range: 1 to 96."
        DEFVAL         { 88 }
        ::= { tnGmreOmsLineImpEntry 1 }

    tnGmreOmsLineImpPMD OBJECT-TYPE
        SYNTAX         Unsigned32 (0..10000)
        UNITS          "1/10 picoSecond"
        MAX-ACCESS     read-create
        STATUS         current
        DESCRIPTION    "GMRE OMS polarization mode dispersion (PMD).  The
                        valid value is 0.0 to 1000.0 pico-seconds with
                        precision of one decimal digit.

                        Current configurable range: 0 to 10000."
        DEFVAL         { 0 }
        ::= { tnGmreOmsLineImpEntry 2 }

    tnGmreOmsLineImpAlcMode OBJECT-TYPE
        SYNTAX         INTEGER {
                         on(1),
                         off(2)
                       }
        MAX-ACCESS     read-create
        STATUS         current
        DESCRIPTION    "An indication as to whether or not the GMRE OMS
                        Automatic Level Control (ALC) Mode is on or not.
                        Equivalent to LNS (Laser Network Stabilization)
                        Mode."
        DEFVAL         { on }
        ::= { tnGmreOmsLineImpEntry 3 }

    tnGmreOmsLineImpDcuFree OBJECT-TYPE
        SYNTAX         INTEGER {
                         yes(1),
                         no(2)
                       }
        MAX-ACCESS     read-create
        STATUS         current
        DESCRIPTION    "GMRE OMS Dispersion Compensation Unit (DCU) is DCM
                        Free or not."
        DEFVAL         { yes }
        ::= { tnGmreOmsLineImpEntry 4 }

    tnGmreOmsLineImpCD OBJECT-TYPE
        SYNTAX         Integer32 (-40000..78000)
        UNITS          "1/10 ps/nm"
        MAX-ACCESS     read-create
        STATUS         current
        DESCRIPTION    "GMRE OMS chromatic dispersion (CD).  The new
                        coherent feasibility model is in units of 1/10
                        ps/nm (picoseconds/nanometer) because it needs
                        to have precision of one decimal digit.  The valid
                        values are -4000.0 to 7800.0 ps/nm.

                        Current configurable range: -40000 to 78000."
        DEFVAL         { 17000 }
        ::= { tnGmreOmsLineImpEntry 5 }

    tnGmreOmsLineImpFiberType OBJECT-TYPE
        SYNTAX         INTEGER {
                         ssmf(1),  -- Standard Single-Mode Fiber (SSMF)
                         eleaf(2), -- Enhanced Large Effective Area Fiber (ELEAF)
                         twrs(3),  -- True Wave Reduced Slope (TWRS)
                         twc(4),   -- True Wave Classic (TWC)
                         twp(5),   -- True Wave Plus (TW+)
                         mixed(6)  -- Mixed fiber type
                       }
        MAX-ACCESS     read-create
        STATUS         current
        DESCRIPTION    "GMRE OMS span fiber type."
        DEFVAL         { ssmf }
        ::= { tnGmreOmsLineImpEntry 6 }

    tnGmreOmsLineImpPDL OBJECT-TYPE
            SYNTAX         Unsigned32 (0..500000)
            UNITS          "1 dB"
            MAX-ACCESS     read-create
            STATUS         current
            DESCRIPTION    "GMRE OMS polarization dependent loss (PDL).  The
                            valid value is 0.00000 to 5.00000 dB  with
                            precision of five decimal digit.
                            Current configurable range: 0 to 500000."
            DEFVAL         { 0 }
            ::= { tnGmreOmsLineImpEntry 7 }

--------------------------------------------------------------------------------
-- GMRE Optical Line Impairment Scalar
--------------------------------------------------------------------------------
    tnGmreOptLineImpAttributeTotal OBJECT-TYPE
        SYNTAX         Integer32
        MAX-ACCESS     read-only
        STATUS         current
        DESCRIPTION    ""
        ::= { tnAsonOptLineImp 1 }

--------------------------------------------------------------------------------
-- GMRE Optical Line Impairment parameters
--------------------------------------------------------------------------------
    tnGmreOptLineImpTable OBJECT-TYPE
        SYNTAX         SEQUENCE OF TnGmreOptLineImpEntry
        MAX-ACCESS     not-accessible
        STATUS         current
        DESCRIPTION    ""
        ::= { tnAsonOptLineImp 2 }

    tnGmreOptLineImpEntry OBJECT-TYPE
        SYNTAX         TnGmreOptLineImpEntry
        MAX-ACCESS     not-accessible
        STATUS         current
        DESCRIPTION    "On creation of TnGmreOptLineImpEntry, the user
                        must fully specify all members before entry will
                        be processed."
        INDEX { ifIndex,
                tnGmreOptLineImpIndex }
        ::= { tnGmreOptLineImpTable 1 }

    TnGmreOptLineImpEntry ::=
        SEQUENCE {
            tnGmreOptLineImpIndex        Unsigned32,
            tnGmreOptLineImpBitRate      INTEGER,
            tnGmreOptLineImpEncoding     INTEGER,
            tnGmreOptLineImpCompModule   INTEGER,
            tnGmreOptLineImpFecMode      AluWdmFecMode,
            tnGmreOptLineImpNLP          Unsigned32,
            tnGmreOptLineImpOSNR         Unsigned32,
            tnGmreOptLineImpNLPNP        Unsigned32,
            tnGmreOptLineImpOSNRNP       Unsigned32,
            tnGmreOptLineImpRowStatus    RowStatus,
            tnGmreOptLineImpPower        Unsigned32
        }

    tnGmreOptLineImpIndex OBJECT-TYPE
        SYNTAX         Unsigned32
        MAX-ACCESS     not-accessible
        STATUS         current
        DESCRIPTION    "GMRE Optical Line Impairment table entry index.
                        Each index must identify a unique combination
                        of BitRate, Encoding, CompModule, and FecMode.

                        Current configurable range: 1 to 255."
        ::= { tnGmreOptLineImpEntry 1 }

    tnGmreOptLineImpBitRate OBJECT-TYPE
        SYNTAX         INTEGER {
                         rate2G5(1),
                         rate10G(2),
                         rate40G(3),
                         rate100G(4),
                         rate260G(5),
                         rate50G(6),
                         rate200G(7),
                         rate250G(8),
                         rate400G(9)
                       }
        MAX-ACCESS     read-create
        STATUS         current
        DESCRIPTION    "GMRE Optical Line transmitted signal bit rate."
        ::= { tnGmreOptLineImpEntry 2 }

    tnGmreOptLineImpEncoding OBJECT-TYPE
        SYNTAX         INTEGER {
                         nrz(1),        -- Non-Return-to-Zero encoding
                         pdpsk(2),      -- Partial Differential Phase Shift Keying
                         dpsk(3),       -- Differential Phase-Shift Keying
                         cohpmbpsk(4),  -- Coherent Path Modulation Binary Phase
                                        -- Shift Keying
                         cohpmqpsk(5),  -- Coherent Path Modulation Quad Phase
                                        -- Shift Keying
                         icohpmqpsk(6), -- Time-interleaved Coherent Path
                                        -- Modulation Quad Phase Shift Keying
                         cohpm16qam(7), -- Coherent Polarization Multiplexed
                                        -- 16-state Quadrature Amplitude Modulation
                         cohpm8qam(8),  -- Coherent Polarization Multiplexed 
                                        -- 8-state Quadrature Amplitude Modulation
                         cohspqpsk(9),  -- Coherent Set Partial Quad Phase 
                                        -- Shift Keying
                         cohpm64qam(10) -- Coherent Polarization Multiplexed 64-state 
                                        -- Quadrature Amplitude Modulation 
                       }
        MAX-ACCESS     read-create
        STATUS         current
        DESCRIPTION    "GMRE optical line encoding or modulation."
        ::= { tnGmreOptLineImpEntry 3 }

    tnGmreOptLineImpCompModule OBJECT-TYPE
        SYNTAX         INTEGER {
                         null(1),
                         pmdc(2),        -- Polarization Mode Dispersion Compensation
                         mlse(3),        -- Maximum-Likelihood Sequence
                         tdcm(4),        -- Tunable Dispersion Compensation Module
                         txfp(5),        -- Tunable 10G Small Form Factor Pluggable
                         hperf1(6),      -- 100G High Performance OT
                         variant1(7),    -- Variant 1
                         variant2(8),    -- Variant 2
                         variant3(9),    -- Variant 3
                         variant4(10),   -- Variant 4
                         variant5(11),   -- Variant 5
                         variant6(12),   -- Variant 6
                         variant7(13),   -- Variant 7
                         variant8(14),   -- Variant 8
                         variant9(15),   -- Variant 9
                         variant10(16),  -- Variant 10
                         tcfp(17),       -- Tunable Compact Form Package
                         cr(18),         -- Cost Reduced
                         ctxfpwt(19),    -- 0-Chirp Tunable XFP with unused WT capability
                         sperf2(20),     -- 100G Standard Performance OT, 2nd Gen
                         hperf2(21),     -- 100G High Performance OT, 2nd Gen
                         add3(22),       -- >= 100G High Performace OT, 3rd Gen
                         add2l(23),      -- >= 100G High Performace OT for metro, 2nd Generation
                         add2lh(24),     -- >= 100G High Performace OT for long haul, 2nd Generation
                         ovclk(25),      -- 200G High Performance OT
                         cm2ac100(26)    -- 100G High Performace OT for metro, 2nd Generation, pluggable
                       }
        MAX-ACCESS     read-create
        STATUS         current
        DESCRIPTION    "GMRE Optical Line Compensation Module (on the OCH
                        transponder line side)."
        ::= { tnGmreOptLineImpEntry 4 }

    tnGmreOptLineImpFecMode OBJECT-TYPE
        SYNTAX         AluWdmFecMode
        MAX-ACCESS     read-create
        STATUS         current
        DESCRIPTION    "GMRE Optical Line Forward Error Correction (FEC)
                        mode."
        ::= { tnGmreOptLineImpEntry 5 }

    tnGmreOptLineImpNLP OBJECT-TYPE
        SYNTAX         Unsigned32 (0..99900000)
        UNITS          "percentage"
        MAX-ACCESS     read-create
        STATUS         current
        DESCRIPTION    "GMRE OPTLINE Non-Linear Phase (NLP).
                        The valid value
                        is 0.00000 to 999.00000 with precision of 5
                        decimal digits.

                        Current configurable range: 0 to 99900000."
        ::= { tnGmreOptLineImpEntry 6 }

    tnGmreOptLineImpOSNR OBJECT-TYPE
        SYNTAX         Unsigned32 (0..1000000000)
        MAX-ACCESS     read-create
        STATUS         current
        DESCRIPTION    "GMRE OPTLINE Optical Signal-To-Noise (OSNR)
                        Power Ratio.  The valid value is 0.00000 to
                        10000.00000 with precision of 5 decimal digits.

                        Current configurable range: 0 to 1000000000.

                        Note:  The OSNR value derived from the MIB value
                        (after dividing by 100000) is the linear inverse
                        of the real value in dB.  To convert the MIB value
                        to a value in dB, use 10 * log(MIBvalue/100000),
                        e.g., 10 * log(100000000/100000 ) = 30 dB."
        ::= { tnGmreOptLineImpEntry 7 }

    tnGmreOptLineImpNLPNP OBJECT-TYPE
        SYNTAX         Unsigned32 (0..99900000)
        UNITS          "percentage"
        MAX-ACCESS     read-create
        STATUS         current
        DESCRIPTION    "GMRE OPTLINE Non-Linear Phase Negative-Positive
                        (NLPNP).
                        The valid value
                        is 0.00000 to 999.00000 with precision of 5
                        decimal digits.

                        Current configurable range: 0 to 99900000."
        ::= { tnGmreOptLineImpEntry 8 }

    tnGmreOptLineImpOSNRNP OBJECT-TYPE
        SYNTAX         Unsigned32 (0..1000000000)
        MAX-ACCESS     read-create
        STATUS         current
        DESCRIPTION    "GMRE OPTLINE Optical Signal-To-Noise Negative-
                        Positive (OSNRNP) Power Ratio.  The valid value
                        is 0.00000 to 10000.00000 with precision of 5
                        decimal digits.

                        Current configurable range: 0 to 1000000000.

                        Note:  The OSNR value derived from the MIB value
                        (after dividing by 100000) is the linear inverse
                        of the real value in dB.  To convert the MIB value
                        to a value in dB, use 10 * log(MIBvalue/100000),
                        e.g., 10 * log(100000000/100000) = 30 dB."
        ::= { tnGmreOptLineImpEntry 9 }

    tnGmreOptLineImpRowStatus OBJECT-TYPE
        SYNTAX         RowStatus
        MAX-ACCESS     read-create
        STATUS         current
        DESCRIPTION    "Row Status of Optical Line Impairment entry.
                        Supported values are active, createAndGo, and
                        destroy."
        ::= { tnGmreOptLineImpEntry 10 }

    tnGmreOptLineImpPower OBJECT-TYPE
        SYNTAX         Unsigned32 (0..40500)
        UNITS          "micro-Watts"
        MAX-ACCESS     read-create
        STATUS         current
        DESCRIPTION    "GMRE OPTLINE Power.  The valid values are 0 to
                        40.50 milli-Watts and the default is 0.79
                        milli-Watt.

                        Current configurable range: 0 to 40500."
        DEFVAL         { 790 }
        ::= { tnGmreOptLineImpEntry 11 }

--------------------------------------------------------------------------------
-- ASON Topology Connectivity Alarm Scalar
--------------------------------------------------------------------------------
    tnAsonTopoAlarmAttributeTotal OBJECT-TYPE
        SYNTAX         Integer32
        MAX-ACCESS     read-only
        STATUS         current
        DESCRIPTION    ""
        ::= { tnAsonTopoAlarm 1 }

--------------------------------------------------------------------------------
-- ASON Topology Connectivity Alarm Table
--------------------------------------------------------------------------------
    tnAsonTopoAlarmTable OBJECT-TYPE
        SYNTAX         SEQUENCE OF TnAsonTopoAlarmEntry
        MAX-ACCESS     not-accessible
        STATUS         current
        DESCRIPTION    ""
        ::= { tnAsonTopoAlarm 2 }

    tnAsonTopoAlarmEntry OBJECT-TYPE
        SYNTAX         TnAsonTopoAlarmEntry
        MAX-ACCESS     not-accessible
        STATUS         current
        DESCRIPTION    ""
        INDEX { ifIndex }
        ::= { tnAsonTopoAlarmTable 1 }

    TnAsonTopoAlarmEntry ::=
        SEQUENCE {
            tnAsonTopoClearAlarm    TnCommand
        }

    tnAsonTopoClearAlarm OBJECT-TYPE
        SYNTAX         TnCommand
        MAX-ACCESS     read-create
        STATUS         current
        DESCRIPTION    "Clears ASON topology connectivity alarm."
        DEFVAL         { noCmd }
        ::= { tnAsonTopoAlarmEntry 1 }

--------------------------------------------------------------------------------
--  ASON Feasibility File Transfer Parameters
--------------------------------------------------------------------------------
    tnAsonFeasibilityCommand OBJECT-TYPE
        SYNTAX         INTEGER {
                         noCmd(1),
                         transferFromRemote(2)
                       }
        MAX-ACCESS     read-write
        STATUS         current
        DESCRIPTION    "This attribute is used to start the feasibility
                        file transfer."
        DEFVAL         { noCmd }
        ::= { tnAsonFeasibility 1 }

    tnAsonFeasibilityRemoteHostIp OBJECT-TYPE
        SYNTAX         IpAddress
        MAX-ACCESS     read-write
        STATUS         current
        DESCRIPTION    "This attribute is used for the ip address of the
                        remote server where the feasibility file resides."

        DEFVAL         { "0.0.0.0" }
        ::= { tnAsonFeasibility 2 }

    tnAsonFeasibilityRemotePath OBJECT-TYPE
        SYNTAX         SnmpAdminString (SIZE(0..255))
        MAX-ACCESS     read-write
        STATUS         current
        DESCRIPTION    "This attribute is used for the path and filename
                        on the remote server to indicate which feasibility
                        file to transfer."
        DEFVAL         { "" }
        ::= { tnAsonFeasibility 3 }

    tnAsonFeasibilityStatus OBJECT-TYPE
        SYNTAX         SnmpAdminString (SIZE(0..255))
        MAX-ACCESS     read-only
        STATUS         current
        DESCRIPTION    "This attribute indicates the status of the
                        previously executed tnAsonFeasibilityCommand
                        operation.  Here are the status strings:

                        * Success
                        * Remote transfer in progress
                        * Failed - Remote path exceeds the max length
                                   of 127 characters
                        * Failed - The remote path must specify a file
                        * Failed - Cannot transfer file while operation
                                   already in progress
                        * Failed - Invalid protocol (only tftp or sftp is
                                   allowed)
                        * Failed - Local error
                        * Failed - Network error
                        * Failed - Remote server error
                        * Failed - Invalid remote server IP address
                        * Failed - Unknown Error
                        * Failed - Authorization failed
                        * Failed - File permission(s) failed
                        * Failed - <Unknown error code>."
        DEFVAL         { "" }
        ::= { tnAsonFeasibility 4 }

    tnAsonFeasibilityLastTransferredVersion OBJECT-TYPE
        SYNTAX         SnmpAdminString (SIZE(0..255))
        MAX-ACCESS     read-only
        STATUS         current
        DESCRIPTION    "This attribute indicates the version of the
                        feasibility file that was last transferred
                        successfully."
        DEFVAL         { "" }
        ::= { tnAsonFeasibility 5 }

    tnAsonFeasibilityProtocol OBJECT-TYPE
        SYNTAX         AluWdmTransferProtocol
        MAX-ACCESS     read-write
        STATUS         current
        DESCRIPTION    "This attributes indicates the feasibility file
                        transfer protocol."
        DEFVAL         { tftp }
        ::= { tnAsonFeasibility 6 }

    tnAsonFeasibilityUserId OBJECT-TYPE
        SYNTAX         SnmpAdminString (SIZE(0..128))
        MAX-ACCESS     read-write
        STATUS         current
        DESCRIPTION    "The userId used to access the feasibility file
                        transfer server."
        DEFVAL         { "" }
        ::= { tnAsonFeasibility 7 }

    tnAsonFeasibilityPassword OBJECT-TYPE
        SYNTAX         SnmpAdminString (SIZE(0..128))
        MAX-ACCESS     read-write
        STATUS         current
        DESCRIPTION    "The password used to access the feasibility file
                        transfer server.

                        When read, this attribute will return an empty
                        string if the password has not been set and
                        '********' if it has been set."
        DEFVAL         { "" }
        ::= { tnAsonFeasibility 8 }

--------------------------------------------------------------------------------
-- ASON Manager Access Control Device Scalar
--------------------------------------------------------------------------------
    tnAsonMgracdAttributeTotal OBJECT-TYPE
        SYNTAX         Integer32
        MAX-ACCESS     read-only
        STATUS         current
        DESCRIPTION    ""
        ::= { tnAsonMgracdInfo 1 }

--------------------------------------------------------------------------------
-- ASON Manager Access Control Device
--------------------------------------------------------------------------------
    tnAsonMgracdTable OBJECT-TYPE
        SYNTAX         SEQUENCE OF TnAsonMgracdEntry
        MAX-ACCESS     not-accessible
        STATUS         current
        DESCRIPTION    ""
        ::= { tnAsonMgracdInfo 2 }

    tnAsonMgracdEntry OBJECT-TYPE
        SYNTAX         TnAsonMgracdEntry
        MAX-ACCESS     not-accessible
        STATUS         current
        DESCRIPTION    ""
        INDEX { ifIndex }
        ::= { tnAsonMgracdTable 1 }

    TnAsonMgracdEntry ::=
        SEQUENCE {
            tnAsonOchMgracd       AluWdmAccessControlDevice,
            tnAsonOmsochifMgracd  AluWdmAccessControlDevice,
            tnAsonOtsMgracd       AluWdmAccessControlDevice
        }

    tnAsonOchMgracd OBJECT-TYPE
        SYNTAX         AluWdmAccessControlDevice
        MAX-ACCESS     read-create
        STATUS         current
        DESCRIPTION    "This attribute indicates ownership of the OCH
                        entity."
        DEFVAL         { null }
        ::= { tnAsonMgracdEntry 1 }

    tnAsonOmsochifMgracd OBJECT-TYPE
        SYNTAX         AluWdmAccessControlDevice
        MAX-ACCESS     read-create
        STATUS         current
        DESCRIPTION    "This attribute indicates ownership of the
                        OMSOCHIF entity."
        DEFVAL         { null }
        ::= { tnAsonMgracdEntry 2 }

    tnAsonOtsMgracd OBJECT-TYPE
        SYNTAX         AluWdmAccessControlDevice
        MAX-ACCESS     read-create
        STATUS         current
        DESCRIPTION    "This attribute indicates ownership of the OTS
                        entity."
        DEFVAL         { null }
        ::= { tnAsonMgracdEntry 3 }

--------------------------------------------------------------------------------
-- GMRE OMS WavelengthSet Encoding Scalar
--------------------------------------------------------------------------------
    tnGmreOmsWavelengthSetAttributeTotal OBJECT-TYPE
        SYNTAX         Integer32
        MAX-ACCESS     read-only
        STATUS         current
        DESCRIPTION    ""
        ::= { tnAsonOmsWavelengthSet 1 }

--------------------------------------------------------------------------------
-- GMRE OMS WavelengthSet Encoding parameters
--------------------------------------------------------------------------------
    tnGmreOmsWavelengthSetTable OBJECT-TYPE
        SYNTAX         SEQUENCE OF TnGmreOmsWavelengthSetEntry
        MAX-ACCESS     not-accessible
        STATUS         current
        DESCRIPTION    ""
        ::= { tnAsonOmsWavelengthSet 2 }

    tnGmreOmsWavelengthSetEntry OBJECT-TYPE
        SYNTAX         TnGmreOmsWavelengthSetEntry
        MAX-ACCESS     not-accessible
        STATUS         current
        DESCRIPTION    ""
        INDEX { ifIndex,
                tnGmreOmsWavelengthEncodingType }
        ::= { tnGmreOmsWavelengthSetTable 1 }

    TnGmreOmsWavelengthSetEntry ::=
        SEQUENCE {
          tnGmreOmsWavelengthEncodingType    INTEGER,
          tnGmreOmsWavelengthEncodingBitMap  OCTET STRING
        }

    tnGmreOmsWavelengthEncodingType OBJECT-TYPE
        SYNTAX         INTEGER {
                         nrz(1),      -- Non-Return-to-Zero encoding
                         pdpsk(2),    -- Partial Differential Phase Shift Keying
                         coherent(3)  -- Coherent encoding
                       }
        MAX-ACCESS     not-accessible
        STATUS         current
        DESCRIPTION    "GMRE OMS line encoding type for Wavelengths/channels."
        ::= { tnGmreOmsWavelengthSetEntry 1 }

    tnGmreOmsWavelengthEncodingBitMap OBJECT-TYPE
        SYNTAX         OCTET STRING (SIZE(11))
        MAX-ACCESS     read-create
        STATUS         current
        DESCRIPTION    "This attribute provides the wavelengths/channels
                        for encoding types on an OMS line.  It is a fixed
                        size octet string.  Each bit represents an ITU
                        channel.  The ITU channel numbers decrement from
                        the MSB of the first octet, 60.5, 60, 59.5, ...,
                        18, 17.5, 17.  Currently we support 88 channels,
                        requiring 88 bits, or 11 characters, to represent
                        the ITU channels.

                        0 = ITU channel is not part of specified encoding type
                        1 = ITU channel is part of the specified encoding type."
        ::= { tnGmreOmsWavelengthSetEntry 2 }

--------------------------------------------------------------------------------
-- Snapshot of Generic Part for Server Access
--------------------------------------------------------------------------------
    tnAsonSnapshotRemoteHostIp OBJECT-TYPE
        SYNTAX         IpAddress
        MAX-ACCESS     read-write
        STATUS         current
        DESCRIPTION    ""
        DEFVAL         { "0.0.0.0" }
        ::= { tnAsonSnapshot 1 }

    tnAsonSnapshotProtocol OBJECT-TYPE
        SYNTAX         AluWdmTransferProtocol
        MAX-ACCESS     read-write
        STATUS         current
        DESCRIPTION    "This attributes indicates the snapshot protocol."
        ::= { tnAsonSnapshot 2 }

    tnAsonSnapshotUserId OBJECT-TYPE
        SYNTAX         SnmpAdminString
        MAX-ACCESS     read-write
        STATUS         current
        DESCRIPTION    "The userId used to access the snapshot server."
        ::= { tnAsonSnapshot 3 }

    tnAsonSnapshotPassword OBJECT-TYPE
        SYNTAX         SnmpAdminString
        MAX-ACCESS     read-write
        STATUS         current
        DESCRIPTION    "The password used to access the snapshot server.
                        When read, this attribute will return an empty
                        string if the password has not been set and
                        '********' if it has been set."
        ::= { tnAsonSnapshot 4 }

    tnAsonSnapshotRootRemotePath OBJECT-TYPE
        SYNTAX         SnmpAdminString (SIZE(0..255))
        MAX-ACCESS     read-write
        STATUS         current
        DESCRIPTION    "Defines the root directory on the server the
                        snapshot shall be stored.  Must be present when
                        row status of snapshot entries is created.
                        Default is empty string."
        DEFVAL         { "" }
        ::= { tnAsonSnapshot 5 }

--------------------------------------------------------------------------------
-- GMPLS Snapshot Requests Scalars
--------------------------------------------------------------------------------
    tnAsonSnapshotAttributeTotal OBJECT-TYPE
        SYNTAX         Integer32
        MAX-ACCESS     read-only
        STATUS         current
        DESCRIPTION    ""
        ::= { tnAsonSnapshot 6 }

--------------------------------------------------------------------------------
-- GMPLS Snapshot Requests Table
--------------------------------------------------------------------------------
    tnAsonSnapshotTable OBJECT-TYPE
        SYNTAX         SEQUENCE OF TnAsonSnapshotEntry
        MAX-ACCESS     not-accessible
        STATUS         current
        DESCRIPTION    ""
        ::= { tnAsonSnapshot 7 }

    tnAsonSnapshotEntry OBJECT-TYPE
        SYNTAX         TnAsonSnapshotEntry
        MAX-ACCESS     not-accessible
        STATUS         current
        DESCRIPTION    ""
        INDEX { tnAsonSnapshotTime }
        ::= { tnAsonSnapshotTable 1 }

    TnAsonSnapshotEntry ::=
        SEQUENCE {
            tnAsonSnapshotTime           Unsigned32,
            tnAsonSnapshotStatus         SnmpAdminString,
            tnAsonSnapshotRemotePath     SnmpAdminString,
            tnAsonSnapshotRowStatus      RowStatus,
            tnAsonSnapshotFilename       SnmpAdminString
        }

    tnAsonSnapshotTime OBJECT-TYPE
        SYNTAX         Unsigned32
        MAX-ACCESS     not-accessible
        STATUS         current
        DESCRIPTION    "The date and time when the snapshot is scheduled."
        ::= { tnAsonSnapshotEntry 1 }

    tnAsonSnapshotStatus OBJECT-TYPE
        SYNTAX         SnmpAdminString (SIZE(0..255))
        MAX-ACCESS     read-only
        STATUS         current
        DESCRIPTION    "This attribute indicates the status of the
                        schedule snapshot operation. Here are the status
                        strings:

                        * Success
                        * Pending - waiting for scheduled time
                        * Snapshot in progress
                        * failed - timed out - e.g. due to node reset at scheduled time.
                        * failed - remote path exceeds the max length of 127 characters
                        * Failed - local error
                        * Failed - network error
                        * Failed - Remote server error.

                        default at creation time is pending."
        ::= { tnAsonSnapshotEntry 2 }

    tnAsonSnapshotRemotePath OBJECT-TYPE
        SYNTAX         SnmpAdminString (SIZE(0..255))
        MAX-ACCESS     read-create
        STATUS         current
        DESCRIPTION    "Defines the directory on the server the snapshot
                        shall be stored.  Must be present when row status
                        is active. Default is empty string."
        DEFVAL         { "" }
        ::= { tnAsonSnapshotEntry 3 }

    tnAsonSnapshotRowStatus OBJECT-TYPE
        SYNTAX         RowStatus
        MAX-ACCESS     read-create
        STATUS         current
        DESCRIPTION    "The following two values are states, which may be
                        may be read or written:
                        - active(1),        - set only used in combination
                                            - with createAndWait.
                        - notInService(2),  - set should not be used, use a destroy.

                        The following value is a state, which may be read only:
                        - notReady(3),      - never used as cannot be incomplete.

                        The following three values are actions, which may
                        be written but are never read:
                        - createAndGo(4),   - recommended way to use.
                        - createAndWait(5), - not recommended way to use.
                        - destroy(6)        - used to delete the row entry
                                            - after completion."
        ::= { tnAsonSnapshotEntry 4 }

    tnAsonSnapshotFilename OBJECT-TYPE
        SYNTAX         SnmpAdminString (SIZE(0..255))
        MAX-ACCESS     read-only
        STATUS         current
        DESCRIPTION    "This attribute indicates the filename for the
                        snapshot performed on the node.  If none exists,
                        this attribute will return an empty string.  If
                        a snapshot is in progress, this attribute will
                        return an empty string."
        ::= { tnAsonSnapshotEntry 5 }

--------------------------------------------------------------------------------
-- Conformance Group Definitions
--------------------------------------------------------------------------------
    tnAsonGlobalGroup OBJECT-GROUP
        OBJECTS {
            tnGmreNodeIpAddr,
            tnGmreNodeSubMask,
            tnGmreNotifyIpAddr,
            tnGmreNotifySubMask
        }
        STATUS         current
        DESCRIPTION    ""
        ::= { tnAsonGroups 1 }

    tnAsonIorGlobalGroup OBJECT-GROUP
        OBJECTS {
            tnGmreCorbaName,
            tnGmreCorbaHostIpAddress,
            tnGmreCorbaIor
        }
        STATUS         current
        DESCRIPTION    ""
        ::= { tnAsonGroups 2 }

    tnAsonOmsLineImpScalarsGroup OBJECT-GROUP
        OBJECTS {
            tnGmreOmsLineImpAttributeTotal
        }
        STATUS         current
        DESCRIPTION    ""
        ::= { tnAsonGroups 3 }

    tnAsonOmsLineImpGroup OBJECT-GROUP
        OBJECTS {
            tnGmreOmsLineImpMaxAlwCh,
            tnGmreOmsLineImpPMD,
            tnGmreOmsLineImpAlcMode,
            tnGmreOmsLineImpDcuFree,
            tnGmreOmsLineImpCD,
            tnGmreOmsLineImpFiberType
        }
        STATUS         current
        DESCRIPTION    ""
        ::= { tnAsonGroups 4 }

    tnAsonOptLineImpScalarsGroup OBJECT-GROUP
        OBJECTS {
            tnGmreOptLineImpAttributeTotal
        }
        STATUS         current
        DESCRIPTION    ""
        ::= { tnAsonGroups 5 }

    tnAsonOptLineImpGroup OBJECT-GROUP
        OBJECTS {
            tnGmreOptLineImpBitRate,
            tnGmreOptLineImpEncoding,
            tnGmreOptLineImpCompModule,
            tnGmreOptLineImpFecMode,
            tnGmreOptLineImpNLP,
            tnGmreOptLineImpOSNR,
            tnGmreOptLineImpNLPNP,
            tnGmreOptLineImpOSNRNP,
            tnGmreOptLineImpRowStatus,
            tnGmreOptLineImpPower
        }
        STATUS         current
        DESCRIPTION    ""
        ::= { tnAsonGroups 6 }

    tnAsonTopoAlarmScalarsGroup OBJECT-GROUP
        OBJECTS {
            tnAsonTopoAlarmAttributeTotal
        }
        STATUS         current
        DESCRIPTION    ""
        ::= { tnAsonGroups 7 }

    tnAsonTopoAlarmGroup OBJECT-GROUP
        OBJECTS {
            tnAsonTopoClearAlarm
        }
        STATUS         current
        DESCRIPTION    ""
        ::= { tnAsonGroups 8 }

    tnAsonFeasibilityGroup OBJECT-GROUP
        OBJECTS {
            tnAsonFeasibilityCommand,
            tnAsonFeasibilityRemoteHostIp,
            tnAsonFeasibilityRemotePath,
            tnAsonFeasibilityStatus,
            tnAsonFeasibilityLastTransferredVersion,
            tnAsonFeasibilityProtocol,
            tnAsonFeasibilityUserId,
            tnAsonFeasibilityPassword
        }
        STATUS         current
        DESCRIPTION    ""
        ::= { tnAsonGroups 9 }

    tnAsonMgracdScalarsGroup OBJECT-GROUP
        OBJECTS {
            tnAsonMgracdAttributeTotal
        }
        STATUS         current
        DESCRIPTION    ""
        ::= { tnAsonGroups 10 }

    tnAsonMgracdGroup OBJECT-GROUP
        OBJECTS {
            tnAsonOchMgracd,
            tnAsonOmsochifMgracd,
            tnAsonOtsMgracd
        }
        STATUS         current
        DESCRIPTION    ""
        ::= { tnAsonGroups 11 }

    tnAsonOmsWavelengthSetScalarsGroup OBJECT-GROUP
        OBJECTS {
            tnGmreOmsWavelengthSetAttributeTotal
        }
        STATUS         current
        DESCRIPTION    ""
        ::= { tnAsonGroups 12 }

    tnAsonOmsWavelengthSetGroup OBJECT-GROUP
        OBJECTS {
            tnGmreOmsWavelengthEncodingBitMap
        }
        STATUS         current
        DESCRIPTION    ""
        ::= { tnAsonGroups 13 }

    tnAsonSnapshotScalarsGroup OBJECT-GROUP
        OBJECTS {
            tnAsonSnapshotRemoteHostIp,
            tnAsonSnapshotProtocol,
            tnAsonSnapshotUserId,
            tnAsonSnapshotPassword,
            tnAsonSnapshotRootRemotePath,
            tnAsonSnapshotAttributeTotal
        }
        STATUS         current
        DESCRIPTION    ""
        ::= { tnAsonGroups 14 }

    tnAsonSnapshotGroup OBJECT-GROUP
        OBJECTS {
            tnAsonSnapshotStatus,
            tnAsonSnapshotRemotePath,
            tnAsonSnapshotRowStatus,
            tnAsonSnapshotFilename
        }
        STATUS         current
        DESCRIPTION    ""
        ::= { tnAsonGroups 15 }

--------------------------------------------------------------------------------
-- Compliance Statements (mandatory)
--------------------------------------------------------------------------------
    tnAsonCompliance MODULE-COMPLIANCE
        STATUS         current
        DESCRIPTION    ""
        MODULE
        MANDATORY-GROUPS {
            tnAsonGlobalGroup,
            tnAsonIorGlobalGroup,
            tnAsonOmsLineImpScalarsGroup,
            tnAsonOmsLineImpGroup,
            tnAsonOptLineImpScalarsGroup,
            tnAsonOptLineImpGroup,
            tnAsonTopoAlarmScalarsGroup,
            tnAsonTopoAlarmGroup,
            tnAsonFeasibilityGroup,
            tnAsonMgracdScalarsGroup,
            tnAsonMgracdGroup,
            tnAsonOmsWavelengthSetScalarsGroup,
            tnAsonOmsWavelengthSetGroup,
            tnAsonSnapshotScalarsGroup,
            tnAsonSnapshotGroup
        }
        ::= { tnAsonCompliances 1 }

END -- DEFINITION OF TROPIC-ASON-MIB
