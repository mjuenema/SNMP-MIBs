TROPIC-OTUODU-MIB DEFINITIONS ::= BEGIN

-- (c) Copyright 2016 Nokia.  All rights reserved.
-- This software is the confidential and proprietary property of
-- Nokia and may only be used in accordance with the
-- terms of the license agreement provided with this software.

 IMPORTS
      OBJECT-TYPE, MODULE-IDENTITY,
      Unsigned32, Integer32, Counter64        FROM SNMPv2-SMI
      MODULE-COMPLIANCE, OBJECT-GROUP         FROM SNMPv2-CONF
      TruthValue,
      ifIndex                                 FROM IF-MIB
      AluWdmFecMode,
      AluWdmPortOchOtuRate,
      AluWdmTtiStatus,
      AluWdmEnabledDisabled,
      AluWdmOdukStatus,
      TropicOperationalCapabilityType,
      TnCommand,
      TropicStateQualifierType                FROM TROPIC-TC
      tnPortModules, tnOtuOduMIB              FROM TROPIC-GLOBAL-REG;

  tnOtuOduMibModule MODULE-IDENTITY
      LAST-UPDATED    "201603231200Z"
      ORGANIZATION    "Nokia"
      CONTACT-INFO    "Nokia
                       Postal: 600 March Rd.
                       Kanata, Ontario
                       Canada K2K 2E6

                       Phone: +1 613 591 3600
                       Fax:   +1 613 591 3680"

      DESCRIPTION "OTUk ODUk MIB types."

      REVISION    "201011141200Z"
      DESCRIPTION "Added the following tables:
                   tnOtukTable
                   tnOdukTable
                   tnOdukXcTable
                   tnOdukApsXcTable
                   tnOdukApsMemberTable."

      REVISION    "201011221200Z"
      DESCRIPTION "Added the following tables:
                   tnTxOptsgTable
                   tnExpOptsgTable
                   tnRxOptsgTable."

      REVISION    "201011241200Z"
      DESCRIPTION "1) Changed INDEX of the following MIB tables:
                      tnOdukXcTable
                      tnOdukApsMemberTable.
                   2) Renamed tnOdukXcType to tnOdukXcRate in
                      tnOdukXcTable.
                   3) Deleted tnOdukApsXcTable.
                   4) Added tnOdukApsGroupTable.
                   5) Changed SYNTAX of the following from OCTET STRING
                      to SnmpAdminString:
                      tnOdukTxOduStruct
                      tnOdukRxOduStruct
                      tnOdukExpOduStruct
                      tnOdukXcName
                      tnTxOptsgTSMap
                      tnExpOptsgTSMap
                      tnRxOptsgTSMap."

      REVISION    "201102231200Z"
      DESCRIPTION "1) Added the following to tnOtukTable:
                      tnOtukIncRes.
                   2) Added the following to tnOdukTable:
                      tnOdukIncFwFTFLTypeID
                      tnOdukIncFwFTFLOperID
                      tnOdukIncBwFTFLTypeID
                      tnOdukIncBwFTFLOperID
                      tnOdukIncExp."

      REVISION    "201103041200Z"
      DESCRIPTION "1) Added the following to tnOdukApsGroupTable:
                      tnOdukApsGroupID.
                   2) Added the following entry and table:
                      tnOdukApsGroupIdAttributeTotal
                      tnOdukApsGroupIdTable."

      REVISION    "201103301200Z"
      DESCRIPTION "1) Updated the value of tnOdukXcRate from oduflex(3)
                      to oduflexFc400(3).
                   2) Added the following to tnOdukXcRate:
                      oduflex3gsdi(5)."

      REVISION    "201104251200Z"
      DESCRIPTION "Added the following to tnOdukApsGroupTable:
                   tnOdukApsGroupK1K2Trans."

      REVISION    "201107221200Z"
      DESCRIPTION "Added the following to tnOdukApsGroupTable:
                   tnOdukApsXcBidirectional."

      REVISION    "201204101200Z"
      DESCRIPTION "Added the following to tnOdukXcRate:
                   oduflexsdr(6)."

      REVISION    "201208221200Z"
      DESCRIPTION "Added the following to tnOtukTable:
                   tnOtukAdminStatus
                   tnOtukStateAINS
                   tnOtukOperStatus
                   tnOtukStateQualifier
                   tnOtukOperationalCapability."

      REVISION    "201209241200Z"
      DESCRIPTION "Added the following to tnOtukTable:
                   tnOtukAINSDebounceTime
                   tnOtukUsingSysAINSDebounceTime
                   tnOtukAINSDebounceTimeRemaining."

      REVISION    "201209281200Z"
      DESCRIPTION "Added the following to tnOtukTable:
                   tnOtukForceAdminStatus."

      REVISION    "201210221200Z"
      DESCRIPTION "Added the following to tnOtukTable:
                   tnOtukPreFec
                   tnOtukPostFec."

      REVISION    "201212051200Z"
      DESCRIPTION "Added the following to tnOtukTable:
                   tnOtukTtpPresent."

      REVISION    "201303141200Z"
      DESCRIPTION "Added the following to tnOtukTable:
                   tnOtukAsymInterworking."

      REVISION    "201304161200Z"
      DESCRIPTION "Marked the following as obsolete:
                   tnOdukTable
                   tnOdukXcTable
                   tnOdukApsGroupTable
                   tnOdukApsMemberTable
                   tnTxOptsgTable
                   tnExpOptsgTable
                   tnRxOptsgTable
                   tnOdukApsGroupIdTable."

      REVISION    "201402261200Z"
      DESCRIPTION "1) Marked the following as obsolete:
                      tnOtukForceAdminStatus
                      tnOtukTtpPresent.
                   2) Added ranges and DEFVAL to attributes."

      REVISION    "201410311200Z"
      DESCRIPTION "Changed the syntax of tnOtukRate 
                   to read-only in tnOtukTable."

      REVISION    "201411131200Z"
      DESCRIPTION "1) Added the following to tnOtukTable:
                      tnOtukDegThr 
                      tnOtukDegM  
                      tnOtukDapiAccepted 
                      tnOtukDapiExpected
                      tnOtukDapiTransmitted
                      tnOtukOsAccepted
                      tnOtukOsTransmitted."

      REVISION    "201411131200Z"
      DESCRIPTION "Added the following to tnOtukTable:
                   tnOtuAlmProfName."  
                 
      REVISION    "201507171200Z"
      DESCRIPTION "Added the following to tnOtukTable:
                   tnOtuServerPort."

      REVISION    "201603021200Z"
      DESCRIPTION "Added the following table:
                   tnOtuApaTable."

      REVISION    "201603021200Z"
      DESCRIPTION "Added the following to tnOtukTable:
                   tnOtukMgracd."
     
     ::= { tnPortModules 5 }

  tnOtuOduConf         OBJECT IDENTIFIER ::= { tnOtuOduMIB 1 }
  tnOtuOduGroups       OBJECT IDENTIFIER ::= { tnOtuOduConf 1 }
  tnOtuOduCompliances  OBJECT IDENTIFIER ::= { tnOtuOduConf 2 }
  tnOtuOduObjs         OBJECT IDENTIFIER ::= { tnOtuOduMIB 2 }
  tnOtuOduBasics       OBJECT IDENTIFIER ::= { tnOtuOduObjs 1 }

--------------------------------------------------------------------------------
-- Textual Conventions
--------------------------------------------------------------------------------

--------------------------------------------------------------------------------
-- Otuk Table
--------------------------------------------------------------------------------
    tnOtukTable OBJECT-TYPE
        SYNTAX         SEQUENCE OF TnOtukEntry
        MAX-ACCESS     not-accessible
        STATUS         current
        DESCRIPTION    "Table of Otuk attributes."
        ::= { tnOtuOduBasics 1 }

    tnOtukEntry OBJECT-TYPE
        SYNTAX         TnOtukEntry
        MAX-ACCESS     not-accessible
        STATUS         current
        DESCRIPTION    ""
        INDEX { ifIndex }
        ::= { tnOtukTable 1 }

    TnOtukEntry ::=
        SEQUENCE {
            tnOtukTtiStatus                     AluWdmTtiStatus,
            tnOtukFecMode                       AluWdmFecMode,
            tnOtukRate                          AluWdmPortOchOtuRate,
            tnOtukIncRes                        OCTET STRING,
            tnOtukAdminStatus                   AluWdmOdukStatus,
            tnOtukStateAINS                     TruthValue,
            tnOtukOperStatus                    AluWdmOdukStatus,
            tnOtukStateQualifier                TropicStateQualifierType,
            tnOtukOperationalCapability         TropicOperationalCapabilityType,
            tnOtukAINSDebounceTime              Integer32,
            tnOtukUsingSysAINSDebounceTime      TruthValue,
            tnOtukAINSDebounceTimeRemaining     Unsigned32,
--            obsolete
--            tnOtukForceAdminStatus              TnCommand,
            tnOtukPreFec                        Counter64,
            tnOtukPostFec                       Counter64,
--            obsolete
--            tnOtukTtpPresent                    TruthValue,
            tnOtukAsymInterworking              TruthValue,
            tnOtukDegThr                        Unsigned32,
            tnOtukDegM                          Unsigned32,
            tnOtukDapiAccepted                  OCTET STRING,
            tnOtukDapiExpected                  OCTET STRING,
            tnOtukDapiTransmitted               OCTET STRING,
            tnOtukOsAccepted                    OCTET STRING,
            tnOtukOsTransmitted                 OCTET STRING,
            tnOtuAlmProfName                    OCTET STRING,
            tnOtuServerPort                     INTEGER,
            tnOtukMgracd                        INTEGER
        }

    tnOtukTtiStatus OBJECT-TYPE
        SYNTAX         AluWdmTtiStatus
        MAX-ACCESS     read-only
        STATUS         current
        DESCRIPTION    "Otuk TTI status."
        DEFVAL         { unspecified }
        ::= { tnOtukEntry 1 }

    tnOtukFecMode OBJECT-TYPE
        SYNTAX         AluWdmFecMode
        MAX-ACCESS     read-create
        STATUS         current
        DESCRIPTION    "Otuk FEC mode."
        DEFVAL         { enhancedFec }
        ::= { tnOtukEntry 2 }

    tnOtukRate OBJECT-TYPE
        SYNTAX         AluWdmPortOchOtuRate
        MAX-ACCESS     read-only
        STATUS         current
        DESCRIPTION    "Otuk Rate."
        DEFVAL         { otm10G709 }
        ::= { tnOtukEntry 3 }

    tnOtukIncRes OBJECT-TYPE
        SYNTAX         OCTET STRING
        MAX-ACCESS     read-only
        STATUS         current
        DESCRIPTION    "OTUk incoming res (reserved for future
                        international standardization)."
        DEFVAL         { "" }
        ::= { tnOtukEntry 4 }

    tnOtukAdminStatus OBJECT-TYPE
        SYNTAX         AluWdmOdukStatus
        MAX-ACCESS     read-create
        STATUS         current
        DESCRIPTION    "OTUk administrative state.  It may be used to
                        suppress the alarms or disable consequent
                        actions on the OTU entity."
        DEFVAL         { down }
        ::= { tnOtukEntry 5 }

    tnOtukStateAINS OBJECT-TYPE
        SYNTAX         TruthValue
        MAX-ACCESS     read-create
        STATUS         current
        DESCRIPTION    "OTUk state AINS attributes."
        DEFVAL         { false }
        ::= { tnOtukEntry 6 }

    tnOtukOperStatus OBJECT-TYPE
        SYNTAX         AluWdmOdukStatus
        MAX-ACCESS     read-only
        STATUS         current
        DESCRIPTION    "OTUk operational state of the interface."
        DEFVAL         { down }
        ::= { tnOtukEntry 7 }

    tnOtukStateQualifier OBJECT-TYPE
        SYNTAX         TropicStateQualifierType
        MAX-ACCESS     read-only
        STATUS         current
        DESCRIPTION    "Indicates the state qualifier (i.e., the
                        secondary state) of the OTUk state."
        ::= { tnOtukEntry 8 }

    tnOtukOperationalCapability OBJECT-TYPE
        SYNTAX         TropicOperationalCapabilityType
        MAX-ACCESS     read-only
        STATUS         current
        DESCRIPTION    "The partiallyEnabled(3) state means an abnormal
                        state."
        DEFVAL         { disabled }
        ::= { tnOtukEntry 9 }

    tnOtukAINSDebounceTime OBJECT-TYPE
        SYNTAX         Integer32
        UNITS          "Seconds"
        MAX-ACCESS     read-create
        STATUS         current
        DESCRIPTION    "This attribute must be set in multiples of 60s.
                        It is equal to System AINS Debounce Time when
                        Port AINS Use System Default is true.  Setting
                        the OTUk AINS Debounce Time and OTUk AINS Use
                        System Default to true in the same set request
                        is restricted.

                        Current configurable range: 1m to 96h 0m."
        ::= { tnOtukEntry 10 }

    tnOtukUsingSysAINSDebounceTime OBJECT-TYPE
        SYNTAX         TruthValue
        MAX-ACCESS     read-create
        STATUS         current
        DESCRIPTION    "Using System AINS Debounce Time.  Sets with a
                        value of false are restricted.  The network
                        operator must set OTUk AINS Debounce Time to
                        some valid value to disable the use of System
                        AINS Debounce Time.  Setting the Port AINS
                        Debounce Time and Port AINS Use System Default
                        to true in the same set request is restricted."
        ::= { tnOtukEntry 11 }

    tnOtukAINSDebounceTimeRemaining OBJECT-TYPE
        SYNTAX         Unsigned32
        MAX-ACCESS     read-only
        STATUS         current
        DESCRIPTION    "Number of seconds until the OTUk AINS DebounceTime
                        expires.  If Port AINS is false or Port AINS
                        Debounce Time is 0, the value of this attribute
                        will be 0 ."
        DEFVAL         { 0 }
        ::= { tnOtukEntry 12 }

--    obsolete
--    tnOtukForceAdminStatus OBJECT-TYPE ::= { tnOtukEntry 13 }

    tnOtukPreFec OBJECT-TYPE
        SYNTAX         Counter64
        MAX-ACCESS     read-only
        STATUS         current
        DESCRIPTION    "Real time error bit rate of pre-FEC (Forward
                        Error Correction).

                        Current range: 0 to 4000."
        ::= { tnOtukEntry 14 }

    tnOtukPostFec OBJECT-TYPE
        SYNTAX         Counter64
        MAX-ACCESS     read-only
        STATUS         current
        DESCRIPTION    "Real time error bit rate of post-FEC (Forward
                        Error Correction).

                        Current range: 0 to 4000."
        ::= { tnOtukEntry 15 }

--    obsolete
--    tnOtukTtpPresent OBJECT-TYPE ::= { tnOtukEntry 16 }

    tnOtukAsymInterworking OBJECT-TYPE
        SYNTAX         TruthValue
        MAX-ACCESS     read-create
        STATUS         current
        DESCRIPTION    "Otuk asymmetric interworking."
        DEFVAL         { false }
        ::= { tnOtukEntry 17 }

    tnOtukDegThr OBJECT-TYPE
        SYNTAX         Unsigned32
        MAX-ACCESS     read-create
        STATUS         current
        DESCRIPTION    "Specifies the burst threshold as a number
                        of errored blocks on the ODU layer.
                        A second is declared as good if the number
                        of detected errored blocks within one second
                        is less than tnOtukDegThr, otherwise the
                        second is declared as bad second."
        ::= { tnOtukEntry 18 }

    tnOtukDegM OBJECT-TYPE
        SYNTAX         Unsigned32
        MAX-ACCESS     read-create
        STATUS         current
        DESCRIPTION    "Specifies the number of consecutive bad seconds
                        to be detected before declaring a signal degrade
                        defect on the ODU.  The defect is cleared if
                        tnOtukDegM consecutive good seconds  are detected.
                    
                        Current Configurable Range:

                        2 to 10."
        ::= { tnOtukEntry 19 }

    tnOtukDapiAccepted OBJECT-TYPE
        SYNTAX         OCTET STRING (SIZE(0..15))
        MAX-ACCESS     read-only
        STATUS         current
        DESCRIPTION    "The DAPI bytes received."
        ::= { tnOtukEntry 20 }

    tnOtukDapiExpected OBJECT-TYPE
        SYNTAX         OCTET STRING (SIZE(0..15))
        MAX-ACCESS     read-create
        STATUS         current
        DESCRIPTION    "The DAPI bytes expected by the receiver."
        ::= { tnOtukEntry 21 }

    tnOtukDapiTransmitted OBJECT-TYPE
        SYNTAX         OCTET STRING (SIZE(0..15))
        MAX-ACCESS     read-create
        STATUS         current
        DESCRIPTION    "The DAPI bytes transmitted.  The TTI[17] to
                        TTI[31] contain the 15-character destination
                        access point identifier(DAPI)."
        ::= { tnOtukEntry 22 }

    tnOtukOsAccepted OBJECT-TYPE
        SYNTAX         OCTET STRING (SIZE(0..32))
        MAX-ACCESS     read-only
        STATUS         current
        DESCRIPTION    "The OS bytes received."
        ::= { tnOtukEntry 23 }

    tnOtukOsTransmitted  OBJECT-TYPE
        SYNTAX         OCTET STRING (SIZE(0..32))
        MAX-ACCESS     read-create
        STATUS         current
        DESCRIPTION    "The OS bytes transmitted.  The TTI[32] to
                        TTI[63] contain the 32-character Operator
                        Specific(OS)."
        ::= { tnOtukEntry 24 }

    tnOtuAlmProfName   OBJECT-TYPE
        SYNTAX         OCTET STRING
        MAX-ACCESS     read-create
        STATUS         current
        DESCRIPTION    ""
        ::= { tnOtukEntry 25 }

    tnOtuServerPort   OBJECT-TYPE
        SYNTAX         INTEGER {
                        unassigned(0),
                        spL1Ch1(11), 
                        spL1Ch2(12), 
                        spL1Ch3(13), 
                        spL1Ch4(14), 
                        spL1L2Ch4(34), 
                        spL1L2Ch5(35), 
                        spL2Ch2(22), 
                        spL2Ch1(21), 
                        spL1L2Ch1(31), 
                        spL1L2Ch2(32), 
                        spL1L2Ch3(33)
             }
        MAX-ACCESS     read-create
        STATUS         current
        DESCRIPTION    "Server port types."
        ::= { tnOtukEntry 26 }

    tnOtukMgracd  OBJECT-TYPE
        SYNTAX         INTEGER {
                          none(1),
                          cp(2),
                          mgnpln(3),
                          cpmgnpln(4)
              }
        MAX-ACCESS     read-create
        STATUS         current
        DESCRIPTION    "Indicates if managed by CP, MGNPLN, shared by both or free."
        DEFVAL         { none }
        ::= { tnOtukEntry 27 }

--    obsolete
--    tnOdukTable OBJECT-TYPE ::= { tnOtuOduBasics 2 }
--    tnOdukXcTable OBJECT-TYPE ::= { tnOtuOduBasics 3 }
--    tnOdukApsGroupTable OBJECT-TYPE ::= { tnOtuOduBasics 4 }
--    tnOdukApsMemberTable OBJECT-TYPE ::= { tnOtuOduBasics 5 }
--    tnTxOptsgTable OBJECT-TYPE ::= { tnOtuOduBasics 6 }
--    tnExpOptsgTable OBJECT-TYPE ::= { tnOtuOduBasics 7 }
--    tnRxOptsgTable OBJECT-TYPE ::= { tnOtuOduBasics 8 }
--    tnOdukApsGroupIdAttributeTotal OBJECT-TYPE ::= { tnOtuOduBasics 9 }
--    tnOdukApsGroupIdTable OBJECT-TYPE ::= { tnOtuOduBasics 10 }

--------------------------------------------------------------------------------
-- Automatic Pre-emphasis Adjustment - Table
--------------------------------------------------------------------------------
    tnOtuApaTable OBJECT-TYPE
        SYNTAX         SEQUENCE OF TnOtuApaEntry
        MAX-ACCESS     not-accessible
        STATUS         current
        DESCRIPTION    "Table of APA attributes."
        ::= { tnOtuOduBasics 11 }

    tnOtuApaEntry OBJECT-TYPE
        SYNTAX         TnOtuApaEntry
        MAX-ACCESS     not-accessible
        STATUS         current
        DESCRIPTION    ""
        INDEX { ifIndex, tnOtuApaInterval }
        ::= { tnOtuApaTable 1 }
    
    TnOtuApaEntry ::=
        SEQUENCE {
            tnOtuApaInterval                    Integer32,
            tnOtuApaPreFecBer                   Counter64,
            tnOtuApaFecUncorrCnt                Counter64
    }

    tnOtuApaInterval OBJECT-TYPE
        SYNTAX         Integer32(1..60)
        MAX-ACCESS     not-accessible
        STATUS         current
        DESCRIPTION    ""
        DEFVAL         { 1 }
        ::= { tnOtuApaEntry 1 }
    
    tnOtuApaPreFecBer OBJECT-TYPE
        SYNTAX         Counter64
        MAX-ACCESS     read-only
        STATUS         current
        DESCRIPTION    ""
        ::= { tnOtuApaEntry 2 }

    tnOtuApaFecUncorrCnt OBJECT-TYPE
        SYNTAX         Counter64
        MAX-ACCESS     read-only
        STATUS         current
        DESCRIPTION    ""
        ::= { tnOtuApaEntry 3 }

--------------------------------------------------------------------------------
-- Conformance Group Definitions
--------------------------------------------------------------------------------
    tnOtukGroup OBJECT-GROUP
        OBJECTS {
            tnOtukTtiStatus,
            tnOtukFecMode,
            tnOtukRate,
            tnOtukIncRes,
            tnOtukAdminStatus,
            tnOtukStateAINS,
            tnOtukOperStatus,
            tnOtukStateQualifier,
            tnOtukOperationalCapability,
            tnOtukAINSDebounceTime,
            tnOtukUsingSysAINSDebounceTime,
            tnOtukAINSDebounceTimeRemaining,
--            obsolete
--            tnOtukForceAdminStatus,
            tnOtukPreFec,
            tnOtukPostFec,
--            obsolete
--            tnOtukTtpPresent,
            tnOtukAsymInterworking,
            tnOtukDegThr,
            tnOtukDegM,
            tnOtukDapiAccepted, 
            tnOtukDapiExpected,
            tnOtukDapiTransmitted,
            tnOtukOsAccepted,
            tnOtukOsTransmitted,
            tnOtuAlmProfName,
            tnOtuServerPort,
            tnOtukMgracd
        }
        STATUS         current
        DESCRIPTION    ""
        ::= { tnOtuOduGroups 1 }

--    obsolete
--    tnOdukGroup OBJECT-GROUP ::= { tnOtuOduGroups 2 }
--    tnOdukXcGroup OBJECT-GROUP ::= { tnOtuOduGroups 3 }
--    tnOdukApsGroupGroup OBJECT-GROUP ::= { tnOtuOduGroups 4 }
--    tnOdukApsMemberGroup OBJECT-GROUP ::= { tnOtuOduGroups 5 }
--    tnTxOptsgGroup OBJECT-GROUP ::= { tnOtuOduGroups 6 }
--    tnExpOptsgGroup OBJECT-GROUP ::= { tnOtuOduGroups 7 }
--    tnRxOptsgGroup OBJECT-GROUP ::= { tnOtuOduGroups 8 }
--    tnOdukApsGroupIdScalarsGroup OBJECT-GROUP ::= { tnOtuOduGroups 9 }
--    tnOdukApsGroupIdGroup OBJECT-GROUP ::= { tnOtuOduGroups 10 }

    tnOtuApaGroup OBJECT-GROUP
        OBJECTS {
            tnOtuApaInterval,
            tnOtuApaPreFecBer,
            tnOtuApaFecUncorrCnt
        }
        STATUS         current
        DESCRIPTION    ""
        ::= { tnOtuOduGroups 11 }

--------------------------------------------------------------------------------
-- Compliance Statements (mandatory)
--------------------------------------------------------------------------------
    tnOdukCompliance MODULE-COMPLIANCE
        STATUS         current
        DESCRIPTION    ""
        MODULE
        MANDATORY-GROUPS {
            tnOtukGroup,
--            obsolete
--            tnOdukGroup,
--            tnOdukXcGroup,
--            tnOdukApsGroupGroup,
--            tnOdukApsMemberGroup,
--            tnTxOptsgGroup,
--            tnExpOptsgGroup,
--            tnRxOptsgGroup,
--            tnOdukApsGroupIdScalarsGroup,
--            tnOdukApsGroupIdGroup
            tnOtuApaGroup
        }
        ::= { tnOtuOduCompliances 1 }

END -- DEFINITION OF TROPIC-OTUODU-MIB
