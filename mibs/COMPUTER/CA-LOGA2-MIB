--MibName=caiLogA2
--
-- ========================================================================
--
--               COMPUTER ASSOCIATES INTERNATIONAL, INC.
--               Proprietary and Confidential Information
--
-- This material contains, and is part of a computer software program
-- which is, proprietary and confidential information owned by COMPUTER
-- ASSOCIATES INTERNATIONAL, INC.  The program, including this material,
-- may not be duplicated, disclosed or reproduced in whole or in part for
-- any purpose without the express written authorization of COMPUTER
-- ASSOCIATES. All authorized reproductions must be marked with this
-- legend.
--                 Computer Associates International, Inc
--
--                          Copyright (c) 1997 - 2001
--                       The Software that Manages eBusiness
--                          All rights reserved
--
--
-- ------------------------------------------------------------------------
-- MIB name: caiLogA2
-- ------------------------------------------------------------------------
-- Version:
-- ------------------------------------------------------------------------
-- Modification history:
--   30.4.1999    Creation
--	 30.6.2000    enum extension for logA2ConfigLogMonitorStatus,logA2StatusLogMonitorStatus
--									 logA2StatusLogStatus
--	 30.6.2000    enum extension for logA2ConfigLogStatusPolicy,logA2StatusLogStatusPolicy
--	 04.12.2000   new mib attributes for callbacks: logA2StatusLogCallbackRef, logA2StatusFileCallbackRef
--	 20.4.2001    new mib attribute logA2ConfigOsType
--
-- ------------------------------------------------------------------------
-- Software version to be used with: TNG 2.2 (2.1)
-- ------------------------------------------------------------------------
-- This is the MIB for the advanced Log Agent.
--
-- The Windows advanced Log Agent provides the following functions:
--
--		Monitoring of American Standard code for Information Interchange (ASCII)
--		logs for user-specified regular expressions.
--
--		Monitoring of user-specified files for their existence or non-existence.
--
--
-- At the lowest level, the Log Agent monitors the following:
--		The current status of the whole agent.
--		The status of the accessibility of the watcher log files
--		The status of all the log file watchers.
--		The status of all the file watchers.
--
-- The Log Agent MIB contains three major groups:
--		logA2ConfigGroup - Contains all configuration groups for Log Agent.
--		logA2StatusGroup - Contains all status groups and tables for Log Agent.
--		logA2HistoryGroup - Contains all history groups and tables for Log Agent.
--=========================================================================

CA-LOGA2-MIB DEFINITIONS ::= BEGIN                 -- defined by IETF
IMPORTS
	OBJECT-TYPE, Counter, Gauge, DisplayString    FROM RFC1155-SMI;

cai				OBJECT IDENTIFIER ::= { enterprises 791 }
caiSysMgr		        OBJECT IDENTIFIER ::= { cai 2 }
agentWorks		        OBJECT IDENTIFIER ::= { caiSysMgr 9 }
misc				OBJECT IDENTIFIER ::= { agentWorks 5 }
caiLogA2		        OBJECT IDENTIFIER ::= { misc 5 }

logA2ConfigGroup		OBJECT IDENTIFIER
--	DESCRIPTION
--     		"Contains all configuration groups for Log Agent."
	::= { caiLogA2 1 }
logA2StatusGroup		OBJECT IDENTIFIER
--	DESCRIPTION
--     		"Contains all status groups and tables for Log Agent."
	::= { caiLogA2 2 }
logA2HistoryGroup		OBJECT IDENTIFIER
--	DESCRIPTION
--   		"Contains all history groups and tables for Log Agent."
	::= { caiLogA2 3 }


--
--			Configuration Group
--
logA2ConfigGeneralGroup	OBJECT IDENTIFIER
--	DESCRIPTION
--     		"Contains the general configuration group for the Log Agent."
	::= { logA2ConfigGroup 1 }

logA2ConfigLogGroup	OBJECT IDENTIFIER
--	DESCRIPTION
--     		"Contains the Log configuration group for the Log Agent."
	::= { logA2ConfigGroup 2 }

logA2ConfigFileGroup	OBJECT IDENTIFIER
--	DESCRIPTION
--     		"Contains the File configuration group for the Log Agent."
	::= { logA2ConfigGroup 3 }

--
--			Configuration General Group
--
logA2ConfigAgentVersion OBJECT-TYPE
	SYNTAX  DisplayString
	ACCESS  read-only
	STATUS  mandatory
	DESCRIPTION
		"&<caiLogA2.100>The current version of agent that is running."
	::= { logA2ConfigGeneralGroup 1 }

logA2ConfigColdStartTime OBJECT-TYPE
	SYNTAX  DisplayString
	ACCESS  read-only
	STATUS  mandatory
	DESCRIPTION
		"&<caiLogA2.101> The time and date that agent was started."
	::= { logA2ConfigGeneralGroup 2 }


logA2ConfigWarmStartTime OBJECT-TYPE
	SYNTAX  DisplayString
	ACCESS  read-only
	STATUS  mandatory
	DESCRIPTION
		"&<caiLogA2.102> The time and date that agent was last reconfigured."
	::= { logA2ConfigGeneralGroup 3 }


logA2ConfigLogPollTime OBJECT-TYPE
	SYNTAX  DisplayString
	ACCESS  read-only
	STATUS  mandatory
	DESCRIPTION
		"&<caiLogA2.103> The time and date that agent last polled the log file watchers."
	::= { logA2ConfigGeneralGroup 4 }


logA2ConfigFilePollTime OBJECT-TYPE
	SYNTAX  DisplayString
	ACCESS  read-only
	STATUS  mandatory
	DESCRIPTION
		"&<caiLogA2.104> The time and date that agent last polled the file watchers."
	::= { logA2ConfigGeneralGroup 5 }

logA2ConfigAutoSave OBJECT-TYPE
	SYNTAX INTEGER {
		yes(1),
		no(2)
	}
	ACCESS  read-write
	STATUS  mandatory
	DESCRIPTION
		"&<caiLogA2.105>Specifies if the agent should save the configuration on the hourly poll and on exit.
1.     yes - Saving shall be done.
2.     no - No saving shall be done."
	::= { logA2ConfigGeneralGroup 6 }

logA2ConfigOsType OBJECT-TYPE
	SYNTAX  DisplayString
	ACCESS  read-only
	STATUS  mandatory
	DESCRIPTION
		"&<caiLogA2.200> Specifies software operating system the agent is running on."
	::= { logA2ConfigGeneralGroup 7 }
--
--  logA2ConfigLogGroup
--
logA2ConfigLogPollInterval OBJECT-TYPE
	SYNTAX  INTEGER
	ACCESS  read-write
	STATUS  mandatory
	DESCRIPTION
		"&<caiLogA2.106> The interval in seconds between polls. Values can be -1 for polling disabled and 30 or more for polling interval. (No upper limit.)"
	::= { logA2ConfigLogGroup 1 }

logA2ConfigLogWatcherName OBJECT-TYPE
	SYNTAX  DisplayString
	ACCESS  read-write
	STATUS  mandatory
	DESCRIPTION
		"&<caiLogA2.107> The description of what the watcher is monitoring."
	::= { logA2ConfigLogGroup 2 }

logA2ConfigLogFileName OBJECT-TYPE
	SYNTAX  DisplayString
	ACCESS  read-write
	STATUS  mandatory
	DESCRIPTION
		"&<caiLogA2.108> The full path and file name of the file to monitor or wild carded (using glob) filename."
	::= { logA2ConfigLogGroup 3 }

logA2ConfigLogPosPattern OBJECT-TYPE
	SYNTAX  DisplayString
	ACCESS  read-write
	STATUS  mandatory
	DESCRIPTION
		"&<caiLogA2.109> Basic or extended regular expression or a file with a list of basic regular expression patterns that is used to match against to change the watcher's state to down. One of  PosPattern or NegPattern must be defined."
	::= { logA2ConfigLogGroup 4 }

logA2ConfigLogPosStart OBJECT-TYPE
	SYNTAX  INTEGER
	ACCESS  read-write
	STATUS  mandatory
	DESCRIPTION
		"&<caiLogA2.110> The starting character position for selecting the part of the line to pass to the regular expression. A value of -1 means that the start of the line is used and any other value is an inclusive value. The whole line is selected by PosStart = -1 and  PosEnd = -1."
 	::= { logA2ConfigLogGroup 5 }

logA2ConfigLogPosEnd OBJECT-TYPE
	SYNTAX  INTEGER
	ACCESS  read-write
	STATUS  mandatory
	DESCRIPTION
		"&<caiLogA2.111> The ending character position for selecting the part of the line to pass to the regular expression. A value of -1 means that the end of the line is used and any other value is an inclusive value, and must be greater or equal then the start position. The whole line is selected by PosStart = -1 and  PosEnd = -1."
	::= { logA2ConfigLogGroup 6 }

logA2ConfigLogNegPattern OBJECT-TYPE
	SYNTAX  DisplayString
	ACCESS  read-write
	STATUS  mandatory
	DESCRIPTION
		"&<caiLogA2.112> Basic or extended regular expression or a file with a list of basic regular expression patterns that, if configured, is used to match against the log message and used once the positive pattern has been matched, and as long as there is not match the state will change to down. One of  PosPattern or NegPattern must be defined."
	::= { logA2ConfigLogGroup 7 }

logA2ConfigLogNegStart OBJECT-TYPE
	SYNTAX  INTEGER
	ACCESS  read-write
	STATUS  mandatory
	DESCRIPTION
		"&<caiLogA2.113> The starting character position for selecting the part of the line to pass to the regular expression. A value of -1 means that the start of the line is used and any other value is an inclusive value. The whole line is selected by NegStart = -1 and  NegEnd = -1."
	::= { logA2ConfigLogGroup 8 }

logA2ConfigLogNegEnd OBJECT-TYPE
	SYNTAX  INTEGER
	ACCESS  read-write
	STATUS  mandatory
	DESCRIPTION
		"&<caiLogA2.114> The ending character position for selecting the part of the line to pass to the regular expression. A value of -1 means that the end of the line is used and any other value is an inclusive value, and must be greater or equal then the start position. The whole line is selected by NegStart = -1 and  NegEnd = -1."
	::= { logA2ConfigLogGroup 9 }

logA2ConfigLogTogglePosPattern OBJECT-TYPE
	SYNTAX  DisplayString
	ACCESS  read-write
	STATUS  mandatory
	DESCRIPTION
		"&<caiLogA2.115> Basic or extended regular expression or a file with a list of basic regular expression patterns that is used to match against to change the watcher's state to up, this is only called when the watcher is in a down state. The group of toggle attributes are only required when the user selects the toggle status policy. One of the  TogglePosPattern or ToggleNegPattern must be defined."
	::= { logA2ConfigLogGroup 10 }

logA2ConfigLogTogglePosStart OBJECT-TYPE
	SYNTAX  INTEGER
	ACCESS  read-write
	STATUS  mandatory
	DESCRIPTION
		"&<caiLogA2.116> The starting character position for selecting the part of the line to pass to the regular expression. A value of -1 means that the start of the line is used and any other value is an inclusive value. The whole line is selected by TogglePosStart = -1 and  TogglePosEnd = -1."
	::= { logA2ConfigLogGroup 11 }

logA2ConfigLogTogglePosEnd OBJECT-TYPE
	SYNTAX  INTEGER
	ACCESS  read-write
	STATUS  mandatory
	DESCRIPTION
		"&<caiLogA2.117> The ending character position for selecting the part of the line to pass to the regular expression. A value of -1 means that the end of the line is used and any other value is an inclusive value, and must be greater or equal then the start position. The whole line is selected by TogglePosStart = -1 and  TogglePosEnd = -1."
	::= { logA2ConfigLogGroup 12 }

logA2ConfigLogToggleNegPattern OBJECT-TYPE
	SYNTAX  DisplayString
	ACCESS  read-write
	STATUS  mandatory
	DESCRIPTION
		"&<caiLogA2.118> Basic or extended regular expression or a file with a list of basic regular expression patterns that, if configured, is used to match against the log message and used once the positive pattern has been matched, and as long as there is not match the state will change to up. The group of toggle attributes are only required when the user selects the toggle status policy. One of TogglePosPattern or ToggleNegPattern must be defined."
 	::= { logA2ConfigLogGroup 13 }

logA2ConfigLogToggleNegStart OBJECT-TYPE
	SYNTAX  INTEGER
	ACCESS  read-write
	STATUS  mandatory
	DESCRIPTION
		"&<caiLogA2.119> The starting character position for selecting the part of the line to pass to the regular expression. A value of -1 means that the start of the line is used and any other value is an inclusive value. The whole line is selected by ToggleNegStart = -1 and  ToggleNegEnd = -1."
	::= { logA2ConfigLogGroup 14 }

logA2ConfigLogToggleNegEnd OBJECT-TYPE
	SYNTAX  INTEGER
	ACCESS  read-write
	STATUS  mandatory
	DESCRIPTION
		"&<caiLogA2.120> The ending character position for selecting the part of the line to pass to the regular expression. A value of -1 means that the end of the line is used and any other value is an inclusive value, and must be greater or equal then the start position. The whole line is selected by ToggleNegStart = -1 and  ToggleNegEnd = -1."
	::= { logA2ConfigLogGroup 15 }

logA2ConfigLogStatusPolicy OBJECT-TYPE
	SYNTAX  INTEGER {
		poll(1),
		historical(2),
		startFromPreviousRead(3),
		toggled(4),
        		firstLineOnly(5),
		pollEOF(6),
		startFromPreviousReadEOF(7),
		toggledEOF(8),
		rescan(9)
	}
	ACCESS  read-write
	STATUS  mandatory
	DESCRIPTION
		"&<caiLogA2.121>This attribute defines the way the watcher behaves with regards to the file handling:
1. poll - The watcher's status is set to up at the beginning of each poll. If a match is made then the state changes to down. The file is scanned from the last read location unless it is a new watcher when the whole file is read.
2. historical - The watcher's status is set to down when a match occurs and will remain down for the life of the log file, i.e. the log file is recreated. The file is scanned from the last read location unless it is a new watcher when the whole file is read.
3. startFromPreviousRead - The watcher's status is set to down when a match occurs will remain down until reset by the user or the life of the log file. The file is scanned from the last read location.
4. toggled - The user specifies a down pattern, as with historical, and also an up pattern (formed with the toggle positive and negative pattern attributes) which is matched against for changing the state back to up. The file is scanned from the last read location.
5. firstLineOnly - The watcher's status is determined the same way as poll, but only the first line of a file is ever read.
6. pollEOF - Same as poll but for a new watcher reading starts at the end of the file.
7. startFromPreviousReadEOF - Same as startFromPreviousRead but for a new watcher reading starts at the end of the file.
8. toggledEOF - Same as toggled but for a new watcher reading starts at the end of the file.
9. rescan - rescan file from beginning, if file length increased. If file >10kB, set watcher into unknown."
	::= { logA2ConfigLogGroup 16 }

logA2ConfigLogTrapSendPolicy OBJECT-TYPE
	SYNTAX  INTEGER {
		never(1),
        once(2),
		perPoll(3),
		each(4)
	}
	ACCESS  read-write
	STATUS  mandatory
	DESCRIPTION
		"&<caiLogA2.122>This attribute defines the policy to be applied to the watcher's status traps:
1. never - The state change never causes traps to be sent.
2. once - The state change trap is sent only when the watcher's state changes.
3. perPoll - The state change trap is sent every poll even if the state does not change but a match condition occured since the last poll.
4. each - The state change trap is send for each match made by the agent. For toggle, once the watcher goes down the next match that will be looked for is the toggle pattern, so subsequent down patterns will not be matched."
	::= { logA2ConfigLogGroup 17 }

logA2ConfigLogHistoryPolicy OBJECT-TYPE
	SYNTAX  INTEGER {
		generateHistory(1),
		noGenerateHistory(2)
	}
	ACCESS  read-write
	STATUS  mandatory
	DESCRIPTION
		"&<caiLogA2.123>This attribute defines whether trap details are stored in the history table.
1. generateHistory - The status traps are recorded in the history table.
2. noGenerateHistory - The status traps are not recorded in the history table."
	::= { logA2ConfigLogGroup 18 }

logA2ConfigLogMatchTrapPolicy OBJECT-TYPE
	SYNTAX  INTEGER {
		send(1),
		doNotSend(2)
	}
	ACCESS  read-write
	STATUS  mandatory
	DESCRIPTION
		"&<caiLogA2.124>This attribute defines the policy to be applied to the match traps:
1. send - Send a trap for each match found. For toggle, once the watcher goes down the next match that will be looked for is the toggle pattern, so subsequent down patterns will not be matched unless status monitoring is switched off.
2. doNotSend - Do not send a trap for each match found."
	::= { logA2ConfigLogGroup 19 }

logA2ConfigLogMonitorStatus OBJECT-TYPE
	SYNTAX  INTEGER {
		downCritical(1),
		doNotMonitor(2),
		downWarning(3)
	}
	ACCESS  read-write
	STATUS  mandatory
	DESCRIPTION
		"&<caiLogA2.125>The attribute that allows the user to disable status side of the watcher but not match trap sending:
1. downCritical - The state change works as configured and a critical alert is raised.
2. doNotMonitor - The log file is monitored but the state is always up.
3. downWarning - The state change works as configured and a warning alert is raised."
	::= { logA2ConfigLogGroup 20 }

logA2ConfigLogOwner OBJECT-TYPE
	SYNTAX  DisplayString
	ACCESS  read-write
	STATUS  mandatory
	DESCRIPTION
		"&<caiLogA2.196>   Class name of the Agent whose DSM Policy handles the status traps for this watcher.
		 Default value is caiLogA2"
	::= { logA2ConfigLogGroup 21 }


logA2ConfigLogButton OBJECT-TYPE
	SYNTAX  INTEGER {
		none(1),
		delete(2),
		add(3)
	}
	ACCESS  read-write
	STATUS  mandatory
	DESCRIPTION
		"&<caiLogA2.126>The attribute that is used to add or delete watchers:
1. none - No action.
2. delete - Use the current value of the watcher name attribute to delete the watcher with that name.
3. add - Use the current contents of the ConfigLogGroup to add a watcher."
	::= { logA2ConfigLogGroup 22 }

--
--  logA2ConfigFileGroup
--
logA2ConfigFilePollInterval OBJECT-TYPE
	SYNTAX  INTEGER
	ACCESS  read-write
	STATUS  mandatory
	DESCRIPTION
		"&<caiLogA2.127> The interval in seconds between polls. Values can be -1 for polling disabled and 30 or more for polling interval. (No upper limit.)"
	::= { logA2ConfigFileGroup 1 }

logA2ConfigFileWatcherName OBJECT-TYPE
	SYNTAX  DisplayString
	ACCESS  read-write
	STATUS  mandatory
	DESCRIPTION
		"&<caiLogA2.128> A description of the watcher's purpose."
	::= { logA2ConfigFileGroup 2 }

logA2ConfigFileName OBJECT-TYPE
	SYNTAX  DisplayString
	ACCESS  read-write
	STATUS  mandatory
	DESCRIPTION
		"&<caiLogA2.129> The path and filename of the file to monitor the existence of."
	::= { logA2ConfigFileGroup 3 }

logA2ConfigFileExist OBJECT-TYPE
	SYNTAX  INTEGER {
		exists(1),
		not-exists(2)
	}
	ACCESS  read-write
	STATUS  mandatory
	DESCRIPTION
		"&<caiLogA2.130> Flag indicating whether the file should exist or not."
	::= { logA2ConfigFileGroup 4 }

logA2ConfigFileTrapSendPolicy OBJECT-TYPE
	SYNTAX  INTEGER {
		never(1),
		once(2),
		perPoll(3)
	}
	ACCESS  read-write
	STATUS  mandatory
	DESCRIPTION
		"&<caiLogA2.131> The frequency that the traps are sent.
1. never - A trap is never sent.
2. once - A trap is sent only once the state has been changed.
3. perPoll - A status trap is sent each poll if the state is down."
	::= { logA2ConfigFileGroup 5 }

logA2ConfigFileHistoryPolicy OBJECT-TYPE
	SYNTAX  INTEGER {
		generateHistory(1),
		noGenerateHistory(2)
	}
	ACCESS  read-write
	STATUS  mandatory
	DESCRIPTION
		"&<caiLogA2.132> When a status trap is sent the information can be stored in a history table:
1. generateHistory - Status traps generated by this watcher will be added to the history table.
2. noGenerateHistory - Status traps generated by this watcher will not be added to the history table."
	::= { logA2ConfigFileGroup 6 }

logA2ConfigFileButton OBJECT-TYPE
	SYNTAX  INTEGER {
		none(1),
		delete(2),
		add(3)
	}
	ACCESS  read-write
	STATUS  mandatory
	DESCRIPTION
		"&<caiLogA2.133> The button to perform an operation on the logConfigFileGroup.
1. none - No action will be taken, the default value.
2. delete - Use the current value of the watcher name attribute to delete the watcher with that name.
3. add - Use the current contents of the ConfigFileGroup to add a watcher."
	::= { logA2ConfigFileGroup 7 }

--
--         Status Group
--
logA2StatusGeneralGroup	OBJECT IDENTIFIER
--	DESCRIPTION
--     		"Contains the general status group for the Log Agent."
	::= { logA2StatusGroup 1 }

logA2StatusLogTable OBJECT-TYPE
	SYNTAX  SEQUENCE OF LogA2StatusLogSequence
	ACCESS  not-accessible
	STATUS  mandatory
	DESCRIPTION
		"&<caiLogA2.134>The list of watchers of log files."
	::= { logA2StatusGroup 2 }

logA2StatusFileTable OBJECT-TYPE
	SYNTAX  SEQUENCE OF LogA2StatusFileSequence
	ACCESS  not-accessible
	STATUS  mandatory
	DESCRIPTION
		"&<caiLogA2.135>The list of watchers of files."
	::= { logA2StatusGroup 3 }

--
--         Status General Group
--

logA2StatusGeneralTotalCount OBJECT-TYPE
	SYNTAX  INTEGER
	ACCESS  read-only
	STATUS  mandatory
	DESCRIPTION
		"&<caiLogA2.136> The total number of watchers configured in the agent."
	::= { logA2StatusGeneralGroup 1 }

logA2StatusGeneralTotalDown OBJECT-TYPE
	SYNTAX  INTEGER
	ACCESS  read-only
	STATUS  mandatory
	DESCRIPTION
		"&<caiLogA2.137> The total number of watchers in a down state."
	::= { logA2StatusGeneralGroup 2 }

logA2StatusGeneralLogCount OBJECT-TYPE
	SYNTAX  INTEGER
	ACCESS  read-only
	STATUS  mandatory
	DESCRIPTION
		"&<caiLogA2.138> The total number of log watchers configured in the agent."
	::= { logA2StatusGeneralGroup 3 }

logA2StatusGeneralLogDown OBJECT-TYPE
	SYNTAX  DisplayString
	ACCESS  read-only
	STATUS  mandatory
	DESCRIPTION
		"&<caiLogA2.139> The total number of log watchers in a down state."
	::= { logA2StatusGeneralGroup 4 }

logA2StatusGeneralLogFileDown OBJECT-TYPE
	SYNTAX  INTEGER
	ACCESS  read-only
	STATUS  mandatory
	DESCRIPTION
		"&<caiLogA2.140> The total number of log watchers which cannot access to log files."
	::= { logA2StatusGeneralGroup 5 }

logA2StatusGeneralFileCount OBJECT-TYPE
	SYNTAX  INTEGER
	ACCESS  read-only
	STATUS  mandatory
	DESCRIPTION
		"&<caiLogA2.141> The total number of file watchers configured in the agent."
	::= { logA2StatusGeneralGroup 6 }

logA2StatusGeneralFileDown OBJECT-TYPE
	SYNTAX  INTEGER
	ACCESS  read-only
	STATUS  mandatory
	DESCRIPTION
		"&<caiLogA2.142> The total number of file watchers in a down state."
	::= { logA2StatusGeneralGroup 7 }


--
--  logA2StatusLogTable
--
logA2StatusLogEntry OBJECT-TYPE
	SYNTAX  LogA2StatusLogSequence
	ACCESS  not-accessible
	STATUS  mandatory
	DESCRIPTION
		"&<caiLogA2.143>A table entry for the log watcher table"
	INDEX { logA2StatusLogWatcherName }
        ::= { logA2StatusLogTable 1 }

LogA2StatusLogSequence::=
	SEQUENCE {
		logA2StatusLogWatcherName	DisplayString,
		logA2StatusLogFileName		DisplayString,
		logA2StatusLogPosPattern	DisplayString,
		logA2StatusLogPosStart		INTEGER,
		logA2StatusLogPosEnd		INTEGER,
		logA2StatusLogNegPattern	DisplayString,
		logA2StatusLogNegStart		INTEGER,
		logA2StatusLogNegEnd		INTEGER,
		logA2StatusLogTogglePosPattern 	DisplayString,
		logA2StatusLogTogglePosStart	INTEGER,
		logA2StatusLogTogglePosEnd	INTEGER,
		logA2StatusLogToggleNegPattern 	DisplayString,
		logA2StatusLogToggleNegStart	INTEGER,
		logA2StatusLogToggleNegEnd	INTEGER,
		logA2StatusLogStatusPolicy	INTEGER,
		logA2StatusLogTrapSendPolicy	INTEGER,
		logA2StatusLogHistoryPolicy	INTEGER,
		logA2StatusLogMatchTrapPolicy	INTEGER,
		logA2StatusLogMonitorStatus		INTEGER,
		logA2StatusLogStatus		INTEGER,
        logA2StatusLogLastTrapMessage   DisplayString,
        logA2StatusLogLastTrapLine      DisplayString,
		logA2StatusLogOwner         DisplayString,
		logA2StatusLogButton		INTEGER,
		logA2StatusLogCallbackRef	DisplayString
	}

logA2StatusLogWatcherName OBJECT-TYPE
	SYNTAX  DisplayString
	ACCESS  read-only
	STATUS  mandatory
	DESCRIPTION
		"&<caiLogA2.144> The description of what the watcher is monitoring. The watchername has to be unique."
	::= { logA2StatusLogEntry 1 }

logA2StatusLogFileName OBJECT-TYPE
	SYNTAX  DisplayString
	ACCESS  read-write
	STATUS  mandatory
	DESCRIPTION
		"&<caiLogA2.145> The full path and file name of the file to monitor or wild carded (using glob) filename."
	::= { logA2StatusLogEntry 2 }

logA2StatusLogPosPattern OBJECT-TYPE
	SYNTAX  DisplayString
	ACCESS  read-write
	STATUS  mandatory
	DESCRIPTION
		"&<caiLogA2.109>Basic or regular expression or a file with a list of basic regular expression patterns that is used to match against to change the watcher's state to down. One of  PosPattern or NegPattern must be defined."
	::= { logA2StatusLogEntry 3 }

logA2StatusLogPosStart OBJECT-TYPE
	SYNTAX  INTEGER
	ACCESS  read-write
	STATUS  mandatory
	DESCRIPTION
		"&<caiLogA2.147> The starting character position for selecting the part of the line to pass to the regular expression. A value of  -1 means that the start of the line is used and any other value is an inclusive value. The whole line is selected by PosStart = -1 and  PosEnd = -1."
        DEFVAL { 0 }
	::= { logA2StatusLogEntry 4 }

logA2StatusLogPosEnd OBJECT-TYPE
	SYNTAX  INTEGER
	ACCESS  read-write
	STATUS  mandatory
	DESCRIPTION
		"&<caiLogA2.148> The ending character position for selecting the part of the line to pass to the regular expression. A value of -1 means that the end of the line is used and any other value is an inclusive value, and must be greater or equal then the start position. The whole line is selected by PosStart = -1 and  PosEnd = -1."
	        DEFVAL { 0 }
	::= { logA2StatusLogEntry 5 }

logA2StatusLogNegPattern OBJECT-TYPE
	SYNTAX  DisplayString
	ACCESS  read-write
	STATUS  mandatory
	DESCRIPTION
		"&<caiLogA2.112>Basic or extended regular expression or a file with a list of basic regular expression patterns that when configured, is used to match against the log message and used once the positive pattern has been matched, and as long as there is not match the state will change to down. One of  PosPattern or NegPattern must be defined."
	::= { logA2StatusLogEntry 6 }

logA2StatusLogNegStart OBJECT-TYPE
	SYNTAX  INTEGER
	ACCESS  read-write
	STATUS  mandatory
	DESCRIPTION
		"&<caiLogA2.150>The starting character position for selecting the part of the line to pass to the regular expression. A value of -1 means that the start of the line is used and any other value is an inclusive value. The whole line is selected by NegStart = -1 and  NegEnd = -1."
        DEFVAL { 0 }
        	::= { logA2StatusLogEntry 7 }

logA2StatusLogNegEnd OBJECT-TYPE
	SYNTAX  INTEGER
	ACCESS  read-write
	STATUS  mandatory
	DESCRIPTION
		"&<caiLogA2.151>The ending character position for selecting the part of the line to pass to the regular expression. A value of -1 means that the end of the line is used and any other value is an inclusive value, and must be greater or equal then the start position. The whole line is selected by NegStart = -1 and  NegEnd = -1."
        DEFVAL { 0 }
        	::= { logA2StatusLogEntry 8 }

logA2StatusLogTogglePosPattern OBJECT-TYPE
	SYNTAX  DisplayString
	ACCESS  read-write
	STATUS  mandatory
	DESCRIPTION
		"&<caiLogA2.115>Basic or extended regular expression or a file with a list of basic regular expression patterns that is used to match against to change the watcher's state to up, this is only called when the watcher is in a down state. The group of toggle attributes are only required when the user selects the toggle status policy. One of the TogglePosPattern or ToggleNegPattern must be defined."
	::= { logA2StatusLogEntry 9 }

logA2StatusLogTogglePosStart OBJECT-TYPE
	SYNTAX  INTEGER
	ACCESS  read-write
	STATUS  mandatory
	DESCRIPTION
		"&<caiLogA2.153>The starting character position for selecting the part of the line to pass to the regular expression. A value of -1 means that the start of the line is used and any other value is an inclusive value. The whole line is selected by TogglePosStart = -1 and  TogglePosEnd = -1."
        DEFVAL { 0 }
        	::= { logA2StatusLogEntry 10 }

logA2StatusLogTogglePosEnd OBJECT-TYPE
	SYNTAX  INTEGER
	ACCESS  read-write
	STATUS  mandatory
	DESCRIPTION
		"&<caiLogA2.154>The ending character position for selecting the part of the line to pass to the regular expression. A value of -1 means that the end of the line is used and any other value is an inclusive value, and must be greater or equal then the start position. The whole line is selected by TogglePosStart = -1 and  TogglePosEnd = -1."
        DEFVAL { 0 }
        	::= { logA2StatusLogEntry 11 }

logA2StatusLogToggleNegPattern OBJECT-TYPE
	SYNTAX  DisplayString
	ACCESS  read-write
	STATUS  mandatory
	DESCRIPTION
		"&<caiLogA2.118>Basic or extended regular expression or a file with a list of basic regular expression patterns that when configured, is used to match against the log message and used once the positive pattern has been matched, and as long as there is not match the state will change to up. The group of toggle attributes are only required when the user selects the toggle status policy. One of the TogglePosPattern or ToggleNegPattern must be defined."
	::= { logA2StatusLogEntry 12 }

logA2StatusLogToggleNegStart OBJECT-TYPE
	SYNTAX  INTEGER
	ACCESS  read-write
	STATUS  mandatory
	DESCRIPTION
		"&<caiLogA2.156> The starting character position for selecting the part of the line to pass to the regular expression. A value of -1 means that the start of the line is used and any other value is an inclusive value. The whole line is selected by ToggleNegStart = -1 and  ToggleNegEnd = -1."
	        DEFVAL { 0 }
	::= { logA2StatusLogEntry 13 }

logA2StatusLogToggleNegEnd OBJECT-TYPE
	SYNTAX  INTEGER
	ACCESS  read-write
	STATUS  mandatory
	DESCRIPTION
		"&<caiLogA2.157> The ending character position for selecting the part of the line to pass to the regular expression. A value of -1 means that the end of the line is used and any other value is an inclusive value, and must be greater or equal then the start position. The whole line is selected by ToggleNegStart = -1 and  ToggleNegEnd = -1."
	        DEFVAL { 0 }
	::= { logA2StatusLogEntry 14 }

logA2StatusLogStatusPolicy OBJECT-TYPE
	SYNTAX  INTEGER {
		poll(1),
		historical(2),
		startFromPreviousRead(3),
		toggled(4),
        		firstLineOnly(5),
		pollEOF(6),
		startFromPreviousReadEOF(7),
		toggledEOF(8),
		rescan(9)
	}
	ACCESS  read-write
	STATUS  mandatory
	DESCRIPTION
		"&<caiLogA2.121>This attribute defines the way the watcher behaves with regards to the file handling:
1. poll - The watcher's status is set to up at the beginning of each poll. If a match is made then the state changes to down. The file is scanned from the last read location unless it is a new watcher when the whole file is read.
2. historical - The watcher's status is set to down when a match occurs and will remain down for the life of the log file, i.e. the log file is recreated. The file is scanned from the last read location unless it is a new watcher when the whole file is read.
3. startFromPreviousRead - The watcher's status is set to down when a match occurs and will remain down until reset by the user or the life of the log file. The file is scanned from the last read location.
4. toggled - The user specifies a down pattern, as with historical, and also an up pattern (formed with the toggle positive and negative pattern attributes) which is matched against for changing the state back to up. The file is scanned from the last read location.
5. firstLineOnly - The watcher's status is determined the same way as poll, but only the first line of a file is ever read.
6. pollEOF - Same as poll but for a new watcher reading starts at the end of the file.
7. startFromPreviousReadEOF - Same as startFromPreviousRead but for a new watcher reading starts at the end of the file.
8. toggledEOF - Same as toggled but for a new watcher reading starts at the end of the file.
9. rescan - rescan file from beginning, if file length increased. If file >10kB, set watcher into unknown."
	        DEFVAL { 0 }
	        	::= { logA2StatusLogEntry 15 }

logA2StatusLogTrapSendPolicy OBJECT-TYPE
	SYNTAX  INTEGER {
		never(1),
	    once(2),
		perPoll(3),
		each(4)
	}
	ACCESS  read-write
	STATUS  mandatory
	DESCRIPTION
		"&<caiLogA2.122> This attribute defines the policy to be applied to the watcher's status traps:
1. never - The state change never causes traps to be sent.
2. once - The state change trap is sent only when the watcher's state changes.
3. perPoll - The state change trap is sent every poll even if the state does not change but a match condition occured since the last poll.
4. each - The state change trap is send for each match made by the agent. For toggle, once the watcher goes down the next match that will be looked for is the toggle pattern, so subsequent down patterns will not be matched."
	        DEFVAL { 0 }
	        	::= { logA2StatusLogEntry 16 }

logA2StatusLogHistoryPolicy OBJECT-TYPE
	SYNTAX  INTEGER {
		generateHistory(1),
		noGenerateHistory(2)
	}
	ACCESS  read-write
	STATUS  mandatory
	DESCRIPTION
		"&<caiLogA2.160> This attribute defines whether trap details are stored in the history table.
1. generateHistory - The traps are recorded in the history table.
2. noGenerateHistory - The traps are not recorded in the history table."
	        DEFVAL { 0 }
	::= { logA2StatusLogEntry 17 }

logA2StatusLogMatchTrapPolicy OBJECT-TYPE
	SYNTAX  INTEGER {
		send(1),
		doNotSend(2)
	}
	ACCESS  read-write
	STATUS  mandatory
	DESCRIPTION
		"&<caiLogA2.161> This attribute defines the policy to be applied to the watcher's match traps:
1. send - Send a trap for each match found. For toggle, once the watcher goes down the next match that will be looked for is the toggle pattern, so subsequent down patterns will not be matched unless status monitoring is switched off.
2. doNotSend - Do not send a trap for each match found."
	  DEFVAL { 0 }
	  ::= { logA2StatusLogEntry 18 }

logA2StatusLogMonitorStatus OBJECT-TYPE
	SYNTAX  INTEGER {
		downCritical(1),
		doNotMonitor(2),
		downWarning(3)
	}
	ACCESS  read-write
	STATUS  mandatory
	DESCRIPTION
		"&<caiLogA2.125> The attribute that allows the user to disable status side of the watcher but not match trap sending:
1. monitorCritical - The state change works as configured and a critical alert is raised.
2. doNotMonitor - The log file is monitored but the state is always up.
3. monitorWarning - The state change works as configured and a warning alert is raised."
	        DEFVAL { 0 }
	::= { logA2StatusLogEntry 19 }

logA2StatusLogStatus OBJECT-TYPE
	SYNTAX  INTEGER {
		up(1),
		downCritical(2),
		unknown(3),
		reset(4),
		downWarning(5),
		clustered-passive(6)
	}
	ACCESS	read-write
	STATUS	mandatory
	DESCRIPTION
		"&<caiLogA2.163> The attribute that shows the current status of the watcher:
1. up - The watcher is in a up state, i.e. the pattern has not been matched or for a toggle watcher the up pattern has been matched to change from a down state to an up state.
2. downCritical - The watcher is in a down state, i.e. the pattern has been matched and a critical alert is raised.
3. unknown - The watcher is a new watcher that has not been polled for the first time or file is not readable.
4. reset - The user may reset the watcher which is in a down state using the reset state.
5. downWarning - The watcher is in a down state, i.e. the pattern has been matched and a warning alert is raised.
6. clustered-passive - The watcher monitors files on a clustered file system and this file system is currently passive."
	::= { logA2StatusLogEntry 20 }

logA2StatusLogLastTrapMessage OBJECT-TYPE
	SYNTAX  DisplayString
	ACCESS  read-only
	STATUS  mandatory
	DESCRIPTION
		"&<caiLogA2.164> The text that was sent for the last trap to be sent for the watcher."
	::= { logA2StatusLogEntry 21 }

logA2StatusLogLastTrapLine OBJECT-TYPE
	SYNTAX  DisplayString
	ACCESS  read-only
	STATUS  mandatory
	DESCRIPTION
		"&<caiLogA2.165> The log file line that caused the last trap to be sent."
	::= { logA2StatusLogEntry 22 }

logA2StatusLogOwner OBJECT-TYPE
	SYNTAX  DisplayString
	ACCESS  read-write
	STATUS  mandatory
	DESCRIPTION
		"&<caiLogA2.196>   Class name of the Agent whose DSM Policy handles the status traps for this watcher.
		 Default value is caiLogA2"
	::= { logA2StatusLogEntry 23 }


logA2StatusLogButton OBJECT-TYPE
	SYNTAX  INTEGER {
		none(1),
		delete(2)
	}
	ACCESS  read-write
	STATUS  mandatory
	DESCRIPTION
		"&<caiLogA2.166> The attribute that is used to delete the current watcher:
1. none - No action will be taken, the default value.
2. delete - Delete this entry from the StatusLogTable."
	::= { logA2StatusLogEntry 24 }


logA2StatusLogCallbackRef OBJECT-TYPE
	SYNTAX DisplayString
	ACCESS read-only
	STATUS mandatory
	DESCRIPTION
		"&<caiLogA2.199>The name of the Call-Back reference that should be invoked in case of a status change."
	::= { logA2StatusLogEntry 25 }

--
--  logA2StatusFileEntry
--
logA2StatusFileEntry OBJECT-TYPE
	SYNTAX  LogA2StatusFileSequence
	ACCESS  not-accessible
	STATUS  mandatory
	DESCRIPTION
		"&<caiLogA2.167>A table entry for the file watcher table"
        INDEX { logA2StatusFileWatcherName }
	::= { logA2StatusFileTable 1 }

LogA2StatusFileSequence ::=
	SEQUENCE {
		logA2StatusFileWatcherName	DisplayString,
		logA2StatusFileName		DisplayString,
		logA2StatusFileExist		INTEGER,
		logA2StatusFileTrapSendPolicy   INTEGER,
		logA2StatusFileStatus		INTEGER,
		logA2StatusFileHistoryPolicy	INTEGER,
		logA2StatusFileButton		INTEGER,
		logA2StatusFileCallbackRef	DisplayString
	}

logA2StatusFileWatcherName OBJECT-TYPE
	SYNTAX  DisplayString
	ACCESS  read-only
	STATUS  mandatory
	DESCRIPTION
		"&<caiLogA2.168> A description of the watcher's purpose. The watchername has to be unique."
	::= { logA2StatusFileEntry 1 }

logA2StatusFileName OBJECT-TYPE
	SYNTAX  DisplayString
	ACCESS  read-only
	STATUS  mandatory
	DESCRIPTION
		"&<caiLogA2.169> The path and filename of the file to monitor the existence of."
	::= { logA2StatusFileEntry 2 }

logA2StatusFileExist OBJECT-TYPE
	SYNTAX  INTEGER {
		exists(1),
		not-exists(2)
	}
	ACCESS  read-only
	STATUS  mandatory
	DESCRIPTION
		"&<caiLogA2.170> Flag indicating whether the file should exist or not."
	        DEFVAL { 0 }
	::= { logA2StatusFileEntry 3 }

logA2StatusFileTrapSendPolicy OBJECT-TYPE
	SYNTAX  INTEGER {
		never(1),
        once(2),
		perPoll(3)
	}
	ACCESS  read-only
	STATUS  mandatory
	DESCRIPTION
		"&<caiLogA2.171> The frequency that the traps are sent.
1. never - A trap is never sent.
2. once - A trap is sent only once the state has been changed.
3. perPoll - A status trap is sent each poll if the state is down."
	        DEFVAL { 0 }
	::= { logA2StatusFileEntry 4 }

logA2StatusFileStatus OBJECT-TYPE
	SYNTAX  INTEGER {
		up(1),
		down(2),
		unknown(3)
	}
	ACCESS	read-write
	STATUS	mandatory
	DESCRIPTION
		"&<caiLogA2.172> The attribute that shows the current status of the watcher
1.    up - The file is in the expected state.
2.    down - The file is not in the expected state.
3.    unknown - The watcher is a new watcher that has not been polled for the first time.
4.   acknowledged - The watcher was in a down state but the user has acknowledged this state."
	        DEFVAL { 0 }
	::= { logA2StatusFileEntry 5 }

logA2StatusFileHistoryPolicy OBJECT-TYPE
	SYNTAX  INTEGER {
		generateHistory(1),
		noGenerateHistory(2)
	}
	ACCESS  read-only
	STATUS  mandatory
	DESCRIPTION
		"&<caiLogA2.173> When a trap is sent the information can be stored in a history table:
1.    generateHistory -Traps generated by this watcher will be added to the history table.
2.    noGenerateHistory - Traps generated by this watcher will not be added to the history table."
	        DEFVAL { 0 }
	::= { logA2StatusFileEntry 6 }

logA2StatusFileButton OBJECT-TYPE
	SYNTAX  INTEGER {
		none(1),
		delete(2)
	}
	ACCESS  read-write
	STATUS  mandatory
	DESCRIPTION
		"&<caiLogA2.174> The button remove a row from the file status table.
1.   none - No action will be taken, the default value.
2.   delete - Delete this entry from the StatusFileTable."
		::= { logA2StatusFileEntry 7 }

logA2StatusFileCallbackRef OBJECT-TYPE
	SYNTAX DisplayString
	ACCESS read-only
	STATUS mandatory
	DESCRIPTION
		"&<caiLogA2.199>The name of the Call-Back reference that should be invoked in case of a status change."
	::= { logA2StatusFileEntry 8 }


--
--         History Group
--

logA2HistoryMaxEntries OBJECT-TYPE
	SYNTAX  INTEGER
	ACCESS  read-write
	STATUS  mandatory
	DESCRIPTION
		"&<caiLogA2.175> The maximum number of elements in the history table."
        DEFVAL { -1 }
	::= { logA2HistoryGroup 1 }

logA2HistoryRefresh OBJECT-TYPE
	SYNTAX  INTEGER {
		refresh(1),
		none(2)
	}
	ACCESS  read-write
	STATUS  mandatory
	DESCRIPTION
		"&<caiLogA2.176> A button to allow the user to empty the history table.
1. none - The default value does nothing.
2. refresh - Set to refresh to empty the history table."
	::= { logA2HistoryGroup 2 }

--logA2HistoryTable OBJECT-TYPE
--	SYNTAX  SEQUENCE OF LogA2HistorySequence
--	ACCESS  not-accessible
--	STATUS  mandatory
--	DESCRIPTION
--		"&<caiLogA2.177> Table with the trap's elements."
--	::= { logA2HistoryGroup 3 }

--
--  logA2HistoryTable
--
--logA2HistoryEntry OBJECT-TYPE
--	SYNTAX  LogA2HistorySequence
--	ACCESS  not-accessible
--	STATUS  mandatory
--	DESCRIPTION
--		"&<caiLogA2.178>A table entry for the history table"
--	INDEX { logA2HistoryTrapSubType }
--	::= { logA2HistoryTable 1 }

--LogA2HistorySequence ::=
--	SEQUENCE {
--		logA2HistoryTrapSubType	        INTEGER,
--		logA2HistoryTrapTime		DisplayString,
--		logA2HistoryFileName    	DisplayString,
--		logA2HistoryWatcherFileName	DisplayString,
--		logA2HistoryWatcherName		DisplayString,
--		logA2HistoryTrapMessage	        DisplayString
--	}

--logA2HistoryTrapSubType OBJECT-TYPE
--	SYNTAX  INTEGER
--	ACCESS  read-only
--	STATUS  mandatory
--	DESCRIPTION
--		"&<caiLogA2.179> All traps are enterprise specific in this table so only list the Sub Type."
--	::= { logA2HistoryEntry 1 }

--logA2HistoryTrapTime OBJECT-TYPE
--	SYNTAX  DisplayString
--	ACCESS  read-only
--	STATUS  mandatory
--	DESCRIPTION
--		"&<caiLogA2.180> The time and date the trap ."
--	::= { logA2HistoryEntry 2 }


--logA2HistoryFileName OBJECT-TYPE
--	SYNTAX  DisplayString
--	ACCESS  read-only
--	STATUS  mandatory
--	DESCRIPTION
--		"&<caiLogA2.181> The path and filename of the file that caused the state change, i.e. no wild cards."
--	::= { logA2HistoryEntry 3 }


--logA2HistoryWatcherFileName OBJECT-TYPE
--	SYNTAX  DisplayString
--	ACCESS  read-only
--	STATUS  mandatory
--	DESCRIPTION
--		"&<caiLogA2.182> The path and filename of the file as described in the watcher, i.e. possible wild cards."
--	::= { logA2HistoryEntry 4 }

--logA2HistoryWatcherName OBJECT-TYPE
--	SYNTAX  DisplayString
--	ACCESS  read-only
--	STATUS  mandatory
--	DESCRIPTION
--		"&<caiLogA2.183> The description from the watcher."
--	::= { logA2HistoryEntry 5 }

--logA2HistoryTrapMessage OBJECT-TYPE
--	SYNTAX  DisplayString
--	ACCESS  read-only
--	STATUS  mandatory
--	DESCRIPTION
--		"&<caiLogA2.184> The line of text was sent with the trap."
--	::= { logA2HistoryEntry 6 }

--
-- TRAP Definitions
--

logA2LogStateUp  TRAP-TYPE
	ENTERPRISE      caiLogA2
	DESCRIPTION
		"&<caiLogA2.185>A log watcher's pattern has not been found."
	::= 10984

logA2LogStateDown  TRAP-TYPE
	ENTERPRISE      caiLogA2
	DESCRIPTION
		"&<caiLogA2.186>A log watcher's pattern has been found for a critical alert."
	::= 10985

logA2LogStateDownWarning  TRAP-TYPE
	ENTERPRISE      caiLogA2
	DESCRIPTION
		"&<caiLogA2.198>A log watcher's pattern has been found for a warning alert."
	::= 10982

logA2LogStateUnknown  TRAP-TYPE
	ENTERPRISE      caiLogA2
	DESCRIPTION
		"&<caiLogA2.187>A log watcher's file is unavailable."
	::= 10980

logA2LogAdded  TRAP-TYPE
	ENTERPRISE      caiLogA2
	DESCRIPTION
		"&<caiLogA2.188>A log watcher has been added."
	::= 10986

logA2LogDeleted  TRAP-TYPE
	ENTERPRISE      caiLogA2
	DESCRIPTION
		"&<caiLogA2.189>A log watcher has been deleted."
	::= 10987

logA2FileStateUp  TRAP-TYPE
	ENTERPRISE      caiLogA2
	DESCRIPTION
		"&<caiLogA2.190>A file watcher is in the expected state."
	::= 11984

logA2FileStateDown  TRAP-TYPE
	ENTERPRISE      caiLogA2
	DESCRIPTION
		"&<caiLogA2.191>A file watcher is not in the expected state."
	::= 11985

logA2FileStateUnknown TRAP-TYPE
	ENTERPRISE	caiLogA2
	DESCRIPTION
		"&<caiLogA2.192>A file watcher is in an unknown state."
	::= 11980

logA2FileAdded  TRAP-TYPE
	ENTERPRISE      caiLogA2
	DESCRIPTION
		"&<caiLogA2.193>A file watcher has been added."
	::= 11986

logA2FileDeleted  TRAP-TYPE
	ENTERPRISE      caiLogA2
	DESCRIPTION
		"&<caiLogA2.194>A file watcher has been deleted."
	::= 11987

logA2LogMatchTrap  TRAP-TYPE
	ENTERPRISE      caiLogA2
	DESCRIPTION
		"&<caiLogA2.195>A match trap is recognized."
	::= 10988

logA2LogClusteredPassiveTrap  TRAP-TYPE
	ENTERPRISE      caiLogA2
	DESCRIPTION
		"&<caiLogA2.201>A log watcher monitors files on a clustered file system and this file system has changed to passive mode."
	::= 10983
	
logA2LogClusteredActiveTrap  TRAP-TYPE
	ENTERPRISE      caiLogA2
	DESCRIPTION
		"&<caiLogA2.201>A log watcher monitors files on a clustered file system and this file system has changed to active mode."
	::= 10981
	
END
