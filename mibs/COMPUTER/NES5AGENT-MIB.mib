--MibName=nes5Agent
--
--******************************************************************************
--*  WSA 5 Agent MIB prototype for NES, IBMHTTPD and Domino                    *
--*  edit nes5 to "ap5" prefix                                                   *
--*  edit Nes5 to "Ap5" prefix                                                   *
--*  edit NES5 to "AP5" prefix                                                   *
--*  edit 78 to OID                                                   	       *
--******************************************************************************

NES5AGENT-MIB DEFINITIONS ::= BEGIN

IMPORTS
	enterprises   FROM RFC1155-SMI
	OBJECT-TYPE   FROM RFC1155-SMI
	DisplayString FROM RFC1158-MIB;
        
-- Base OID  1.3.6.1.4.1.791.2.10.2.78

    cai         OBJECT IDENTIFIER ::= { enterprises 791 }

    caiSysMgr   OBJECT IDENTIFIER ::= { cai 2 }

    tng         OBJECT IDENTIFIER ::= { caiSysMgr 10 }

    unix-nt      OBJECT IDENTIFIER ::= { tng 2 }
                      
    nes5Agent   OBJECT IDENTIFIER ::= { unix-nt 78 }

    nes5ServerGroup           OBJECT IDENTIFIER   ::=  {  nes5Agent 1   }
    nes5ServiceGroup          OBJECT IDENTIFIER   ::=  {  nes5Agent 2   }
    nes5BadLinkGroup          OBJECT IDENTIFIER   ::=  {  nes5Agent 3   }
    nes5TopURLGroup           OBJECT IDENTIFIER   ::=  {  nes5Agent 4   }
    nes5URLAvailCounterGroup  OBJECT IDENTIFIER   ::=  {  nes5Agent 5   }
    nes5URLMntrGroup          OBJECT IDENTIFIER   ::=  {  nes5Agent 6   }
    nes5DiskGroup             OBJECT IDENTIFIER   ::=  {  nes5Agent 7   }
    nes5AvailCounterGroup     OBJECT IDENTIFIER   ::=  {  nes5Agent 8   }
    nes5PolledCounterGroup    OBJECT IDENTIFIER   ::=  {  nes5Agent 9   }
    nes5EventGroup            OBJECT IDENTIFIER   ::=  {  nes5Agent 10  }
    nes5AgentGroup            OBJECT IDENTIFIER   ::=  {  nes5Agent 11  }
    nes5WCGroup               OBJECT IDENTIFIER   ::=  {  nes5Agent 12  }
    nes5SHGroup               OBJECT IDENTIFIER   ::=  {  nes5Agent 13  }
    nes5LocalActionGroup      OBJECT IDENTIFIER   ::=  {  nes5Agent 14  }
    nes5ServLogGroup          OBJECT IDENTIFIER   ::=  {  nes5Agent 15  }
    nes5ExpressionGroup       OBJECT IDENTIFIER   ::=  {  nes5Agent 16  }

--******************************************************************************
--* ServerGroup - Site and summary information                               *
--******************************************************************************

        nes5ServerName OBJECT-TYPE
                SYNTAX  DisplayString
                ACCESS  read-only
                STATUS  mandatory
                DESCRIPTION
                "The host name of the computer."
                ::=  {  nes5ServerGroup 1   }

        nes5ServerSummaryStatus OBJECT-TYPE
                SYNTAX  INTEGER
                {
                    ok(1),
                    warning(2),
                    critical(3)
                }
                ACCESS  read-only
                STATUS  mandatory
                DESCRIPTION
                "The status of the monitored server."
                ::=  {  nes5ServerGroup 2   }

        nes5ServerPollingInterval OBJECT-TYPE
                SYNTAX  INTEGER
                ACCESS  read-write
                STATUS  mandatory
                DESCRIPTION
                "Poll interval for the server group in seconds."
                ::=  {  nes5ServerGroup 3   }

        nes5ServerResetCounts OBJECT-TYPE
                SYNTAX  INTEGER
                {
                    Reset(1)
                }
                ACCESS  read-write
                STATUS  mandatory
                DESCRIPTION
                "Resets all history counts to zero when set."
                ::=  {  nes5ServerGroup 4   }

        nes5ServerResetTS OBJECT-TYPE
                SYNTAX  INTEGER
                ACCESS  read-only
                STATUS  mandatory
                DESCRIPTION
                "Time of last reset in ctime form."
                ::=  {  nes5ServerGroup 5   }

        nes5ServerResetTSEdit OBJECT-TYPE
                SYNTAX  DisplayString
                ACCESS  read-only
                STATUS  mandatory
                DESCRIPTION
                "Time of last reset in display form."
                ::=  {  nes5ServerGroup 6   }

        nes5ServerResetDays OBJECT-TYPE
                SYNTAX  INTEGER
                ACCESS  read-write
                STATUS  mandatory
                DESCRIPTION
                "Number of days between automatic history count resets."
                ::=  {  nes5ServerGroup 7   }

        nes5ServerVersion OBJECT-TYPE
                SYNTAX  DisplayString
                ACCESS  read-only
                STATUS  mandatory
                DESCRIPTION
                "The version of the web server."
                ::=  {  nes5ServerGroup 8   }

        nes5ServerPort OBJECT-TYPE
                SYNTAX  INTEGER
                ACCESS  read-only
                STATUS  mandatory
                DESCRIPTION
                "Port the server is listening on."
                ::=  {  nes5ServerGroup 9   }

        nes5ServerLBHost OBJECT-TYPE
                SYNTAX  DisplayString
                ACCESS  read-write
                STATUS  mandatory
                DESCRIPTION
                "Host name of Agent Collector."
                ::=  {  nes5ServerGroup 10   }

        nes5ServerLBPort OBJECT-TYPE
                SYNTAX  DisplayString
                ACCESS  read-write
                STATUS  mandatory
                DESCRIPTION
                "Agent Collector name."
                ::=  {  nes5ServerGroup 11   }

	nes5ServerLBEnaDis OBJECT-TYPE
		SYNTAX      INTEGER {enable(1), disable(2)}
		ACCESS      read-write
		STATUS      mandatory
		DESCRIPTION "Enable or disable agent sending data to Agent Collector."
		::= {nes5ServerGroup 12}

        nes5SuperAgentRequest OBJECT-TYPE
                SYNTAX  DisplayString
                ACCESS  read-write
                STATUS  mandatory
                DESCRIPTION
                "Super Agent service request."
                ::=  {  nes5ServerGroup 13   }

        nes5ServerHiLevelVersion OBJECT-TYPE
                SYNTAX  DisplayString
                ACCESS  read-only
                STATUS  mandatory
                DESCRIPTION
                "Oracle server: The high level version number of the web server."
                ::=  {  nes5ServerGroup 14   }

        nes5ServerSetBaseLine OBJECT-TYPE
                SYNTAX  INTEGER {
                                set(1)
                               }
                ACCESS  write-only
                STATUS  mandatory
                DESCRIPTION
                "Immediately set Adaptive Configuration values."
                ::=  {  nes5ServerGroup 15   }

        nes5ServerBaseLineWarnWeight OBJECT-TYPE
                SYNTAX  INTEGER 
                ACCESS  read-write
                STATUS  mandatory
                DESCRIPTION
                "Adaptive Configuration warning weighing factor."
                ::=  {  nes5ServerGroup 16   }

        nes5ServerBaseLineCritWeight OBJECT-TYPE
                SYNTAX  INTEGER 
                ACCESS  read-write
                STATUS  mandatory
                DESCRIPTION
                "Adaptive Configuration critical weighing factor."
                ::=  {  nes5ServerGroup 17   }

	nes5ServerBaseLineEnaDis OBJECT-TYPE
		SYNTAX      INTEGER {disable(1), enable(2)}
		ACCESS      read-write
		STATUS      mandatory
		DESCRIPTION "Enable or disable Active Adaptive Configuration."
		::= {  nes5ServerGroup 18  }

	nes5ServerBaseLineTimer OBJECT-TYPE
		SYNTAX      INTEGER
		ACCESS      read-write
		STATUS      mandatory
		DESCRIPTION "Active Adaptive Configuration timer."
		::= {  nes5ServerGroup 19  }
                
        nes5ServerExportConfigSet OBJECT-TYPE
                SYNTAX  DisplayString
                ACCESS  read-write
                STATUS  mandatory
                DESCRIPTION
                "Name of config to export to."
                ::=  {  nes5ServerGroup 20   }
                
        nes5ServerImportConfigSet OBJECT-TYPE
                SYNTAX  DisplayString
                ACCESS  read-write
                STATUS  mandatory
                DESCRIPTION
                "Name of config to import from."
                ::=  {  nes5ServerGroup 21   }


--******************************************************************************
--* ServiceGroup - Services                                                  *
--******************************************************************************

        nes5ServiceTableEntries OBJECT-TYPE
                SYNTAX  INTEGER
                ACCESS  read-only
                STATUS  mandatory
                DESCRIPTION
                "The number of entries in the table."
                ::=  {  nes5ServiceGroup 1  }

        nes5ServiceSummaryStatus OBJECT-TYPE
                SYNTAX  INTEGER
                {
                    normal(1),
                    warning(2),
                    critical(3)
                }
                ACCESS  read-only
                STATUS  mandatory
                DESCRIPTION
                "Summary status of the service group."
                ::=  {  nes5ServiceGroup 2  }

        nes5ServicePollingInterval OBJECT-TYPE
                SYNTAX  INTEGER
                ACCESS  read-write
                STATUS  mandatory
                DESCRIPTION
                "Poll interval for the service group in seconds."
                ::=  {  nes5ServiceGroup 3  }

        -- Start, start service
        -- Stop, stop service, don't reset autorestart
        -- Recycle, stop and then restart service
        -- Stop no AutoRestart - stop and turn off autorestart
        nes5ServiceControl OBJECT-TYPE
                SYNTAX  INTEGER
                {
                    start(1),
                    stop(2),
                    recycle(3),
                    stop-NoAutoRestart(4)
                }
                ACCESS  read-write
                STATUS  mandatory
                DESCRIPTION
                "Start and stop all services in the service table."
                ::=  {  nes5ServiceGroup 4  }

        nes5ServiceWarningCount OBJECT-TYPE
                SYNTAX  INTEGER
                ACCESS  read-only
                STATUS  mandatory
                DESCRIPTION
                "Number of services in warning state."
                ::=  {  nes5ServiceGroup 5  }

        nes5ServiceCriticalCount OBJECT-TYPE
                SYNTAX  INTEGER
                ACCESS  read-only
                STATUS  mandatory
                DESCRIPTION
                "Number of services in critical state."
                ::=  {  nes5ServiceGroup 6  }

        nes5NumberOfPolls OBJECT-TYPE
               SYNTAX  INTEGER
               ACCESS  read-only
               STATUS  mandatory
               DESCRIPTION
               "Number of times services have been polled"
               ::=  {  nes5ServiceGroup 7}

        nes5ServiceTable OBJECT-TYPE
                SYNTAX  SEQUENCE OF Nes5ServiceEntry
                ACCESS  not-accessible
                STATUS  mandatory
                DESCRIPTION
                "The list of all monitored services."
                ::=  {  nes5ServiceGroup 8}

	nes5ServiceGPEnaDis OBJECT-TYPE
		SYNTAX      INTEGER {enable(1), disable(2)}
		ACCESS      read-write
		STATUS      mandatory
		DESCRIPTION "Enable or disable for the Group."
		::= { nes5ServiceGroup 9 }
		
        nes5ServiceEntry OBJECT-TYPE
                 SYNTAX  Nes5ServiceEntry
                 ACCESS  not-accessible
                 STATUS  mandatory
                 DESCRIPTION
                 "The ServiceTable entry."
                 INDEX { nes5ServiceName }
                     ::=  { nes5ServiceTable 1 }

        Nes5ServiceEntry ::= SEQUENCE
        {
            nes5ServiceName           DisplayString,
            nes5ServiceState          INTEGER,
            nes5AutoRestart           INTEGER,
            nes5AutoReboot            INTEGER,
            nes5RestartAttempts       INTEGER,
            nes5RestartCount          INTEGER,
            nes5RebootAttempts        INTEGER,
            nes5RebootCount           INTEGER,
            nes5LocalAction           DisplayString,
            nes5TotalRestarts         INTEGER,
            nes5TotalReboots          INTEGER,
            nes5ServiceStateStatus    INTEGER,
            nes5ServiceWarnings       INTEGER,
            nes5ServiceCriticals      INTEGER,
            nes5StateIfStopped        INTEGER,
            nes5ServiceCtrl           INTEGER,
            nes5ServiceAvail          DisplayString,
            nes5ServiceRunningPolls   INTEGER,
	    nes5ServicePorts	    DisplayString,
            nes5ServiceType	    DisplayString,
	    nes5ServiceLagSetting	    INTEGER,
	    nes5ServiceLagValue	    INTEGER
        }

        nes5ServiceName OBJECT-TYPE
                SYNTAX  DisplayString
                ACCESS  read-only
                STATUS  mandatory
                DESCRIPTION
                "The name of the service."
                ::=  {  nes5ServiceEntry 1   }

        nes5ServiceState OBJECT-TYPE
                SYNTAX  INTEGER
                {
                    stopped(1),
                    started(2),
                    notinstalled(3),
                    actionpending(4)
                }
                ACCESS  read-only
                STATUS  mandatory
                DESCRIPTION
                "The state of the service."
                ::=  {  nes5ServiceEntry 2   }

        nes5AutoRestart OBJECT-TYPE
                SYNTAX  INTEGER
                {
                    yes(1),
                    no(2)
                }
                ACCESS  read-write
                STATUS  mandatory
                DESCRIPTION
                "Flag indicating whether to attempt to restart the service if it's down."
                ::=  {  nes5ServiceEntry 3   }

        nes5AutoReboot OBJECT-TYPE
                SYNTAX  INTEGER
                {
                    yes(1),
                    no(2)
                }
                ACCESS  read-write
                STATUS  mandatory
                DESCRIPTION
                "Flag indicating whether to attempt to reboot the host if service is down."
                ::=  {  nes5ServiceEntry 4   }

        nes5RestartAttempts OBJECT-TYPE
                SYNTAX  INTEGER
                ACCESS  read-write
                STATUS  mandatory
                DESCRIPTION
                "Reboot the host after this many restart attempts are unsuccessful."
                ::=  {  nes5ServiceEntry 5   }

        nes5RestartCount OBJECT-TYPE
                SYNTAX  INTEGER
                ACCESS  read-only
                STATUS  mandatory
                DESCRIPTION
                "Number of service restarts attempted since last successful service restart."
                ::=  {  nes5ServiceEntry 6   }

        nes5RebootAttempts OBJECT-TYPE
                SYNTAX  INTEGER
                ACCESS  read-write
                STATUS  mandatory
                DESCRIPTION
                "Execute local action after this many reboot attempts are unsuccessful."
                ::=  {  nes5ServiceEntry 7   }

        nes5RebootCount OBJECT-TYPE
                SYNTAX  INTEGER
                ACCESS  read-only
                STATUS  mandatory
                DESCRIPTION
                "Number of reboots attempted since last successful service restart."
                ::=  {  nes5ServiceEntry 8   }

        nes5LocalAction OBJECT-TYPE
                SYNTAX  DisplayString
                ACCESS  read-write
                STATUS  mandatory
                DESCRIPTION
                "Local action to perform when reboot attempts exceeded."
                ::=  {  nes5ServiceEntry 9   }

        nes5TotalRestarts OBJECT-TYPE
                SYNTAX  INTEGER
                ACCESS  read-only
                STATUS  mandatory
                DESCRIPTION
                "Total number of service restarts attempted."
                ::=  {  nes5ServiceEntry 10   }

        nes5TotalReboots OBJECT-TYPE
                SYNTAX  INTEGER
                ACCESS  read-only
                STATUS  mandatory
                DESCRIPTION
                "Total number of host reboots attempted."
                ::=  {  nes5ServiceEntry 11   }

        nes5ServiceStateStatus OBJECT-TYPE
                SYNTAX  INTEGER
                {
                    normal(1),
                    warning(2),
                    critical(3)
                }
                ACCESS  read-only
                STATUS  mandatory
                DESCRIPTION
                "Status of this service."
                ::=  {  nes5ServiceEntry 12   }

        nes5ServiceWarnings OBJECT-TYPE
                SYNTAX  INTEGER
                ACCESS  read-only
                STATUS  mandatory
                DESCRIPTION
                "Number of warnings generated by this service."
                ::=  {  nes5ServiceEntry 13   }

        nes5ServiceCriticals OBJECT-TYPE
                SYNTAX  INTEGER
                ACCESS  read-only
                STATUS  mandatory
                DESCRIPTION
                "Number of criticals generated by this service."
                ::=  {  nes5ServiceEntry 14   }

        nes5StateIfStopped OBJECT-TYPE
                SYNTAX  INTEGER
                {
                    normal(1),
                    warning(2),
                    critical(3)
                }
                ACCESS  read-write
                STATUS  mandatory
                DESCRIPTION
                "Service status reported if service is stopped."
                ::=  {  nes5ServiceEntry 15   }

        nes5ServiceCtrl OBJECT-TYPE
               SYNTAX  INTEGER {
                                start(1),
                                stop(2),
                                recycle(3),
                                stop-noautorestart(4)
                               }
               ACCESS  read-write
               STATUS  mandatory
               DESCRIPTION
               "Start and stop this service."
               ::=  {  nes5ServiceEntry 16   }

        nes5ServiceAvail OBJECT-TYPE
               SYNTAX  DisplayString
               ACCESS  read-only
               STATUS  mandatory
               DESCRIPTION
               "% of time service available (running) = running/number of polls"
               ::=  {  nes5ServiceEntry 17  }

        nes5ServiceRunningPolls OBJECT-TYPE
                SYNTAX  INTEGER
                ACCESS  read-only
                STATUS  mandatory
                DESCRIPTION
                "Number of polls showing service running(used for availability calc)."
                ::=  {  nes5ServiceEntry 18   }

        nes5ServicePorts OBJECT-TYPE
                SYNTAX  DisplayString
                ACCESS  read-write
                STATUS  mandatory
                DESCRIPTION
                "Additional PORTS to check for the service."
                ::=  {  nes5ServiceEntry 19   }

	 nes5ServiceType OBJECT-TYPE
	        SYNTAX      DisplayString
	        ACCESS      read-only
	        STATUS      mandatory
	        DESCRIPTION "Type of Service (Server, Admin, FTP)."
	        ::= { nes5ServiceEntry 20 }
		
        nes5ServiceLagSetting OBJECT-TYPE
                SYNTAX  INTEGER
                ACCESS  read-write
                STATUS  mandatory
                DESCRIPTION
                "Lag setting for the service."
                ::=  {  nes5ServiceEntry 21   }
		
        nes5ServiceLagValue OBJECT-TYPE
                SYNTAX  INTEGER
                ACCESS  read-only
                STATUS  mandatory
                DESCRIPTION
                "Current Lag value for the service."
                ::=  {  nes5ServiceEntry 22   }

--******************************************************************************
--* BadLinkGroup - URL links not found by requestors                            *
--******************************************************************************

        nes5BLTableEntries OBJECT-TYPE
                SYNTAX  INTEGER
                ACCESS  read-only
                STATUS  mandatory
                DESCRIPTION
                "The number of entries in the table."
                ::=  {  nes5BadLinkGroup 1   }


        nes5BLClearTable OBJECT-TYPE
               SYNTAX  INTEGER {
                                Reset(1)
                               }
               ACCESS  read-write
               STATUS  mandatory
               DESCRIPTION
               "Clear the table when set."
               ::=  {  nes5BadLinkGroup 2   }

        nes5BLSummaryStatus OBJECT-TYPE
               SYNTAX  INTEGER {
                                normal(1),
                                warning(2),
                                critical(3)
                               }
               ACCESS  read-only
               STATUS  mandatory
               DESCRIPTION
               "Summary status for bad links."
               ::=  {  nes5BadLinkGroup 3   }

        nes5BLInterval OBJECT-TYPE
               SYNTAX  INTEGER
               ACCESS  read-write
               STATUS  mandatory
               DESCRIPTION
               "Seconds to poll for changes."
               ::=  {  nes5BadLinkGroup 4   }

        nes5BLCircularBuffSize OBJECT-TYPE
               SYNTAX  INTEGER
               ACCESS  read-write
               STATUS  mandatory
               DESCRIPTION
               "Max entries in the table (default 50)(Not a circular buffer)."
               ::=  {  nes5BadLinkGroup 5   }

        nes5BLWarningThreshold OBJECT-TYPE
               SYNTAX  INTEGER
               ACCESS  read-write
               STATUS  mandatory
               DESCRIPTION
               "Number of requests on a row before warning is generated."
               ::=  {  nes5BadLinkGroup 6   }

        nes5BLCriticalThreshold OBJECT-TYPE
               SYNTAX  INTEGER
               ACCESS  read-write
               STATUS  mandatory
               DESCRIPTION
               "Number of requests on a row before critical is generated."
               ::=  {  nes5BadLinkGroup 7   }

        nes5BLWarningCount OBJECT-TYPE
               SYNTAX  INTEGER
               ACCESS  read-only
               STATUS  mandatory
               DESCRIPTION
               "The number of entries in the table with a warning status."
               ::=  {  nes5BadLinkGroup 8   }

        nes5BLCriticalCount OBJECT-TYPE
               SYNTAX  INTEGER
               ACCESS  read-only
               STATUS  mandatory
               DESCRIPTION
               "The number of entries in the table with a critical status."
               ::=  {  nes5BadLinkGroup 9   }

        nes5BLWarningAction OBJECT-TYPE
               SYNTAX  DisplayString
               ACCESS  read-write
               STATUS  mandatory
               DESCRIPTION
               "Command to be executed when warning threshold is crossed on a row."
               ::=  {  nes5BadLinkGroup 10   }

        nes5BLCriticalAction OBJECT-TYPE
               SYNTAX  DisplayString
               ACCESS  read-write
               STATUS  mandatory
               DESCRIPTION
               "Command to be executed when critical threshold is crossed on a row."
               ::=  {  nes5BadLinkGroup 11   }


        nes5BLCreateReportURL OBJECT-TYPE
               SYNTAX  INTEGER {
                                Create(1)
                               }
               ACCESS  read-write
               STATUS  mandatory
               DESCRIPTION
               "When triggered, create report using path and file in BLReportURL."
               ::=  {  nes5BadLinkGroup 12   }

        nes5BLReportURL OBJECT-TYPE
               SYNTAX  DisplayString
               ACCESS  read-write
               STATUS  mandatory
               DESCRIPTION
               "Path and filename for report; Relative to DocumentRoot unless starts with '/'."
               ::=  {  nes5BadLinkGroup 13   }

        nes5BLTable OBJECT-TYPE
               SYNTAX  SEQUENCE OF Nes5BLEntry
               ACCESS  not-accessible
               STATUS  mandatory
               DESCRIPTION
               "This table contains a list bad links."
               ::=  {  nes5BadLinkGroup 14  }

	nes5BLGPEnaDis OBJECT-TYPE
		SYNTAX      INTEGER {enable(1), disable(2)}
		ACCESS      read-write
		STATUS      mandatory
		DESCRIPTION "Enable or disable for the Group."
		::= { nes5BadLinkGroup 15 }

        nes5BLEntry OBJECT-TYPE
               SYNTAX  Nes5BLEntry
               ACCESS  not-accessible
               STATUS  mandatory
               DESCRIPTION
               "This is an entry in the BLTable"
               INDEX { nes5BLURL, nes5BLReferringURL }
               ::=  { nes5BLTable 1 }

        Nes5BLEntry ::= SEQUENCE
        {
           nes5BLURL                              DisplayString,
           nes5BLReferringURL                     DisplayString,
           nes5BLFirstAccessTS                    DisplayString,
           nes5BLlastAccessTS                     DisplayString,
           nes5BLNumRequests                      INTEGER,
           nes5BLStatus                           INTEGER
        }

        nes5BLURL OBJECT-TYPE
               SYNTAX  DisplayString
               ACCESS  read-only
               STATUS  mandatory
               DESCRIPTION
               "Bad URL."
               ::=  {  nes5BLEntry 1   }

        nes5BLReferringURL OBJECT-TYPE
               SYNTAX  DisplayString
               ACCESS  read-only
               STATUS  mandatory
               DESCRIPTION
               "Referring URL to Bad URL."
               ::=  {  nes5BLEntry 2   }

        nes5BLFirstAccessTS OBJECT-TYPE
               SYNTAX  DisplayString
               ACCESS  read-only
               STATUS  mandatory
               DESCRIPTION
               "Time first bad access occurred (time row added to table)."
               ::=  {  nes5BLEntry 3   }

        nes5BLlastAccessTS OBJECT-TYPE
               SYNTAX  DisplayString
               ACCESS  read-only
               STATUS  mandatory
               DESCRIPTION
               "Time of last access to bad URL."
               ::=  {  nes5BLEntry 4   }

        nes5BLNumRequests OBJECT-TYPE
               SYNTAX  INTEGER
               ACCESS  read-only
               STATUS  mandatory
               DESCRIPTION
               "Count of requests."
               ::=  {  nes5BLEntry 5   }

        nes5BLStatus OBJECT-TYPE
               SYNTAX  INTEGER {
                                normal(1),
                                warning(2),
                                critical(3)
                               }
               ACCESS  read-only
               STATUS  mandatory
               DESCRIPTION
               "Summary status for BL."
               ::=  {  nes5BLEntry 6   }


--******************************************************************************
--* TopURLGroup - URLs with highest access rates                             *
--******************************************************************************

        nes5TopURLTableEntries OBJECT-TYPE
               SYNTAX  INTEGER
               ACCESS  read-only
               STATUS  mandatory
               DESCRIPTION
               "The number of entries in the table."
               ::=  {  nes5TopURLGroup 1   }

        nes5TopURLClearTable OBJECT-TYPE
               SYNTAX  INTEGER {
                                Reset(1)
                               }
               ACCESS  read-write
               STATUS  mandatory
               DESCRIPTION
               "Clear the table when set."
               ::=  {  nes5TopURLGroup 2   }

        nes5TopURLInterval OBJECT-TYPE
               SYNTAX  INTEGER
               ACCESS  read-write
               STATUS  mandatory
               DESCRIPTION
               "Seconds to poll for changes."
               ::=  {  nes5TopURLGroup 3   }

        nes5TopURLCircularBuffSize OBJECT-TYPE
               SYNTAX  INTEGER
               ACCESS  read-write
               STATUS  mandatory
               DESCRIPTION
               "Max entries in the table (default 50)."
               ::=  {  nes5TopURLGroup 4   }


        nes5TopURLTable OBJECT-TYPE
               SYNTAX  SEQUENCE OF Nes5TopURLEntry
               ACCESS  not-accessible
               STATUS  mandatory
               DESCRIPTION
               "This table contains a list of the top URLs by hit count."
               ::=  {  nes5TopURLGroup 5 }

        nes5TopURLExclude OBJECT-TYPE
               SYNTAX  DisplayString
               ACCESS  read-write
               STATUS  mandatory
               DESCRIPTION
               "Exclude URLs with these extensions."
               ::=  {  nes5TopURLGroup 6   }

        nes5TopURLExcludeReset OBJECT-TYPE
               SYNTAX  INTEGER {
                                Reset(1)
                               }
               ACCESS  read-write
               STATUS  mandatory
               DESCRIPTION
               "Reset exclude list to defaults."
               ::=  {  nes5TopURLGroup 7   }

	nes5TopURLGPEnaDis OBJECT-TYPE
		SYNTAX      INTEGER {enable(1), disable(2)}
		ACCESS      read-write
		STATUS      mandatory
		DESCRIPTION "Enable or disable for the Group."
		::= { nes5TopURLGroup 8 }

        nes5TopURLEntry OBJECT-TYPE
               SYNTAX  Nes5TopURLEntry
               ACCESS  not-accessible
               STATUS  mandatory
               DESCRIPTION
               "This is an entry in the TopURLTable"
               INDEX { nes5TopURLURL}
               ::=  { nes5TopURLTable 1 }

        Nes5TopURLEntry ::= SEQUENCE
        {
           nes5TopURLURL          DisplayString,
           nes5TopURLNumHits      INTEGER,
           nes5TopURLRank         INTEGER
        }

        nes5TopURLURL OBJECT-TYPE
               SYNTAX  DisplayString
               ACCESS  read-only
               STATUS  mandatory
               DESCRIPTION
               "URL."
               ::=  {  nes5TopURLEntry 1   }

        nes5TopURLNumHits OBJECT-TYPE
               SYNTAX  INTEGER
               ACCESS  read-only
               STATUS  mandatory
               DESCRIPTION
               "Number of hits."
               ::=  {  nes5TopURLEntry 2   }

        nes5TopURLRank OBJECT-TYPE
               SYNTAX  INTEGER
               ACCESS  read-only
               STATUS  mandatory
               DESCRIPTION
               "For easy sorting in Abrowser."
               ::=  {  nes5TopURLEntry 3   }


--******************************************************************************
--* URLAvailCounterGroup - Counters available for URL monitoring             *
--******************************************************************************

        nes5URLAvailCounterTableEntries OBJECT-TYPE
               SYNTAX  INTEGER
               ACCESS  read-only
               STATUS  mandatory
               DESCRIPTION
               "The number of entries in the table."
               ::=  {  nes5URLAvailCounterGroup 1   }

        nes5URLAvailCounterTable OBJECT-TYPE
           SYNTAX  SEQUENCE OF Nes5URLAvailCounterEntry
           ACCESS  not-accessible
           STATUS  mandatory
           DESCRIPTION
           "This table contains a list of all monitored AvailCounters"
           ::=  {  nes5URLAvailCounterGroup 2}

        nes5URLAvailCounterEntry OBJECT-TYPE
                                SYNTAX  Nes5URLAvailCounterEntry
                                ACCESS  not-accessible
                                STATUS  mandatory
                                DESCRIPTION
                                "This is an entry in the URLAvailCounterTable"
                                INDEX { nes5URLAvailCounterDescription }
                                        ::=  { nes5URLAvailCounterTable 1 }

        Nes5URLAvailCounterEntry ::= SEQUENCE {
                        nes5URLAvailCounterDescription    DisplayString
        }

        nes5URLAvailCounterDescription OBJECT-TYPE
               SYNTAX  DisplayString
               ACCESS  read-only
               STATUS  mandatory
               DESCRIPTION
               "The description of the AvailCounter"
               ::=  {  nes5URLAvailCounterEntry 1   }

--******************************************************************************
--* URLMntrGroup - Monitored URLs                                            *
--******************************************************************************

        nes5URLMntrTableEntries OBJECT-TYPE
               SYNTAX  INTEGER
               ACCESS  read-only
               STATUS  mandatory
               DESCRIPTION
               "The number of entries in the table."
               ::=  {  nes5URLMntrGroup 1   }

        nes5URLMntrInterval OBJECT-TYPE
               SYNTAX  INTEGER
               ACCESS  read-write
               STATUS  mandatory
               DESCRIPTION
               "Seconds between polls for the counter."
               ::=  {  nes5URLMntrGroup 2   }

        nes5URLMntrHitRate OBJECT-TYPE
               SYNTAX  INTEGER
               ACCESS  read-write
               STATUS  mandatory
               DESCRIPTION
               "Interval in seconds over which the counter is measured."
               ::=  {  nes5URLMntrGroup 3   }

--      Add a counter to the table.  The value must include at least the first four of
--      the 6 items listed, separated by commas.
--      <nes5URLAvailCounterDescription> is a value from nes5URLAvailCounterDescription in nes5URLAvailCounterTable.

        nes5URLMntrAdd OBJECT-TYPE
               SYNTAX  DisplayString
               ACCESS  write-only
               STATUS  mandatory
               DESCRIPTION
               "Add this entry to the table: <url>,<URLAvailCounterDescription>,<warning threshold>,<critical threshold>,<warning action>,<critical action>."
               ::=  {  nes5URLMntrGroup 4   }

--      Delete a counter from the table.  The value must include the 2 items listed.
        nes5URLMntrDelete OBJECT-TYPE
               SYNTAX  DisplayString
               ACCESS  write-only
               STATUS  mandatory
               DESCRIPTION
               "Delete entry from the table: <URLMntrDesc>,<url>."
               ::=  {  nes5URLMntrGroup 5   }

        nes5URLMntrUpdate OBJECT-TYPE
               SYNTAX  DisplayString
               ACCESS  write-only
               STATUS  mandatory
	       DESCRIPTION "Update this entry in the table."
               ::=  {  nes5URLMntrGroup 6   }

        nes5URLMntrSummaryStatus OBJECT-TYPE
               SYNTAX  INTEGER {
                                normal(1),
                                warning(2),
                                critical(3)
                               }
               ACCESS  read-only
               STATUS  mandatory
               DESCRIPTION
               "Most severe status of all rows in the table."
               ::=  {  nes5URLMntrGroup 7   }

        nes5URLMntrTable OBJECT-TYPE
               SYNTAX  SEQUENCE OF Nes5URLMntrEntry
               ACCESS  not-accessible
               STATUS  mandatory
               DESCRIPTION
               "This table contains a list of URLs to monitor."
               ::=  {  nes5URLMntrGroup 8}

        nes5URLMntrEntry OBJECT-TYPE
               SYNTAX  Nes5URLMntrEntry
               ACCESS  not-accessible
               STATUS  mandatory
               DESCRIPTION
               "This is an entry in the URLMntrTable"
               INDEX { nes5URLMntrURL, nes5URLMntrDesc}
               ::=  { nes5URLMntrTable 1 }

        Nes5URLMntrEntry ::= SEQUENCE
        {
           nes5URLMntrURL                                 DisplayString,
           nes5URLMntrDesc                                DisplayString,
           nes5URLMntrValue                               DisplayString,
           nes5URLMntrWarningThreshold                    INTEGER,
           nes5URLMntrCriticalThreshold                   INTEGER,
           nes5URLMntrWarningAction                       DisplayString,
           nes5URLMntrCriticalAction                      DisplayString,
           nes5URLMntrStatus                              INTEGER,
           nes5URLMntrEnableDisable                       INTEGER,
           nes5URLMntrDescending                          INTEGER,
           nes5URLMntrReset                               INTEGER,
           nes5URLMntrResetTime                           DisplayString,
	   nes5URLMntrValueReported			INTEGER,
           nes5URLMntrPrevStatus          INTEGER,
	   nes5URLMntrLagSetting		INTEGER,
	   nes5URLMntrLagValue		INTEGER
        }

        nes5URLMntrURL OBJECT-TYPE
               SYNTAX  DisplayString
               ACCESS  read-only
               STATUS  mandatory
               DESCRIPTION
               "URL to monitor."
               ::=  {  nes5URLMntrEntry 1   }

        nes5URLMntrDesc OBJECT-TYPE
               SYNTAX  DisplayString
               ACCESS  read-only
               STATUS  mandatory
               DESCRIPTION
               "Description of the monitored value."
               ::=  {  nes5URLMntrEntry 2   }

        nes5URLMntrValue OBJECT-TYPE
               SYNTAX  DisplayString
               ACCESS  read-only
               STATUS  mandatory
               DESCRIPTION
               "Peak number of hits per URLMntrHitRate seconds."
               ::=  {  nes5URLMntrEntry 3   }

        nes5URLMntrWarningThreshold OBJECT-TYPE
               SYNTAX  INTEGER
               ACCESS  read-write
               STATUS  mandatory
               DESCRIPTION
               "Warning threshold in MS"
               ::=  {  nes5URLMntrEntry 4   }

        nes5URLMntrCriticalThreshold OBJECT-TYPE
               SYNTAX  INTEGER
               ACCESS  read-write
               STATUS  mandatory
               DESCRIPTION
               "Critical threshold in MS"
               ::=  {  nes5URLMntrEntry 5   }

        nes5URLMntrWarningAction OBJECT-TYPE
               SYNTAX  DisplayString
               ACCESS  read-write
               STATUS  mandatory
               DESCRIPTION
               "Command to be executed when warning threshold is exceeded."
               ::=  {  nes5URLMntrEntry 6   }

        nes5URLMntrCriticalAction OBJECT-TYPE
               SYNTAX  DisplayString
               ACCESS  read-write
               STATUS  mandatory
               DESCRIPTION
               "Command to be executed when critical threshold is exceeded."
               ::=  {  nes5URLMntrEntry 7  }

        nes5URLMntrStatus OBJECT-TYPE
               SYNTAX  INTEGER {
                                normal(1),
                                warning(2),
                                critical(3)
                               }
               ACCESS  read-only
               STATUS  mandatory
               DESCRIPTION
               "Status of this URL."
               ::=  {  nes5URLMntrEntry 8 }

        nes5URLMntrEnableDisable OBJECT-TYPE
                SYNTAX  INTEGER
                {
                    enable(1),
                    disable(2)
                }
                ACCESS  read-write
                STATUS  mandatory
                DESCRIPTION
                "Enable or disable alerts for this URL."
                ::=  {  nes5URLMntrEntry 9   }

        nes5URLMntrDescending OBJECT-TYPE
               SYNTAX  INTEGER {
                                no(1),
                                yes(2)
                               }
               ACCESS  read-only
               STATUS  mandatory
               DESCRIPTION
               "Yes if lower value triggers thresholds."
               ::=  {  nes5URLMntrEntry 10 }

        nes5URLMntrReset OBJECT-TYPE
               SYNTAX  INTEGER {
                                Reset(1)
                               }
               ACCESS  write-only
               STATUS  mandatory
               DESCRIPTION
               "Reset value for this counter."
               ::=  {  nes5URLMntrEntry 11 }

        nes5URLMntrResetTime OBJECT-TYPE
               SYNTAX  DisplayString
               ACCESS  read-only
               STATUS  mandatory
               DESCRIPTION
               "Time stamp of when this counter was reset."
               ::=  {  nes5URLMntrEntry 12  }
	       

        nes5URLMntrValueReported OBJECT-TYPE
               SYNTAX  INTEGER {
                                summary(1),
                                average(2),
				vhost(3)
                               }
               ACCESS  read-write
               STATUS  mandatory
               DESCRIPTION
               "The reported value of the counter is either a summary or average of all servers, or virtaul host."
               ::=  {  nes5URLMntrEntry 13 }

        nes5URLMntrPrevStatus OBJECT-TYPE
               SYNTAX  INTEGER {
                                normal(1),
                                warning(2),
                                critical(3)
                               }
               ACCESS  read-only
               STATUS  mandatory
               DESCRIPTION
               "Status of this URL."
               ::=  {  nes5URLMntrEntry 14 }

        nes5URLMntrLagSetting OBJECT-TYPE
                SYNTAX  INTEGER
                ACCESS  read-write
                STATUS  mandatory
                DESCRIPTION
                "Lag setting for the counter."
                ::=  {  nes5URLMntrEntry 15   }
		
        nes5URLMntrLagValue OBJECT-TYPE
                SYNTAX  INTEGER
                ACCESS  read-only
                STATUS  mandatory
                DESCRIPTION
                "Current Lag value for the counter."
                ::=  {  nes5URLMntrEntry 16   }

	nes5URLMntrGPEnaDis OBJECT-TYPE
		SYNTAX      INTEGER {enable(1), disable(2)}
		ACCESS      read-write
		STATUS      mandatory
		DESCRIPTION "Enable or disable for the Group."
		::= { nes5URLMntrGroup 11 }


--******************************************************************************
--* DiskGroup - Primary disks used by the web server                         *
--******************************************************************************

        nes5DiskTableEntries OBJECT-TYPE
                SYNTAX  INTEGER
                ACCESS  read-only
                STATUS  mandatory
                DESCRIPTION
                "The number of entries in the table."
                ::=  {  nes5DiskGroup 1   }

        nes5DiskSummaryStatus OBJECT-TYPE
                SYNTAX  INTEGER
                {
                    ok(1),
                    warning(2),
                    critical(3)
                }
                ACCESS  read-only
                STATUS  mandatory
                DESCRIPTION
                "The summary status of all monitored disks."
                ::=  {  nes5DiskGroup 2   }

        nes5DiskPollingInterval OBJECT-TYPE
                SYNTAX  INTEGER
                ACCESS  read-write
                STATUS  mandatory
                DESCRIPTION
                "Poll interval for the disk group in seconds."
                ::=  {  nes5DiskGroup 3   }

        nes5DiskWarningCount OBJECT-TYPE
                SYNTAX  INTEGER
                ACCESS  read-only
                STATUS  mandatory
                DESCRIPTION
                "Number of disks in warning state."
                ::=  {  nes5DiskGroup 4   }

        nes5DiskCriticalCount OBJECT-TYPE
                SYNTAX  INTEGER
                ACCESS  read-only
                STATUS  mandatory
                DESCRIPTION
                "Number of disks in critical state."
                ::=  {  nes5DiskGroup 5  }

        nes5DiskTable OBJECT-TYPE
                SYNTAX  SEQUENCE OF Nes5DiskEntry
                ACCESS  not-accessible
                STATUS  mandatory
                DESCRIPTION
                "The list of all monitored disks."
                ::=  {  nes5DiskGroup 6 }

	nes5DiskGPEnaDis OBJECT-TYPE
		SYNTAX      INTEGER {enable(1), disable(2)}
		ACCESS      read-write
		STATUS      mandatory
		DESCRIPTION "Enable or disable for the Group."
		::= { nes5DiskGroup 7 }

        nes5DiskEntry OBJECT-TYPE
                SYNTAX  Nes5DiskEntry
                ACCESS  not-accessible
                STATUS  mandatory
                DESCRIPTION
                "The DiskTable entry."
                INDEX { nes5DiskID }
                    ::=  { nes5DiskTable 1 }

        Nes5DiskEntry ::= SEQUENCE
        {
            nes5DiskID                 DisplayString,
            nes5DiskSize               DisplayString,
            nes5DiskUsed               DisplayString,
            nes5DiskFree               DisplayString,
            nes5DiskWarningThreshold   INTEGER,
            nes5DiskCriticalThreshold  INTEGER,
            nes5DiskStatus             INTEGER,
            nes5WarningCounts          INTEGER,
            nes5CriticalCounts         INTEGER,
            nes5DiskUsage              DisplayString,
            nes5PrevWarningCounts      INTEGER,
            nes5PrevCriticalCounts     	INTEGER,
	    nes5DiskLagSetting		INTEGER,
	    nes5DiskLagValue		INTEGER
        }

        nes5DiskID OBJECT-TYPE
                SYNTAX  DisplayString
                ACCESS  read-only
                STATUS  mandatory
                DESCRIPTION
                "The directory whose disk is measured."
                ::=  {  nes5DiskEntry 1   }

        nes5DiskSize OBJECT-TYPE
                SYNTAX  DisplayString
                ACCESS  read-only
                STATUS  mandatory
                DESCRIPTION
                "Size of the disk in Mbytes."
                ::=  {  nes5DiskEntry 2   }

        nes5DiskUsed OBJECT-TYPE
                SYNTAX  DisplayString
                ACCESS  read-only
                STATUS  mandatory
                DESCRIPTION
                "Space used on the disk in Mbytes"
                ::=  {  nes5DiskEntry 3   }

        nes5DiskFree OBJECT-TYPE
                SYNTAX  DisplayString
                ACCESS  read-only
                STATUS  mandatory
                DESCRIPTION
                "Free space on the disk in Mbytes"
                ::=  {  nes5DiskEntry 4   }

        nes5DiskWarningThreshold OBJECT-TYPE
                SYNTAX  INTEGER
                ACCESS  read-write
                STATUS  mandatory
                DESCRIPTION
                "Percentage of disk used which will trigger warning status."
                ::=  {  nes5DiskEntry 5   }

        nes5DiskCriticalThreshold OBJECT-TYPE
                SYNTAX  INTEGER
                ACCESS  read-write
                STATUS  mandatory
                DESCRIPTION
                "Percentage of disk used which will trigger critical status."
                ::=  {  nes5DiskEntry 6   }

        nes5DiskStatus OBJECT-TYPE
                SYNTAX  INTEGER
                {
                    ok(1),
                    warning(2),
                    critical(3)
                }
                ACCESS  read-only
                STATUS  mandatory
                DESCRIPTION
                "The status of the disk."
                ::=  {  nes5DiskEntry 7   }

        nes5WarningCounts OBJECT-TYPE
                SYNTAX  INTEGER
                ACCESS  read-only
                STATUS  mandatory
                DESCRIPTION
                "Number of times warning alert generated."
                ::=  {  nes5DiskEntry 8   }

        nes5CriticalCounts OBJECT-TYPE
                SYNTAX  INTEGER
                ACCESS  read-only
                STATUS  mandatory
                DESCRIPTION
                "Number of times critical alert generated."
                ::=  {  nes5DiskEntry 9   }

        nes5DiskUsage OBJECT-TYPE
                SYNTAX  DisplayString
                ACCESS  read-only
                STATUS  mandatory
                DESCRIPTION
                "What the web server uses this disk for."
                ::=  {  nes5DiskEntry 10   }

        nes5PrevWarningCounts OBJECT-TYPE
               SYNTAX  INTEGER
               ACCESS  read-only
               STATUS  mandatory
               DESCRIPTION
               "Previous number of times warning alert generated."
               ::=  {  nes5DiskEntry 11  }

        nes5PrevCriticalCounts OBJECT-TYPE
               SYNTAX  INTEGER
               ACCESS  read-only
               STATUS  mandatory
               DESCRIPTION
               "Previous number of times critical alert generated."
               ::=  {  nes5DiskEntry 12   }

        nes5DiskLagSetting OBJECT-TYPE
                SYNTAX  INTEGER
                ACCESS  read-write
                STATUS  mandatory
                DESCRIPTION
                "Lag setting for the disk."
                ::=  {  nes5DiskEntry 13   }
		
        nes5DiskLagValue OBJECT-TYPE
                SYNTAX  INTEGER
                ACCESS  read-only
                STATUS  mandatory
                DESCRIPTION
                "Current Lag value for the disk."
                ::=  {  nes5DiskEntry 14   }


--******************************************************************************
--* AvailCounterGroup - Counters currently available                         *
--******************************************************************************

        nes5AvailCounterTableEntries OBJECT-TYPE
                SYNTAX  INTEGER
                ACCESS  read-only
                STATUS  mandatory
                DESCRIPTION
                "The number of entries in the table."
                ::=  {  nes5AvailCounterGroup 1   }

        nes5AvailCounterTable OBJECT-TYPE
                SYNTAX  SEQUENCE OF Nes5AvailCounterEntry
                ACCESS  not-accessible
                STATUS  mandatory
                DESCRIPTION
                "The list of all available counters"
                ::=  {  nes5AvailCounterGroup 2}

        nes5AvailCounterEntry OBJECT-TYPE
                 SYNTAX  Nes5AvailCounterEntry
                 ACCESS  not-accessible
                 STATUS  mandatory
                 DESCRIPTION
                 "The AvailCounterTable entry."
                 INDEX { nes5AvailCounterDescription }
                     ::=  { nes5AvailCounterTable 1 }

        Nes5AvailCounterEntry ::= SEQUENCE
        {
            nes5AvailCounterDescription   DisplayString
        }

        nes5AvailCounterDescription OBJECT-TYPE
                SYNTAX  DisplayString
                ACCESS  read-only
                STATUS  mandatory
                DESCRIPTION
                "The description of the available counter"
                ::=  {  nes5AvailCounterEntry 1   }


--******************************************************************************
--* PolledCounterGroup - Counters being polled                               *
--******************************************************************************

        nes5PolledCounterTableEntries OBJECT-TYPE
                SYNTAX  INTEGER
                ACCESS  read-only
                STATUS  mandatory
                DESCRIPTION
                "The number of entries in the table."
                ::=  {  nes5PolledCounterGroup 1   }

        nes5PolledCounterAdd OBJECT-TYPE
                SYNTAX  DisplayString
                ACCESS  write-only
                STATUS  mandatory
                DESCRIPTION
                "Add this counter to the polled counter table."
                ::=  {  nes5PolledCounterGroup 2   }

        nes5PolledCounterDelete OBJECT-TYPE
                SYNTAX  DisplayString
                ACCESS  write-only
                STATUS  mandatory
                DESCRIPTION
                "Delete this counter from the polled counter table."
                ::=  {  nes5PolledCounterGroup 3   }

        nes5PolledSummaryStatus OBJECT-TYPE
                SYNTAX  INTEGER
                {
                    normal(1),
                    warning(2),
                    critical(3)
                }
                ACCESS  read-only
                STATUS  mandatory
                DESCRIPTION
                "The summary status of all polled counters."
                ::=  {  nes5PolledCounterGroup 4   }

        nes5PollingInterval OBJECT-TYPE
                SYNTAX  INTEGER
                ACCESS  read-write
                STATUS  mandatory
                DESCRIPTION
                "Poll interval for the polled counter group in seconds."
                ::=  {  nes5PolledCounterGroup 5   }

        nes5PolledWarningCount OBJECT-TYPE
                SYNTAX  INTEGER
                ACCESS  read-only
                STATUS  mandatory
                DESCRIPTION
                "Number of polled counters in warning state."
                ::=  {  nes5PolledCounterGroup 6   }

        nes5PolledCriticalCount OBJECT-TYPE
                SYNTAX  INTEGER
                ACCESS  read-only
                STATUS  mandatory
                DESCRIPTION
                "Number of polled counters in critical state."
                ::=  {  nes5PolledCounterGroup 7   }

        nes5PolledCounterTable OBJECT-TYPE
                SYNTAX  SEQUENCE OF Nes5PolledCounterEntry
                ACCESS  not-accessible
                STATUS  mandatory
                DESCRIPTION
                "The list of all polled counters."
                ::=  {  nes5PolledCounterGroup 8}

        nes5PolledCounterEntry OBJECT-TYPE
                 SYNTAX  Nes5PolledCounterEntry
                 ACCESS  not-accessible
                 STATUS  mandatory
                 DESCRIPTION
                 "The PolledCounterTable entry."
                 INDEX { nes5Description }
                     ::=  { nes5PolledCounterTable 1 }

        Nes5PolledCounterEntry ::= SEQUENCE {
            nes5Description               DisplayString,
            nes5Available                 INTEGER,
            nes5WarningThreshold          DisplayString,
            nes5CriticalThreshold         DisplayString,
            nes5Value                     DisplayString,
            nes5WarningCount              INTEGER,
            nes5CriticalCount             INTEGER,
            nes5WarningAction             DisplayString,
            nes5CriticalAction            DisplayString,
            nes5Status                    INTEGER,
            nes5EnableDisable             INTEGER,
            nes5DescendingCounter         INTEGER,
            nes5Minimum                   DisplayString,
            nes5Maximum                   DisplayString,
            nes5Average                   DisplayString,
            nes5StdDev                    DisplayString,
	    nes5ValueReported		INTEGER,
            nes5PrevStatus          	INTEGER,
	    nes5LagSetting		INTEGER,
	    nes5LagValue			INTEGER
        }

        nes5Description OBJECT-TYPE
                SYNTAX  DisplayString
                ACCESS  read-only
                STATUS  mandatory
                DESCRIPTION
                "The description of the polled counter."
                ::=  {  nes5PolledCounterEntry 1   }

        nes5Available OBJECT-TYPE
                SYNTAX  INTEGER
                {
                    available(1),
                    notavailable(2)
                }
                ACCESS  read-only
                STATUS  mandatory
                DESCRIPTION
                "Describes whether this counter is currently available."
                ::=  {  nes5PolledCounterEntry 2   }

        nes5WarningThreshold OBJECT-TYPE
                SYNTAX  DisplayString
                ACCESS  read-write
                STATUS  mandatory
                DESCRIPTION
                "Counter value that will trigger warning status if value exceeds it."
                ::=  {  nes5PolledCounterEntry 3   }

        nes5CriticalThreshold OBJECT-TYPE
                SYNTAX  DisplayString
                ACCESS  read-write
                STATUS  mandatory
                DESCRIPTION
                "Counter value that will trigger critical status if value exceeds it."
                ::=  {  nes5PolledCounterEntry 4   }

        nes5Value OBJECT-TYPE
                SYNTAX  DisplayString
                ACCESS  read-only
                STATUS  mandatory
                DESCRIPTION
                "Value of the polled counter."
                ::=  {  nes5PolledCounterEntry 5   }

        nes5WarningCount OBJECT-TYPE
                SYNTAX  INTEGER
                ACCESS  read-only
                STATUS  mandatory
                DESCRIPTION
                "Number of times warning alert generated."
                ::=  {  nes5PolledCounterEntry 6   }

        nes5CriticalCount OBJECT-TYPE
                SYNTAX  INTEGER
                ACCESS  read-only
                STATUS  mandatory
                DESCRIPTION
                "Number of times critical alert generated."
                ::=  {  nes5PolledCounterEntry 7   }

        nes5WarningAction OBJECT-TYPE
                SYNTAX  DisplayString
                ACCESS  read-write
                STATUS  mandatory
                DESCRIPTION
                "Command to be executed when warning threshold is exceeded."
                ::=  {  nes5PolledCounterEntry 8   }

        nes5CriticalAction OBJECT-TYPE
                SYNTAX  DisplayString
                ACCESS  read-write
                STATUS  mandatory
                DESCRIPTION
                "Command to be executed when critical threshold is exceeded."
                ::=  {  nes5PolledCounterEntry 9   }

        nes5Status OBJECT-TYPE
                SYNTAX  INTEGER
                {
                    normal(1),
                    warning(2),
                    critical(3)
                }
                ACCESS  read-only
                STATUS  mandatory
                DESCRIPTION
                "Status of the polled counter."
                ::=  {  nes5PolledCounterEntry 10   }

        nes5EnableDisable OBJECT-TYPE
                SYNTAX  INTEGER
                {
                    enable(1),
                    disable(2)
                }
                ACCESS  read-write
                STATUS  mandatory
                DESCRIPTION
                "Enable or disable alerts for this counter."
                ::=  {  nes5PolledCounterEntry 11   }

        nes5DescendingCounter OBJECT-TYPE
                SYNTAX  INTEGER
                {
                    no(1),
                    yes(2)
                }
                ACCESS  read-write
                STATUS  mandatory
                DESCRIPTION
                "Yes if lower value triggers thresholds, no if higher value triggers thresholds."
                ::=  {  nes5PolledCounterEntry 12   }

        nes5Minimum OBJECT-TYPE
               SYNTAX  DisplayString
               ACCESS  read-only
               STATUS  mandatory
               DESCRIPTION
               "The minimum reading since the last reset."
               ::=  {  nes5PolledCounterEntry 13   }

        nes5Maximum OBJECT-TYPE
               SYNTAX  DisplayString
               ACCESS  read-only
               STATUS  mandatory
               DESCRIPTION
               "The maximum reading since the last reset."
               ::=  {  nes5PolledCounterEntry 14   }

        nes5Average OBJECT-TYPE
               SYNTAX  DisplayString
               ACCESS  read-only
               STATUS  mandatory
               DESCRIPTION
               "The average reading since the last reset."
               ::=  {  nes5PolledCounterEntry 15   }

        nes5StdDev OBJECT-TYPE
               SYNTAX  DisplayString
               ACCESS  read-only
               STATUS  mandatory
               DESCRIPTION
               "The standard deviation based on the last 100 readings."
               ::=  {  nes5PolledCounterEntry 16   }

        nes5ValueReported OBJECT-TYPE
               SYNTAX  INTEGER {
                                summary(1),
                                average(2),
				vhost(3)
                               }
               ACCESS  read-write
               STATUS  mandatory
               DESCRIPTION
               "The reported value of the counter is either a summary or average of all servers."
               ::=  {  nes5PolledCounterEntry 17 }

        nes5PrevStatus OBJECT-TYPE
                SYNTAX  INTEGER
                {
                    normal(1),
                    warning(2),
                    critical(3)
                }
                ACCESS  read-only
                STATUS  mandatory
                DESCRIPTION
                "Previous status of the polled counter."
                ::=  {  nes5PolledCounterEntry 18   }
		
        nes5LagSetting OBJECT-TYPE
                SYNTAX  INTEGER
                ACCESS  read-write
                STATUS  mandatory
                DESCRIPTION
                "Lag setting for the counter."
                ::=  {  nes5PolledCounterEntry 19   }
		
        nes5LagValue OBJECT-TYPE
                SYNTAX  INTEGER
                ACCESS  read-only
                STATUS  mandatory
                DESCRIPTION
                "Current Lag value for the counter."
                ::=  {  nes5PolledCounterEntry 20   }
	       

        nes5PolledCounterUpdate OBJECT-TYPE
               SYNTAX  DisplayString
               ACCESS  write-only
               STATUS  mandatory
	       DESCRIPTION "Update this entry in the table."
               ::=  {  nes5PolledCounterGroup 9  }


	nes5PolledGPEnaDis OBJECT-TYPE
		SYNTAX      INTEGER {enable(1), disable(2)}
		ACCESS      read-write
		STATUS      mandatory
		DESCRIPTION "Enable or disable for the Group."
		::= { nes5PolledCounterGroup 12 }



--******************************************************************************
--* EventGroup - user defined event monitoring                               *
--******************************************************************************
--      In this agent, we'll put available events in wsEventTable ahead of time
--      and allow the user to enable them for monitoring.

        nes5EventTableEntries OBJECT-TYPE
                SYNTAX  INTEGER
                ACCESS  read-only
                STATUS  mandatory
                DESCRIPTION
                "The number of entries in the event description table."
                ::=  {  nes5EventGroup 1   }

        nes5EventLogTableEntries OBJECT-TYPE
                SYNTAX  INTEGER
                ACCESS  read-only
                STATUS  mandatory
                DESCRIPTION
                "The number of entries in the event log table."
                ::=  {  nes5EventGroup 2   }

        nes5EventAdd OBJECT-TYPE
                SYNTAX  DisplayString
                ACCESS  write-only
                STATUS  mandatory
                DESCRIPTION
                "Event ID to be added to the event table."
                ::=  {  nes5EventGroup 3   }

        nes5EventDelete OBJECT-TYPE
                SYNTAX  INTEGER
                ACCESS  write-only
                STATUS  mandatory
                DESCRIPTION
                "Event ID to be deleted from the event table."
                ::=  {  nes5EventGroup 4   }

        nes5EventSummaryStatus OBJECT-TYPE
                SYNTAX  INTEGER
                {
                    normal(1),
                    warning(2),
                    critical(3)
                }
                ACCESS  read-write
                STATUS  mandatory
                DESCRIPTION
                "Summary status for events. Not automatic, must be manually reset to normal."
                ::=  {  nes5EventGroup 5   }

        nes5EventInterval OBJECT-TYPE
                SYNTAX  INTEGER
                ACCESS  read-write
                STATUS  mandatory
                DESCRIPTION
                "Poll interval for the Event group in seconds."
                ::=  {  nes5EventGroup 6   }

        nes5EventCircularBuffSize OBJECT-TYPE
                SYNTAX  INTEGER
                ACCESS  read-write
                STATUS  mandatory
                DESCRIPTION
                "Maximum number of entries in the event log table.  When this size is
                exceeded, oldest events are deleted to make room for the newest events."
                ::=  {  nes5EventGroup 7   }

        nes5EventTable OBJECT-TYPE
                SYNTAX  SEQUENCE OF Nes5EventEntry
                ACCESS  not-accessible
                STATUS  mandatory
                DESCRIPTION
                "The table of events being monitored."
                ::=  {  nes5EventGroup 8}

        nes5EventLogTable OBJECT-TYPE
                SYNTAX  SEQUENCE OF Nes5EventLogEntry
                ACCESS  not-accessible
                STATUS  mandatory
                DESCRIPTION
                "The table of events that occurred."
                ::=  {  nes5EventGroup 9}

        nes5EventWarningCount OBJECT-TYPE
                SYNTAX  INTEGER
                ACCESS  read-only
                STATUS  mandatory
                DESCRIPTION
                "Number of warning events since last reset."
                ::=  {  nes5EventGroup 10  }

        nes5EventCriticalCount OBJECT-TYPE
                SYNTAX  INTEGER
                ACCESS  read-only
                STATUS  mandatory
                DESCRIPTION
                "Number of critical events since last reset."
                ::=  {  nes5EventGroup 11 }

	nes5EventCmd OBJECT-TYPE
		SYNTAX      DisplayString
		ACCESS      read-write
		STATUS      mandatory
		DESCRIPTION 
		"Modify,id,severity,enabled.  EnableAll DisableAll"
		::= {nes5EventGroup 12 }

	nes5EventGPEnaDis OBJECT-TYPE
		SYNTAX      INTEGER {enable(1), disable(2)}
		ACCESS      read-write
		STATUS      mandatory
		DESCRIPTION "Enable or disable for the Group."
		::= { nes5EventGroup 13 }
		
        nes5EventEntry OBJECT-TYPE
                 SYNTAX  Nes5EventEntry
                 ACCESS  not-accessible
                 STATUS  mandatory
                 DESCRIPTION
                 "The EventTable entry."
                 INDEX { nes5EventID }
                 ::=  { nes5EventTable 1 }

        Nes5EventEntry ::= SEQUENCE
        {
                nes5EventID                    INTEGER,
                nes5EVDescription              DisplayString,
                nes5EVSeverity                 INTEGER,
                nes5EVSyslogText               DisplayString,
                nes5EVEnable                   INTEGER
        }

        nes5EventID OBJECT-TYPE
                SYNTAX  INTEGER
                ACCESS  read-only
                STATUS  mandatory
                DESCRIPTION
                "ID of the event."
                ::=  {  nes5EventEntry 1   }

        nes5EVDescription OBJECT-TYPE
                SYNTAX  DisplayString
                ACCESS  read-write
                STATUS  mandatory
                DESCRIPTION
                "Description of the event."
                ::=  {  nes5EventEntry 2   }

        nes5EVSeverity OBJECT-TYPE
                SYNTAX  INTEGER
                {
                    warning(1),
                    critical(2)
                }
                ACCESS  read-write
                STATUS  mandatory
                DESCRIPTION
                "Severity level of the event."
                ::=  {  nes5EventEntry 3   }

        nes5EVSyslogText OBJECT-TYPE
                SYNTAX  DisplayString
                ACCESS  read-write
                STATUS  mandatory
                DESCRIPTION
                "Text to search for in the syslog file that indicates this event occurred."
                ::=  {  nes5EventEntry 4   }

        nes5EVEnable OBJECT-TYPE
               SYNTAX  INTEGER {
                                enabled(1),
                                disabled(2)
                               }
               ACCESS  read-write
               STATUS  mandatory
               DESCRIPTION
               "Enable logging of this event."
               ::=  {  nes5EventEntry 5   }


        nes5EventLogEntry OBJECT-TYPE
                 SYNTAX  Nes5EventLogEntry
                 ACCESS  not-accessible
                 STATUS  mandatory
                 DESCRIPTION
                 "The EventTable entry."
                 INDEX { nes5EVLTimestamp, nes5EVLIndex }
                 ::=  { nes5EventLogTable 1 }

        Nes5EventLogEntry ::= SEQUENCE {
           nes5EVLTimestamp               DisplayString,
           nes5EVLID                      INTEGER,
           nes5EVLDescription             DisplayString,
           nes5EVLStatus                  INTEGER,
           nes5EVLIndex                   INTEGER
        }

        nes5EVLTimestamp OBJECT-TYPE
                SYNTAX  DisplayString
                ACCESS  read-only
                STATUS  mandatory
                DESCRIPTION
                "Human-readable timestamp of when the event happened."
                ::=  {  nes5EventLogEntry 1   }

        nes5EVLID OBJECT-TYPE
                SYNTAX  INTEGER
                ACCESS  read-only
                STATUS  mandatory
                DESCRIPTION
                "ID of the event."
                ::=  {  nes5EventLogEntry 2   }

        nes5EVLDescription OBJECT-TYPE
                SYNTAX  DisplayString
                ACCESS  read-only
                STATUS  mandatory
                DESCRIPTION
                "Description of the event."
                ::=  {  nes5EventLogEntry 3   }

        nes5EVLStatus OBJECT-TYPE
                SYNTAX  INTEGER
                {
                    warning(1),
                    critical(2)
                }
                ACCESS  read-only
                STATUS  mandatory
                DESCRIPTION
                "Status caused by the event."
                ::=  {  nes5EventLogEntry 4   }

        nes5EVLIndex OBJECT-TYPE
                SYNTAX  INTEGER
                ACCESS  read-only
                STATUS  mandatory
                DESCRIPTION
                "Index value that ensures uniqueness of events with same ID and timestamp."
                ::=  {  nes5EventLogEntry 5   }


--******************************************************************************
--* AgentGroup - Agent version and update information                        *
--******************************************************************************

        nes5AgentDescription OBJECT-TYPE
                SYNTAX  DisplayString
                ACCESS  read-only
                STATUS  mandatory
                DESCRIPTION
                "Description of the agent."
                ::=  {  nes5AgentGroup 1   }

        nes5AgentVersion OBJECT-TYPE
                SYNTAX  DisplayString
                ACCESS  read-only
                STATUS  mandatory
                DESCRIPTION
                "Version of the agent."
                ::=  {  nes5AgentGroup 2   }

        nes5AgentStartTime OBJECT-TYPE
                SYNTAX  DisplayString
                ACCESS  read-only
                STATUS  mandatory
                DESCRIPTION
                "The time the agent was started."
                ::=  {  nes5AgentGroup 3   }

        nes5ServerLastUpdate OBJECT-TYPE
                SYNTAX  DisplayString
                ACCESS  read-only
                STATUS  mandatory
                DESCRIPTION
                "The time the ServerGroup was last updated"
                ::=  {  nes5AgentGroup 4   }

        nes5ServicesLastUpdate OBJECT-TYPE
                SYNTAX  DisplayString
                ACCESS  read-only
                STATUS  mandatory
                DESCRIPTION
                "The time the ServicesGroup was last updated"
                ::=  {  nes5AgentGroup 5   }

        nes5DiskLastUpdate OBJECT-TYPE
                SYNTAX  DisplayString
                ACCESS  read-only
                STATUS  mandatory
                DESCRIPTION
                "The time the DiskGroup was last updated"
                ::=  {  nes5AgentGroup 6   }

        nes5PolledCounterLastUpdate OBJECT-TYPE
                SYNTAX  DisplayString
                ACCESS  read-only
                STATUS  mandatory
                DESCRIPTION
                "The time the PolledCounterGroup was last updated"
                ::=  {  nes5AgentGroup 7   }

        nes5EventsLastUpdate OBJECT-TYPE
                SYNTAX  DisplayString
                ACCESS  read-only
                STATUS  mandatory
                DESCRIPTION
                "The time the EventGroup was last updated"
                ::=  {  nes5AgentGroup 8   }

        nes5BadLinksLastUpdate OBJECT-TYPE
                SYNTAX  DisplayString
                ACCESS  read-only
                STATUS  mandatory
                DESCRIPTION
                "The time the LinkGroup was last updated"
                ::=  {  nes5AgentGroup 9   }

        nes5WebCrwlrLastUpdate OBJECT-TYPE
                SYNTAX  DisplayString
                ACCESS  read-only
                STATUS  mandatory
                DESCRIPTION
                "The time the WCGroup was last updated"
                ::=  {  nes5AgentGroup 10   }

        nes5URLMntrLastUpdate OBJECT-TYPE
                SYNTAX  DisplayString
                ACCESS  read-only
                STATUS  mandatory
                DESCRIPTION
                "The time the URLMntrGroup was last updated"
                ::=  {  nes5AgentGroup 11   }

        nes5TopURLsLastUpdate OBJECT-TYPE
                SYNTAX  DisplayString
                ACCESS  read-only
                STATUS  mandatory
                DESCRIPTION
                "The time the TopURLGroup was last updated"
                ::=  {  nes5AgentGroup 12   }

        nes5ServerHealthLastUpdate OBJECT-TYPE
               SYNTAX  DisplayString
               ACCESS  read-only
               STATUS  mandatory
               DESCRIPTION
               "The time the ServerHealthGroup was last updated"
               ::=  {  nes5AgentGroup 13   }

        nes5LocalActionLastUpdate OBJECT-TYPE
               SYNTAX  DisplayString
               ACCESS  read-only
               STATUS  mandatory
               DESCRIPTION
               "The last time a local action executed)"
               ::=  {  nes5AgentGroup 14   }

        nes5Nes5LogPath OBJECT-TYPE
               SYNTAX  DisplayString
               ACCESS  read-write
               STATUS  mandatory
               DESCRIPTION
               "OPTIONAL-File name for the Common Log format file"
               ::=  {  nes5AgentGroup 15   }

        nes5ServerRoot OBJECT-TYPE
               SYNTAX  DisplayString
               ACCESS  read-write
               STATUS  mandatory
               DESCRIPTION
               "Server root to prepend to paths in config file."
               ::=  {  nes5AgentGroup 16   }

        nes5ServerConfig OBJECT-TYPE
               SYNTAX  DisplayString
               ACCESS  read-write
               STATUS  mandatory
               DESCRIPTION
               "Server config file path."
               ::=  {  nes5AgentGroup 17   }

        nes5WebServerName OBJECT-TYPE
               SYNTAX  DisplayString
               ACCESS  read-write
               STATUS  mandatory
               DESCRIPTION
               "Service name in NT; command in UNIX; used for start/stop."
               ::=  {  nes5AgentGroup 18   }


        nes5FTPName OBJECT-TYPE
               SYNTAX  DisplayString
               ACCESS  read-write
               STATUS  mandatory
               DESCRIPTION
               "FTP service name in NT; command in UNIX; used for start/stop."
               ::=  {  nes5AgentGroup 19   }


        nes5CGIstrings OBJECT-TYPE
               SYNTAX  DisplayString
               ACCESS  read-write
               STATUS  mandatory
               DESCRIPTION
               "Comma seperated strings used to identify CGI URLs."
               ::=  {  nes5AgentGroup 20   }


        nes5AvailCounterLastUpdate OBJECT-TYPE
               SYNTAX  DisplayString
               ACCESS  read-only
               STATUS  mandatory
               DESCRIPTION
               "The last time a AvailCounter group was updated."
               ::=  {  nes5AgentGroup 21   }


        nes5InstanceName OBJECT-TYPE
               SYNTAX  DisplayString
               ACCESS  read-only
               STATUS  mandatory
               DESCRIPTION
               "The Instance name for this agent."
               ::=  {  nes5AgentGroup 22   }


        nes5ErrorMsg OBJECT-TYPE
               SYNTAX  DisplayString
               ACCESS  read-write
               STATUS  mandatory
               DESCRIPTION
               "The Last Error Message as a result of GET/SET of a MIB value."
               ::=  {  nes5AgentGroup 23   }


        nes5FTPPort OBJECT-TYPE
               SYNTAX  DisplayString
               ACCESS  read-write
               STATUS  mandatory
               DESCRIPTION
               "FTP service port; to change the default (21)."
               ::=  {  nes5AgentGroup 24 }

        nes5ExpressionsLastUpdate OBJECT-TYPE
                SYNTAX  DisplayString
                ACCESS  read-only
                STATUS  mandatory
                DESCRIPTION
                "The time the ExpressionsGroup was last updated"
                ::=  {  nes5AgentGroup 25   }
		
        nes5AdminConfig OBJECT-TYPE
               SYNTAX  DisplayString
               ACCESS  read-write
               STATUS  mandatory
               DESCRIPTION
               "Admin Server config file path."
               ::=  {  nes5AgentGroup 26   }

        nes5WebAdminName OBJECT-TYPE
               SYNTAX  DisplayString
               ACCESS  read-write
               STATUS  mandatory
               DESCRIPTION
               "Admin service name in NT; command qualifier in UNIX; used for start/stop."
               ::=  {  nes5AgentGroup 27   }

        nes5EnableDatabaseUse OBJECT-TYPE
                SYNTAX  INTEGER
                { yes(1), no(2) }
                ACCESS  read-only
                STATUS  mandatory
                DESCRIPTION
                "Domino server: 'Yes' indicates the agent obtains information from Domino Database.
                'No' indicates the agent obtains infomation from Domino generated logfiles."
                ::=  {  nes5AgentGroup 28  }

        nes5DominoName OBJECT-TYPE
                SYNTAX  DisplayString
                ACCESS  read-only
                STATUS  mandatory
                DESCRIPTION
                "Domino server: name for this HTTP server."
                ::=  {  nes5AgentGroup 29   }

        nes5PartitionPath OBJECT-TYPE
                SYNTAX  DisplayString
                ACCESS  read-only
                STATUS  mandatory
                DESCRIPTION
                "Domino server: partition PATH for this HTTP server."
                ::=  {  nes5AgentGroup 30  }

        nes5PartitionNumber OBJECT-TYPE
                SYNTAX  INTEGER
                ACCESS  read-only
                STATUS  mandatory
                DESCRIPTION
                "Domino server: partition number for this HTTP server."
                ::=  {  nes5AgentGroup 31  }
		
        nes5DocPath OBJECT-TYPE
               SYNTAX  DisplayString
               ACCESS  read-write
               STATUS  mandatory
               DESCRIPTION
               "Oracle server: Server doc path."
               ::=  {  nes5AgentGroup 32  }
	       
        nes5ListenerName OBJECT-TYPE
               SYNTAX  DisplayString
               ACCESS  read-write
               STATUS  mandatory
               DESCRIPTION
               "Oracle server: Web listener name."
               ::=  {  nes5AgentGroup 33  }

        nes5ProductRoot OBJECT-TYPE
               SYNTAX  DisplayString
               ACCESS  read-write
               STATUS  mandatory
               DESCRIPTION
               "Oracle server: Product root path."
               ::=  {  nes5AgentGroup 34  }
	       

        nes5IISAvailCounterLastUpdate OBJECT-TYPE
               SYNTAX  DisplayString
               ACCESS  read-only
               STATUS  mandatory
               DESCRIPTION
               "The last time a IISAvailCounter group was updated."
               ::=  {  nes5AgentGroup 35   }

        nes5IISPolledCounterLastUpdate OBJECT-TYPE
               SYNTAX  DisplayString
               ACCESS  read-only
               STATUS  mandatory
               DESCRIPTION
               "The last time a IISPolledCounter group was updated."
               ::=  {  nes5AgentGroup 36   }


--******************************************************************************
--* ServerHealthGroup - overall server performance indicators                  *
--******************************************************************************

        nes5SHSummaryStatus OBJECT-TYPE
               SYNTAX  INTEGER {
                                normal(1),
                                warning(2),
                                critical(3)
                                }
               ACCESS  read-only
               STATUS  mandatory
               DESCRIPTION
               "Summary status for group."
               ::=  {  nes5SHGroup 1   }

        nes5SHPollingInterval OBJECT-TYPE
               SYNTAX  INTEGER
               ACCESS  read-write
               STATUS  mandatory
               DESCRIPTION
               "Seconds to poll for changes."
               ::=  {  nes5SHGroup 2   }

        nes5SHCpuUsage OBJECT-TYPE
               SYNTAX  INTEGER
               ACCESS  read-only
               STATUS  mandatory
               DESCRIPTION
               "CPU usage of the web server."
               ::=  {  nes5SHGroup 3   }

        nes5SHCpuWarningThreshold OBJECT-TYPE
               SYNTAX  INTEGER
               ACCESS  read-write
               STATUS  mandatory
               DESCRIPTION
               "Generate a warning if SHCpuUsage exceeds this."
               ::=  {  nes5SHGroup 4   }

        nes5SHCpuCriticalThreshold OBJECT-TYPE
               SYNTAX  INTEGER
               ACCESS  read-write
               STATUS  mandatory
               DESCRIPTION
               "Generate a critical if SHCpuUsage exceeds this."
               ::=  {  nes5SHGroup 5   }

        nes5SHReqRate OBJECT-TYPE
               SYNTAX  INTEGER
               ACCESS  read-only
               STATUS  mandatory
               DESCRIPTION
               "Requests per second."
               ::=  {  nes5SHGroup 6   }

        nes5SHReqRateWarningThreshold OBJECT-TYPE
               SYNTAX  INTEGER
               ACCESS  read-write
               STATUS  mandatory
               DESCRIPTION
               "Generate a warning if SHReqRate exceeds this."
               ::=  {  nes5SHGroup 7   }

        nes5SHReqRateCriticalThreshold OBJECT-TYPE
               SYNTAX  INTEGER
               ACCESS  read-write
               STATUS  mandatory
               DESCRIPTION
               "Generate a critical if SHReqRate exceeds this."
               ::=  {  nes5SHGroup 8   }

        nes5SHByteRate OBJECT-TYPE
               SYNTAX  INTEGER
               ACCESS  read-only
               STATUS  mandatory
               DESCRIPTION
               "Kilobytes transferred per second."
               ::=  {  nes5SHGroup 9   }

        nes5SHByteRateWarningThreshold OBJECT-TYPE
               SYNTAX  INTEGER
               ACCESS  read-write
               STATUS  mandatory
               DESCRIPTION
               "Generate a warning if SHByteRate exceeds this."
               ::=  {  nes5SHGroup 10   }

        nes5SHByteRateCriticalThreshold OBJECT-TYPE
               SYNTAX  INTEGER
               ACCESS  read-write
               STATUS  mandatory
               DESCRIPTION
               "Generate a critical if SHByteRate exceeds this."
               ::=  {  nes5SHGroup 11   }

        nes5SHWarningAction OBJECT-TYPE
               SYNTAX  DisplayString
               ACCESS  read-write
               STATUS  mandatory
               DESCRIPTION
               "Command to be executed when any warning threshold is exceeded."
               ::=  {  nes5SHGroup 12   }

        nes5SHCriticalAction OBJECT-TYPE
               SYNTAX  DisplayString
               ACCESS  read-write
               STATUS  mandatory
               DESCRIPTION
               "Command to be executed when any critical threshold is exceeded."
               ::=  {  nes5SHGroup 13   }

        nes5SHProcesses OBJECT-TYPE
               SYNTAX  INTEGER
               ACCESS  read-only
               STATUS  mandatory
               DESCRIPTION
               "Number of current server processes."
               ::=  {  nes5SHGroup 14   }

        nes5SHTotalHits OBJECT-TYPE
               SYNTAX  INTEGER
               ACCESS  read-only
               STATUS  mandatory
               DESCRIPTION
               "Totals requests."
               ::=  {  nes5SHGroup 15   }

        nes5SHTotalErrors OBJECT-TYPE
               SYNTAX  INTEGER
               ACCESS  read-only
               STATUS  mandatory
               DESCRIPTION
               "Totals error requests."
               ::=  {  nes5SHGroup 16   }

        nes5SHTotalGETS OBJECT-TYPE
               SYNTAX  INTEGER
               ACCESS  read-only
               STATUS  mandatory
               DESCRIPTION
               "Totals GET requests."
               ::=  {  nes5SHGroup 17   }

        nes5SHTotalPOSTS OBJECT-TYPE
               SYNTAX  INTEGER
               ACCESS  read-only
               STATUS  mandatory
               DESCRIPTION
               "Totals POST requests."
               ::=  {  nes5SHGroup 18   }

        nes5SHTotalHEADS OBJECT-TYPE
               SYNTAX  INTEGER
               ACCESS  read-only
               STATUS  mandatory
               DESCRIPTION
               "Totals HEAD requests."
               ::=  {  nes5SHGroup 19   }

        nes5SHTotalCGI OBJECT-TYPE
               SYNTAX  INTEGER
               ACCESS  read-only
               STATUS  mandatory
               DESCRIPTION
               "Totals CGI requests."
               ::=  {  nes5SHGroup 20   }

        nes5SHServerUptime OBJECT-TYPE
               SYNTAX  INTEGER
               ACCESS  read-only
               STATUS  mandatory
               DESCRIPTION
               "Server uptime in days."
               ::=  {  nes5SHGroup 21   }

        nes5SHMaxReqRate OBJECT-TYPE
               SYNTAX  INTEGER
               ACCESS  read-write
               STATUS  mandatory
               DESCRIPTION
               "Max value for the abrowser max requests scale."
               ::=  {  nes5SHGroup 22   }

        nes5SHMaxByteRate OBJECT-TYPE
               SYNTAX  INTEGER
               ACCESS  read-write
               STATUS  mandatory
               DESCRIPTION
               "Max value for the abrowser max bytes scale."
               ::=  {  nes5SHGroup 23   }

	nes5SHGPEnaDis OBJECT-TYPE
		SYNTAX      INTEGER {enable(1), disable(2)}
		ACCESS      read-write
		STATUS      mandatory
		DESCRIPTION "Enable or disable for the Group."
		::= { nes5SHGroup 24 }
		
        nes5SHCPULagSetting OBJECT-TYPE
                SYNTAX  INTEGER
                ACCESS  read-write
                STATUS  mandatory
                DESCRIPTION
                "Lag setting for the counter."
                ::=  {  nes5SHGroup 25   }
		
        nes5SHCPULagValue OBJECT-TYPE
                SYNTAX  INTEGER
                ACCESS  read-only
                STATUS  mandatory
                DESCRIPTION
                "Current Lag value for the counter."
                ::=  {  nes5SHGroup 26   }
		
        nes5SHRSLagSetting OBJECT-TYPE
                SYNTAX  INTEGER
                ACCESS  read-write
                STATUS  mandatory
                DESCRIPTION
                "Lag setting for the counter."
                ::=  {  nes5SHGroup 27   }
		
        nes5SHRSLagValue OBJECT-TYPE
                SYNTAX  INTEGER
                ACCESS  read-only
                STATUS  mandatory
                DESCRIPTION
                "Current Lag value for the counter."
                ::=  {  nes5SHGroup 28   }
		
        nes5SHKSLagSetting OBJECT-TYPE
                SYNTAX  INTEGER
                ACCESS  read-write
                STATUS  mandatory
                DESCRIPTION
                "Lag setting for the counter."
                ::=  {  nes5SHGroup 29   }
		
        nes5SHKSLagValue OBJECT-TYPE
                SYNTAX  INTEGER
                ACCESS  read-only
                STATUS  mandatory
                DESCRIPTION
                "Current Lag value for the counter."
                ::=  {  nes5SHGroup 30   }


--******************************************************************************
--* Local action log - circular buffer of local actions performed              *
--* Dynamic get, not polled.                                                   *
--******************************************************************************

        nes5LocalActionTableEntries OBJECT-TYPE
               SYNTAX  INTEGER
               ACCESS  read-only
               STATUS  mandatory
               DESCRIPTION
               "The number of entries in the local action log table."
               ::=  {  nes5LocalActionGroup 1   }

        nes5LocalActionCircularBuffSize OBJECT-TYPE
               SYNTAX  INTEGER
               ACCESS  read-write
               STATUS  mandatory
               DESCRIPTION
               "Max entries in the LocalActionLogTable (default 50)."
               ::=  {  nes5LocalActionGroup 2   }

        nes5LocalActionRefresh OBJECT-TYPE
               SYNTAX  INTEGER
               ACCESS  read-write
               STATUS  mandatory
               DESCRIPTION
               "Refresh the table starting with the most recent action."
               ::=  {  nes5LocalActionGroup 3   }

        nes5LocalActionStartDateTime OBJECT-TYPE
               SYNTAX  DisplayString
               ACCESS  read-write
               STATUS  mandatory
               DESCRIPTION
               "Refresh the table starting at the specified date and time."
               ::=  {  nes5LocalActionGroup 4   }

        nes5LocalActionScrollDown OBJECT-TYPE
               SYNTAX  INTEGER
               ACCESS  read-write
               STATUS  mandatory
               DESCRIPTION
               "Read the next older set of log entries into the table."
               ::=  {  nes5LocalActionGroup 5   }

        nes5LocalActionScrollUp OBJECT-TYPE
               SYNTAX  INTEGER
               ACCESS  read-write
               STATUS  mandatory
               DESCRIPTION
               "Read the next newer set of log entries into the table."
               ::=  {  nes5LocalActionGroup 6   }

        nes5LocalActionLogTable OBJECT-TYPE
               SYNTAX  SEQUENCE OF Nes5LocalActionLogEntry
               ACCESS  not-accessible
               STATUS  mandatory
               DESCRIPTION
               "This table contains a list of command actions taken in response to events."
               ::=  {  nes5LocalActionGroup 7 }

        nes5LocalActionLogEntry OBJECT-TYPE
                                SYNTAX  Nes5LocalActionLogEntry
                                ACCESS  not-accessible
                                STATUS  mandatory
                                DESCRIPTION
                                "This is an entry in the LocalActionTable"
                                INDEX { nes5LocalActionSequencer }
                                ::=  { nes5LocalActionLogTable 1 }

        Nes5LocalActionLogEntry ::= SEQUENCE
        {
           nes5LocalActionSequencer               INTEGER,
           nes5LocalActionTimestamp               DisplayString,
           nes5LocalActionSeverity                INTEGER,
           nes5LocalActionReason                  DisplayString,
           nes5LocalActionCommand                 DisplayString
        }

        nes5LocalActionSequencer OBJECT-TYPE
               SYNTAX  INTEGER
               ACCESS  read-only
               STATUS  mandatory
               DESCRIPTION
               "Table sequencer"
               ::=  {  nes5LocalActionLogEntry 1   }

        nes5LocalActionTimestamp OBJECT-TYPE
               SYNTAX  DisplayString
               ACCESS  read-only
               STATUS  mandatory
               DESCRIPTION
               "Time the command was executed (action taken)."
               ::=  {  nes5LocalActionLogEntry 2   }

-- The Warning and Critical values for severity must match CLocalAction::enum Severity.
        nes5LocalActionSeverity OBJECT-TYPE
               SYNTAX  INTEGER
               {
                   normal(1),
                   warning(2),
                   critical(3)
               }
               ACCESS  read-only
               STATUS  mandatory
               DESCRIPTION
               "The severity of the event which triggered the action."
               ::=  {  nes5LocalActionLogEntry 3   }

        nes5LocalActionReason OBJECT-TYPE
               SYNTAX  DisplayString
               ACCESS  read-only
               STATUS  mandatory
               DESCRIPTION
               "The reason the action was taken."
               ::=  {  nes5LocalActionLogEntry 4   }

        nes5LocalActionCommand OBJECT-TYPE
               SYNTAX  DisplayString
               ACCESS  read-only
               STATUS  mandatory
               DESCRIPTION
               "Command executed (action taken)."
               ::=  {  nes5LocalActionLogEntry 5   }


--******************************************************************************
--* ServLogGroup - buffer of server error log                                *
--******************************************************************************

        nes5ServLogTableEntries OBJECT-TYPE
               SYNTAX  INTEGER
               ACCESS  read-only
               STATUS  mandatory
               DESCRIPTION
               "The number of entries in the table."
               ::=  {  nes5ServLogGroup 1   }

        nes5ServLogStartDateTime OBJECT-TYPE
               SYNTAX  DisplayString
               ACCESS  read-write
               STATUS  mandatory
               DESCRIPTION
               "Refresh the table starting at the specified date and time."
               ::=  {  nes5ServLogGroup 2   }

        nes5ServLogReadLog OBJECT-TYPE
               SYNTAX  INTEGER
               ACCESS  read-write
               STATUS  mandatory
               DESCRIPTION
               "Refresh the table starting with the most recent entry."
               ::=  {  nes5ServLogGroup 3   }

        nes5ServLogScrollDown OBJECT-TYPE
               SYNTAX  INTEGER
               ACCESS  read-write
               STATUS  mandatory
               DESCRIPTION
               "Read the next older set of log entries into the table."
               ::=  {  nes5ServLogGroup 4   }

        nes5ServLogScrollUp OBJECT-TYPE
               SYNTAX  INTEGER
               ACCESS  read-write
               STATUS  mandatory
               DESCRIPTION
               "Read the next newer set of log entries into the table."
               ::=  {  nes5ServLogGroup 5   }

        nes5ServLogMaxBuffSize OBJECT-TYPE
               SYNTAX  INTEGER
               ACCESS  read-write
               STATUS  mandatory
               DESCRIPTION
               "Max lines in the wsServLogTable (default 50)."
               ::=  {  nes5ServLogGroup 6   }

        nes5ServLogTable OBJECT-TYPE
               SYNTAX  SEQUENCE OF Nes5ServLogEntry
               ACCESS  not-accessible
               STATUS  mandatory
               DESCRIPTION
               "This table contains the contents of the server log."
               ::=  {  nes5ServLogGroup 7}

        nes5ServLogEntry OBJECT-TYPE
                                SYNTAX  Nes5ServLogEntry
                                ACCESS  not-accessible
                                STATUS  mandatory
                                DESCRIPTION
                                "This is an entry in the ServLogTable"
                                INDEX { nes5ServLogSequencer }
                                ::=  { nes5ServLogTable 1 }

        Nes5ServLogEntry ::= SEQUENCE
        {
           nes5ServLogSequencer           INTEGER,
           nes5ServLogDateTime            DisplayString,
           nes5ServLogMsgType             DisplayString,
           nes5ServLogMsgText             DisplayString
        }

        nes5ServLogSequencer OBJECT-TYPE
               SYNTAX  INTEGER
               ACCESS  read-only
               STATUS  mandatory
               DESCRIPTION
               "Table sequencer"
               ::=  {  nes5ServLogEntry 1   }

        nes5ServLogDateTime OBJECT-TYPE
               SYNTAX  DisplayString
               ACCESS  read-only
               STATUS  mandatory
               DESCRIPTION
               "Log entry data and time"
               ::=  {  nes5ServLogEntry 2   }

        nes5ServLogMsgType OBJECT-TYPE
               SYNTAX  DisplayString
               ACCESS  read-only
               STATUS  mandatory
               DESCRIPTION
               "Log message type"
               ::=  {  nes5ServLogEntry 3   }

        nes5ServLogMsgText OBJECT-TYPE
               SYNTAX  DisplayString
               ACCESS  read-only
               STATUS  mandatory
               DESCRIPTION
               "Log message text."
               ::=  {  nes5ServLogEntry 4   }

--******************************************************************************
--* WCGroup - WebCrawler Group                                               *
--******************************************************************************

        nes5WCSummaryStatus OBJECT-TYPE
                SYNTAX  INTEGER
                {
                    normal(1),
                    warning(2),
                    critical(3)
                }
                ACCESS  read-only
                STATUS  mandatory
                DESCRIPTION
                "Summary status for WebCrawler group."
                ::=  {  nes5WCGroup 1  }

        nes5WCTableEntries OBJECT-TYPE
               SYNTAX  INTEGER
               ACCESS  read-only
               STATUS  mandatory
               DESCRIPTION
               "The number of entries in the table."
               ::=  {  nes5WCGroup 2   }

        nes5WCMaxTableEntries OBJECT-TYPE
               SYNTAX  INTEGER
               ACCESS  read-write
               STATUS  mandatory
               DESCRIPTION
               "The maximum number of table entries allowed."
               ::=  {  nes5WCGroup 3   }

        nes5WCClearTrigger OBJECT-TYPE
               SYNTAX  INTEGER {
                                Execute(1)
                               }
               ACCESS  read-write
               STATUS  mandatory
               DESCRIPTION
               "Clear the data and trigger the WebCrawler."
               ::=  {  nes5WCGroup 4   }

        nes5WCTaskStatus OBJECT-TYPE
               SYNTAX  INTEGER {
                                inactive(1),
                                executing(2),
                                internalerror(3)
                               }
               ACCESS  read-only
               STATUS  mandatory
               DESCRIPTION
               "Current status of the Web crawler process."
               ::=  {  nes5WCGroup 5   }

        nes5WCLastRanTS OBJECT-TYPE
               SYNTAX  DisplayString
               ACCESS  read-only
               STATUS  mandatory
               DESCRIPTION
               "Time WebCrawler was last run."
               ::=  {  nes5WCGroup 6   }

        nes5WCInterval OBJECT-TYPE
               SYNTAX  INTEGER
               ACCESS  read-write
               STATUS  mandatory
               DESCRIPTION
               "Interval between executions of the Web Crawler process."
               ::=  {  nes5WCGroup 7  }

        nes5WCIntervalType OBJECT-TYPE
               SYNTAX  INTEGER {
                                hours(1),
                                days(2),
                                weeks(3)
                               }
               ACCESS  read-write
               STATUS  mandatory
               DESCRIPTION
               "Type of interval to be used in WCInterval."
               ::=  {  nes5WCGroup 8   }

        nes5WCStartTS OBJECT-TYPE
               SYNTAX  DisplayString
               ACCESS  read-write
               STATUS  mandatory
               DESCRIPTION
               "Time to start WebCrawler."
               ::=  {  nes5WCGroup 9   }

        nes5WCNewPageDays OBJECT-TYPE
               SYNTAX  INTEGER
               ACCESS  read-write
               STATUS  mandatory
               DESCRIPTION
               "Days previous to current that will be used by WebCrawler to determine new pages."
               ::=  {  nes5WCGroup 10   }

        nes5WCSlowSize OBJECT-TYPE
               SYNTAX  INTEGER
               ACCESS  read-write
               STATUS  mandatory
               DESCRIPTION
               "Size in bytes that will be used by WebCrawler to determine slow pages."
               ::=  {  nes5WCGroup 11  }

        nes5WCStartURL OBJECT-TYPE
               SYNTAX  DisplayString
               ACCESS  read-write
               STATUS  mandatory
               DESCRIPTION
               "First URL to start parsing with WebCrawler."
               ::=  {  nes5WCGroup 12   }

        nes5WCExecTime OBJECT-TYPE
               SYNTAX  DisplayString
               ACCESS  read-only
               STATUS  mandatory
               DESCRIPTION
               "WebCrawler elapsed execution time(mm:ss)."
               ::=  {  nes5WCGroup 13  }

        nes5WCReport OBJECT-TYPE
               SYNTAX  DisplayString
               ACCESS  read-write
               STATUS  mandatory
               DESCRIPTION
               "Web Crawler process report file path and name."
               ::=  {  nes5WCGroup 14   }

        nes5WCCheckExternal OBJECT-TYPE
               SYNTAX  INTEGER{
                               yes(1),
                               no(2)
                              }
               ACCESS  read-write
               STATUS  mandatory
               DESCRIPTION
               "Check external links in pages."
               ::=  {  nes5WCGroup 15  }

        nes5WCInvalidPages OBJECT-TYPE
               SYNTAX  INTEGER
               ACCESS  read-only
               STATUS  mandatory
               DESCRIPTION
               "Count of invalid pages based verify attributes."
               ::=  {  nes5WCGroup 16  }

        nes5WCIntWarningThreshold OBJECT-TYPE
               SYNTAX  INTEGER
               ACCESS  read-write
               STATUS  mandatory
               DESCRIPTION
               "WCIntStatus is Warning when WCInvalidPages exceeds this value."
               ::=  {  nes5WCGroup 17  }

        nes5WCIntCriticalThreshold OBJECT-TYPE
               SYNTAX  INTEGER
               ACCESS  read-write
               STATUS  mandatory
               DESCRIPTION
               "WCIntStatus is Critical when WCInvalidPages exceeds this value."
               ::=  {  nes5WCGroup 18  }

        nes5WCWarningAction OBJECT-TYPE
               SYNTAX  DisplayString
               ACCESS  read-write
               STATUS  mandatory
               DESCRIPTION
               "Command to be executed when WCSummaryStatus increases to Warning."
               ::=  {  nes5WCGroup 19  }

        nes5WCCriticalAction OBJECT-TYPE
               SYNTAX  DisplayString
               ACCESS  read-write
               STATUS  mandatory
               DESCRIPTION
               "Command to be executed when WCSummaryStatus increases to Critical."
               ::=  {  nes5WCGroup 20   }

        nes5WCVerifyIntLink OBJECT-TYPE
               SYNTAX  INTEGER{
                               yes(1),
                               no(2)
                              }
               ACCESS  read-write
               STATUS  mandatory
               DESCRIPTION
               "Verify internal links for page status."
               ::=  {  nes5WCGroup 21   }

        nes5WCVerifyExtLink OBJECT-TYPE
               SYNTAX  INTEGER{
                               yes(1),
                               no(2)
                              }
               ACCESS  read-write
               STATUS  mandatory
               DESCRIPTION
               "Verify external links for page status."
               ::=  {  nes5WCGroup 22   }

        nes5WCVerifyTitle OBJECT-TYPE
               SYNTAX  INTEGER{
                               yes(1),
                               no(2)
                              }
               ACCESS  read-write
               STATUS  mandatory
               DESCRIPTION
               "Verify title for page status."
               ::=  {  nes5WCGroup 23   }

        nes5WCVerifyAnchors OBJECT-TYPE
               SYNTAX  INTEGER{
                               yes(1),
                               no(2)
                              }
               ACCESS  read-write
               STATUS  mandatory
               DESCRIPTION
               "Verify anchors for page status."
               ::=  {  nes5WCGroup 24   }

        nes5WCVerifyImages OBJECT-TYPE
               SYNTAX  INTEGER{
                               yes(1),
                               no(2)
                              }
               ACCESS  read-write
               STATUS  mandatory
               DESCRIPTION
               "Verify images for page status."
               ::=  {  nes5WCGroup 25   }

        nes5WCPageCount OBJECT-TYPE
               SYNTAX  INTEGER
               ACCESS  read-only
               STATUS  mandatory
               DESCRIPTION
               "Count of pages."
               ::=  {  nes5WCGroup 26  }

        nes5WCNewPageCount OBJECT-TYPE
               SYNTAX  INTEGER
               ACCESS  read-only
               STATUS  mandatory
               DESCRIPTION
               "Count of new pages."
               ::=  {  nes5WCGroup 27  }

        nes5WCSlowPageCount OBJECT-TYPE
               SYNTAX  INTEGER
               ACCESS  read-only
               STATUS  mandatory
               DESCRIPTION
               "Count of slow pages."
               ::=  {  nes5WCGroup 28  }

        nes5WCImageCount OBJECT-TYPE
               SYNTAX  INTEGER
               ACCESS  read-only
               STATUS  mandatory
               DESCRIPTION
               "Count of images."
               ::=  {  nes5WCGroup 29  }

        nes5WCImageRefCount OBJECT-TYPE
               SYNTAX  INTEGER
               ACCESS  read-only
               STATUS  mandatory
               DESCRIPTION
               "Count of image references."
               ::=  {  nes5WCGroup 30  }

        nes5WCMissingImageCount OBJECT-TYPE
               SYNTAX  INTEGER
               ACCESS  read-only
               STATUS  mandatory
               DESCRIPTION
               "Count of missing images."
               ::=  {  nes5WCGroup 31  }

        nes5WCMissingImageRefCount OBJECT-TYPE
               SYNTAX  INTEGER
               ACCESS  read-only
               STATUS  mandatory
               DESCRIPTION
               "Count of missing image references."
               ::=  {  nes5WCGroup 32  }

        nes5WCNamedAnchorCount OBJECT-TYPE
               SYNTAX  INTEGER
               ACCESS  read-only
               STATUS  mandatory
               DESCRIPTION
               "Count of named anchors."
               ::=  {  nes5WCGroup 33  }

        nes5WCNamedAnchorRefCount OBJECT-TYPE
               SYNTAX  INTEGER
               ACCESS  read-only
               STATUS  mandatory
               DESCRIPTION
               "Count of named anchor references."
               ::=  {  nes5WCGroup 34  }

        nes5WCMissingNamedAnchorCount OBJECT-TYPE
               SYNTAX  INTEGER
               ACCESS  read-only
               STATUS  mandatory
               DESCRIPTION
               "Count of missing named anchors."
               ::=  {  nes5WCGroup 35  }

        nes5WCMissingNamedAnchorRefCount OBJECT-TYPE
               SYNTAX  INTEGER
               ACCESS  read-only
               STATUS  mandatory
               DESCRIPTION
               "Count of missing named anchor references."
               ::=  {  nes5WCGroup 36  }

        nes5WCHTTPCount OBJECT-TYPE
               SYNTAX  INTEGER
               ACCESS  read-only
               STATUS  mandatory
               DESCRIPTION
               "Count of HTTP URLs."
               ::=  {  nes5WCGroup 37  }

        nes5WCFTPCount OBJECT-TYPE
               SYNTAX  INTEGER
               ACCESS  read-only
               STATUS  mandatory
               DESCRIPTION
               "Count of FTP URLs."
               ::=  {  nes5WCGroup 38  }

        nes5WCMAILCount OBJECT-TYPE
               SYNTAX  INTEGER
               ACCESS  read-only
               STATUS  mandatory
               DESCRIPTION
               "Count of MAIL URLs."
               ::=  {  nes5WCGroup 39  }

        nes5WCNEWSCount OBJECT-TYPE
               SYNTAX  INTEGER
               ACCESS  read-only
               STATUS  mandatory
               DESCRIPTION
               "Count of NEWS URLs."
               ::=  {  nes5WCGroup 40  }

        nes5WCGOPHERCount OBJECT-TYPE
               SYNTAX  INTEGER
               ACCESS  read-only
               STATUS  mandatory
               DESCRIPTION
               "Count of GOPHER URLs."
               ::=  {  nes5WCGroup 41  }

        nes5WCFILECount OBJECT-TYPE
               SYNTAX  INTEGER
               ACCESS  read-only
               STATUS  mandatory
               DESCRIPTION
               "Count of FILE URLs."
               ::=  {  nes5WCGroup 42  }

        nes5WCThrottle OBJECT-TYPE
               SYNTAX  INTEGER{
                               fast(1),
                               background(2)
                              }
               ACCESS  read-write
               STATUS  mandatory
               DESCRIPTION
               "Control CPU usage."
               ::=  {  nes5WCGroup 43   }

        nes5WCProxy OBJECT-TYPE
               SYNTAX  DisplayString
               ACCESS  read-write
               STATUS  mandatory
               DESCRIPTION
               "Proxy server to use when checking external URLs"
               ::=  {  nes5WCGroup 44  }

        nes5WCReportType OBJECT-TYPE
               SYNTAX  INTEGER{
                               local(1),
                               remote(2)
                              }
               ACCESS  read-write
               STATUS  mandatory
               DESCRIPTION
               "Specify if report is local file or remote browse URL."
               ::=  {  nes5WCGroup 45   }

        nes5WCTimeoutExternal OBJECT-TYPE
               SYNTAX  INTEGER
               ACCESS  read-write
               STATUS  mandatory
               DESCRIPTION
               "Specify time to wait when checking an external URL"
               ::=  {  nes5WCGroup 46   }

        nes5WCOldPageDays OBJECT-TYPE
               SYNTAX  INTEGER
               ACCESS  read-write
               STATUS  mandatory
               DESCRIPTION
               "Days previous to current that will be used by WebCrawler to determine old pages."
               ::=  {  nes5WCGroup 47   }

        nes5WCOldPageCount OBJECT-TYPE
               SYNTAX  INTEGER
               ACCESS  read-only
               STATUS  mandatory
               DESCRIPTION
               "Count of old pages."
               ::=  {  nes5WCGroup 48  }

        nes5WCTable OBJECT-TYPE
               SYNTAX  SEQUENCE OF Nes5WCEntry
               ACCESS  not-accessible
               STATUS  mandatory
               DESCRIPTION
               "This table contains missing URL links found by WebCrawler."
               ::=  {  nes5WCGroup 49  }

        nes5WCReset OBJECT-TYPE
               SYNTAX  INTEGER{
                               reset(1)
                              }
               ACCESS  read-write
               STATUS  mandatory
               DESCRIPTION
               "Count of old pages."
               ::=  { nes5WCGroup 50  }

        nes5WCEntry OBJECT-TYPE
               SYNTAX  Nes5WCEntry
               ACCESS  not-accessible
               STATUS  mandatory
               DESCRIPTION
               "This is an entry in the WCTable"
               INDEX { nes5WCURL }
               ::=  { nes5WCTable 1 }

        Nes5WCEntry ::= SEQUENCE
        {
           nes5WCURL                      DisplayString,
           nes5WCReferences               INTEGER,
           nes5WCBadIntLink               INTEGER,
           nes5WCBadExtLink               INTEGER,
           nes5WCTitle                    INTEGER,
           nes5WCBadAnchors               INTEGER,
           nes5WCBadImages                INTEGER,
           nes5WCAccessTS                 DisplayString
        }

        nes5WCURL OBJECT-TYPE
               SYNTAX  DisplayString
               ACCESS  read-only
               STATUS  mandatory
               DESCRIPTION
               "Bad URL."
               ::=  {  nes5WCEntry 1   }

        nes5WCReferences OBJECT-TYPE
               SYNTAX  INTEGER
               ACCESS  read-only
               STATUS  mandatory
               DESCRIPTION
               "Count of references to this bad URL."
               ::=  {  nes5WCEntry 2   }

        nes5WCBadIntLink OBJECT-TYPE
               SYNTAX  INTEGER
               ACCESS  read-only
               STATUS  mandatory
               DESCRIPTION
               "Count of bad internal Links."
               ::=  {  nes5WCEntry 3   }

        nes5WCBadExtLink OBJECT-TYPE
               SYNTAX  INTEGER
               ACCESS  read-only
               STATUS  mandatory
               DESCRIPTION
               "Count of bad external Links."
               ::=  {  nes5WCEntry 4   }

        nes5WCTitle OBJECT-TYPE
               SYNTAX  INTEGER{
                               ok(1),
                               missing(2)
                              }
               ACCESS  read-only
               STATUS  mandatory
               DESCRIPTION
               "Does page have title."
               ::=  {  nes5WCEntry 5   }

        nes5WCBadAnchors OBJECT-TYPE
               SYNTAX  INTEGER
               ACCESS  read-only
               STATUS  mandatory
               DESCRIPTION
               "Count of bad anchors on page."
               ::=  {  nes5WCEntry 6   }

        nes5WCBadImages OBJECT-TYPE
               SYNTAX  INTEGER
               ACCESS  read-only
               STATUS  mandatory
               DESCRIPTION
               "Count of bad images on page."
               ::=  {  nes5WCEntry 7   }

        nes5WCAccessTS OBJECT-TYPE
               SYNTAX  DisplayString
               ACCESS  read-only
               STATUS  mandatory
               DESCRIPTION
               "Time first access occurred (time row added to table)."
               ::=  {  nes5WCEntry 8   }


--******************************************************************************
--* ExpressionGroup - User defined expressions                               *
--******************************************************************************

        nes5ExpressionTableEntries OBJECT-TYPE
               SYNTAX  INTEGER
               ACCESS  read-only
               STATUS  mandatory
               DESCRIPTION
               "The number of entries in the table."
               ::=  {  nes5ExpressionGroup 1   }

        nes5ExpressionInterval OBJECT-TYPE
               SYNTAX  INTEGER
               ACCESS  read-write
               STATUS  mandatory
               DESCRIPTION
               "Seconds between polls for the counter."
               ::=  {  nes5ExpressionGroup 2   }

        nes5ExpressionCalcInterval OBJECT-TYPE
               SYNTAX  INTEGER
               ACCESS  read-write
               STATUS  mandatory
               DESCRIPTION
               "Interval in seconds over which the counter is measured."
               ::=  {  nes5ExpressionGroup 3   }

--      Update this comment.
--      Add a counter to the table.  The value must include at least the first four of
--      the 6 items listed, separated by commas.
--      <nes5URLAvailCounterDescription> is a value from nes5URLAvailCounterDescription in nes5URLAvailCounterTable.

        nes5ExpressionAdd OBJECT-TYPE
               SYNTAX  DisplayString
               ACCESS  write-only
               STATUS  mandatory
               DESCRIPTION
               "Add this entry to the table."
               ::=  {  nes5ExpressionGroup 4   }

--      Delete a counter from the table.  The value must include the 2 items listed.
        nes5ExpressionDelete OBJECT-TYPE
               SYNTAX  DisplayString
               ACCESS  write-only
               STATUS  mandatory
               DESCRIPTION
               "Delete entry from the table: <ExpressionDesc>,<Expression>."
               ::=  {  nes5ExpressionGroup 5   }

--      For future use with bulk load.  Currently ignored.
        nes5ExpressionUpdate OBJECT-TYPE
               SYNTAX  DisplayString
               ACCESS  write-only
               STATUS  mandatory
               DESCRIPTION
               "Reserved for future use."
               ::=  {  nes5ExpressionGroup 6   }

        nes5ExpressionSummaryStatus OBJECT-TYPE
               SYNTAX  INTEGER {
                                normal(1),
                                warning(2),
                                critical(3)
                               }
               ACCESS  read-only
               STATUS  mandatory
               DESCRIPTION
               "Most severe status of all rows in the table."
               ::=  {  nes5ExpressionGroup 7   }

        nes5ExpressionTable OBJECT-TYPE
               SYNTAX  SEQUENCE OF Nes5ExpressionEntry
               ACCESS  not-accessible
               STATUS  mandatory
               DESCRIPTION
               "This table contains a list of expressions to monitor."
               ::=  {  nes5ExpressionGroup 8}

        nes5ExpressionEntry OBJECT-TYPE
               SYNTAX  Nes5ExpressionEntry
               ACCESS  not-accessible
               STATUS  mandatory
               DESCRIPTION
               "This is an entry in the ExpressionTable"
               INDEX { nes5ExpressionIdentifier}
               ::=  { nes5ExpressionTable 1 }

        Nes5ExpressionEntry ::= SEQUENCE
        {
           nes5Expression                                    DisplayString,
           nes5ExpressionDesc                                DisplayString,
           nes5ExpressionValue                               DisplayString,
           nes5ExpressionWarningThreshold                    INTEGER,
           nes5ExpressionCriticalThreshold                   INTEGER,
           nes5ExpressionWarningAction                       DisplayString,
           nes5ExpressionCriticalAction                      DisplayString,
           nes5ExpressionStatus                              INTEGER,
           nes5ExpressionEnableDisable                       INTEGER,
           nes5ExpressionDescending                          INTEGER,
           nes5ExpressionResultType                          INTEGER,
           nes5ExpressionBooleanAlertLevel                   INTEGER,
           nes5ExpressionEvalErrorAlertLevel                 INTEGER,
           nes5ExpressionNumericMonitor                      INTEGER,
           nes5ExpressionEntryInterval                       INTEGER,
           nes5ExpressionReset                               INTEGER,
           nes5ExpressionResetTime                           DisplayString,
           nes5ExpressionEntryWarningCount                   INTEGER,
           nes5ExpressionEntryCriticalCount                  INTEGER,
           nes5ExpressionIdentifier                          DisplayString,
           nes5ExpressionErrorMsg                            DisplayString,
           nes5ExpressionEvalStatus                          INTEGER,
           nes5ExpressionBoolAlertCondition                  INTEGER,
	   nes5ExpressionLagSetting	                   INTEGER,
	   nes5ExpressionLagValue	                           INTEGER
        }

--     Changed from read only to read write to allow introducing evaluation errors
        nes5Expression OBJECT-TYPE
               SYNTAX  DisplayString
               ACCESS  read-write
               STATUS  mandatory
               DESCRIPTION
               "Expression to be monitored."
               ::=  {  nes5ExpressionEntry 1   }

        nes5ExpressionDesc OBJECT-TYPE
               SYNTAX  DisplayString
               ACCESS  read-write
               STATUS  mandatory
               DESCRIPTION
               "Description of the monitored expression."
               ::=  {  nes5ExpressionEntry 2   }

        nes5ExpressionValue OBJECT-TYPE
               SYNTAX  DisplayString
               ACCESS  read-only
               STATUS  mandatory
               DESCRIPTION
               "Expression evaluation."
               ::=  {  nes5ExpressionEntry 3   }

        nes5ExpressionWarningThreshold OBJECT-TYPE
               SYNTAX  INTEGER
               ACCESS  read-write
               STATUS  mandatory
               DESCRIPTION
               "Warning threshold"
               ::=  {  nes5ExpressionEntry 4   }

        nes5ExpressionCriticalThreshold OBJECT-TYPE
               SYNTAX  INTEGER
               ACCESS  read-write
               STATUS  mandatory
               DESCRIPTION
               "Critical threshold"
               ::=  {  nes5ExpressionEntry 5   }

        nes5ExpressionWarningAction OBJECT-TYPE
               SYNTAX  DisplayString
               ACCESS  read-write
               STATUS  mandatory
               DESCRIPTION
               "Command to be executed when warning threshold is exceeded."
               ::=  {  nes5ExpressionEntry 6   }

        nes5ExpressionCriticalAction OBJECT-TYPE
               SYNTAX  DisplayString
               ACCESS  read-write
               STATUS  mandatory
               DESCRIPTION
               "Command to be executed when critical threshold is exceeded."
               ::=  {  nes5ExpressionEntry 7  }

        nes5ExpressionStatus OBJECT-TYPE
               SYNTAX  INTEGER {
                                normal(1),
                                warning(2),
                                critical(3)
                               }
               ACCESS  read-only
               STATUS  mandatory
               DESCRIPTION
               "Status of this expression."
               ::=  {  nes5ExpressionEntry 8 }

        nes5ExpressionEnableDisable OBJECT-TYPE
                SYNTAX  INTEGER
                {
                    enable(1),
                    disable(2)
                }
                ACCESS  read-write
                STATUS  mandatory
                DESCRIPTION
                "Enable or disable alerts for this expression."
                ::=  {  nes5ExpressionEntry 9   }

        nes5ExpressionDescending OBJECT-TYPE
               SYNTAX  INTEGER {
                                no(1),
                                yes(2)
                               }
               ACCESS  read-only
               STATUS  mandatory
               DESCRIPTION
               "Yes if lower value triggers thresholds."
               ::=  {  nes5ExpressionEntry 10 }


        nes5ExpressionResultType OBJECT-TYPE
               SYNTAX  INTEGER {
                                numeric(1),
                                boolean(2)
                               }
               ACCESS  read-only
               STATUS  mandatory
               DESCRIPTION
               "Result type of expression."
               ::=  {  nes5ExpressionEntry 11 }

        nes5ExpressionBooleanAlertLevel OBJECT-TYPE
                SYNTAX INTEGER {
                                warning-on-false(1),
                                critical-on-false(2)
                               }
                ACCESS read-write
                STATUS mandatory
                DESCRIPTION
                "Flag indicating for boolean expressions the level of alert to raise on false."
                DEFVAL { 2 }
                ::= { nes5ExpressionEntry 12 }

        nes5ExpressionEvalErrorAlertLevel OBJECT-TYPE
                SYNTAX INTEGER {
                                do-not-monitor(1),
                                warning-on-error(2),
                                critical-on-error(3)
                               }
                ACCESS read-write
                STATUS mandatory
                DESCRIPTION
                "Flag indicating the level of alert to raise on an evaluation error."
                DEFVAL { 3 }
                ::= { nes5ExpressionEntry 13 }

        nes5ExpressionNumericMonitor OBJECT-TYPE
                SYNTAX INTEGER {
                                warning-only(1),
                                critical-only(2),
                                both(3)
                               }
                ACCESS read-write
                STATUS mandatory
                DESCRIPTION
                "Flag indicating for numeric expressions which thresholds should be evaluated."
                DEFVAL { 3 }
                ::= { nes5ExpressionEntry 14 }

        nes5ExpressionEntryInterval OBJECT-TYPE
               SYNTAX  INTEGER
               ACCESS  read-write
               STATUS  mandatory
               DESCRIPTION
               "Evaluation interval for expression"
               ::=  {  nes5ExpressionEntry 15   }

        nes5ExpressionReset OBJECT-TYPE
               SYNTAX  INTEGER {
                                reset(1)
                               }
               ACCESS  write-only
               STATUS  mandatory
               DESCRIPTION
               "Reset value for this counter."
               ::=  {  nes5ExpressionEntry 16 }

        nes5ExpressionResetTime OBJECT-TYPE
               SYNTAX  DisplayString
               ACCESS  read-only
               STATUS  mandatory
               DESCRIPTION
               "Time stamp of when this counter was reset."
               ::=  {  nes5ExpressionEntry 17  }

        nes5ExpressionEntryWarningCount OBJECT-TYPE
                SYNTAX  INTEGER
                ACCESS  read-only
                STATUS  mandatory
                DESCRIPTION
                "Number of warning events since last reset."
                ::=  {  nes5ExpressionEntry 18   }

        nes5ExpressionEntryCriticalCount OBJECT-TYPE
                SYNTAX  INTEGER
                ACCESS  read-only
                STATUS  mandatory
                DESCRIPTION
                "Number of critical events since last reset."
                ::=  {  nes5ExpressionEntry 19   }

        nes5ExpressionIdentifier OBJECT-TYPE
               SYNTAX  DisplayString
               ACCESS  read-write
               STATUS  mandatory
               DESCRIPTION
               "Short identifier of the monitored expression."
               ::=  {  nes5ExpressionEntry 20   }

        nes5ExpressionErrorMsg OBJECT-TYPE
               SYNTAX  DisplayString
               ACCESS  read-write
               STATUS  mandatory
               DESCRIPTION
               "Validation or evaluation error message."
               ::=  {  nes5ExpressionEntry 21   }

        nes5ExpressionEvalStatus OBJECT-TYPE
               SYNTAX  INTEGER {
                                normal(1),
                                error(2)
                               }
               ACCESS  read-only
               STATUS  mandatory
               DESCRIPTION
               "Was this expression able to be evaluated."
               ::=  {  nes5ExpressionEntry 22 }

        nes5ExpressionBoolAlertCondition OBJECT-TYPE
               SYNTAX  INTEGER {
                                alertonfalse(1),
                                alertontrue(2)
                               }
               ACCESS  read-write
               STATUS  mandatory
               DESCRIPTION
               "Alert on true or alert on false."
               ::=  {  nes5ExpressionEntry 23 }
		
        nes5ExpressionLagSetting OBJECT-TYPE
                SYNTAX  INTEGER
                ACCESS  read-write
                STATUS  mandatory
                DESCRIPTION
                "Lag setting for the expression."
                ::=  {  nes5ExpressionEntry 24   }
		
        nes5ExpressionLagValue OBJECT-TYPE
                SYNTAX  INTEGER
                ACCESS  read-only
                STATUS  mandatory
                DESCRIPTION
                "Current Lag value for the expression."
                ::=  {  nes5ExpressionEntry 25   }

--******************************************************************************
--*  End of expressions table                                                  *
--******************************************************************************

        nes5ExpressionWarningCount OBJECT-TYPE
                SYNTAX  INTEGER
                ACCESS  read-only
                STATUS  mandatory
                DESCRIPTION
                "Number of expressions in warning state."
                DEFVAL { 0 }
                ::=  {  nes5ExpressionGroup 9   }

        nes5ExpressionCriticalCount OBJECT-TYPE
                SYNTAX  INTEGER
                ACCESS  read-only
                STATUS  mandatory
                DESCRIPTION
                "Number of expressions in critical state."
                DEFVAL { 0 }
                ::=  {  nes5ExpressionGroup 10   }

       nes5ExpressionValidate OBJECT-TYPE
               SYNTAX  DisplayString
               ACCESS  write-only
               STATUS  mandatory
               DESCRIPTION
               "Validate this entry."
               ::=  {  nes5ExpressionGroup 11   }

        nes5ExpressionEvaluate OBJECT-TYPE
               SYNTAX  DisplayString
               ACCESS  write-only
               STATUS  mandatory
               DESCRIPTION
               "Evaluate this expression."
               ::=  {  nes5ExpressionGroup 12   }

        nes5ExpressionTemp OBJECT-TYPE
               SYNTAX  DisplayString
               ACCESS  read-write
               STATUS  mandatory
               DESCRIPTION
               "Temporary storage for expression building."
               ::=  {  nes5ExpressionGroup 13   }

        nes5ExpressionVariableTable OBJECT-TYPE
               SYNTAX  SEQUENCE OF Nes5ExpressionVariableEntry
               ACCESS  not-accessible
               STATUS  mandatory
               DESCRIPTION
               "This table contains a list of expressions to monitor."
               ::=  {  nes5ExpressionGroup 14}

        nes5ExpressionVariableEntry OBJECT-TYPE
               SYNTAX  Nes5ExpressionVariableEntry
               ACCESS  not-accessible
               STATUS  mandatory
               DESCRIPTION
               "This is an entry in the ExpressionVariableTable"
               INDEX { nes5ExpressionVariableDisplayName}
               ::=  { nes5ExpressionVariableTable 1 }

        Nes5ExpressionVariableEntry ::= SEQUENCE
        {
           nes5ExpressionVariableDisplayName        DisplayString,
           nes5ExpressionVariableAccessName         DisplayString,
           nes5ExpressionVariableGroup              DisplayString
        }

       nes5ExpressionVariableDisplayName OBJECT-TYPE
               SYNTAX  DisplayString
               ACCESS  read-only
               STATUS  mandatory
               DESCRIPTION
               "Expression variable displayed in list."
               ::=  {  nes5ExpressionVariableEntry 1   }

       nes5ExpressionVariableAccessName OBJECT-TYPE
               SYNTAX  DisplayString
               ACCESS  read-only
               STATUS  mandatory
               DESCRIPTION
               "Expression variable used to access MIB entry."
               ::=  {  nes5ExpressionVariableEntry 2   }

        nes5ExpressionVariableGroup OBJECT-TYPE
               SYNTAX  DisplayString
               ACCESS  read-only
               STATUS  mandatory
               DESCRIPTION
               "MIB group where the variable is stored."
               ::=  {  nes5ExpressionVariableEntry 3   }

--******************************************************************************
--*  End of expression variables table                                         *
--******************************************************************************

       nes5ExpressionVariableTableEntries OBJECT-TYPE
               SYNTAX  INTEGER
               ACCESS  read-only
               STATUS  mandatory
               DESCRIPTION
               "The number of entries in the variables table."
               ::=  {  nes5ExpressionGroup 15   }

       nes5ExpressionBuild OBJECT-TYPE
               SYNTAX  DisplayString
               ACCESS  write-only
               STATUS  mandatory
               DESCRIPTION
               "Add this variable to the expression."
               ::=  {  nes5ExpressionGroup 16   }

        nes5ExpressionTempValue OBJECT-TYPE
               SYNTAX  DisplayString
               ACCESS  read-write
               STATUS  mandatory
               DESCRIPTION
               "Temporary storage for result of expression validation or evaluation."
               ::=  {  nes5ExpressionGroup 17   }


        nes5ExpressionClear OBJECT-TYPE
               SYNTAX  INTEGER {
                                donotclear(1),
                                clear(2)
                               }
               ACCESS  read-only
               STATUS  mandatory
               DESCRIPTION
               "Clear the variables in the gui"
               ::=  {  nes5ExpressionGroup 18 }

--******************************************************************************
--*  Start of global expression variables table                                *
--******************************************************************************

        nes5ExpressionGlobalVariableTableEntries OBJECT-TYPE
               SYNTAX  INTEGER
               ACCESS  read-only
               STATUS  mandatory
               DESCRIPTION
               "The number of entries in the global variables table."
               ::=  {  nes5ExpressionGroup 19   }

        nes5ExpressionGlobalVariableTableAdd OBJECT-TYPE
               SYNTAX  DisplayString
               ACCESS  write-only
               STATUS  mandatory
               DESCRIPTION
               "Add this entry to the global variables table."
               ::=  {  nes5ExpressionGroup 20   }

--      Delete a counter from the table.  The value must include the 2 items listed.
        nes5ExpressionGlobalVariableTableDelete OBJECT-TYPE
               SYNTAX  DisplayString
               ACCESS  write-only
               STATUS  mandatory
               DESCRIPTION
               "Delete entry from the global varialbles table."
               ::=  {  nes5ExpressionGroup 21   }

        nes5ExpressionGlobalVariableTable OBJECT-TYPE
               SYNTAX  SEQUENCE OF Nes5ExpressionGlobalVariableEntry
               ACCESS  not-accessible
               STATUS  mandatory
               DESCRIPTION
               "This table contains a list of global variables used in expressions."
               ::=  {  nes5ExpressionGroup 22}

        nes5ExpressionGlobalVariableEntry OBJECT-TYPE
               SYNTAX  Nes5ExpressionGlobalVariableEntry
               ACCESS  not-accessible
               STATUS  mandatory
               DESCRIPTION
               "This is an entry in the ExpressionGlobalVariableTable"
               INDEX { nes5ExpressionGlobalVariableName}
               ::=  { nes5ExpressionGlobalVariableTable 1 }

        Nes5ExpressionGlobalVariableEntry ::= SEQUENCE
        {
           nes5ExpressionGlobalVariableName                DisplayString,
           nes5ExpressionGlobalVariableDisplayName         DisplayString,
           nes5ExpressionGlobalVariableDescription         DisplayString,
           nes5ExpressionGlobalVariableAccessKey           DisplayString,
           nes5ExpressionGlobalVariableType                DisplayString,
           nes5ExpressionGlobalVariablePollIntervalPeriod  INTEGER,
           nes5ExpressionGlobalVariableFunctionName        DisplayString,
           nes5ExpressionGlobalVariableFunctionTimePeriod  INTEGER
        }

        nes5ExpressionGlobalVariableName OBJECT-TYPE
               SYNTAX  DisplayString
               ACCESS  read-only
               STATUS  mandatory
               DESCRIPTION
               "Expression global variable name."
               ::=  {  nes5ExpressionGlobalVariableEntry 1   }

        nes5ExpressionGlobalVariableDisplayName OBJECT-TYPE
               SYNTAX  DisplayString
               ACCESS  read-only
               STATUS  mandatory
               DESCRIPTION
               "Expression global variable display name."
               ::=  {  nes5ExpressionGlobalVariableEntry 2   }

        nes5ExpressionGlobalVariableDescription OBJECT-TYPE
               SYNTAX  DisplayString
               ACCESS  read-only
               STATUS  mandatory
               DESCRIPTION
               "Expression global variable description."
               ::=  {  nes5ExpressionGlobalVariableEntry 3   }

        nes5ExpressionGlobalVariableAccessKey OBJECT-TYPE
               SYNTAX  DisplayString
               ACCESS  read-only
               STATUS  mandatory
               DESCRIPTION
               "Expression global variable key to access counter."
               ::=  {  nes5ExpressionGlobalVariableEntry 4   }

        nes5ExpressionGlobalVariableType OBJECT-TYPE
               SYNTAX  DisplayString
               ACCESS  read-only
               STATUS  mandatory
               DESCRIPTION
               "Expression global variable - interval or time variable."
               ::=  {  nes5ExpressionGlobalVariableEntry 5   }

        nes5ExpressionGlobalVariablePollIntervalPeriod OBJECT-TYPE
               SYNTAX  INTEGER
               ACCESS  read-only
               STATUS  mandatory
               DESCRIPTION
               "Expression global variable poll interval for interval type."
               ::=  {  nes5ExpressionGlobalVariableEntry 6   }

        nes5ExpressionGlobalVariableFunctionName OBJECT-TYPE
               SYNTAX  DisplayString
               ACCESS  read-only
               STATUS  mandatory
               DESCRIPTION
               "Expression global variable function name."
               ::=  {  nes5ExpressionGlobalVariableEntry 7   }

        nes5ExpressionGlobalVariableFunctionTimePeriod OBJECT-TYPE
               SYNTAX  INTEGER
               ACCESS  read-only
               STATUS  mandatory
               DESCRIPTION
               "Expression global variable function time period."
               ::=  {  nes5ExpressionGlobalVariableEntry 8   }

--******************************************************************************
--*  End of global expression variables table                                  *
--******************************************************************************

       nes5ExpressionGlobalVariableBuild OBJECT-TYPE
               SYNTAX  DisplayString
               ACCESS  write-only
               STATUS  mandatory
               DESCRIPTION
               "Add an access key to the variable using a friendly name."
               ::=  {  nes5ExpressionGroup 23   }

        nes5ExpressionGlobalVariableClear OBJECT-TYPE
               SYNTAX  INTEGER {
                                donotclear(1),
                                clear(2)
                               }
               ACCESS  read-only
               STATUS  mandatory
               DESCRIPTION
               "Clear the variables in the gui"
               ::=  {  nes5ExpressionGroup 24 }

        nes5ExpressionGlobalVariableTemp OBJECT-TYPE
               SYNTAX  DisplayString
               ACCESS  read-write
               STATUS  mandatory
               DESCRIPTION
               "Temporary storage for variable access key."
               ::=  {  nes5ExpressionGroup 25   }

        nes5ExpressionGlobalVariableTableModify OBJECT-TYPE
               SYNTAX  DisplayString
               ACCESS  write-only
               STATUS  mandatory
               DESCRIPTION
               "Modify entry in the global varialbles table."
               ::=  {  nes5ExpressionGroup 26   }

	nes5ExpressionGPEnaDis OBJECT-TYPE
		SYNTAX      INTEGER {enable(1), disable(2)}
		ACCESS      read-write
		STATUS      mandatory
		DESCRIPTION "Enable or disable for the Group."
		::= { nes5ExpressionGroup 27 }
                

--******************************************************************************
--*  Traps                                                                     *
--******************************************************************************

    statusNormal TRAP-TYPE
        ENTERPRISE nes5Agent
        DESCRIPTION "Set status to normal"
        ::= 1

    statusWarning TRAP-TYPE
        ENTERPRISE nes5Agent
        DESCRIPTION "Set status to warning"
        ::= 2

    statusCritical TRAP-TYPE
        ENTERPRISE nes5Agent
        DESCRIPTION "Set status to critical"
        ::= 3

    statusDetailTrap TRAP-TYPE
        ENTERPRISE nes5Agent
--        VARIABLES   {szStatus}
        DESCRIPTION "Status of group or table (row) changed"
        ::= 4
END
