--MibName=hpxAgent
--
--                  Proprietary and Confidential Information
--
--   This material contains, and is part of a computer software program
--   which is, proprietary and confidential information owned by COMPUTER
--   ASSOCIATES INTERNATIONAL, INC.  The program, including this material,
--   may not be duplicated, disclosed or reproduced in whole or in part for
--   any purpose without the express written authorization of COMPUTER
--   ASSOCIATES. All authorized reproductions must be marked with this
--   legend.
--
--                          Copyright (c) 1998-2000
--               Computer Associates International, Incorporated
--                        Software Superior by Design
--                            All rights reserved
--

--
-- Name
--  hpxagent.txt
--
-- Description
--  This is the MIB for the Extended Historical Performance agent.
--
-- Modification History
--  V2.1.5                  New MIB definition created.
--  V2.1.6                  Gave it the correct OID.
--                          Enhanced the descriptions of the attributes and
--                          added new config table attribute to contain the
--                          locale that the agent is using for each host.
--  V2.2.7                  Additional scenario definitions in Scenario table
--                          enum, trap definitions corresponding to new 
--                          scenarios, and additional fields in Scenario table
--                          to handle information related to neugent 
--                          predictions.
--
-- Source Control History
--    VSS ID; @(--) $Workfile: hpxAgent.txt $ $Revision: 17 $ $Modtime: 11/12/01 4:20p $
--    $NoKeywords: $
--

HPAAGENT-MIB DEFINITIONS ::= BEGIN

    --
    --  Define the root OID.
    --

    IMPORTS
        OBJECT-TYPE, DisplayString
        FROM RFC1155-SMI;

    cai                     OBJECT IDENTIFIER ::= { enterprises 791 }
    caiSysMgt               OBJECT IDENTIFIER ::= { cai           2 }
    agentWorks              OBJECT IDENTIFIER ::= { caiSysMgt     9 }
    miscellaneousAgents     OBJECT IDENTIFIER ::= { agentWorks    5 }
    hpxAgent                OBJECT IDENTIFIER ::= { miscellaneousAgents 4 }

    --  
    --  hpxAgent Configuration Group Definition:
    --
    --  This consists of information about the agent, the platform it is 
    --  running on, the configuration format that it can accept and the 
    --  configuration that it is using.
    --

    hpxConfigGroup OBJECT IDENTIFIER ::= { hpxAgent 1 }
    hpxConfigAgentVersion OBJECT-TYPE
        SYNTAX DisplayString
        ACCESS read-only
        STATUS mandatory
        DESCRIPTION 
        "&<hpxAgent.100>The version number of the Historical Performance agent.  Note:  This number may be different from the release number of Unicenter."
        ::= { hpxConfigGroup 1 }
    hpxConfigProfileVersion OBJECT-TYPE
        SYNTAX DisplayString
        ACCESS read-only
        STATUS mandatory
        DESCRIPTION 
        "&<hpxAgent.101>The highest version of Configuration Profile format or content that the Historical Performance agent can accept.  This value is an integer."
        ::= { hpxConfigGroup 2 }
    hpxConfigColdStartTimestamp OBJECT-TYPE
        SYNTAX DisplayString
        ACCESS read-only
        STATUS mandatory
        DESCRIPTION 
        "&<hpxAgent.102>The date and time the Historical Performance agent was last started.  The timestamp reflects the system clock of the host on which the agent resides.  Note:  A cold start trap is issued when the agent starts up."
        ::= { hpxConfigGroup 3 }
    hpxConfigWarmStartTimestamp OBJECT-TYPE
        SYNTAX DisplayString
        ACCESS read-only
        STATUS mandatory
        DESCRIPTION 
        "&<hpxAgent.103>The date and time that the Historical Performance agent was last reconfigured.  The timestamp reflects the system clock of the host on which the agent resides.  Note:  A warm start trap is issued when a new configuration file is sent to the Historical Performance agent from the Unicenter Performance Configuration application."
        ::= { hpxConfigGroup 4 }

    --  
    --  hpxAgent Configuration Table Definition:
    --
    --  This table pertains to the Historical Performance agent and its
    --  configuration for the local host and any other hosts that are being
    --  proxied. Note that if no hosts have yet been configured there will only
	--  be a table row for the local host and this will have some attributes
	--  defaulted.
    --

--    hpxConfigTable OBJECT-TYPE
--        SYNTAX SEQUENCE OF HpxConfigEntry
--        ACCESS read-only
--        STATUS mandatory
--        DESCRIPTION
--        "&<hpxAgent.104>The hpxConfigTable contains general configuration information about each host the Historical Performance agent is monitoring.  This table contains one row per host, with each row containing attributes related to the configuration of the Historical Performance agent on that host.  There will always be at least one row in the table, containing configuration information for the local host the agent is monitoring."
--        ::= {  hpxConfigGroup 5 }
--    HpxConfigEntry OBJECT-TYPE
--        SYNTAX HpxConfigEntry
--        ACCESS read-only
--        STATUS mandatory
--        DESCRIPTION
--        "&<hpxAgent.105>A row in the configuration table.  The first row always exists and represents the local host the agent is monitoring."
--        ::= { hpxConfigTable 1 }
--    HpxConfigEntry ::= SEQUENCE {
--		hpxConfigHostName
--	        DisplayString,
--	    hpxConfigSystemType
--	        DisplayString,
--	    hpxConfigProfileName
--	        DisplayString,
--		hpxConfigProfileModificationTimestamp
--	        DisplayString,
--		hpxConfigProfileUser
--	        DisplayString,
--        hpxConfigLocale
--            DisplayString
--    }
--    hpxConfigHostName OBJECT-TYPE
--        SYNTAX DisplayString
--        ACCESS read-only
--        STATUS mandatory
--        DESCRIPTION
--        "&<hpxAgent.106>The name of the host to which this configuration information applies.  This attribute allows for proxy collection and management of performance data from remote machines and devices in addition to the local host."
--        ::= { HpxConfigEntry 1 }
--    hpxConfigSystemType OBJECT-TYPE
--        SYNTAX DisplayString
--        ACCESS read-only
--        STATUS mandatory
--        DESCRIPTION 
--        "&<hpxAgent.107>The performance system type for this host.  The performance system type is the system type name used by Unicenter Performance Management to indicate the hardware and operating system the Historical Performance agent is monitoring."
--        ::= { HpxConfigEntry 2 }
--    hpxConfigProfileName OBJECT-TYPE
--        SYNTAX DisplayString
--        ACCESS read-only
--        STATUS mandatory
--        DESCRIPTION 
--        "&<hpxAgent.108>The name of the configuration profile applied to the Historical Performance agent for this host.  Configuration profiles are applied in the Unicenter Performance Configuration application."
--        ::= { HpxConfigEntry 3 }
--    hpxConfigProfileModificationTimestamp OBJECT-TYPE
--        SYNTAX DisplayString
--        ACCESS read-only
--        STATUS mandatory
--        DESCRIPTION 
--        "&<hpxAgent.109>The date and time the configuration profile was last modified before it was sent to the host in the Unicenter Performance Configuration application."
--        ::= { HpxConfigEntry 4 }
--    hpxConfigProfileUser OBJECT-TYPE
--        SYNTAX DisplayString
--        ACCESS read-only
--        STATUS mandatory
--        DESCRIPTION 
--        "&<hpxAgent.110>The account name of the user who last transferred the configuration profile to the Historical Performance agent for this host."
--        ::= { HpxConfigEntry 5 }
--    hpxConfigLocale OBJECT-TYPE
--        SYNTAX DisplayString
--        ACCESS read-only
--        STATUS mandatory
--        DESCRIPTION 
--        "&<hpxAgent.111>The performance locale identifier for the locale that the agent is operating in for this host. The performance locale identifier is used by Unicenter Performance Management to correctly present locale specific text."
--        ::= { HpxConfigEntry 6 }

    --  
    --  hpxAgent Threshold Breach Table Definition:
    --
    --  This consists of the state information about performance resources to
    --  which thresholds have been applied, and all information required to
    --  raise informative messages to the Unicenter Event Console.
    --  Note that this table only contains rows for breaches, anything in the
    --  Ok state will not be retained in the table.
    --

    hpxThresholdBreachTable OBJECT-TYPE
        SYNTAX SEQUENCE OF HpxThresholdBreachEntry
        ACCESS read-only
        STATUS mandatory
        DESCRIPTION
        "&<hpxAgent.112>The hpxThresholdBreachTable contains attributes related to resources that have breached preconfigured limits established in the Unicenter Performance Configuration application.  This table contains multiple rows per thresholded host.  This may include hosts for which the local machine is performing proxy thresholding (such as printers and routers) as well as the local machine."
        ::= {  hpxAgent 2 }
    HpxThresholdBreachEntry OBJECT-TYPE
        SYNTAX HpxThresholdBreachEntry
        ACCESS read-only
        STATUS mandatory
        DESCRIPTION
        "&<hpxAgent.113>A row in the threshold breach table.  Each row represents a monitored resource that has breached a threshold configured in the Unicenter Performance Configuration application."
        INDEX {
            hpxThresholdBreachHostName,
            hpxThresholdBreachResourceTypeName,
            hpxThresholdBreachResourceSubtypeName,
            hpxThresholdBreachResourceInstanceName,
            hpxThresholdBreachOperator
        }
        ::= { hpxThresholdBreachTable 1 }
    HpxThresholdBreachEntry ::= SEQUENCE {
		hpxThresholdBreachHostName
			DisplayString,
		hpxThresholdBreachResourceTypeName
			DisplayString,
		hpxThresholdBreachResourceSubtypeName
			DisplayString,
		hpxThresholdBreachResourceInstanceName
			DisplayString,
		hpxThresholdBreachOperator
			INTEGER,
		hpxThresholdBreachValue
            DisplayString,
        hpxThresholdBreachWarning
            DisplayString,
        hpxThresholdBreachCritical
            DisplayString,
        hpxThresholdBreachState
            INTEGER,
        hpxThresholdBreachTimestamp
            DisplayString
    }
    hpxThresholdBreachHostName OBJECT-TYPE
        SYNTAX DisplayString
        ACCESS read-only
        STATUS mandatory
        DESCRIPTION
        "&<hpxAgent.114>This is the name of the host on which the threshold breach was detected.  This attribute allows for proxy thresholding for performance data from remote machines and devices in addition to the local host."
        ::= { HpxThresholdBreachEntry 1 }
    hpxThresholdBreachResourceTypeName OBJECT-TYPE
        SYNTAX DisplayString
        ACCESS read-only
        STATUS mandatory
        DESCRIPTION 
        "&<hpxAgent.115>The resource type name (for example, System) for the breached resource."
        ::= { HpxThresholdBreachEntry 2 }
    hpxThresholdBreachResourceSubtypeName OBJECT-TYPE
        SYNTAX DisplayString
        ACCESS read-only
        STATUS mandatory
        DESCRIPTION 
        "&<hpxAgent.116>The resource subtype name (for example, % Total Processor Time) for the breached resource."
        ::= { HpxThresholdBreachEntry 3 }
    hpxThresholdBreachResourceInstanceName OBJECT-TYPE
        SYNTAX DisplayString
        ACCESS read-only
        STATUS mandatory
        DESCRIPTION 
        "&<hpxAgent.117>The resource instance name (for example, the disk drive letter) for the breached resource.  This attribute may not have a value if the values of hpxThresholdBreachResourceTypeName and hpxThresholdBreachResourceSubtypeName are sufficient for the identification of the resource."
        ::= { HpxThresholdBreachEntry 4 }
    hpxThresholdBreachOperator OBJECT-TYPE
        SYNTAX INTEGER {
            absoluteLessThan(1),
            absoluteGreaterThan(2)
        }
        ACCESS read-only
        STATUS mandatory
        DESCRIPTION 
        "&<hpxAgent.118>The operator (that is, greater than > or less than <) that is used to compare hpxThresholdBreachValue to hpxThresholdBreachWarning and hpxThresholdBreachCritical to determine whether a threshold has been breached."
        ::= { HpxThresholdBreachEntry 5 }
    hpxThresholdBreachValue OBJECT-TYPE
        SYNTAX DisplayString
        ACCESS read-only
        STATUS mandatory
        DESCRIPTION 
        "&<hpxAgent.119>The floating point value of the resource when it was first detected as having breached the threshold setting."
        ::= { HpxThresholdBreachEntry 6 }
    hpxThresholdBreachWarning OBJECT-TYPE
        SYNTAX DisplayString
        ACCESS read-only
        STATUS mandatory
        DESCRIPTION 
        "&<hpxAgent.120>The floating point warning threshold setting for the resource being monitored.  Depending on the value of hpxThresholdBreachOperator, the warning threshold can be breached when hpxThresholdBreachValue is either above or below this warning threshold setting."
        ::= { HpxThresholdBreachEntry 7 }
    hpxThresholdBreachCritical OBJECT-TYPE
        SYNTAX DisplayString
        ACCESS read-only
        STATUS mandatory
        DESCRIPTION 
        "&<hpxAgent.121>The floating point critical threshold setting for the resource being monitored.  Depending on the value of hpxThresholdBreachOperator, the critical threshold can be breached when hpxThresholdBreachValue is either above or below this critical threshold setting."
        ::= { HpxThresholdBreachEntry 8 }
    hpxThresholdBreachState OBJECT-TYPE
        SYNTAX INTEGER {
            unknown(1),
            ok(2),
            warning(3),
            critical(4)
        }
        ACCESS read-only
        STATUS mandatory
        DESCRIPTION 
        "&<hpxAgent.122>The last recorded state of the resource.  The values are as follows:
1-(unknown) The Historical Performance agent has been unable to obtain resource information.
2-(ok) The resource being monitored by the Historical Performance agent has not breached the configured warning or critical thresholds.  Note: The state of 'ok' is defined but should never be seen in the table, because the table contains threshold breaches only.
3-(warning) The resource being monitored by the Historical Performance agent has breached the hpxThresholdBreachWarning condition, but not the hpxThresholdBreachCritical condition.
4-(critical) The resource being monitored by the Historical Performance agent has breached the hpxThresholdBreachCritical condition.
Associated traps:
hpxThresholdBreachUnknownTrap (6:201)
hpxThresholdBreachOkTrap (6:202)
hpxThresholdBreachWarningTrap (6:203)
hpxThresholdBreachCriticalTrap (6:204)
Note:  Another trap, hpxThresholdBreachTableUpdatedTrap (6:299), is issued each time that thresholding has completed if the threshold breach table has had rows added to it, or removed from it."
        ::= { HpxThresholdBreachEntry 9 }
    hpxThresholdBreachTimestamp OBJECT-TYPE
        SYNTAX DisplayString
        ACCESS read-only
        STATUS mandatory
        DESCRIPTION 
        "&<hpxAgent.123>The date and time that the resource was first detected as having entered the current state.  The timestamp reflects the system clock of the host on which the agent resides."
        ::= { HpxThresholdBreachEntry 10 }

    --  
    --  hpxAgent Error Table Definition:
    --
    --  This table pertains to the last N (N defined within the agent) error
    --  messages logged by the Historical Performance agent.
    --

--    hpxErrorTable OBJECT-TYPE
--        SYNTAX SEQUENCE OF HpxErrorEntry
--        ACCESS read-only
--        STATUS mandatory
--        DESCRIPTION
--        "&<hpxAgent.124>The hpxErrorTable contains attributes related to the last N fatal errors reported by the agent.  A fatal error, for example, occurs when the Historical Performance agent is unable to collect any performance data because of a fault in the agent's configuration file.  The table contains one row per fatal error.  Note:  The hpxErrorTrap (6:301) trap is issued each time that a fatal error is reported by the agent."
--        ::= {  hpxAgent 3 }
--    HpxErrorEntry OBJECT-TYPE
--        SYNTAX HpxErrorEntry
--        ACCESS read-only
--        STATUS mandatory
--        DESCRIPTION
--        "&<hpxAgent.125>A row in the error table.  Each row represents a fatal error reported by the Historical Performance agent."
--        ::= { hpxErrorTable 1 }
--    HpxErrorEntry ::= SEQUENCE {
--    	hpxErrorHostName
--            DisplayString,
--        hpxErrorCode
--            INTEGER,
--        hpxErrorMessage
--            DisplayString,
--	hpxErrorTimestamp
--            DisplayString	
--	}    
--    hpxErrorHostName OBJECT-TYPE
--        SYNTAX DisplayString
--        ACCESS read-only
--        STATUS mandatory
--        DESCRIPTION 
--        "&<hpxAgent.126>The name of the host for which the error was reported.  This attribute allows for proxy monitoring for remote machines and devices in addition to the local host."
--        ::= { HpxErrorEntry 1 }
--    hpxErrorCode OBJECT-TYPE
--        SYNTAX INTEGER
--        ACCESS read-only
--        STATUS mandatory
--        DESCRIPTION 
--        "&<hpxAgent.127>The error code associated with the error.  The error code is a unique alphanumeric identifier for the error.
--The first digit of the last four numbers of the error code represents a module within the Historical Performance agent.  The last three digits represent a unique number for the error message within that module.
--The module error numbers are as follows:
--0-Common library routines and general error messages used by all executables of this agent
--1-The hpaAgent executable (which includes the message handler, dispatcher, configuration file validator and thresholder)
--2-Reserved for future use
--3-The hpacbcol executable (which includes standard system data collector, porcess data collector and CA Sponsor data collection)
--4-The CA sponsor data collection manager (built into the hpacbcol executable)
--5-The hpacbman executable (which includes cube transfer, cube transformation and cube house-keeping)
--6-Configuration file parser (built into all executables)
--7-Resource accounting manager (which includes csv data transformation, csv transfer and csv house-keeping)
--8-Additional built in data collectors (which includes process data collection and SNMP data collection, built into the hpacbcol executable)
--9-Performance Evaluation neugent"
--        ::= { HpxErrorEntry 2 }
--    hpxErrorText OBJECT-TYPE
--        SYNTAX DisplayString
--        ACCESS read-only
--        STATUS mandatory
--        DESCRIPTION 
--        "&<hpxAgent.128>The text description of the fatal error that occurred."
--        ::= { HpxErrorEntry 3 }
--    hpxErrorTimestamp OBJECT-TYPE
--        SYNTAX DisplayString
--        ACCESS read-only
--        STATUS mandatory
--        DESCRIPTION 
--        "&<hpxAgent.129>The date and time that the fatal error was logged.  The timestamp reflects the system clock of the host on which the agent resides."
--        ::= { HpxErrorEntry 4 }

    --
    --  The following tables are for the Historical Performance Evaluation
    --  neugent's data.
    --

    --  
    --  hpxAgent Evaluation Configuration Group Definition:
    --
    --  This group pertains to the Performance Evaluation neugent and its
    --  configuration for the local host and any other hosts that are being
    --  proxied.
    --

    hpxEvalConfigGroup OBJECT IDENTIFIER ::= { hpxAgent 4 }
    hpxEvalConfigNeugentVersion OBJECT-TYPE
        SYNTAX DisplayString
        ACCESS read-only
        STATUS mandatory
        DESCRIPTION 
        "&<hpxAgent.130>The version of the Historical Performance Evaluation neugent that has been loaded."
        ::= { hpxEvalConfigGroup 1 }
    hpxEvalConfigProfileVersion OBJECT-TYPE
        SYNTAX INTEGER
        ACCESS read-only
        STATUS mandatory
        DESCRIPTION 
        "&<hpxAgent.131>The highest version of Personality Profile format or content that the neugent supports."
        ::= { hpxEvalConfigGroup 2 }

    --  
    --  hpxAgent Evaluation Configuration Table Definition:
    --
    --  This table pertains to the Performance Evaluation neugent and its
    --  configuration for the local host and any other hosts that are being
    --  proxied. Note that if no hosts have been configured for evaluation or 
    --  the Historical Performance Evaluation option is not installed, this 
    --  table is empty.
    --

--    hpxEvalConfigTable OBJECT-TYPE
--        SYNTAX SEQUENCE OF HpxEvalConfigEntry
--        ACCESS read-only
--        STATUS mandatory
--        DESCRIPTION
--        "&<hpxAgent.132>The hpxEvalConfigTable contains one row per evaluated host that contains attributes related to the configuration of the Performance Evaluation neugent."
--        ::= {  hpxEvalConfigGroup 3 }
--    HpxEvalConfigEntry OBJECT-TYPE
--        SYNTAX HpxEvalConfigEntry
--        ACCESS read-only
--        STATUS mandatory
--        DESCRIPTION
--        "&<hpxAgent.133>A row in the evaluation configuration table."
--        ::= { hpxEvalConfigTable 1 }
--    HpxEvalConfigEntry ::= SEQUENCE {
--    	hpxEvalConfigHostName
--	        DisplayString,
--		hpxEvalConfigPersonalityName
--	        DisplayString,
--		hpxEvalConfigPersonalityModificationTimestamp
--	        DisplayString,
--		hpxEvalConfigPersonalityRevision
--	        INTEGER
--    }
--    hpxEvalConfigHostName OBJECT-TYPE
--        SYNTAX DisplayString
--        ACCESS read-only
--        STATUS mandatory
--        DESCRIPTION
--        "&<hpxAgent.134>The name of the host to which this configuration information applies.  This attribute allows for proxy Performance Evaluation for remote machines and devices in addition to the local host."
--        ::= { HpxEvalConfigEntry 1 }
--    hpxEvalConfigPersonalityName OBJECT-TYPE
--        SYNTAX DisplayString
--        ACCESS read-only
--        STATUS mandatory
--        DESCRIPTION
--        "&<hpxAgent.135>The name of the Performance Evaluation Personality Profile with which the neugent has been configured."
--        ::= { HpxEvalConfigEntry 2 }
--    hpxEvalConfigPersonalityModificationTimestamp OBJECT-TYPE
--        SYNTAX DisplayString
--        ACCESS read-only
--        STATUS mandatory
--        DESCRIPTION
--        "&<hpxAgent.136>The date and time that the current personality profile was last updated before transfer to the neugent."
--        ::= { HpxEvalConfigEntry 3 }
--    hpxEvalConfigPersonalityVersion OBJECT-TYPE
--        SYNTAX DisplayString
--        ACCESS read-only
--        STATUS mandatory
--        DESCRIPTION
--        "&<hpxAgent.137>The revision number of the personality profile."
--        ::= { HpxEvalConfigEntry 4 }

    --  
    --  hpxAgent Evaluation Scenario Table Definition:
    --
    --  This table pertains to the state of the monitored machines according
    --  to the Performance Evaluation neugent.
    --

    hpxEvalScenarioTable OBJECT-TYPE
        SYNTAX SEQUENCE OF HpxEvalScenarioEntry
        ACCESS read-only
        STATUS mandatory
        DESCRIPTION
        "&<hpxAgent.138>The hpxEvalScenarioTable contains one row per evaluated host that contains attributes related to the current state of the host.  If no hosts have been configured for evaluation or the Historical Performance Evaluation option is not installed, this table is empty."
        ::= {  hpxAgent 5 }
    HpxEvalScenarioEntry OBJECT-TYPE
        SYNTAX HpxEvalScenarioEntry
        ACCESS read-only
        STATUS mandatory
        DESCRIPTION
        "&<hpxAgent.139>A row in the evaluation scenario table."
        INDEX {
            hpxEvalScenarioHostName
        }
        ::= { hpxEvalScenarioTable 1 }
    HpxEvalScenarioEntry ::= SEQUENCE {
    	hpxEvalScenarioHostName
	        DisplayString,
        hpxEvalScenarioId
            INTEGER,
        hpxEvalScenarioModeIndex
            DisplayString,
        hpxEvalScenarioTimestamp
            DisplayString,
        hpxEvalScenarioProblem
            DisplayString,
        hpxEvalScenarioProbabilityOfProblem
            DisplayString,
        hpxEvalScenarioTimeToProblem
            DisplayString,
        hpxEvalScenarioAdditionalInfo
            DisplayString
    }
    hpxEvalScenarioHostName OBJECT-TYPE
        SYNTAX DisplayString
        ACCESS read-only
        STATUS mandatory
        DESCRIPTION
        "&<hpxAgent.140>The name of the host to which this configuration information applies.  This allows for proxy Performance Evaluation for remote machines and devices in addition to the local host."
        ::= { HpxEvalScenarioEntry 1 }
    hpxEvalScenarioId OBJECT-TYPE
        SYNTAX INTEGER {
            nominal(1),
            nearNominal(2),
            someParamsUnusualButNominal(3),
            manyParamsUnusual(4),
            beyondHistoricalLimitsButNearNominal(5),
            beyondHistoricalLimits(6),
            highlyUnusual(7),
            cannotCategorise(8),
            notEvaluated(9),
            predictedSeverity1(10),
            predictedSeverity2(11),
            currentSeverity1(12),
            currentSeverity2(13)
        }
        ACCESS read-only
        STATUS mandatory
        DESCRIPTION
        "&<hpxAgent.141>The identity of the evaluated scenario for this host.  The 'notEvaluated' value is used as the default prior to the first evaluation, and if the evaluation fails.
Associated traps:
hpxEvalScenarioNominalTrap (6:501)
hpxEvalScenarioNearNominalTrap (6:502)
hpxEvalScenarioSomeParamsUnusualButNominalTrap (6:503)
hpxEvalScenarioManyParamsUnusualTrap (6:504)
hpxEvalScenarioBeyondHistoricalLimitsButNearNominalTrap (6:505)
hpxEvalScenarioBeyondHistoricalLimitsTrap (6:506)
hpxEvalScenarioHighlyUnusualTrap (6:507)
hpxEvalScenarioCannotCategoriseTrap (6:508)
hpxEvalScenarioNotEvaluatedTrap (6:509)
hpxEvalScenarioPredictedSeverity1 (6:510)
hpxEvalScenarioPredictedSeverity2 (6:511)
hpxEvalScenarioCurrentSeverity1 (6:512)
hpxEvalScenarioCurrentSeverity2 (6:513)
Note:  Another trap, hpxEvalScenarioTableUpdatedTrap (6:599), is issued when all changes to the scenario table have been completed after an evaluation."
        ::= { HpxEvalScenarioEntry 2 }
    hpxEvalScenarioModeIndex OBJECT-TYPE
        SYNTAX INTEGER
        ACCESS read-only
        STATUS mandatory
        DESCRIPTION
        "&<hpxAgent.142>The mode that the Historical Performance Evaluation neugent deems the machine's current behaviour to be closest to.  If the scenario Id is 'notEvaluated', this value should be ignored."
        ::= { HpxEvalScenarioEntry 3 }
    hpxEvalScenarioTimestamp OBJECT-TYPE
        SYNTAX DisplayString
        ACCESS read-only
        STATUS mandatory
        DESCRIPTION
        "&<hpxAgent.143>The date and time that the evaluation was performed, resulting in the current scenario Id.  If the scenario Id is 'notEvaluated', this value can be blank.  The timestamp reflects the system clock of the host on which the neugent resides."
        ::= { HpxEvalScenarioEntry 4 }
    hpxEvalScenarioProblem OBJECT-TYPE
        SYNTAX DisplayString
        ACCESS read-only
        STATUS mandatory
        DESCRIPTION
        "&<hpxAgent.144>A description of any predicted problem."
        ::= { HpxEvalScenarioEntry 5 }
    hpxEvalScenarioProbabilityOfProblem OBJECT-TYPE
        SYNTAX DisplayString
        ACCESS read-only
        STATUS mandatory
        DESCRIPTION
        "&<hpxAgent.145>The probability of occurrence of any predicted problem."
        ::= { HpxEvalScenarioEntry 6 }
    hpxEvalScenarioTimeToProblem OBJECT-TYPE
        SYNTAX DisplayString
        ACCESS read-only
        STATUS mandatory
        DESCRIPTION
        "&<hpxAgent.146>The projected time to occurrence for any predicted problem."
        ::= { HpxEvalScenarioEntry 7 }
    hpxEvalScenarioAdditionalInfo OBJECT-TYPE
        SYNTAX DisplayString
        ACCESS read-only
        STATUS mandatory
        DESCRIPTION
        "&<hpxAgent.147>Supplemental information about the scenario."
        ::= { HpxEvalScenarioEntry 8 }

    --  
    --  hpxAgent Evaluation Exceptions Table Definition:
    --
    --  This table pertains to exceptional conditions detected by the
    --  Performance Evaluation neugent.
    --

--    hpxEvalExceptionTable OBJECT-TYPE
--        SYNTAX SEQUENCE OF HpxEvalExceptionEntry
--        ACCESS read-only
--        STATUS mandatory
--        DESCRIPTION
--        "&<hpxAgent.148>The hpxEvalExceptionTable contains multiple rows per evaluated host that contain attributes related to exceptional conditions.  If no hosts have been configured for evaluation, the Historical Performance Evaluation option is not installed, or no exceptions have been detected during the last evaluation, this table is empty.  Note:  the hpxEvalExceptionDetectedTrap (6:601) trap is issued each time that an exception is reported by the neugent.  In addition the hpxEvalExceptionTableUpdatedTrap (6:699) trap is issued once all exceptions have been reported after an evaluation."
--        ::= {  hpxAgent 6 }
--    HpxEvalExceptionEntry OBJECT-TYPE
--        SYNTAX HpxEvalExceptionEntry
--        ACCESS read-only
--        STATUS mandatory
--        DESCRIPTION
--        "&<hpxAgent.149>A row in the evaluation exception table."
--        ::= { hpxEvalExceptionTable 1 }
--    HpxEvalExceptionEntry ::= SEQUENCE {
--    	hpxEvalExceptionHostName
--	        DisplayString,
--        hpxEvalExceptionResourceTypeName
--	        DisplayString,
--        hpxEvalExceptionResourceSubtypeName
--	        DisplayString,
--        hpxEvalExceptionResourceInstanceName
--	        DisplayString,
--        hpxEvalExceptionResourceValue
--	        DisplayString,
--        hpxEvalExceptionLowerHistoricalBound
--	        DisplayString,
--        hpxEvalExceptionUpperHistoricalBound
--	        DisplayString,
--        hpxEvalExceptionLowerModeBound
--	        DisplayString,
--        hpxEvalExceptionUpperModeBound
--	        DisplayString,
--        hpxEvalExceptionViolatedBound
--            INTEGER,
--        hpxEvalExceptionViolationType
--            INTEGER,
--        hpxEvalExceptionRangePercentage
--	        DisplayString,
--        hpxEvalExceptionAdditionalInfo
--	        DisplayString
--    }
--    hpxEvalExceptionHostName OBJECT-TYPE
--        SYNTAX DisplayString
--        ACCESS read-only
--        STATUS mandatory
--        DESCRIPTION
--        "&<hpxAgent.150>The name of the host to which this exception information applies.  This attribute allows for proxy Performance Evaluation for remote machines and devices in addition to the local host."
--        ::= { HpxEvalExceptionEntry 1 }
--    hpxEvalExceptionResourceTypeName OBJECT-TYPE
--        SYNTAX DisplayString
--        ACCESS read-only
--        STATUS mandatory
--        DESCRIPTION
--        "&<hpxAgent.151>The type name of the resource that is behaving out of bounds."
--        ::= { HpxEvalExceptionEntry 2 }
--    hpxEvalExceptionResourceSubtypeName OBJECT-TYPE
--        SYNTAX DisplayString
--        ACCESS read-only
--        STATUS mandatory
--        DESCRIPTION
--        "&<hpxAgent.152>The subtype name of the resource that is behaving out of bounds."
--        ::= { HpxEvalExceptionEntry 3 }
--    hpxEvalExceptionResourceInstanceName OBJECT-TYPE
--        SYNTAX DisplayString
--        ACCESS read-only
--        STATUS mandatory
--        DESCRIPTION
--        "&<hpxAgent.153>The instance name of the resource that is behaving out of bounds."
--        ::= { HpxEvalExceptionEntry 4 }
--    hpxEvalExceptionResourceValue OBJECT-TYPE
--        SYNTAX DisplayString
--        ACCESS read-only
--        STATUS mandatory
--        DESCRIPTION
--        "&<hpxAgent.154>The floating point value of the resource that is behaving out of bounds."
--        ::= { HpxEvalExceptionEntry 5 }
--    hpxEvalExceptionLowerHistoricalBound OBJECT-TYPE
--        SYNTAX DisplayString
--        ACCESS read-only
--        STATUS mandatory
--        DESCRIPTION
--        "&<hpxAgent.155>The floating point lower limit of the historical bound which has been violated."
--        ::= { HpxEvalExceptionEntry 6 }
--    hpxEvalExceptionUpperHistoricalBound OBJECT-TYPE
--        SYNTAX DisplayString
--        ACCESS read-only
--        STATUS mandatory
--        DESCRIPTION
--        "&<hpxAgent.156>The floating point upper limit of the historical bound which has been violated."
--        ::= { HpxEvalExceptionEntry 7 }
--    hpxEvalExceptionLowerModeBound OBJECT-TYPE
--        SYNTAX DisplayString
--        ACCESS read-only
--        STATUS mandatory
--        DESCRIPTION
--        "&<hpxAgent.157>The floating point lower limit of the mode bound which has been violated."
--        ::= { HpxEvalExceptionEntry 8 }
--    hpxEvalExceptionUpperModeBound OBJECT-TYPE
--        SYNTAX DisplayString
--        ACCESS read-only
--        STATUS mandatory
--        DESCRIPTION
--        "&<hpxAgent.158>The floating point upper limit of the mode bound which has been violated."
--        ::= { HpxEvalExceptionEntry 9 }
--    hpxEvalExceptionViolatedBound OBJECT-TYPE
--        SYNTAX INTEGER {
--            upper(1),
--            lower(2)
--        }
--        ACCESS read-only
--        STATUS mandatory
--        DESCRIPTION
--        "&<hpxAgent.159>The bound that has been broken, leading to this exception report."
--        ::= { HpxEvalExceptionEntry 10 }
--    hpxEvalExceptionViolationType OBJECT-TYPE
--        SYNTAX INTEGER {
--            cluster(1),
--            resource(2),
--            rule(3)
--        }
--        ACCESS read-only
--        STATUS mandatory
--        DESCRIPTION
--        "&<hpxAgent.160>Whether a mode or historical resource bound was violated."
--        ::= { HpxEvalExceptionEntry 11 }
--    hpxEvalExceptionRangePercentage OBJECT-TYPE
--        SYNTAX DisplayString
--        ACCESS read-only
--        STATUS mandatory
--        DESCRIPTION
--        "&<hpxAgent.161>The amount that the value is outside of the breached bound, expressed as a percentage of the normal value range."
--        ::= { HpxEvalExceptionEntry 12 }
--    hpxEvalExceptionAdditionalInfo OBJECT-TYPE
--        SYNTAX DisplayString
--        ACCESS read-only
--        STATUS mandatory
--        DESCRIPTION
--        "&<hpxAgent.162>Supplementary information about the exception in a textual form."
--        ::= { HpxEvalExceptionEntry 13 }

    --  
    --  hpxAgent Trap Definitions.
    --

    hpxThresholdBreachUnknownTrap TRAP-TYPE
        ENTERPRISE hpxAgent
        DESCRIPTION
        "&<hpxAgent.163>A thresholded performance resource has changed state to 'unknown'.  The varbind entry contains all of the attributes of the row in the threshold breach table."
        ::= 201
    hpxThresholdBreachOkTrap TRAP-TYPE
        ENTERPRISE hpxAgent
        DESCRIPTION
        "&<hpxAgent.164>A thresholded performance resource has changed state to 'ok'.  The varbind entry contains all of the attributes of the row in the threshold breach table.  Note:  This trap indicates to the Distributed State Machine that the row representing the resource has been deleted from the threshold breach table."
        ::= 202
    hpxThresholdBreachWarningTrap TRAP-TYPE
        ENTERPRISE hpxAgent
        DESCRIPTION
        "&<hpxAgent.165>A thresholded performance resource has changed state to 'warning'.  The varbind entry contains all of the attributes of the row in the threshold breach table."
        ::= 203
    hpxThresholdBreachCriticalTrap TRAP-TYPE
        ENTERPRISE hpxAgent
        DESCRIPTION
        "&<hpxAgent.166>A thresholded performance resource has changed state to 'critical'.  The varbind entry contains all of the attributes of the row in the threshold breach table."
        ::= 204
    hpxThresholdBreachTableUpdatedTrap TRAP-TYPE
        ENTERPRISE hpxAgent
        DESCRIPTION
        "&<hpxAgent.167>The threshold breach table has been reconfigured and should be rediscovered.  There is no varbind entry."
        ::= 299
    hpxErrorTrap TRAP-TYPE
        ENTERPRISE hpxAgent
        DESCRIPTION
        "&<hpxAgent.168>A fatal error has occurred at the hpxAgent.  The varbind entry contains all of the attributes of the row in the error table."
        ::= 301
    hpxEvalScenarioNominalTrap TRAP-TYPE
        ENTERPRISE hpxAgent
        DESCRIPTION
        "&<hpxAgent.169>The scenario Id has changed to 'nominal' for a particular host.  The varbind entry consists of the attributes of the row in the evaluation scenario Id table."
        ::= 501
    hpxEvalScenarioNearNominalTrap TRAP-TYPE
        ENTERPRISE hpxAgent
        DESCRIPTION
        "&<hpxAgent.170>The scenario Id has changed to 'nearNominal' for a particular host.  The varbind entry consists of the attributes of the row in the evaluation scenario Id table."
        ::= 502
    hpxEvalScenarioSomeParamsUnusualButNominalTrap TRAP-TYPE
        ENTERPRISE hpxAgent
        DESCRIPTION
        "&<hpxAgent.171>The scenario Id has changed to 'someParamsUnusualButNominal' for a particular host.  The varbind consists of the attributes of the row in the evaluation scenario Id table."
        ::= 503
    hpxEvalScenarioManyParamsUnusualTrap TRAP-TYPE
        ENTERPRISE hpxAgent
        DESCRIPTION
        "&<hpxAgent.172>The scenario Id has changed to 'manyParamsUnusual' for a particular host.  The varbind entry consists of the attributes of the row in the evaluation scenario Id table."
        ::= 504
    hpxEvalScenarioBeyondHistoricalLimitsButNearNominalTrap TRAP-TYPE
        ENTERPRISE hpxAgent
        DESCRIPTION
        "&<hpxAgent.173>The scenario Id has changed to 'beyondHistoricalLimitsButNearNominal' for a particular host.  The varbind entry  consists of the attributes of the row in the evaluation scenario Id table."
        ::= 505
    hpxEvalScenarioBeyondHistoricalLimitsTrap TRAP-TYPE
        ENTERPRISE hpxAgent
        DESCRIPTION
        "&<hpxAgent.174>The scenario Id has changed to 'beyondHistoricalLimits' for a particular host.  The varbind entry consists of the attributes of the row in the evaluation scenario Id table."
        ::= 506
    hpxEvalScenarioHighlyUnusualTrap TRAP-TYPE
        ENTERPRISE hpxAgent
        DESCRIPTION
        "&<hpxAgent.175>The scenario Id has changed to 'highlyUnusual' for a particular host.  The varbind entry consists of the attributes of the row in the evaluation scenario Id table."
        ::= 507
    hpxEvalScenarioCannotCategoriseTrap TRAP-TYPE
        ENTERPRISE hpxAgent
        DESCRIPTION
        "&<hpxAgent.176>The scenario Id has changed to 'cannotCategorise' for a particular host.  The varbind entry consists of the attributes of the row in the evaluation scenario Id table."
        ::= 508
    hpxEvalScenarioNotEvaluatedTrap TRAP-TYPE
        ENTERPRISE hpxAgent
        DESCRIPTION
        "&<hpxAgent.177>The scenario Id has changed to 'notEvaluated' for a particular host.  The varbind entry consists of the attributes of the row in the evaluation scenario Id table."
        ::= 509
    hpxEvalScenarioPredictedSeverity1Trap TRAP-TYPE
        ENTERPRISE hpxAgent
        DESCRIPTION
        "&<hpxAgent.178>The scenario Id has changed to 'predictedSeverity1' for a particular host.  The varbind entry consists of the attributes of the row in the evaluation scenario Id table."
        ::= 510
    hpxEvalScenarioPredictedSeverity2Trap TRAP-TYPE
        ENTERPRISE hpxAgent
        DESCRIPTION
        "&<hpxAgent.179>The scenario Id has changed to 'predictedSeverity2' for a particular host.  The varbind entry consists of the attributes of the row in the evaluation scenario Id table."
        ::= 511
    hpxEvalScenarioCurrentSeverity1Trap TRAP-TYPE
        ENTERPRISE hpxAgent
        DESCRIPTION
        "&<hpxAgent.180>The scenario Id has changed to 'currentSeverity1' for a particular host.  The varbind entry consists of the attributes of the row in the evaluation scenario Id table."
        ::= 512
    hpxEvalScenarioCurrentSeverity2Trap TRAP-TYPE
        ENTERPRISE hpxAgent
        DESCRIPTION
        "&<hpxAgent.181>The scenario Id has changed to 'currentSeverity2' for a particular host.  The varbind entry consists of the attributes of the row in the evaluation scenario Id table."
        ::= 513
    hpxEvalScenarioTableUpdatedTrap TRAP-TYPE
        ENTERPRISE hpxAgent
        DESCRIPTION
        "&<hpxAgent.182>All changes to the scenario table have been completed after an evaluation.  There is no varbind entry."
		::= 599
    hpxEvalExceptionDetectedTrap TRAP-TYPE
        ENTERPRISE hpxAgent
        DESCRIPTION
        "&<hpxAgent.183>A new exception row has been added to the evaluation exception table.  The rows in this table are deleted and recreated every time an evaluation takes place.  The varbind entry consists of the attributes of the row in this table."
        ::= 601
    hpxEvalExceptionTableUpdatedTrap TRAP-TYPE
        ENTERPRISE hpxAgent
        DESCRIPTION
        "&<hpxAgent.184>All changes have been made to the evaluation exception table after an evaluation.  There is no varbind entry."
        ::= 699

END
