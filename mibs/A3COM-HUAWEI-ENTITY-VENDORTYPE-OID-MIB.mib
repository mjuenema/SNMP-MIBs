-- =================================================================
-- Copyright (C) 2008 by H3C Technologies. All rights reserved.
--
-- Description:the definition of H3C Entity Vendortype OID
-- Reference:
-- Version: V4.46
-- History:
-- V1.0 2004.05.13  Created by lvzhenfeng, modified by gaolong.
-- V1.1 2004.05.22  Adjusted by gaolong and lvzhenfeng.
--   1. Adjust module name to h3cEntityVendorTypeOID and its location is set to { h3c 3 }.
--   2. Rename module name prefix from h3cevtModule to h3cevtModuleRt_
--   and h3cevtModuleSw_ for routers and switches seperately.
--   3. Add h3cevtSubModuleRouter and h3cevtSubModuleSwitch under h3cevtModule.
--   4. Split port type into two groups, one for routers, another for switches.
-- V1.11 2004.6.17 add h3cevtHotSwapFan node by limeng for garibaldi
-- V1.12 2004.7.19 add h3cevtModuleSwitchType {117-138}
-- V1.13 2004.7.29 add h3cevtPortSwitchType {50-58}
-- V1.14 2004.8.12 add h3cevtModuleSw_LSA1FP8U(h3cevtModuleSwitchType 139)
-- V1.15 2004.8.25 change enumeration name
--                     from h3cevtModuleSw_LS81SFCA(120) to h3cevtModuleSw_LS81SRPG0(120),
--                     from h3cevtModuleSw_LS81SFCB(121) to h3cevtModuleSw_LS81SRPG1(121),
--                     from h3cevtModuleSw_LS81SFCC(122) to h3cevtModuleSw_LS81SRPG2(122),
--                     from h3cevtModuleSw_LS81SFCD(123) to h3cevtModuleSw_LS81SRPG3(123).
--                 modify comments for these enumerations as well.
-- V1.2  2004.8.26 add sub identifier of h3cevtPortSwitchType from 59 to 71.
-- V1.21  2004.09.08 add sub identifier of h3cevtModuleSwitchType from 140 to 148.
-- V1.3  2004-09-14 add subidentifier under h3cevtModuleSwitchType from 149 to 157 by wangyahui
--                  add subidentifier under h3cevtModuleSwitchType from 158 to 159 by kangyinan
--                  add subidentifier under h3cevtModuleSwitchType from 72 to 93 by wangyahui
--                  add subidentifier under h3cevtModuleSwitchType from 94 to 96 by kangyinan
--                  add type description for h3cevtModuleSw_SP4, h3cevtModuleSw_UP1, h3cevtModuleSw_XP4 by kangyinan
-- V2.0 2004-10-12 updated by gaolong
--      Change all underscore('_') characters to hyphen characters('-') because underscore character is not allowed in MIB module.
--      Remove some adjacent hyphens
-- V2.1  2004-10-19 add subidentifier under h3cevtModuleSwitchType from 160 to 162 by kangyinan
--                  add subidentifier under h3cevtPortSwitchType 97 by kangyinan
-- V2.2  2004-09-18 add sub identifier for h3cevtModuleRouterType from 111 to 117 by taotao
-- V2.3  2004-11-18 add sub identifier 2 under h3cevtFan by liyutao
-- V2.4  2004-11-23 add subidentifier under h3cevtModuleSwitchType from 163 to 166 by zhangchengmei
-- V2.5  2004-12-04 add subidentifier 118 under h3cevtModuleRouterType by lizhiyong
-- V2.6  2004-12-23 add sub identifier 4 to 7 under h3cevtPowerSupply by Zhangjianfeng
--                  add sub identifier 167 to 169 under h3cevtModuleSwitchType by Zhangjianfeng
-- V2.7  2004-12-26 add subidentifier 170 under h3cevtModuleSwitchType by wangyahui
-- v2.8  2004-12-23 add subidentifier under h3cevtModuleSwitchType from 171 to 172 and
--                  add sub identifier 98 to 99 under h3cevtPortSwitchType by liyue
-- V2.9  2004-12-26 add sub identifier 173 under h3cevtModuleSwitchType by Zhangjianfeng
--                  add sub identifier 100 for 24G cascade port under h3cevtPort by Zhangjianfeng
-- V3.0  2004-01-07 add subidentifier 174 and 175 under h3cevtModuleSwitchType by wangyahui
-- V3.1  2005-01-31 add subidentifier 176 under h3cevtModuleSwitchType by wangyahui
-- V3.2  2005-02-26 add subidentifier 177 under h3cevtModuleSwitchType by zhangchengmei
--                  add subidentifier 101 to 137 under h3cevtPortSwitchType by zhangchengmei
--                  add subidentifier 178 under h3cevtModuleSwitchType by zhouqiang
--                  add subidentifier 138 under h3cevtPortSwitchType by zhouqiang
--                  add subidentifier 179 to 180 under h3cevtModuleSwitchType by wangyahui
--                  remove trailing spaces
-- V3.3  2005-03-22 add subidentifier 181 to 187 under h3cevtModuleSwitchType by zhangchengmei
-- V3.4  2004-12-29 add subidentifier 119 to 120 under h3cevtModuleRouterType by lizhiyong
-- V3.5  2005-04-12 add subidentifier 141 to 144 under h3cevtModuleRouterType by yinxiaoyu
--                  add subidentifier 30 to 33 under h3cevtPortRouterType by yinxiaoyu
-- V3.6  2005-04-07 add subidentifier 121 to 140 under h3cevtModuleRouterType by taotao
--                  change the name of subidentifier 118 under h3cevtModuleRouterType by taotao
--                  adjust file format
-- V3.7  2005-05-10 add subidentifier 188 to 216 under h3cevtModuleSwitchType by zhangchengmei
-- V3.8  2005-06-12 add subidentifier 145 to 149 under h3cevtModuleRouterType,
--                  add subidentifier 34 under h3cevtPortRouterType by wanghanlin
-- V3.9  2005-06-22 add subidentifier 150 under h3cevtModuleRouterType by yinxiaoyu
-- V4.0  2005-07-18 add subidentifier 217 to 219 under h3cevtModuleSwitchType by yangliming
--                  add subidentifier 139 to 142 under h3cevtPortSwitchType by wangyahui
-- V4.01 2005-07-29 add subidentifier 220 to 225 under h3cevtModuleSwitchType by wangyahui
-- V4.02 2005-07-21 change the name of subidentifier 183 under h3cevtModuleSwitchType,
--                  add subidentifier 226 to 227 under h3cevtModuleSwitchType by zhangchengmei
--       2005-08-29 add subidentifier 143 under h3cevtPortSwitchType by qianxiaoyu
--                  add subidentifier 151 to 161 under h3cevtModuleRouterType by taotao
--                  add subidentifier 35 to 41 under h3cevtPortRouterType by taotao
-- V4.03 2005-09-07 add h3cevtCPU and h3cevtGeneralCPU by taotao
--                  add subidentifier 162 to 163 under h3cevtModuleRouterType by taotao
--                  adjust file format by gaolong
-- V4.04 2005-09-13 add subidentifier 228 to 253 under h3cevtModuleSwitchType by zhangchengmei
--       2005-09-13 add subidentifier 257 to 268 under h3cevtModuleSwitchType by zhangchengmei
-- V4.05 2005-11-04 add subidentifier 144 to 149 under h3cevtPortSwitchType by zhangchengmei
--                  add subidentifier 150 under h3cevtPortSwitchType by huangyuetao
--                  add subidentifier 269 to 271 under h3cevtModuleSwitchType by yangxiaopeng
--                  add subidentifier 272 under h3cevtModuleSwitchType by qianxiaoyu
--                  add subidentifier 164 to 165 under h3cevtModuleRouterType by xuejiayong
-- V4.06 2005-11-24 add subidentifier 500 to 501 under h3cevtModuleSwitchType by wangyahui
-- V4.07 2005-11-28 add subidentifier 300 to 316 under h3cevtModuleSwitchType by zhangchengmei
-- V4.08 2005-12-09 add subidentifier 220 to 223 under h3cevtModuleRouterType by taotao
-- V4.09 2005-12-30 add subidentifier 151 to 170 under h3cevtPortSwitchType by zhangchengmei
-- V4.10 2006-01-04 add subidentifier 701 under h3cevtModuleSwitchType by qianxiaoyu
-- V4.11 2006-02-12 add subidentifier 200 to 219 under h3cevtModuleRouterType by liutinghai
--                  add subidentifier 702 under h3cevtModuleSwitchType by chenxiaohui
--                  add subidentifier 600 under h3cevtModuleRouterType by qujin
--                  add subidentifier 317 under h3cevtModuleSwitchType by zhangchengmei
-- V4.12 2006-02-24 add subidentifier 703 under h3cevtModuleSwitchType by chijuntao
--                  add subidentifier 224 to 228 under h3cevtModuleRouterType by taotao
-- V4.13 2006-02-27 add subidentifier 171 to 174 under h3cevtPortSwitchType by wangshunli
--                  add subidentifier 318 to 336 under h3cevtModuleSwitchType by zhaiyingying
-- V4.14 2006-03-14 add subidentifier 175 under h3cevtPortSwitchType by wangyahui
--                  add subidentifier 502 to 504 under h3cevtModuleSwitchType by wangyahui
-- V4.15 2006-04-03 add subidentifier 176 under h3cevtPortSwitchType by wangyahui
-- V4.16 2006-04-26 add subidentifier 229 to 233 under h3cevtModuleRouterType by taotao
-- V4.17 2006-04-21 add subidentifier 337 to 340 under h3cevtModuleSwitchType by zhaiyingying
-- V4.18 2006-06-05 add subidentifier 704 to 705 under h3cevtModuleSwitchType by zhangxianguo
--                  add subidentifier 505 to 506 under h3cevtModuleSwitchType by zhangjianfeng
--                  add subidentifier 341 to 349 under h3cevtModuleSwitchType by zhaiyingying
--                  add subidentifier 177 to 178 under h3cevtPortSwitchType by zhangjianfeng
--                  add subidentifier 179 to 180 under h3cevtPortSwitchType by zhangxianguo
-- V4.19 2006-08-23 add subidentifier 507 to 509 under h3cevtModuleSwitchType by wangyahui
--                  modify object name of subidentifier 502 and 503 under h3cevtModuleSwitchType by wangyahui
--                  add subidentifier 234 to 235 under h3cevtModuleRouterType by liutinghai
--                  add subidentifier 350 to 357 under h3cevtModuleSwitchType by zhaiyingying
-- V4.20 2006-09-26 add subidentifier 510 to 514 under h3cevtModuleSwitchType by wangyahui
--                  add subidentifier 601 to 603 under h3cevtModuleRouterType by zhoujianming
--                  add subidentifier 236 to 239 under h3cevtModuleRouterType by qikai
--                  add subidentifier 240 to 241 under h3cevtModuleRouterType by liutinghai
--                  add subidentifier 800 to 801 under h3cevtModuleSwitchType by luoguixing
-- V4.21 2006-10-26 add subidentifier 358 to 370 under h3cevtModuleSwitchType by zhaiyingying
--                  add subidentifier 183 under h3cevtPortSwitchType by zhaiyingying
--                  add subidentifier 515 to 526 under h3cevtModuleSwitchType by wangyahui
--                  add subidentifier 181 to 182 under h3cevtPortSwitchType by wangyahui
-- V4.22 2006-11-02 add subidentifier 527 to 536 under h3cevtModuleSwitchType by wangyahui
--                  modify description of 511 to 513 under h3cevtModuleSwitchType by wangyahui
--       2006-11-10 add subidentifier 371 to 378 under h3cevtModuleSwitchType by shuxiongtao
--       2006-11-08 add subidentifier 184 to 185 under h3cevtPortSwitchType by zhaiyingying
-- V4.23 2006-12-04 add subidentifier 242 to 243 under h3cevtModuleRouterType by liutinghai
-- V4.24 2006-01-24 add subidentifier 244 to 245 under h3cevtModuleRouterType by liutinghai
-- V4.25 2007-03-19 add subidentifier 537 under h3cevtModuleSwitchType by wangyahui
-- V4.26 2007-04-12 add subidentifier 538 to 542 under h3cevtModuleSwitchType by wangyahui
-- V4.27 2007-04-25 add subidentifier 706 under h3cevtModuleSwitchType by zhangzongyi
--                  add subidentifier 379 to 380 under h3cevtModuleSwitchType by zhaiyingying
--                  add subidentifier 246 to 250 under h3cevtModuleRouterType by liutinghai
--                  add subidentifier 42 under h3cevtPortRouterType by liutinghai
-- V4.28 2007-05-28 add subidentifier 707 under h3cevtModuleSwitchType by ligaoxu
--                  add subidentifier 381 to 392 under h3cevtModuleSwitchType by shuxiongtao
--                  modify name of subidentifier 371 and 374 under h3cevtModuleSwitchType by shuxiongtao
--                  add subidentifier 251 to 253 under h3cevtModuleRouterType by qikai
--                  add subidentifier 254 to 255 under h3cevtModuleRouterType by liutinghai
--                  add subidentifier 186 under h3cevtPortSwitchType by jinzhaoqiong
-- V4.29 2007-07-09 add subidentifier 543 to 551 under h3cevtModuleSwitchType by zhangjianfeng
--                  add subidentifier 552 to 554 under h3cevtModuleSwitchType by wangyahui
-- V4.30 2007-07-26 add subidentifier 400 under h3cevtModuleRouterType by xuejiayong
--                  add subidentifier 708 under h3cevtModuleSwitchType by xiuyihong
--                  add subidentifier 256 to 258 under h3cevtModuleRouterType by qikai
--                  add subidentifier 259 to 263 under h3cevtModuleRouterType by liutinghai
--                  add subidentifier 3 to 5 under h3cevtOther by gaolong
-- V4.31 2007-08-27 add subidentifier 187 to 188 under h3cevtPortSwitchType by ruanhan
--                  add subidentifier 802 to 804 under h3cevtModuleSwitchType by luoguixing
--                  add subidentifier 393 to 397 under h3cevtModuleSwitchType by shuxiongtao
-- V4.32 2007-09-25 add subidentifier 555 to 559 under h3cevtModuleSwitchType by wangyahui
--                  add subidentifier 805 under h3cevtModuleSwitchType by luoguixing
--                  add subidentifier 401 to 403 under h3cevtModuleRouterType by tanwen
--                  add subidentifier 43 under h3cevtPortRouterType by qikai
--                  add subidentifier 266 to 267 under h3cevtModuleRouterType by qikai
--                  add subidentifier 398 to 399 under h3cevtModuleSwitchType by hexuefei
-- V4.33 2007-10-22 add subidentifier 189 under h3cevtPortSwitchType by liaoxin
--                  add subidentifier 268 under h3cevtModuleRouterType by liutinghai
-- V4.34 2007-11-26 add subidentifier 269 to 273 under h3cevtModuleRouterType by liutinghai
--                  add subidentifier 274 to 276 under h3cevtModuleRouterType by qikai
--                  add subidentifier 404 to 406 under h3cevtModuleRouterType by chaiyaqin
--                  add subidentifier 400 to 407 under h3cevtModuleSwitchType by shuxiongtao
-- V4.35 2007-12-27 add subidentifier 277 to 278 under h3cevtModuleRouterType by liutinghai
--                  add subidentifier 560 to 568 under h3cevtModuleSwitchType by wangyahui
-- V4.36 2008-01-30 add subidentifier 408 under h3cevtModuleSwitchType by hexuefei
--                  add subidentifier 569 to 572 under h3cevtModuleSwitchType by wangyahui
--                  add subidentifier 279 to 280 under h3cevtModuleRouterType by qikai
--                  add subidentifier 190 under h3cevtPortSwitchType by liujingya
-- V4.37 2008-02-20 add subidentifier 720 to 724 under h3cevtModuleSwitchType by chaiyaqin
--                  add subidentifier 573 to 574 under h3cevtModuleSwitchType by zhangjianfeng
--                  modify name of subidentifier 546 and 550 under h3cevtModuleSwitchType by zhangjianfeng
--                  add subidentifier 575 to 576 under h3cevtModuleSwitchType by wangyahui
--                  add subidentifier 281 under h3cevtModuleRouterType by liutinghai
-- V4.38 2008-03-31 add subidentifier 806 to 808 under h3cevtModuleSwitchType by luoguixing
--                  add subidentifier 709 to 715 under h3cevtModuleSwitchType by wangcong
--                  add subidentifier 191 to 196 under h3cevtPortSwitchType by wangcong
--                  add subidentifier 44 under h3cevtPortRouterType by liutinghai
--                  add subidentifier 409 to 431 under h3cevtModuleSwitchType by zhaiyingying
--                  add subidentifier 432 under h3cevtModuleSwitchType by shuxiongtao
-- V4.39 2008-04-29 add subidentifier 577 to 589 under h3cevtModuleSwitchType by wangyahui
--                  add subidentifier 407 to 409 under h3cevtModuleRouterType by tanwen
-- V4.40 2008-05-31 add subidentifier 410 to 413 under h3cevtModuleRouterType by tanwen
--                  add subidentifier 282 to 284 under h3cevtModuleRouterType by qikai
--                  add subidentifier 285 to 286 under h3cevtModuleRouterType by liutinghai
-- V4.41 2008-07-28 add subidentifier 590 to 592 under h3cevtModuleSwitchType by wangyahui
--                  add subidentifier 287 to 289 under h3cevtModuleRouterType by qikai
--                  add subidentifier 290 to 291 under h3cevtModuleRouterType by liutinghai
--                  add subidentifier 45 to 46 under h3cevtPortRouterType by liutinghai
--                  add subidentifier 809 to 810 under h3cevtModuleSwitchType by luoguixing
-- V4.42 2008-08-26 modify name of 379 and 399 under h3cevtModuleSwitchType by wangwei
--                  modify description of 408 under h3cevtModuleSwitchType by wangwei
--                  modify name and description of 804 under h3cevtModuleSwitchType by wangwei
--                  add subidentifier 433 to 434 under h3cevtModuleSwitchType by wangwei
--                  add subidentifier 593 to 595 under h3cevtModuleSwitchType by wangyahui
--                  modify name and description of 256 and 288 under h3cevtPortRouterType by qikai
--                  add subidentifier 292 to 293 under h3cevtPortRouterType by qikai
-- V4.43 2008-10-13 add subidentifier 725 under h3cevtModuleSwitchType by ruanhan
--                  add subidentifier 197 under h3cevtPortSwitchType by ruanhan
--                  add subidentifier 811 under h3cevtModuleSwitchType by luoguixing
--                  add subidentifier 596 to 601 under h3cevtModuleSwitchType by wangyahui
-- V4.44 2008-11-04 add subidentifier 294 under h3cevtPortRouterType by qikai
--                  add subidentifier 414 under h3cevtModuleRouterType by tanwen
-- V4.45 2008-12-01 add subidentifier 602 to 619 under h3cevtModuleSwitchType by wangyahui
--                  add subidentifier 435 to 442 under h3cevtModuleSwitchType by zhaiyingying
--                  modify name of 546 under h3cevtModuleSwitchType by zhangjianfeng
--                  add subidentifier 295 under h3cevtPortRouterType by qikai
--                  add subidentifier 443 under h3cevtModuleSwitchType by shuxiongtao
-- V4.46 2008-12-25 add subidentifier 620 to 622 under h3cevtModuleSwitchType by wangyahui
--                  add subidentifier 716 to 718 under h3cevtModuleSwitchType by zhangshilin
--                  add subidentifier 444 to 445 under h3cevtModuleSwitchType by wangchang
-- =================================================================
A3COM-HUAWEI-ENTITY-VENDORTYPE-OID-MIB DEFINITIONS ::= BEGIN

IMPORTS
    MODULE-IDENTITY
        FROM SNMPv2-SMI
    h3c
        FROM A3COM-HUAWEI-OID-MIB;


h3cEntityVendorTypeOID MODULE-IDENTITY

        LAST-UPDATED "200403280000Z"
        ORGANIZATION "Hangzhou H3C Technologies Co., Ltd."
        CONTACT-INFO
            "Platform Team H3C Technologies Co., Ltd.
            Hai-Dian District Beijing P.R. China
            Zip:100085
            http://www.h3c.com"
        DESCRIPTION
            "The private MIB includes the definition of the object
            identifiers on H3C products, which are used by the
            entPhysicalTable of the ENTITY-MIB to uniquely identify the
            type of each physical entry."
        ::= { h3c 3 }


h3cEntityVendortypeObjects   OBJECT IDENTIFIER ::= { h3cEntityVendorTypeOID 1 }

-- This MIB assigns OIDs for use as the values of entPhysicalVendorType.
-- The subtrees in which the OID values are assigned, are structured
-- into a hierarchy based on the values of RFC 2037's PhysicalClass
-- textual convention.  For reference, the definition of PhysicalClass
-- is as follows:
--
--      PhysicalClass ::= TEXTUAL-CONVENTION
--      STATUS          current
--      DESCRIPTION
--             "An enumerated value which provides an indication of the
--              general hardware type of a particular physical entity."
--      SYNTAX      INTEGER  {
--              other(1),
--              unknown(2),
--              chassis(3),
--              backplane(4),
--              container(5),    e.g. slot or daughter-card holder
--              powerSupply(6),
--              fan(7),
--              sensor(8),
--              module(9),       e.g. plug-in card or daughter-card
--              port(10),
--              stack(11)        e.g., stack of multiple chassis entities
--          }
--

h3cevtOther     OBJECT IDENTIFIER ::= { h3cEntityVendortypeObjects 1 }

-- May be defined detailed in future.

h3cevtOtherUnknownCard  OBJECT IDENTIFIER ::= { h3cevtOther 1 }
h3cevtCPU               OBJECT IDENTIFIER ::= { h3cevtOther 2 }
h3cevtDOM               OBJECT IDENTIFIER ::= { h3cevtOther 3 }  -- Disk on Module
h3cevtCFCard            OBJECT IDENTIFIER ::= { h3cevtOther 4 }  -- Compact Flash Card
h3cevtHardDisk          OBJECT IDENTIFIER ::= { h3cevtOther 5 }  -- Hard Disk

-- h3cevtGeneralCPU is a general vendor type of CPU.  It is used only for
-- general purpose.  It is strongly recommended that this object should not
-- be used to present the specific CPU vendor type in most cases.  More
-- accurate and clear vendor types should be defined to present specific CPU.
h3cevtGeneralCPU        OBJECT IDENTIFIER ::= { h3cevtCPU 1 }


h3cevtUnknown   OBJECT IDENTIFIER ::= { h3cEntityVendortypeObjects 2 }

h3cevtChassis   OBJECT IDENTIFIER ::= { h3cEntityVendortypeObjects 3 }

-- chassis OID assignments
-- May be substituted by sysObjectID.  So none is assigned at present.

--
--backplane
--   The enumeration 'backplane' is applicable if the physical
--   entity class is some sort of device for aggregating and
--   forwarding networking traffic, such as a shared backplane in
--   a modular ethernet switch.  Note that an agent may model a
--   backplane as a single physical entity, which is actually
--   implemented as multiple discrete physical components (within
--   a chassis or stack).
--

h3cevtBackplane     OBJECT IDENTIFIER ::= { h3cEntityVendortypeObjects 4 }

--
-- h3cevtContainer section:
--
h3cevtContainer     OBJECT IDENTIFIER ::= { h3cEntityVendortypeObjects 5 }
--
-- h3cevtPowerSupply section:
--

h3cevtPowerSupply   OBJECT IDENTIFIER ::= { h3cEntityVendortypeObjects 6 }
h3cevtPowerSupplyAC         OBJECT IDENTIFIER ::= { h3cevtPowerSupply 2 }
h3cevtPowerSupplyDC         OBJECT IDENTIFIER ::= { h3cevtPowerSupply 3 }
h3cevtPowerSupplySTD130W    OBJECT IDENTIFIER ::= { h3cevtPowerSupply 4 }     -- Standard 130W PSU
h3cevtPowerSupplySTD180W    OBJECT IDENTIFIER ::= { h3cevtPowerSupply 5 }     -- Standard 180W PSU
h3cevtPowerSupplyPOE24Port  OBJECT IDENTIFIER ::= { h3cevtPowerSupply 6 }     -- 24 Port POE PSU 480W
h3cevtPowerSupplyPOE48Port  OBJECT IDENTIFIER ::= { h3cevtPowerSupply 7 }     -- 48 Port POE PSU 480W

--
-- h3cevtFan section:
--

h3cevtFan       OBJECT IDENTIFIER ::= { h3cEntityVendortypeObjects 7 }
h3cevtHotSwapFan        OBJECT IDENTIFIER ::=  { h3cevtFan 1 }
h3cevtNonHotSwapFan     OBJECT IDENTIFIER ::=  { h3cevtFan 2 }

--
-- h3cevtSensor section:
--
h3cevtSensor        OBJECT IDENTIFIER ::= { h3cEntityVendortypeObjects 8 }
h3cevtSensorTemperature     OBJECT IDENTIFIER ::= { h3cevtSensor 1 }
h3cevtSensorVoltage         OBJECT IDENTIFIER ::= { h3cevtSensor 2 }
h3cevtSensorFanSpeed        OBJECT IDENTIFIER ::= { h3cevtSensor 3 }


--
-- h3cevtModule section:
--

h3cevtModule        OBJECT IDENTIFIER ::= { h3cEntityVendortypeObjects 9 }

-- h3cevtModule is subdivided into sections like Router and Switch. These represent
-- cards used only on the router and switch.
-- h3cevtModuleCommonCards contains cards that can be used interchangeably
-- across more than one platform


-- Acronyms used in the h3cevtModule section:
--

h3cevtModuleUnknownCard     OBJECT IDENTIFIER ::= { h3cevtModule 1 }

-- h3cevtModuleCommonCards - cards and subcards common to more
-- than one platform

h3cevtModuleCommonCards     OBJECT IDENTIFIER ::= { h3cevtModule 2 }

-- h3cevtModuleRouterType cards are slot-cards specific to the Router.
h3cevtModuleRouterType      OBJECT IDENTIFIER ::= { h3cevtModule 3 }

--h3cevtModuleRt-Unavailable               OBJECT IDENTIFIER ::= { h3cevtModuleRouterType 1 }

h3cevtModuleRt-As                          OBJECT IDENTIFIER ::= { h3cevtModuleRouterType 2 }

h3cevtModuleRt-Sa                          OBJECT IDENTIFIER ::= { h3cevtModuleRouterType 3 }

h3cevtModuleRt-Bi                          OBJECT IDENTIFIER ::= { h3cevtModuleRouterType 4 }

h3cevtModuleRt-E12                         OBJECT IDENTIFIER ::= { h3cevtModuleRouterType 5 }

h3cevtModuleRt-E14                         OBJECT IDENTIFIER ::= { h3cevtModuleRouterType 6 }

h3cevtModuleRt-Fe1                         OBJECT IDENTIFIER ::= { h3cevtModuleRouterType 7 }

h3cevtModuleRt-E1                          OBJECT IDENTIFIER ::= { h3cevtModuleRouterType 8 }

h3cevtModuleRt-Fe2                         OBJECT IDENTIFIER ::= { h3cevtModuleRouterType 9 }

h3cevtModuleRt-Vi2                         OBJECT IDENTIFIER ::= { h3cevtModuleRouterType 11 }

h3cevtModuleRt-Vi4                         OBJECT IDENTIFIER ::= { h3cevtModuleRouterType 12 }

h3cevtModuleRt-Vi30                        OBJECT IDENTIFIER ::= { h3cevtModuleRouterType 13 }

h3cevtModuleRt-S1b                         OBJECT IDENTIFIER ::= { h3cevtModuleRouterType 14 }

h3cevtModuleRt-Sa2                         OBJECT IDENTIFIER ::= { h3cevtModuleRouterType 15 }

h3cevtModuleRt-As16                        OBJECT IDENTIFIER ::= { h3cevtModuleRouterType 16 }

h3cevtModuleRt-New8as                      OBJECT IDENTIFIER ::= { h3cevtModuleRouterType 17 }

h3cevtModuleRt-Sa1                         OBJECT IDENTIFIER ::= { h3cevtModuleRouterType 18 }

h3cevtModuleRt-Fxs2                        OBJECT IDENTIFIER ::= { h3cevtModuleRouterType 19 }

h3cevtModuleRt-Fxo2                        OBJECT IDENTIFIER ::= { h3cevtModuleRouterType 20 }

h3cevtModuleRt-Em2                         OBJECT IDENTIFIER ::= { h3cevtModuleRouterType 21 }

h3cevtModuleRt-Fxs4                        OBJECT IDENTIFIER ::= { h3cevtModuleRouterType 22 }

h3cevtModuleRt-Fxo4                        OBJECT IDENTIFIER ::= { h3cevtModuleRouterType 23 }

h3cevtModuleRt-Em4                         OBJECT IDENTIFIER ::= { h3cevtModuleRouterType 24 }

h3cevtModuleRt-Sab                         OBJECT IDENTIFIER ::= { h3cevtModuleRouterType 25 }

h3cevtModuleRt-E1vi                        OBJECT IDENTIFIER ::= { h3cevtModuleRouterType 26 }

h3cevtModuleRt-Am12                        OBJECT IDENTIFIER ::= { h3cevtModuleRouterType 27 }

h3cevtModuleRt-Am6                         OBJECT IDENTIFIER ::= { h3cevtModuleRouterType 28 }

h3cevtModuleRt-Ndec                        OBJECT IDENTIFIER ::= { h3cevtModuleRouterType 29 }

h3cevtModuleRt-Newsa2                      OBJECT IDENTIFIER ::= { h3cevtModuleRouterType 30 }

h3cevtModuleRt-Aux                         OBJECT IDENTIFIER ::= { h3cevtModuleRouterType 31 }

h3cevtModuleRt-Console                     OBJECT IDENTIFIER ::= { h3cevtModuleRouterType 32 }

h3cevtModuleRt-Sic-wan                     OBJECT IDENTIFIER ::= { h3cevtModuleRouterType 33 }

h3cevtModuleRt-Sic-1fe                     OBJECT IDENTIFIER ::= { h3cevtModuleRouterType 34 }

h3cevtModuleRt-Sic-1sa                     OBJECT IDENTIFIER ::= { h3cevtModuleRouterType 35 }

h3cevtModuleRt-Sic-3as                     OBJECT IDENTIFIER ::= { h3cevtModuleRouterType 36 }

h3cevtModuleRt-Sic-1e1                     OBJECT IDENTIFIER ::= { h3cevtModuleRouterType 37 }

h3cevtModuleRt-Sic-1t1                     OBJECT IDENTIFIER ::= { h3cevtModuleRouterType 38 }

h3cevtModuleRt-Sic-1bu                     OBJECT IDENTIFIER ::= { h3cevtModuleRouterType 39 }

h3cevtModuleRt-Sic-2bu                     OBJECT IDENTIFIER ::= { h3cevtModuleRouterType 40 }

h3cevtModuleRt-Sic-1bs                     OBJECT IDENTIFIER ::= { h3cevtModuleRouterType 41 }

h3cevtModuleRt-Sic-2bs                     OBJECT IDENTIFIER ::= { h3cevtModuleRouterType 42 }

h3cevtModuleRt-Sic-1am                     OBJECT IDENTIFIER ::= { h3cevtModuleRouterType 43 }

h3cevtModuleRt-Sic-2am                     OBJECT IDENTIFIER ::= { h3cevtModuleRouterType 44 }

h3cevtModuleRt-Sic-1em                     OBJECT IDENTIFIER ::= { h3cevtModuleRouterType 45 }

h3cevtModuleRt-Sic-2em                     OBJECT IDENTIFIER ::= { h3cevtModuleRouterType 46 }

h3cevtModuleRt-Sic-1fxs                    OBJECT IDENTIFIER ::= { h3cevtModuleRouterType 47 }

h3cevtModuleRt-Sic-2fxs                    OBJECT IDENTIFIER ::= { h3cevtModuleRouterType 48 }

h3cevtModuleRt-Sic-1fxo                    OBJECT IDENTIFIER ::= { h3cevtModuleRouterType 49 }

h3cevtModuleRt-Sic-2fxo                    OBJECT IDENTIFIER ::= { h3cevtModuleRouterType 50 }

h3cevtModuleRt-Fcm6                        OBJECT IDENTIFIER ::= { h3cevtModuleRouterType 51 }

h3cevtModuleRt-Sa8                         OBJECT IDENTIFIER ::= { h3cevtModuleRouterType 52 }

h3cevtModuleRt-T11                         OBJECT IDENTIFIER ::= { h3cevtModuleRouterType 53 }

h3cevtModuleRt-T12                         OBJECT IDENTIFIER ::= { h3cevtModuleRouterType 54 }

h3cevtModuleRt-T14                         OBJECT IDENTIFIER ::= { h3cevtModuleRouterType 55 }

h3cevtModuleRt-T1vi                        OBJECT IDENTIFIER ::= { h3cevtModuleRouterType 56 }

h3cevtModuleRt-Fcm4                        OBJECT IDENTIFIER ::= { h3cevtModuleRouterType 57 }

h3cevtModuleRt-Fcm2                        OBJECT IDENTIFIER ::= { h3cevtModuleRouterType 58 }

h3cevtModuleRt-Rtb21ce3                    OBJECT IDENTIFIER ::= { h3cevtModuleRouterType 59 }

h3cevtModuleRt-Ame6                        OBJECT IDENTIFIER ::= { h3cevtModuleRouterType 60 }

h3cevtModuleRt-Ame12                       OBJECT IDENTIFIER ::= { h3cevtModuleRouterType 61 }

h3cevtModuleRt-E11-f                       OBJECT IDENTIFIER ::= { h3cevtModuleRouterType 65 }

h3cevtModuleRt-E12-f                       OBJECT IDENTIFIER ::= { h3cevtModuleRouterType 66 }

h3cevtModuleRt-E14-f                       OBJECT IDENTIFIER ::= { h3cevtModuleRouterType 67 }

h3cevtModuleRt-T11-f                       OBJECT IDENTIFIER ::= { h3cevtModuleRouterType 68 }

h3cevtModuleRt-T12-f                       OBJECT IDENTIFIER ::= { h3cevtModuleRouterType 69 }

h3cevtModuleRt-T14-f                       OBJECT IDENTIFIER ::= { h3cevtModuleRouterType 70 }

h3cevtModuleRt-E11-f-17                    OBJECT IDENTIFIER ::= { h3cevtModuleRouterType 71 }

h3cevtModuleRt-T11-f-17                    OBJECT IDENTIFIER ::= { h3cevtModuleRouterType 72 }

h3cevtModuleRt-Rtb21ct3                    OBJECT IDENTIFIER ::= { h3cevtModuleRouterType 73 }

h3cevtModuleRt-Atmadsl1                    OBJECT IDENTIFIER ::= { h3cevtModuleRouterType 74 }

h3cevtModuleRt-Atmadsl2                    OBJECT IDENTIFIER ::= { h3cevtModuleRouterType 75 }

h3cevtModuleRt-Atm155m                     OBJECT IDENTIFIER ::= { h3cevtModuleRouterType 76 }

h3cevtModuleRt-Ase8                        OBJECT IDENTIFIER ::= { h3cevtModuleRouterType 77 }

h3cevtModuleRt-Ase16                       OBJECT IDENTIFIER ::= { h3cevtModuleRouterType 78 }

h3cevtModuleRt-Sae4                        OBJECT IDENTIFIER ::= { h3cevtModuleRouterType 79 }

h3cevtModuleRt-Sae2                        OBJECT IDENTIFIER ::= { h3cevtModuleRouterType 80 }

h3cevtModuleRt-Atmshdsl1                   OBJECT IDENTIFIER ::= { h3cevtModuleRouterType 90 }

h3cevtModuleRt-Atmshdsl2                   OBJECT IDENTIFIER ::= { h3cevtModuleRouterType 91 }

h3cevtModuleRt-Atmshdsl4                   OBJECT IDENTIFIER ::= { h3cevtModuleRouterType 92 }

h3cevtModuleRt-Atm25m                      OBJECT IDENTIFIER ::= { h3cevtModuleRouterType 93 }

h3cevtModuleRt-Atme3                       OBJECT IDENTIFIER ::= { h3cevtModuleRouterType 94 }

h3cevtModuleRt-Atmt3                       OBJECT IDENTIFIER ::= { h3cevtModuleRouterType 95 }

h3cevtModuleRt-Xdsl-fec                    OBJECT IDENTIFIER ::= { h3cevtModuleRouterType 96 }

h3cevtModuleRt-Xdsl-adsl                   OBJECT IDENTIFIER ::= { h3cevtModuleRouterType 97 }

h3cevtModuleRt-Xdsl-gshdsl                 OBJECT IDENTIFIER ::= { h3cevtModuleRouterType 98 }

h3cevtModuleRt-Xdsl-bri                    OBJECT IDENTIFIER ::= { h3cevtModuleRouterType 99 }

h3cevtModuleRt-Xdsl-scc                    OBJECT IDENTIFIER ::= { h3cevtModuleRouterType 100 }

h3cevtModuleRt-Ge1                         OBJECT IDENTIFIER ::= { h3cevtModuleRouterType 101 }

h3cevtModuleRt-Pos155m                     OBJECT IDENTIFIER ::= { h3cevtModuleRouterType 102 }

h3cevtModuleRt-Cpos                        OBJECT IDENTIFIER ::= { h3cevtModuleRouterType 103 }

h3cevtModuleRt-Fe1op                       OBJECT IDENTIFIER ::= { h3cevtModuleRouterType 104 }

h3cevtModuleRt-Sae8                        OBJECT IDENTIFIER ::= { h3cevtModuleRouterType 105 }

h3cevtModuleRt-Atm155m-mm                  OBJECT IDENTIFIER ::= { h3cevtModuleRouterType 106 }

h3cevtModuleRt-Atm155m-sm                  OBJECT IDENTIFIER ::= { h3cevtModuleRouterType 107 }

h3cevtModuleRt-Atm155m-sml                 OBJECT IDENTIFIER ::= { h3cevtModuleRouterType 108 }

h3cevtModuleRt-Fe1op-sfx                   OBJECT IDENTIFIER ::= { h3cevtModuleRouterType 109 }

h3cevtModuleRt-Fe1op-mfx                   OBJECT IDENTIFIER ::= { h3cevtModuleRouterType 110 }

h3cevtModuleRt-Cpos-t1                     OBJECT IDENTIFIER ::= { h3cevtModuleRouterType 111 }

h3cevtModuleRt-Ge1op                       OBJECT IDENTIFIER ::= { h3cevtModuleRouterType 112 }

h3cevtModuleRt-Ge2op                       OBJECT IDENTIFIER ::= { h3cevtModuleRouterType 113 }

h3cevtModuleRt-Ge2                         OBJECT IDENTIFIER ::= { h3cevtModuleRouterType 114 }

h3cevtModuleRt-Fix-1wan                    OBJECT IDENTIFIER ::= { h3cevtModuleRouterType 115 }

h3cevtModuleRt-Fix-1sae                    OBJECT IDENTIFIER ::= { h3cevtModuleRouterType 116 }

h3cevtModuleRt-Cavium                      OBJECT IDENTIFIER ::= { h3cevtModuleRouterType 117 }

h3cevtModuleRt-Sic1Eth                     OBJECT IDENTIFIER ::= { h3cevtModuleRouterType 118 }

h3cevtModuleRt-atm1ADSLI                   OBJECT IDENTIFIER ::= { h3cevtModuleRouterType 119 }

h3cevtModuleRt-atm2ADSLI                   OBJECT IDENTIFIER ::= { h3cevtModuleRouterType 120 }

h3cevtModuleRt-fix-e11                     OBJECT IDENTIFIER ::= { h3cevtModuleRouterType 121 }

h3cevtModuleRt-fix-t11                     OBJECT IDENTIFIER ::= { h3cevtModuleRouterType 122 }

h3cevtModuleRt-e18-75                      OBJECT IDENTIFIER ::= { h3cevtModuleRouterType 123 }

h3cevtModuleRt-e18-120                     OBJECT IDENTIFIER ::= { h3cevtModuleRouterType 124 }

h3cevtModuleRt-t18                         OBJECT IDENTIFIER ::= { h3cevtModuleRouterType 125 }

h3cevtModuleRt-sic-1vifxs                  OBJECT IDENTIFIER ::= { h3cevtModuleRouterType 126 }

h3cevtModuleRt-sic-1vifxo                  OBJECT IDENTIFIER ::= { h3cevtModuleRouterType 127 }

h3cevtModuleRt-sic-2vifxs                  OBJECT IDENTIFIER ::= { h3cevtModuleRouterType 128 }

h3cevtModuleRt-sic-2vifxo                  OBJECT IDENTIFIER ::= { h3cevtModuleRouterType 129 }

h3cevtModuleRt-xdsl-fec-new                OBJECT IDENTIFIER ::= { h3cevtModuleRouterType 130 }

h3cevtModuleRt-xdsl-sa                     OBJECT IDENTIFIER ::= { h3cevtModuleRouterType 131 }

h3cevtModuleRt-bs4                         OBJECT IDENTIFIER ::= { h3cevtModuleRouterType 132 }

h3cevtModuleRt-ima-8e175                   OBJECT IDENTIFIER ::= { h3cevtModuleRouterType 133 }

h3cevtModuleRt-ima-8e1120                  OBJECT IDENTIFIER ::= { h3cevtModuleRouterType 134 }

h3cevtModuleRt-ima-4e175                   OBJECT IDENTIFIER ::= { h3cevtModuleRouterType 135 }

h3cevtModuleRt-ima-4e1120                  OBJECT IDENTIFIER ::= { h3cevtModuleRouterType 136 }

h3cevtModuleRt-ima-8t1                     OBJECT IDENTIFIER ::= { h3cevtModuleRouterType 137 }

h3cevtModuleRt-ima-4t1                     OBJECT IDENTIFIER ::= { h3cevtModuleRouterType 138 }

h3cevtModuleRt-sic-1t1f                    OBJECT IDENTIFIER ::= { h3cevtModuleRouterType 139 }

h3cevtModuleRt-sic-1e1f                    OBJECT IDENTIFIER ::= { h3cevtModuleRouterType 140 }

h3cevtModuleRt-VG-16fxs                    OBJECT IDENTIFIER ::= { h3cevtModuleRouterType 141 }

h3cevtModuleRt-VG-32fxs                    OBJECT IDENTIFIER ::= { h3cevtModuleRouterType 142 }

h3cevtModuleRt-VG-8fxo                     OBJECT IDENTIFIER ::= { h3cevtModuleRouterType 143 }

h3cevtModuleRt-VG-2fe                      OBJECT IDENTIFIER ::= { h3cevtModuleRouterType 144 }

h3cevtModuleRt-sib                         OBJECT IDENTIFIER ::= { h3cevtModuleRouterType 145 } -- SIB card

h3cevtModuleRt-cie32                       OBJECT IDENTIFIER ::= { h3cevtModuleRouterType 146 } -- 32M SSRAM CIE card

h3cevtModuleRt-cie64                       OBJECT IDENTIFIER ::= { h3cevtModuleRouterType 147 } -- 64M SSRAM CIE card

h3cevtModuleRt-cie96                       OBJECT IDENTIFIER ::= { h3cevtModuleRouterType 148 } -- 96M SSRAM CIE card

h3cevtModuleRt-Fe4                         OBJECT IDENTIFIER ::= { h3cevtModuleRouterType 149 } -- 4FE card

h3cevtModuleRt-fxs4fxo1                    OBJECT IDENTIFIER ::= { h3cevtModuleRouterType 150 } -- 4 Port Foreign Exchange Station and 1 Port Foreign Exchange Office Interface

h3cevtModuleRt-atm1shdsl4wire              OBJECT IDENTIFIER ::= { h3cevtModuleRouterType 151 } -- G.SHDSL 4 wire MIM card, 1 port

h3cevtModuleRt-atmIma4shdsl                OBJECT IDENTIFIER ::= { h3cevtModuleRouterType 152 } -- G.SHDSL 8 wire MIM card, 4 ports

h3cevtModuleRt-ls4                         OBJECT IDENTIFIER ::= { h3cevtModuleRouterType 153 } -- 4 Ports Layer 2 Lanswitch Module

h3cevtModuleRt-ls8                         OBJECT IDENTIFIER ::= { h3cevtModuleRouterType 154 } -- 8 Ports Layer 2 Lanswitch Module

h3cevtModuleRt-ls16                        OBJECT IDENTIFIER ::= { h3cevtModuleRouterType 155 } -- 16 Ports Layer 2 Lanswitch Module

h3cevtModuleRt-sic-adls2plus-isdn          OBJECT IDENTIFIER ::= { h3cevtModuleRouterType 156 } -- ADLS2Plus SIC card, ISDN port

h3cevtModuleRt-sic-adls2plus-pots          OBJECT IDENTIFIER ::= { h3cevtModuleRouterType 157 } -- ADLS2Plus SIC card, POTS port

h3cevtModuleRt-ft3                         OBJECT IDENTIFIER ::= { h3cevtModuleRouterType 158 } -- 1 Port Fractional T3 module

h3cevtModuleRt-ce32                        OBJECT IDENTIFIER ::= { h3cevtModuleRouterType 159 } -- 2 Port Channelized E3 module

h3cevtModuleRt-bsv2                        OBJECT IDENTIFIER ::= { h3cevtModuleRouterType 160 } -- 2 Port BSV module

h3cevtModuleRt-bsv4                        OBJECT IDENTIFIER ::= { h3cevtModuleRouterType 161 } -- 4 Port BSV module

h3cevtModuleRt-RPU                         OBJECT IDENTIFIER ::= { h3cevtModuleRouterType 162 } -- Route processing unit

h3cevtModuleRt-ERPU                        OBJECT IDENTIFIER ::= { h3cevtModuleRouterType 163 } -- Enhanced route processing unit

h3cevtModuleRt-SSL                         OBJECT IDENTIFIER ::= { h3cevtModuleRouterType 164 } -- SSL Encrypt Card

h3cevtModuleRt-NSA                         OBJECT IDENTIFIER ::= { h3cevtModuleRouterType 165 } -- NSA Encrypt Card

--
-- 166 to 199 reserved for other devices
--


--
-- 200 to 399 reserved for normal routers
--

h3cevtModuleRT-SIC-1GEC                    OBJECT IDENTIFIER ::= { h3cevtModuleRouterType 200 } -- 1-Port 10M/100M/1000M COMBO Ethernet Interface SIC Module

h3cevtModuleRT-24FSW                       OBJECT IDENTIFIER ::= { h3cevtModuleRouterType 201 } -- 24-Port 10M/100M and 2-Port 1000BASE-T/1000BASE-X(COMBO) Ethernet L2 Switch Module

h3cevtModuleRT-24FSWP                      OBJECT IDENTIFIER ::= { h3cevtModuleRouterType 202 } -- 24-Port 10M/100M(WITH POE) and 2-Port 1000BASE-T/1000BASE-X(COMBO) Ethernet L2 Switch Module

h3cevtModuleRT-16FSW                       OBJECT IDENTIFIER ::= { h3cevtModuleRouterType 203 } -- 16-Port 10M/100M Ethernet L2 Switch Module

h3cevtModuleRT-16FSWP                      OBJECT IDENTIFIER ::= { h3cevtModuleRouterType 204 } -- 16-Port 10M/100M(WITH POE) Ethernet L2 Switch Module

h3cevtModuleRT-1VE1                        OBJECT IDENTIFIER ::= { h3cevtModuleRouterType 205 } -- 1-Port Voice E1 Module

h3cevtModuleRT-1VT1                        OBJECT IDENTIFIER ::= { h3cevtModuleRouterType 206 } -- 1-Port Voice T1 Module

h3cevtModuleRT-2VE1                        OBJECT IDENTIFIER ::= { h3cevtModuleRouterType 207 } -- 2-Port Voice E1 Module

h3cevtModuleRT-2VT1                        OBJECT IDENTIFIER ::= { h3cevtModuleRouterType 208 } -- 2-Port Voice T1 Module

h3cevtModuleRT-SIC-4FSW                    OBJECT IDENTIFIER ::= { h3cevtModuleRouterType 209 } -- 4-Port 10M/100M Ethernet L2 Switch Module (RJ45)

h3cevtModuleRT-SIC-4FSWP                   OBJECT IDENTIFIER ::= { h3cevtModuleRouterType 210 } -- 4-Port 10M/100M Ethernet L2 Switch Module(RJ45,WITH POE)

h3cevtModuleRT-DSIC-9FSW                   OBJECT IDENTIFIER ::= { h3cevtModuleRouterType 211 } -- 9-Port 10M/100M Ethernet L2 Switch Module(RJ45)

h3cevtModuleRT-DSIC-9FSWP                  OBJECT IDENTIFIER ::= { h3cevtModuleRouterType 212 } -- 9-Port 10M/100M Ethernet L2 Switch Module(RJ45,WITH POE)

h3cevtModuleRT-SIC-1VE1                    OBJECT IDENTIFIER ::= { h3cevtModuleRouterType 213 } -- 1-Port Voice E1 SIC Interface Module

h3cevtModuleRT-SIC-1VT1                    OBJECT IDENTIFIER ::= { h3cevtModuleRouterType 214 } -- 1-Port Voice T1 SIC Interface Module

h3cevtModuleRT-VCPM                        OBJECT IDENTIFIER ::= { h3cevtModuleRouterType 215 } -- Voice Co-Processing Module

h3cevtModuleRT-VPM                         OBJECT IDENTIFIER ::= { h3cevtModuleRouterType 216 } -- 32-Channels Voice Processing Module

h3cevtModuleRT-VPMA                        OBJECT IDENTIFIER ::= { h3cevtModuleRouterType 217 } -- 16-Channels Voice Processing Module

h3cevtModuleRT-VPMB                        OBJECT IDENTIFIER ::= { h3cevtModuleRouterType 218 } -- 8-Channels Voice Processing Module

h3cevtModuleRT-VPMC                        OBJECT IDENTIFIER ::= { h3cevtModuleRouterType 219 } -- 24-Channels Voice Processing Module

h3cevtModuleRt-fe18-75                     OBJECT IDENTIFIER ::= { h3cevtModuleRouterType 220 } -- 8 Port FE1(75 O) module

h3cevtModuleRt-fe18-120                    OBJECT IDENTIFIER ::= { h3cevtModuleRouterType 221 } -- 8 Port FE1(120 O) module

h3cevtModuleRt-ft18                        OBJECT IDENTIFIER ::= { h3cevtModuleRouterType 222 } -- 8 Port FT1 module

h3cevtModuleRt-CF                          OBJECT IDENTIFIER ::= { h3cevtModuleRouterType 223 } -- Compact Flash Card

h3cevtModuleRt-bsv2-v2                     OBJECT IDENTIFIER ::= { h3cevtModuleRouterType 224 } -- 2 Port BSV Version 2

h3cevtModuleRt-e1vi1-v2                    OBJECT IDENTIFIER ::= { h3cevtModuleRouterType 225 } -- E1VI Version 2

h3cevtModuleRt-e1vi2                       OBJECT IDENTIFIER ::= { h3cevtModuleRouterType 226 } -- 2 Port E1VI

h3cevtModuleRt-t1vi1-v2                    OBJECT IDENTIFIER ::= { h3cevtModuleRouterType 227 } -- T1VI Version 2

h3cevtModuleRt-t1vi2                       OBJECT IDENTIFIER ::= { h3cevtModuleRouterType 228 } -- 2 Port T1VI

h3cevtModuleRt-osm                         OBJECT IDENTIFIER ::= { h3cevtModuleRouterType 229 } -- Open Service Module

h3cevtModuleRt-sd707                       OBJECT IDENTIFIER ::= { h3cevtModuleRouterType 230 } -- Encryption Accelerator

h3cevtModuleRt-dm-epri                     OBJECT IDENTIFIER ::= { h3cevtModuleRouterType 231 } -- E1 Pri Digital Modem

h3cevtModuleRt-dm-tpri                     OBJECT IDENTIFIER ::= { h3cevtModuleRouterType 232 } -- T1 Pri Digital Modem

h3cevtModuleRt-ERPU-H                      OBJECT IDENTIFIER ::= { h3cevtModuleRouterType 233 } -- Enhanced route processing unit with only one optic GE interface

h3cevtModuleRT-SIC-1BSV                    OBJECT IDENTIFIER ::= { h3cevtModuleRouterType 234 } -- 1-Port Bri S/T VoiceInterface SIC Module

h3cevtModuleRT-SIC-2BSV                    OBJECT IDENTIFIER ::= { h3cevtModuleRouterType 235 } -- 2-Port Bri S/T VoiceInterface SIC Module

h3cevtModuleRt-gbe8                        OBJECT IDENTIFIER ::= { h3cevtModuleRouterType 236 } -- 8-Port Gigabit Ethernet interface card

h3cevtModuleRt-gbe4                        OBJECT IDENTIFIER ::= { h3cevtModuleRouterType 237 } -- 4-Port Gigabit Ethernet interface card

h3cevtModuleRt-cpos2-v2                    OBJECT IDENTIFIER ::= { h3cevtModuleRouterType 238 } -- 2-Port Channelized Low speed POS interface card

h3cevtModuleRt-cpos1-v2                    OBJECT IDENTIFIER ::= { h3cevtModuleRouterType 239 } -- 1-Port Channelized Low speed POS interface card

h3cevtModuleRt-oap                         OBJECT IDENTIFIER ::= { h3cevtModuleRouterType 240 } -- Open Application Platform

h3cevtModuleRT-48FSWP                      OBJECT IDENTIFIER ::= { h3cevtModuleRouterType 241 } -- 46-Port 10M/100M(With PoE) and 2-Port 1000BASE-T(With PoE) Ethernet L2 Switch Module

h3cevtModuleRT-48FSW                       OBJECT IDENTIFIER ::= { h3cevtModuleRouterType 242 } -- 46-Port 10M/100M and 2-Port 1000BASE-T Ethernet L2 Switch Module

h3cevtModuleRT-ASM                         OBJECT IDENTIFIER ::= { h3cevtModuleRouterType 243 } -- Anti-virus Security Module

h3cevtModuleRT-SIC-1FEF                    OBJECT IDENTIFIER ::= { h3cevtModuleRouterType 244 } -- 1-Port 100M SFP Interface SIC Module

h3cevtModuleRT-XMIM-24FSW                  OBJECT IDENTIFIER ::= { h3cevtModuleRouterType 245 } -- 24-Port 10M/100MBASE-TX Ethernet L2 Switch Interface XMIM-Module

h3cevtModuleRT-WLAN-AG-1RADIO              OBJECT IDENTIFIER ::= { h3cevtModuleRouterType 246 } -- Mini PCI Interface 802.11ag Radio Frequency Adapter Card

h3cevtModuleRT-1CE3                        OBJECT IDENTIFIER ::= { h3cevtModuleRouterType 247 } -- 1-port E3/CE3/FE3 Compatible Interface Module,(M)

h3cevtModuleRT-XMIM-16FSW                  OBJECT IDENTIFIER ::= { h3cevtModuleRouterType 248 } -- 16-Port 10M/100MBASE-TX Ethernet L2 Switch Interface XMIM-Module

h3cevtModuleRT-OAPS                        OBJECT IDENTIFIER ::= { h3cevtModuleRouterType 249 } -- Open Application System-Smart

h3cevtModuleRT-NAM                         OBJECT IDENTIFIER ::= { h3cevtModuleRouterType 250 } -- Network Analysis Module

h3cevtModuleRT-RPE-X1                      OBJECT IDENTIFIER ::= { h3cevtModuleRouterType 251 } -- Route Processing Engine

h3cevtModuleRT-FIP-100                     OBJECT IDENTIFIER ::= { h3cevtModuleRouterType 252 } -- Flexible Interface Platform-100

h3cevtModuleRT-FIP-200                     OBJECT IDENTIFIER ::= { h3cevtModuleRouterType 253 } -- Flexible Interface Platform-200

h3cevtModuleRT-SIC-8AS                     OBJECT IDENTIFIER ::= { h3cevtModuleRouterType 254 } -- 8-Port Asynchronous Serial

h3cevtModuleRT-WAAM                        OBJECT IDENTIFIER ::= { h3cevtModuleRouterType 255 } -- WAN Application Acceleration Module

h3cevtModuleRt-msp4p-OC3c                  OBJECT IDENTIFIER ::= { h3cevtModuleRouterType 256 } -- 4 Port Multi-Speed POS Interface Module (OC-3c Mode)

h3cevtModuleRt-1pos-oc48                   OBJECT IDENTIFIER ::= { h3cevtModuleRouterType 257 } -- 1 Port Super-Speed POS Interface Card

h3cevtModuleRt-xgbe                        OBJECT IDENTIFIER ::= { h3cevtModuleRouterType 258 } -- 1-Port 10GBASE-R/W Ethernet Optical Interface Card

h3cevtModuleRT-EADM                        OBJECT IDENTIFIER ::= { h3cevtModuleRouterType 259 } -- EAD Integrated Module

h3cevtModuleRT-VCM                         OBJECT IDENTIFIER ::= { h3cevtModuleRouterType 260 } -- Voice Convergence Module

h3cevtModuleRT-SIC-2FXS1FXO                OBJECT IDENTIFIER ::= { h3cevtModuleRouterType 261 } -- 2FXS+1FXO Interface SIC-Module

h3cevtModuleRT-8FXS8FXO                    OBJECT IDENTIFIER ::= { h3cevtModuleRouterType 262 } -- 8FXS+8FXO Interface Module

h3cevtModuleRT-16FXS                       OBJECT IDENTIFIER ::= { h3cevtModuleRouterType 263 } -- 16-port FXS Interface Module

h3cevtModuleRT-OAPS-ICM                    OBJECT IDENTIFIER ::= { h3cevtModuleRouterType 264 } -- OAPS Information Communication Module

h3cevtModuleRT-OAP-ICM                     OBJECT IDENTIFIER ::= { h3cevtModuleRouterType 265 } -- OAP Information Communication Module

h3cevtModuleRT-8fe                         OBJECT IDENTIFIER ::= { h3cevtModuleRouterType 266 } -- 8-Port 100M Ethernet Electrical Interface Module

h3cevtModuleRT-4gbp                        OBJECT IDENTIFIER ::= { h3cevtModuleRouterType 267 } -- 4-Port GigaBit Ethernet Optical Interface Module(SFP)

h3cevtModuleRT-MPU-G2                      OBJECT IDENTIFIER ::= { h3cevtModuleRouterType 268 } -- Main Processor Unit

h3cevtModuleRT-OAPS-OCE                    OBJECT IDENTIFIER ::= { h3cevtModuleRouterType 269 } -- OAPS Office Communication Engine

h3cevtModuleRT-OAP-OCE                     OBJECT IDENTIFIER ::= { h3cevtModuleRouterType 270 } -- OAP Office Communication Engine

h3cevtModuleRT-OAPS-ICE                    OBJECT IDENTIFIER ::= { h3cevtModuleRouterType 271 } -- OAPS Information Communication Engine

h3cevtModuleRT-OAP-ICE                     OBJECT IDENTIFIER ::= { h3cevtModuleRouterType 272 } -- OAP Information Communication Module

h3cevtModuleRT-SIC-16AS                    OBJECT IDENTIFIER ::= { h3cevtModuleRouterType 273 } -- 16-Port Asynchronous Serial

h3cevtModuleRT-SPE-FWM                     OBJECT IDENTIFIER ::= { h3cevtModuleRouterType 274 } -- Gigabit Firewall Module

h3cevtModuleRT-cls2p                       OBJECT IDENTIFIER ::= { h3cevtModuleRouterType 275 } -- 2 Port Channelized 155M POS to E3/T3 Interface Module

h3cevtModuleRT-cls1p                       OBJECT IDENTIFIER ::= { h3cevtModuleRouterType 276 } -- 1 Port Channelized 155M POS to E3/T3 Interface Module

h3cevtModuleRT-SIC-2E1-F                   OBJECT IDENTIFIER ::= { h3cevtModuleRouterType 277 } -- 2-Port Fractional E1 Interface SIC-Module

h3cevtModuleRT-SIC-1E1-F-V2                OBJECT IDENTIFIER ::= { h3cevtModuleRouterType 278 } -- 1-Port Fractional E1 Interface SIC-Module

h3cevtModuleRT-MCU                         OBJECT IDENTIFIER ::= { h3cevtModuleRouterType 279 } -- Main Control Unit

h3cevtModuleRT-ACU                         OBJECT IDENTIFIER ::= { h3cevtModuleRouterType 280 } -- Access Control Unit

h3cevtModuleRT-1ATM-OC3                    OBJECT IDENTIFIER ::= { h3cevtModuleRouterType 281 } -- 1-Port Asynchronous Transfer Mode OC3 Board

h3cevtModuleRT-RSE-X1                      OBJECT IDENTIFIER ::= { h3cevtModuleRouterType 282 } -- Main Processing Unit With XAUI Switch

h3cevtModuleRT-FIP-210                     OBJECT IDENTIFIER ::= { h3cevtModuleRouterType 283 } -- Multi-core CPU Line Processing Board with 2 Combo GE Ports

h3cevtModuleRT-1expa                       OBJECT IDENTIFIER ::= { h3cevtModuleRouterType 284 } -- 1 Port Ten Gigabit Interface Module

h3cevtModuleRT-WLAN-SIC-N-1RADIO           OBJECT IDENTIFIER ::= { h3cevtModuleRouterType 285 } -- 1 wlan-radio 802.11n sic Interface Board

h3cevtModuleRT-WLAN-SIC-BG-1RADIO          OBJECT IDENTIFIER ::= { h3cevtModuleRouterType 286 } -- 1 wlan-radio 802.11b/g sic Interface Board

h3cevtModuleRT-al2p                        OBJECT IDENTIFIER ::= { h3cevtModuleRouterType 287 } -- 2 Port 155M ATM Interface Module

h3cevtModuleRT-msp2p-OC3c                  OBJECT IDENTIFIER ::= { h3cevtModuleRouterType 288 } -- 2-Port Multi-speed POS Interface Module (OC-3c Mode)

h3cevtModuleRT-8gbp                        OBJECT IDENTIFIER ::= { h3cevtModuleRouterType 289 } -- 8-Port GigaBit Ethernet Optical Interface Module(SFP)

h3cevtModuleRT-SIC-EPON                    OBJECT IDENTIFIER ::= { h3cevtModuleRouterType 290 } -- 1-Port Ethernet Passive Optical Network SIC Card(SFF)

h3cevtModuleRT-SIC-3G-GSM-H3               OBJECT IDENTIFIER ::= { h3cevtModuleRouterType 291 } -- 3G Wireless WAN Interface SIC Module Supporting GPRS/EDGE/UMTS/HSDPA

h3cevtModuleRT-msp2p-OC12c                 OBJECT IDENTIFIER ::= { h3cevtModuleRouterType 292 } -- 2-Port Multi-speed POS Interface Module (OC-12c Mode)

h3cevtModuleRt-msp4p-OC12c                 OBJECT IDENTIFIER ::= { h3cevtModuleRouterType 293 } -- 4-Port Multi-Speed POS Interface Module (OC-12c Mode)

h3cevtModuleRt-al1p                        OBJECT IDENTIFIER ::= { h3cevtModuleRouterType 294 } -- 1-Port 155M ATM Interface Module

h3cevtModuleRt-OAP-100                     OBJECT IDENTIFIER ::= { h3cevtModuleRouterType 295 } -- Open Application Platform Module

--
-- 400 to 599 reserved for security routers
--
h3cevtModuleRt-IPU                         OBJECT IDENTIFIER ::= { h3cevtModuleRouterType 400 } -- IPS Processing Unit

h3cevtModuleRt-MIM2GEBE-PCIE               OBJECT IDENTIFIER ::= { h3cevtModuleRouterType 401 } -- 2-port UTM GigabitEthernet Interface Module

h3cevtModuleRt-HIM12GE-PCIE                OBJECT IDENTIFIER ::= { h3cevtModuleRouterType 402 } -- 12-port GigabitEthernet Interface Module

h3cevtModuleRt-HIM2XGE-PCIE                OBJECT IDENTIFIER ::= { h3cevtModuleRouterType 403 } -- 2-port Ten-GigabitEthernet Interface Module

h3cevtModuleRt-IPU-T1000-M                 OBJECT IDENTIFIER ::= { h3cevtModuleRouterType 404 } -- IPS Processing Unit for T1000-M Mainboard Module

h3cevtModuleRt-IPU-GX4C                    OBJECT IDENTIFIER ::= { h3cevtModuleRouterType 405 } -- 4 Port Gigabit Fiber Module

h3cevtModuleRt-IPU-GT4C                    OBJECT IDENTIFIER ::= { h3cevtModuleRouterType 406 } -- 4 Port 1000BASE-T Module

h3cevtModuleRt-RPU-IAG2000-A               OBJECT IDENTIFIER ::= { h3cevtModuleRouterType 407 } -- Intelligence Application Gateway Module

h3cevtModuleRt-RPU-AFD1000-A               OBJECT IDENTIFIER ::= { h3cevtModuleRouterType 408 } -- Anomaly Flow Detector Module

h3cevtModuleRt-RPU-F5000-A                 OBJECT IDENTIFIER ::= { h3cevtModuleRouterType 409 } -- Advanced Firewall Module

h3cevtModuleRt-ACG-8800S3-MPU              OBJECT IDENTIFIER ::= { h3cevtModuleRouterType 410 } -- Main Control Unit,with 24 1000BASE-X/100BASE-FX Optical Ports,including 8 Combo Ports,SFP Req

h3cevtModuleRt-T5000S3-MPU                 OBJECT IDENTIFIER ::= { h3cevtModuleRouterType 411 } -- Main Control Unit,with 24 1000BASE-X/100BASE-FX Optical Ports,including 8 Combo Ports,SFP Req

h3cevtModuleRt-NS21S2MSPB0                 OBJECT IDENTIFIER ::= { h3cevtModuleRouterType 412 } -- Multi Service Processing Module

h3cevtModuleRt-NS11S2MSPB0                 OBJECT IDENTIFIER ::= { h3cevtModuleRouterType 413 } -- Multi Service Processing Module

h3cevtModuleRt-NSQ1WLAN                    OBJECT IDENTIFIER ::= { h3cevtModuleRouterType 414 } -- Dual-Band,Multi-Mode 802.11a/b/g Wireless LAN card

--
-- 600 to 799 reserved for voice routers
--

h3cevtModuleRt-VG-8fxs                     OBJECT IDENTIFIER ::= { h3cevtModuleRouterType 600 } -- 8 Port Foreign Exchange Station module

h3cevtModuleRt-VG-24fxs                    OBJECT IDENTIFIER ::= { h3cevtModuleRouterType 601 } -- 24 Port Foreign Exchange Station module

h3cevtModuleRt-VG-24fxs24fxo               OBJECT IDENTIFIER ::= { h3cevtModuleRouterType 602 } -- 24 Port Foreign Exchange Station and 24 Port Foreign Exchange Office module

h3cevtModuleRt-VG-MPU                      OBJECT IDENTIFIER ::= { h3cevtModuleRouterType 603 } -- Media Processing Unit


-- h3cevtModuleSwitchType cards are slot-cards specific to the Switch.
h3cevtModuleSwitchType  OBJECT IDENTIFIER ::= { h3cevtModule 4 }

--h3cevtModuleNULL(0),
h3cevtModuleSw-10OR100M                    OBJECT IDENTIFIER ::= { h3cevtModuleSwitchType 1 }

h3cevtModuleSw-1000BASE-LX-SM              OBJECT IDENTIFIER ::= { h3cevtModuleSwitchType 2 }

h3cevtModuleSw-1000BASE-SX-MM              OBJECT IDENTIFIER ::= { h3cevtModuleSwitchType 3 }

h3cevtModuleSw-1000BASE-TX                 OBJECT IDENTIFIER ::= { h3cevtModuleSwitchType 4 }

h3cevtModuleSw-100M-SINGLEMODE-FX          OBJECT IDENTIFIER ::= { h3cevtModuleSwitchType 5 }

h3cevtModuleSw-100M-MULTIMODE-FX           OBJECT IDENTIFIER ::= { h3cevtModuleSwitchType 6 }

h3cevtModuleSw-100M-100BASE-TX             OBJECT IDENTIFIER ::= { h3cevtModuleSwitchType 7 }

h3cevtModuleSw-100M-HUB                    OBJECT IDENTIFIER ::= { h3cevtModuleSwitchType 8 }

h3cevtModuleSw-VDSL                        OBJECT IDENTIFIER ::= { h3cevtModuleSwitchType 9 }

h3cevtModuleSw-STACK                       OBJECT IDENTIFIER ::= { h3cevtModuleSwitchType 10 }

h3cevtModuleSw-1000BASE-ZENITH-FX          OBJECT IDENTIFIER ::= { h3cevtModuleSwitchType 11 }

h3cevtModuleSw-1000BASE-LONG-FX            OBJECT IDENTIFIER ::= { h3cevtModuleSwitchType 12 }

h3cevtModuleSw-ADSL                        OBJECT IDENTIFIER ::= { h3cevtModuleSwitchType 13 }

h3cevtModuleSw-4T10OR100-4FX100SM          OBJECT IDENTIFIER ::= { h3cevtModuleSwitchType 14 }

h3cevtModuleSw-4T10OR100-4FX100MM          OBJECT IDENTIFIER ::= { h3cevtModuleSwitchType 15 }

h3cevtModuleSw-VSPL                        OBJECT IDENTIFIER ::= { h3cevtModuleSwitchType 16 }

h3cevtModuleSw-ASPL                        OBJECT IDENTIFIER ::= { h3cevtModuleSwitchType 17 }

h3cevtModuleSw-1000M-SFP                   OBJECT IDENTIFIER ::= { h3cevtModuleSwitchType 18 }

h3cevtModuleSw-LS82O2CM                    OBJECT IDENTIFIER ::= { h3cevtModuleSwitchType 19 }

h3cevtModuleSw-LS82P2CM                    OBJECT IDENTIFIER ::= { h3cevtModuleSwitchType 20 }

h3cevtModuleSw-LS82O4GM                    OBJECT IDENTIFIER ::= { h3cevtModuleSwitchType 21 }

h3cevtModuleSw-LS82GB4C                    OBJECT IDENTIFIER ::= { h3cevtModuleSwitchType 22 }

h3cevtModuleSw-LS82GT4C                    OBJECT IDENTIFIER ::= { h3cevtModuleSwitchType 23 }

h3cevtModuleSw-LS82ST4C                    OBJECT IDENTIFIER ::= { h3cevtModuleSwitchType 24 }

h3cevtModuleSw-BOARD-LS82DSPU              OBJECT IDENTIFIER ::= { h3cevtModuleSwitchType 25 }

h3cevtModuleSw-BOARD-LS81GP8U              OBJECT IDENTIFIER ::= { h3cevtModuleSwitchType 26 }

h3cevtModuleSw-BOARD-LS82GT20              OBJECT IDENTIFIER ::= { h3cevtModuleSwitchType 27 }

h3cevtModuleSw-BOARD-LS82FE48              OBJECT IDENTIFIER ::= { h3cevtModuleSwitchType 28 }

h3cevtModuleSw-LS82T24B                    OBJECT IDENTIFIER ::= { h3cevtModuleSwitchType 29 }

h3cevtModuleSw-LSB1SRPA                    OBJECT IDENTIFIER ::= { h3cevtModuleSwitchType 30 }

h3cevtModuleSw-LSB1FT48A                   OBJECT IDENTIFIER ::= { h3cevtModuleSwitchType 31 }

h3cevtModuleSw-LSB1FT48B                   OBJECT IDENTIFIER ::= { h3cevtModuleSwitchType 32 }

h3cevtModuleSw-LSB1F48GA                   OBJECT IDENTIFIER ::= { h3cevtModuleSwitchType 33 }

h3cevtModuleSw-LSB1F48GB                   OBJECT IDENTIFIER ::= { h3cevtModuleSwitchType 34 }

h3cevtModuleSw-LSB1FP20A                   OBJECT IDENTIFIER ::= { h3cevtModuleSwitchType 35 }

h3cevtModuleSw-LSB1FP20B                   OBJECT IDENTIFIER ::= { h3cevtModuleSwitchType 36 }

h3cevtModuleSw-FT48A                       OBJECT IDENTIFIER ::= { h3cevtModuleSwitchType 37 }

h3cevtModuleSw-GP4U                        OBJECT IDENTIFIER ::= { h3cevtModuleSwitchType 38 }

h3cevtModuleSw-GP2U                        OBJECT IDENTIFIER ::= { h3cevtModuleSwitchType 39 }

h3cevtModuleSw-TGX1A                       OBJECT IDENTIFIER ::= { h3cevtModuleSwitchType 40 }

h3cevtModuleSw-1000BASE-LX-SM-IR-SC        OBJECT IDENTIFIER ::= { h3cevtModuleSwitchType 41 }

h3cevtModuleSw-1000BASE-SX-MM-SR-SC        OBJECT IDENTIFIER ::= { h3cevtModuleSwitchType 42 }

h3cevtModuleSw-1000BASE-T-RJ45             OBJECT IDENTIFIER ::= { h3cevtModuleSwitchType 43 }

h3cevtModuleSw-100BASE-FX-SM-IR-SC         OBJECT IDENTIFIER ::= { h3cevtModuleSwitchType 44 }

h3cevtModuleSw-100BASE-FX-MM-SR-SC         OBJECT IDENTIFIER ::= { h3cevtModuleSwitchType 45 }

h3cevtModuleSw-GIGA-STACK-1M-PC            OBJECT IDENTIFIER ::= { h3cevtModuleSwitchType 46 }

h3cevtModuleSw-1000BASE-LX-SM-VLR-LC       OBJECT IDENTIFIER ::= { h3cevtModuleSwitchType 47 }

h3cevtModuleSw-1000BASE-LX-SM-LR-LC        OBJECT IDENTIFIER ::= { h3cevtModuleSwitchType 48 }

h3cevtModuleSw-100BASE-FX-SM-LR-SC         OBJECT IDENTIFIER ::= { h3cevtModuleSwitchType 49 }

h3cevtModuleSw-1000BASE-X-GBIC             OBJECT IDENTIFIER ::= { h3cevtModuleSwitchType 50 }

h3cevtModuleSw-100M-SINGLEMODE-FX-LC       OBJECT IDENTIFIER ::= { h3cevtModuleSwitchType 51 }

h3cevtModuleSw-100M-MULTIMODE-FX-LC        OBJECT IDENTIFIER ::= { h3cevtModuleSwitchType 52 }

h3cevtModuleSw-1000BASE-4SFP               OBJECT IDENTIFIER ::= { h3cevtModuleSwitchType 53 }

h3cevtModuleSw-1000BASE-4GBIC              OBJECT IDENTIFIER ::= { h3cevtModuleSwitchType 54 }

h3cevtModuleSw-1000BASE-FIXED-4SFP         OBJECT IDENTIFIER ::= { h3cevtModuleSwitchType 55 }

h3cevtModuleSw-1000BASE-FIXED-4GBIC        OBJECT IDENTIFIER ::= { h3cevtModuleSwitchType 56 }

h3cevtModuleSw-LSB1GP12A                   OBJECT IDENTIFIER ::= { h3cevtModuleSwitchType 57 }

h3cevtModuleSw-LSB1GP12B                   OBJECT IDENTIFIER ::= { h3cevtModuleSwitchType 58 }

h3cevtModuleSw-LSB1TGX1A                   OBJECT IDENTIFIER ::= { h3cevtModuleSwitchType 59 }

h3cevtModuleSw-LSB1TGX1B                   OBJECT IDENTIFIER ::= { h3cevtModuleSwitchType 60 }

h3cevtModuleSw-LSB1P4G8A                   OBJECT IDENTIFIER ::= { h3cevtModuleSwitchType 61 }

h3cevtModuleSw-LSB1P4G8B                   OBJECT IDENTIFIER ::= { h3cevtModuleSwitchType 62 }

h3cevtModuleSw-LSB1A4G8A                   OBJECT IDENTIFIER ::= { h3cevtModuleSwitchType 63 }

h3cevtModuleSw-LSB1A4G8B                   OBJECT IDENTIFIER ::= { h3cevtModuleSwitchType 64 }

h3cevtModuleSw-FT48C                       OBJECT IDENTIFIER ::= { h3cevtModuleSwitchType 65 }

h3cevtModuleSw-FP20                        OBJECT IDENTIFIER ::= { h3cevtModuleSwitchType 66 }

h3cevtModuleSw-BOARD-LS81FT48              OBJECT IDENTIFIER ::= { h3cevtModuleSwitchType 67 }

h3cevtModuleSw-BOARD-LS81GB8U              OBJECT IDENTIFIER ::= { h3cevtModuleSwitchType 68 }

h3cevtModuleSw-BOARD-LS81GT8U              OBJECT IDENTIFIER ::= { h3cevtModuleSwitchType 69 }

h3cevtModuleSw-BOARD-LS81FS24              OBJECT IDENTIFIER ::= { h3cevtModuleSwitchType 70 }

h3cevtModuleSw-BOARD-LS81FM24              OBJECT IDENTIFIER ::= { h3cevtModuleSwitchType 71 }

h3cevtModuleSw-BOARD-LS82GP20              OBJECT IDENTIFIER ::= { h3cevtModuleSwitchType 72 }

h3cevtModuleSw-LSB1SRPB                    OBJECT IDENTIFIER ::= { h3cevtModuleSwitchType 73 }

h3cevtModuleSw-LSB1F32GA                   OBJECT IDENTIFIER ::= { h3cevtModuleSwitchType 74 }

h3cevtModuleSw-LSB1F32GB                   OBJECT IDENTIFIER ::= { h3cevtModuleSwitchType 75 }

h3cevtModuleSw-LSB2FT48A                   OBJECT IDENTIFIER ::= { h3cevtModuleSwitchType 76 }

h3cevtModuleSw-LSB2FT48B                   OBJECT IDENTIFIER ::= { h3cevtModuleSwitchType 77 }

h3cevtModuleSw-LSB1GT12A                   OBJECT IDENTIFIER ::= { h3cevtModuleSwitchType 78 }

h3cevtModuleSw-LSB1GT12B                   OBJECT IDENTIFIER ::= { h3cevtModuleSwitchType 79 }

h3cevtModuleSw-PC4U                        OBJECT IDENTIFIER ::= { h3cevtModuleSwitchType 80 }

h3cevtModuleSw-FT32A                       OBJECT IDENTIFIER ::= { h3cevtModuleSwitchType 81 }

h3cevtModuleSw-GT4U                        OBJECT IDENTIFIER ::= { h3cevtModuleSwitchType 82 }

h3cevtModuleSw-BOARD-LS83FP20A             OBJECT IDENTIFIER ::= { h3cevtModuleSwitchType 83 }

h3cevtModuleSw-BOARD-LS82HGMU              OBJECT IDENTIFIER ::= { h3cevtModuleSwitchType 84 }

h3cevtModuleSw-LSB1GP8TB                   OBJECT IDENTIFIER ::= { h3cevtModuleSwitchType 85 }

h3cevtModuleSw-LSB1GP8TC                   OBJECT IDENTIFIER ::= { h3cevtModuleSwitchType 86 }

h3cevtModuleSw-LSB1GT8PB                   OBJECT IDENTIFIER ::= { h3cevtModuleSwitchType 87 }

h3cevtModuleSw-LSB1GT8PC                   OBJECT IDENTIFIER ::= { h3cevtModuleSwitchType 88 }

h3cevtModuleSw-LSB1FT48C                   OBJECT IDENTIFIER ::= { h3cevtModuleSwitchType 89 }

h3cevtModuleSw-LSB1FP20C                   OBJECT IDENTIFIER ::= { h3cevtModuleSwitchType 90 }

h3cevtModuleSw-LSB1F32GC                   OBJECT IDENTIFIER ::= { h3cevtModuleSwitchType 91 }

h3cevtModuleSw-LSB1GT12C                   OBJECT IDENTIFIER ::= { h3cevtModuleSwitchType 92 }

h3cevtModuleSw-LSB1GP12C                   OBJECT IDENTIFIER ::= { h3cevtModuleSwitchType 93 }

h3cevtModuleSw-LSB1P4G8C                   OBJECT IDENTIFIER ::= { h3cevtModuleSwitchType 94 }

h3cevtModuleSw-LSB1TGX1C                   OBJECT IDENTIFIER ::= { h3cevtModuleSwitchType 95 }

h3cevtModuleSw-LSB1GT24B                   OBJECT IDENTIFIER ::= { h3cevtModuleSwitchType 96 }

h3cevtModuleSw-LSB1GT24C                   OBJECT IDENTIFIER ::= { h3cevtModuleSwitchType 97 }

h3cevtModuleSw-LSB1GP24B                   OBJECT IDENTIFIER ::= { h3cevtModuleSwitchType 98 }

h3cevtModuleSw-LSB1GP24C                   OBJECT IDENTIFIER ::= { h3cevtModuleSwitchType 99 }

h3cevtModuleSw-LSB1XP2B                    OBJECT IDENTIFIER ::= { h3cevtModuleSwitchType 100 }

h3cevtModuleSw-LSB1XP2C                    OBJECT IDENTIFIER ::= { h3cevtModuleSwitchType 101 }

h3cevtModuleSw-LSB1GV48B                   OBJECT IDENTIFIER ::= { h3cevtModuleSwitchType 102 }

h3cevtModuleSw-LSB1GV48C                   OBJECT IDENTIFIER ::= { h3cevtModuleSwitchType 103 }

h3cevtModuleSw-LSB1SRPC                    OBJECT IDENTIFIER ::= { h3cevtModuleSwitchType 104 }

h3cevtModuleSw-LSB1SRP1N0                  OBJECT IDENTIFIER ::= { h3cevtModuleSwitchType 105 }

h3cevtModuleSw-LSB1SRP1N1                  OBJECT IDENTIFIER ::= { h3cevtModuleSwitchType 106 }

h3cevtModuleSw-LSB1SRP1N2                  OBJECT IDENTIFIER ::= { h3cevtModuleSwitchType 107 }

h3cevtModuleSw-GT24                        OBJECT IDENTIFIER ::= { h3cevtModuleSwitchType 108 }

h3cevtModuleSw-GP24                        OBJECT IDENTIFIER ::= { h3cevtModuleSwitchType 109 }

h3cevtModuleSw-XP2                         OBJECT IDENTIFIER ::= { h3cevtModuleSwitchType 110 }

h3cevtModuleSw-GV48                        OBJECT IDENTIFIER ::= { h3cevtModuleSwitchType 111 }

h3cevtModuleSw-LSG1GP8U                    OBJECT IDENTIFIER ::= { h3cevtModuleSwitchType 112 }

h3cevtModuleSw-LSG1GT8U                    OBJECT IDENTIFIER ::= { h3cevtModuleSwitchType 113 }

h3cevtModuleSw-LSG1TG1U                    OBJECT IDENTIFIER ::= { h3cevtModuleSwitchType 114 }

h3cevtModuleSw-LSG1TD1U                    OBJECT IDENTIFIER ::= { h3cevtModuleSwitchType 115 }

h3cevtModuleSw-LSB2FT48C                   OBJECT IDENTIFIER ::= { h3cevtModuleSwitchType 116 } -- 48-Ports 100Base-TX Ethernet Interface module C

h3cevtModuleSw-LSB1GT48B                   OBJECT IDENTIFIER ::= { h3cevtModuleSwitchType 117 } -- 48-Ports 10/100/1000Base-T Ethernet Interface Module B

h3cevtModuleSw-LSB1GT48C                   OBJECT IDENTIFIER ::= { h3cevtModuleSwitchType 118 } -- 48-Ports 10/100/1000Base-T Ethernet Interface Module C

h3cevtModuleSw-LS81GT48                    OBJECT IDENTIFIER ::= { h3cevtModuleSwitchType 119 } -- 48 Port Gigabit Ethernet Electric Interface Unit

h3cevtModuleSw-LS81SRPG0                   OBJECT IDENTIFIER ::= { h3cevtModuleSwitchType 120 } -- Salience III, Switch and Route Processing Board

h3cevtModuleSw-LS81SRPG1                   OBJECT IDENTIFIER ::= { h3cevtModuleSwitchType 121 } -- Salience III Plus

h3cevtModuleSw-LS81SRPG2                   OBJECT IDENTIFIER ::= { h3cevtModuleSwitchType 122 } -- Salience III Lite

h3cevtModuleSw-LS81SRPG3                   OBJECT IDENTIFIER ::= { h3cevtModuleSwitchType 123 } -- Salience III Edge

--h3cevtModuleSw-LS81SRPG                  OBJECT IDENTIFIER ::= { h3cevtModuleSwitchType 124 } Switch And Route Processing Unit, Salience III. not used.

h3cevtModuleSw-SR01SRPUB                   OBJECT IDENTIFIER ::= { h3cevtModuleSwitchType 125 } -- SR8812 Switching and Route Processing Unit

h3cevtModuleSw-SR01SRPUA                   OBJECT IDENTIFIER ::= { h3cevtModuleSwitchType 126 } -- SR8805 Switching and Route Processing Unit

h3cevtModuleSw-SR01GP12L                   OBJECT IDENTIFIER ::= { h3cevtModuleSwitchType 127 } -- 12-Port 1000Base-X Ethernet SFP Optical Interface Line Card(L)

h3cevtModuleSw-SR01GP12W                   OBJECT IDENTIFIER ::= { h3cevtModuleSwitchType 128 } -- 12-Port 1000Base-X Ethernet SFP Optical Interface Line Card(W)

h3cevtModuleSw-SR01FT48L                   OBJECT IDENTIFIER ::= { h3cevtModuleSwitchType 129 } -- 48-Port 10/100Base-TX Ethernet RJ45 Electrical Interface Line Card (L)

h3cevtModuleSw-SR01FT48W                   OBJECT IDENTIFIER ::= { h3cevtModuleSwitchType 130 } -- 48-Port 10/100Base-TX Ethernet RJ45 Electrical Interface Line Card (W)

h3cevtModuleSw-SR01XK1W                    OBJECT IDENTIFIER ::= { h3cevtModuleSwitchType 131 } -- 1-Port 10GBase-R Ethernet XENPAK Optical Interface Line Card (W)

h3cevtModuleSw-SR01FP20W                   OBJECT IDENTIFIER ::= { h3cevtModuleSwitchType 132 } -- 20-Port 100Base-FX Ethernet SFP Optical Interface Line Card (W)

h3cevtModuleSw-SR01GT12W                   OBJECT IDENTIFIER ::= { h3cevtModuleSwitchType 133 } -- 12-Port 10/100/1000Base-T Ethernet RJ45 Electrical Interface Line Card (W)

h3cevtModuleSw-SR01F32GL                   OBJECT IDENTIFIER ::= { h3cevtModuleSwitchType 134 } -- 32-Port 10/100Base-TX Ethernet RJ45 Electrical Interface + 4-Port 1000Base-X Ethernet SFP Optical interface Line Card (L)

h3cevtModuleSw-SR01F32GW                   OBJECT IDENTIFIER ::= { h3cevtModuleSwitchType 135 } -- 32-Port 10/100Base-TX Ethernet RJ45 Electrical Interface  + 4-Port 1000Base-X  Ethernet SFP Optical interface Line Card (W)

h3cevtModuleSw-SR01GT8PL                   OBJECT IDENTIFIER ::= { h3cevtModuleSwitchType 136 } -- 8-Port 10/100/1000Base-T Ethernet RJ45 Electrical Interface + 4-Port 1000Base-X Ethernet SFP Optical Line Card (L)

h3cevtModuleSw-SR01GT8PW                   OBJECT IDENTIFIER ::= { h3cevtModuleSwitchType 137 } -- 8-Port 10/100/1000Base-T Ethernet RJ45 Electrical Interface + 4-Port 1000Base-X Ethernet SFP Optical Line Card (W)

h3cevtModuleSw-SR01P4G8W                   OBJECT IDENTIFIER ::= { h3cevtModuleSwitchType 138 } -- 4-Port 155M POS Optical Interface + 8-Port 1000Base-X Ethernet SFP Optical Interface Line Card (W)

h3cevtModuleSw-LSA1FP8U                    OBJECT IDENTIFIER ::= { h3cevtModuleSwitchType 139 } -- 8 Ports 100Base-FX Ethernet SFP Card

h3cevtModuleSw-LSB1SP4B                    OBJECT IDENTIFIER ::= { h3cevtModuleSwitchType 140 } -- 4-Port OC-48 POS SFP Optical Interface Board B

h3cevtModuleSw-LSB1SP4C                    OBJECT IDENTIFIER ::= { h3cevtModuleSwitchType 141 } -- 4-Port OC-48 POS SFP Optical Interface Board C

h3cevtModuleSw-LSB1UP1B                    OBJECT IDENTIFIER ::= { h3cevtModuleSwitchType 142 } -- 1-Port OC-192 POS XFP Optical Interface Board B

h3cevtModuleSw-LSB1UP1C                    OBJECT IDENTIFIER ::= { h3cevtModuleSwitchType 143 } -- 1-Port OC-192 POS XFP Optical Interface Board C

h3cevtModuleSw-LSB1XP4B                    OBJECT IDENTIFIER ::= { h3cevtModuleSwitchType 144 } -- 4-Port 10GBase Ethernet XFP Optical Interface Board B

h3cevtModuleSw-LSB1XP4C                    OBJECT IDENTIFIER ::= { h3cevtModuleSwitchType 145 } -- 4-Port 10GBase Ethernet XFP Optical Interface Board C

h3cevtModuleSw-SP4                         OBJECT IDENTIFIER ::= { h3cevtModuleSwitchType 146 } -- 4-Port OC-48 POS SFP Optical Interface Module

h3cevtModuleSw-UP1                         OBJECT IDENTIFIER ::= { h3cevtModuleSwitchType 147 } -- 1-Port OC-192 POS XFP Optical Interface Module

h3cevtModuleSw-XP4                         OBJECT IDENTIFIER ::= { h3cevtModuleSwitchType 148 } -- 4-Port 10GBase Ethernet XFP Optical Interface Module

h3cevtModuleSw-LS81VSNP                    OBJECT IDENTIFIER ::= { h3cevtModuleSwitchType 149 } -- VerSatile Network Processing Board

h3cevtModuleSw-LS81T12P                    OBJECT IDENTIFIER ::= { h3cevtModuleSwitchType 150 } -- 12-Port 1000Base-T Gigabit Ethernet Interface(RJ45)+4-Port 1000BASE-X  Gigabit Ethernet Optical Interface Board(SFP,LC)

h3cevtModuleSw-LS81P12T                    OBJECT IDENTIFIER ::= { h3cevtModuleSwitchType 151 } -- 12-Port 1000BASE-X Gigabit Ethernet Optical Interface(SFP,LC)+4-Port 1000BASE-T Gigabit Ethernet Interface Board(RJ45)

h3cevtModuleSw-LS81GP8UB                   OBJECT IDENTIFIER ::= { h3cevtModuleSwitchType 152 } -- 8-Port 1000M Ethernet Optical Interface Board(SFP,LC),LC Connector

h3cevtModuleSw-LS81FT48E                   OBJECT IDENTIFIER ::= { h3cevtModuleSwitchType 153 } -- 48-Port 100M Ethernet Electrical Interface Switch Unit(RJ45)

h3cevtModuleSw-LS81GP4UB                   OBJECT IDENTIFIER ::= { h3cevtModuleSwitchType 154 } -- 4-Port 1000M Ethernet Optical Interface Board(SFP,LC)

h3cevtModuleSw-LS81GT8UE                   OBJECT IDENTIFIER ::= { h3cevtModuleSwitchType 155 } -- 8-Port 1000M Ethernet Electrical Interface Switch Unit (RJ45)

h3cevtModuleSw-LS81GT48A                   OBJECT IDENTIFIER ::= { h3cevtModuleSwitchType 156 } -- 48 Port Gigabit Ethernet Electric Interface Unit

h3cevtModuleSw-LS81FP48                    OBJECT IDENTIFIER ::= { h3cevtModuleSwitchType 157 } -- 48 Port 100M Ethernet Optical Interface Board(SFP,LC)

h3cevtModuleSw-LSB1XK1B                    OBJECT IDENTIFIER ::= { h3cevtModuleSwitchType 158 } -- 1-Port 10GBase-R Ethernet XENPAK Optical Interface Board B

h3cevtModuleSw-LSB1XK1C                    OBJECT IDENTIFIER ::= { h3cevtModuleSwitchType 159 } -- 1-Port 10GBase-R Ethernet XENPAK Optical Interface Board C

h3cevtModuleSw-SR01SRPUC                   OBJECT IDENTIFIER ::= { h3cevtModuleSwitchType 160 } -- Switching and Route Processing Unit C

h3cevtModuleSw-SR01SRPUD                   OBJECT IDENTIFIER ::= { h3cevtModuleSwitchType 161 } -- Switching and Route Processing Unit D

h3cevtModuleSw-SR01SRPUE                   OBJECT IDENTIFIER ::= { h3cevtModuleSwitchType 162 } -- Switching and Route Processing Unit E

h3cevtModuleSw-LSB1SRP1N3                  OBJECT IDENTIFIER ::= { h3cevtModuleSwitchType 163 } -- Switching and Route Process Unit, Clock Module

h3cevtModuleSw-LSB1VP2B                    OBJECT IDENTIFIER ::= { h3cevtModuleSwitchType 164 } -- 2*10G Resilient Packet Ring Interface Line Card

h3cevtModuleSw-LSB1NATB                    OBJECT IDENTIFIER ::= { h3cevtModuleSwitchType 165 } -- NAT Service Processing Card (B)

h3cevtModuleSw-LSB1VPNB                    OBJECT IDENTIFIER ::= { h3cevtModuleSwitchType 166 } -- VPN Service Processing Card (B)

h3cevtModuleSw-LSGP8P                      OBJECT IDENTIFIER ::= { h3cevtModuleSwitchType 167 } -- 8-Port 1000M SFP Module

h3cevtModuleSw-LSXK1P                      OBJECT IDENTIFIER ::= { h3cevtModuleSwitchType 168 } -- 1-Port 10G Xenpak Module

h3cevtModuleSw-LSXP2P                      OBJECT IDENTIFIER ::= { h3cevtModuleSwitchType 169 } -- 2-Port 10G XFP Module

h3cevtModuleSw-LS81FT48F                   OBJECT IDENTIFIER ::= { h3cevtModuleSwitchType 170 } -- 48-Port 100M Ethernet Electrical Interface Switch Unit(RJ45)

h3cevtModuleSw-LS81PT8G                    OBJECT IDENTIFIER ::= { h3cevtModuleSwitchType 171 } -- 8 Port 1000BASE-X Gigabit Passive Optical Line Interface Board

h3cevtModuleSw-LS81PT4G                    OBJECT IDENTIFIER ::= { h3cevtModuleSwitchType 172 } -- 4 Port 1000BASE-X Gigabit Passive Optical Line Interface Board

h3cevtModuleSw-LSSTK24G                    OBJECT IDENTIFIER ::= { h3cevtModuleSwitchType 173 } -- 24G Stacking Ports Module

h3cevtModuleSw-LS82GT20A                   OBJECT IDENTIFIER ::= { h3cevtModuleSwitchType 174 } -- 20-Port 1000Base-T Gigabit Ethernet Electrical Interface Board(RJ45), BCM5697

h3cevtModuleSw-LS82GP20A                   OBJECT IDENTIFIER ::= { h3cevtModuleSwitchType 175 } -- 20-Port 1000BASE-X Gigabit Ethernet Optical Interface Board(SFP,LC), BCM5697

h3cevtModuleSw-LS81TGX1C                   OBJECT IDENTIFIER ::= { h3cevtModuleSwitchType 176 } -- 1-Port 10G Base-R Ethernet Board

h3cevtModuleSw-VP2                         OBJECT IDENTIFIER ::= { h3cevtModuleSwitchType 177 } -- 2*10G Resilient Packet Ring Interface Module

h3cevtModuleSw-LSA1FB8U                    OBJECT IDENTIFIER ::= { h3cevtModuleSwitchType 178 } -- 8-Port 100Base-Fx BIDI Ethernet Board

h3cevtModuleSw-LS81T12PE                   OBJECT IDENTIFIER ::= { h3cevtModuleSwitchType 179 } -- 12-Port 1000Base-T GE Interface+4-Port 1000BASE-X GE Optical Interface Board(SFP,LC)

h3cevtModuleSw-LS81P12TE                   OBJECT IDENTIFIER ::= { h3cevtModuleSwitchType 180 } -- 12-Port 1000BASE-X GE Optical Interface(SFP,LC)+4-Port 1000 BASE-T GE Interface Board(RJ45)

h3cevtModuleSw-LSB1SRP2N0                  OBJECT IDENTIFIER ::= { h3cevtModuleSwitchType 181 } -- Switching and Route Process Unit,12*LPU

h3cevtModuleSw-LSB1SRP2N3                  OBJECT IDENTIFIER ::= { h3cevtModuleSwitchType 182 } -- Switching and Route Process Unit, Clock Module

h3cevtModuleSw-LSB1GV48DB                  OBJECT IDENTIFIER ::= { h3cevtModuleSwitchType 183 } -- 48 Ports 1000Base-T Ethernet Interface Line Card with POE(DB)

h3cevtModuleSw-LSB1FW8B                    OBJECT IDENTIFIER ::= { h3cevtModuleSwitchType 184 } -- Firewall Service Processing Board with 8GE (B)

h3cevtModuleSw-LSB1IPSEC8B                 OBJECT IDENTIFIER ::= { h3cevtModuleSwitchType 185 } -- VPN Service Processing Board with 8GE (B)

h3cevtModuleSw-LSB1IDSB                    OBJECT IDENTIFIER ::= { h3cevtModuleSwitchType 186 } -- IDS Service Processing Board (B)

h3cevtModuleSw-LSB1IPSB                    OBJECT IDENTIFIER ::= { h3cevtModuleSwitchType 187 } -- IPS Service Processing Board (B)

h3cevtModuleSw-LSB2FT48CA                  OBJECT IDENTIFIER ::= { h3cevtModuleSwitchType 188 } -- 48 Ports 100Base-TX Ethernet Line Card (CA)

h3cevtModuleSw-LSB1FP20CA                  OBJECT IDENTIFIER ::= { h3cevtModuleSwitchType 189 } -- 20 Ports 100Base-FX Ethernet Interface Service Card (CA)

h3cevtModuleSw-LSB1F32GCA                  OBJECT IDENTIFIER ::= { h3cevtModuleSwitchType 190 } -- 32 Ports FE and 4 Ports GE Line Card(CA)

h3cevtModuleSw-LSB1P4G8CA                  OBJECT IDENTIFIER ::= { h3cevtModuleSwitchType 191 } -- 4 Ports OC-3c POS and 8 Ports GE Line Card(CA)

h3cevtModuleSw-LSB1GT12CA                  OBJECT IDENTIFIER ::= { h3cevtModuleSwitchType 192 } -- 12 Ports 1000Base-T Ethernet Interface Line Card(CA)

h3cevtModuleSw-LSB1GT24CA                  OBJECT IDENTIFIER ::= { h3cevtModuleSwitchType 193 } -- 24 Ports 1000Base-T Ethernet Interface Line Card(CA)

h3cevtModuleSw-LSB1GP12CA                  OBJECT IDENTIFIER ::= { h3cevtModuleSwitchType 194 } -- 12 Ports 1000Base Ethernet Optical Interface Service Card(CA)

h3cevtModuleSw-LSB1GP24CA                  OBJECT IDENTIFIER ::= { h3cevtModuleSwitchType 195 } -- 24 Ports 1000Base-X Ethernet Interface Line Card (CA)

h3cevtModuleSw-LSB1GT8PCA                  OBJECT IDENTIFIER ::= { h3cevtModuleSwitchType 196 } -- 8 Ports 1000Base-T Ethernet Interface & 4 Ports 1000Base-X Ethernet SFP Interface Line Card(CA)

h3cevtModuleSw-LSB1XP2CA                   OBJECT IDENTIFIER ::= { h3cevtModuleSwitchType 197 } -- 2-Port 10GBase-R/W Ethernet XFP Optical Interface Card(CA)

h3cevtModuleSw-LSB1XK1CA                   OBJECT IDENTIFIER ::= { h3cevtModuleSwitchType 198 } -- 10GBase-R Ethernet XENPAK Optical Interface Line Card(CA)

h3cevtModuleSw-LSB1XP4CA                   OBJECT IDENTIFIER ::= { h3cevtModuleSwitchType 199 } -- 4-Port 10GBase-R/X Ethernet Optical Interface Line Card(CA)

h3cevtModuleSw-LSB1UP1CA                   OBJECT IDENTIFIER ::= { h3cevtModuleSwitchType 200 } -- Single Port OC-192c POS XFP Optical Interface Card(CA)

h3cevtModuleSw-LSB1SP4CA                   OBJECT IDENTIFIER ::= { h3cevtModuleSwitchType 201 } -- 4-Port OC-48c POS SFP Optical Interface Card(CA)

h3cevtModuleSw-LSB1VP2CA                   OBJECT IDENTIFIER ::= { h3cevtModuleSwitchType 202 } -- 2*10G RPR Process Unit(CA)

h3cevtModuleSw-SR01FT48WA                  OBJECT IDENTIFIER ::= { h3cevtModuleSwitchType 203 } -- 48 Ports 100Base-TX Ethernet Line Card (WA)

h3cevtModuleSw-SR01FP20WA                  OBJECT IDENTIFIER ::= { h3cevtModuleSwitchType 204 } -- 20 Ports 100Base-FX Ethernet Interface Service Card (WA)

h3cevtModuleSw-SR01F32GWA                  OBJECT IDENTIFIER ::= { h3cevtModuleSwitchType 205 } -- 32 Ports FE and 4 Ports GE Line Card(WA)

h3cevtModuleSw-SR01P4G8WA                  OBJECT IDENTIFIER ::= { h3cevtModuleSwitchType 206 } -- 4 Ports OC-3c POS and 8 Ports GE Line Card(WA)

h3cevtModuleSw-SR01GT12WA                  OBJECT IDENTIFIER ::= { h3cevtModuleSwitchType 207 } -- 12 Ports 1000Base-T Ethernet Interface Line Card(WA)

h3cevtModuleSw-SR01GT24WA                  OBJECT IDENTIFIER ::= { h3cevtModuleSwitchType 208 } -- 24 Ports 1000Base-T Ethernet Interface Line Card(WA)

h3cevtModuleSw-SR01GP12WA                  OBJECT IDENTIFIER ::= { h3cevtModuleSwitchType 209 } -- 12 Ports 1000Base Ethernet Optical Interface Service Card(WA)

h3cevtModuleSw-SR01GP24WA                  OBJECT IDENTIFIER ::= { h3cevtModuleSwitchType 210 } -- 24 Ports 1000Base-X Ethernet Interface Line Card (WA)

h3cevtModuleSw-SR01GT8PWA                  OBJECT IDENTIFIER ::= { h3cevtModuleSwitchType 211 } -- 8 Ports 1000Base-T Ethernet Interface & 4 Ports 1000Base-X Ethernet SFP Interface Line Card(WA)

h3cevtModuleSw-SR01XP2WA                   OBJECT IDENTIFIER ::= { h3cevtModuleSwitchType 212 } -- 2-Port 10GBase-R/W Ethernet XFP Optical Interface Card(WA)

h3cevtModuleSw-SR01XK1WA                   OBJECT IDENTIFIER ::= { h3cevtModuleSwitchType 213 } -- 10GBase-R Ethernet XENPAK Optical Interface Line Card(WA)

h3cevtModuleSw-SR01UP1WA                   OBJECT IDENTIFIER ::= { h3cevtModuleSwitchType 214 } -- Single Port OC-192c POS XFP Optical Interface Card(WA)

h3cevtModuleSw-SR01SP4WA                   OBJECT IDENTIFIER ::= { h3cevtModuleSwitchType 215 } -- 4-Port OC-48c POS SFP Optical Interface Card(WA)

h3cevtModuleSw-GP8U                        OBJECT IDENTIFIER ::= { h3cevtModuleSwitchType 216 } -- 8-Port 1000Base-X SFP Optical Interface Module

h3cevtModuleSw-LSEXP1P                     OBJECT IDENTIFIER ::= { h3cevtModuleSwitchType 217 } -- Single 10G SFP Optical Interface Module

h3cevtModuleSw-LSEXK1P                     OBJECT IDENTIFIER ::= { h3cevtModuleSwitchType 218 } -- Single 10G XENPAK Interface Module

h3cevtModuleSw-LSEXS1P                     OBJECT IDENTIFIER ::= { h3cevtModuleSwitchType 219 } -- Single 10G STACK Interface Module

h3cevtModuleSw-LS81GP48                    OBJECT IDENTIFIER ::= { h3cevtModuleSwitchType 220 } -- 48-Port 1000M Ethernet Optical Interface Board(SFP,LC),LC Connector

h3cevtModuleSw-LS81GT48B                   OBJECT IDENTIFIER ::= { h3cevtModuleSwitchType 221 } -- 48-Port 1000Base-T Gigabit Ethernet Interface Board(RJ45)

h3cevtModuleSw-LS81T16P                    OBJECT IDENTIFIER ::= { h3cevtModuleSwitchType 222 } -- 16-Port 1000Base-T Gigabit Ethernet Interface(RJ45) + 8-Port 1000BASE-X Gigabit Ethernet Optical Interface Board(SFP,LC)

h3cevtModuleSw-LS81T32P                    OBJECT IDENTIFIER ::= { h3cevtModuleSwitchType 223 } -- 32-Port 1000Base-T Gigabit Ethernet Interface(RJ45) + 16-Port 1000BASE-X Gigabit Ethernet Optical Interface Board(SFP,LC)

h3cevtModuleSw-LS81TGX2                    OBJECT IDENTIFIER ::= { h3cevtModuleSwitchType 224 } -- 2-Port 10GBASE Ethernet Interface Board(XFP,LC)

h3cevtModuleSw-LS81TGX4                    OBJECT IDENTIFIER ::= { h3cevtModuleSwitchType 225 } -- 4-Port 10GBASE Ethernet Interface Module(XFP,LC),XG

h3cevtModuleSw-LSB1GV48DA                  OBJECT IDENTIFIER ::= { h3cevtModuleSwitchType 226 } -- 48 Ports 1000Base-T Ethernet Interface Line Card with POE(DA)

h3cevtModuleSw-SR01GV48VB                  OBJECT IDENTIFIER ::= { h3cevtModuleSwitchType 227 } -- 48 Ports 1000Base-T Ethernet Interface Line Card with POE(VB)

h3cevtModuleSw-LSB1GT24DB                  OBJECT IDENTIFIER ::= { h3cevtModuleSwitchType 228 } -- 24 Ports 1000Base-T Ethernet Interface Line Card(DB)

h3cevtModuleSw-LSB1GP24DB                  OBJECT IDENTIFIER ::= { h3cevtModuleSwitchType 229 } -- 24 Ports 1000Base-X Ethernet Interface Line Card(DB)

h3cevtModuleSw-LSB1GP24DC                  OBJECT IDENTIFIER ::= { h3cevtModuleSwitchType 230 } -- 24 Ports 1000Base-X Ethernet Interface Line Card(DC)

h3cevtModuleSw-LSB1FW8DB                   OBJECT IDENTIFIER ::= { h3cevtModuleSwitchType 231 } -- 8-port 1000BASE-X (SFP) Firewall Service Card(DB)

h3cevtModuleSw-LSB1IPSEC8DB                OBJECT IDENTIFIER ::= { h3cevtModuleSwitchType 232 } -- 8-port 1000BASE-X (SFP) IPSEC Service Card(DB)

h3cevtModuleSw-SR01GT24VB                  OBJECT IDENTIFIER ::= { h3cevtModuleSwitchType 233 } -- 24 Ports 1000Base-T Ethernet Interface Line Card(VB)

h3cevtModuleSw-SR01GP24VC                  OBJECT IDENTIFIER ::= { h3cevtModuleSwitchType 234 } -- 24 Ports 1000Base-X Ethernet Interface Line Card(VC)

h3cevtModuleSw-SR01VP2WA                   OBJECT IDENTIFIER ::= { h3cevtModuleSwitchType 235 } -- 2*10G RPR Process Unit(WA)

h3cevtModuleSw-SR01FW8VB                   OBJECT IDENTIFIER ::= { h3cevtModuleSwitchType 236 } -- 8-port 1000BASE-X (SFP) Firewall Service Card(VB)

h3cevtModuleSw-SR01IPSEC8VB                OBJECT IDENTIFIER ::= { h3cevtModuleSwitchType 237 } -- 8-port 1000BASE-X (SFP) IPSEC Service Card(VB)

h3cevtModuleSw-SR01NATL                    OBJECT IDENTIFIER ::= { h3cevtModuleSwitchType 238 } -- NAT Service Processing Card (L)

h3cevtModuleSw-SR01VPNL                    OBJECT IDENTIFIER ::= { h3cevtModuleSwitchType 239 } -- VPN Service Processing Card (L)

h3cevtModuleSw-LSB1GP24CB                  OBJECT IDENTIFIER ::= { h3cevtModuleSwitchType 240 } -- 24 Ports 1000Base-X Ethernet Interface Line Card(CB)

h3cevtModuleSw-LSB1GP48DB                  OBJECT IDENTIFIER ::= { h3cevtModuleSwitchType 241 } -- 48-Port Gigabit Ethernet Optical Interface Line Card(DB)

h3cevtModuleSw-LSB1XP2CB                   OBJECT IDENTIFIER ::= { h3cevtModuleSwitchType 242 } -- 2-Port 10Gigabit Ethernet Optical Interface Card(CB)

h3cevtModuleSw-XP4L                        OBJECT IDENTIFIER ::= { h3cevtModuleSwitchType 243 } -- 4 Port 1000BASE Optic Interface Module (XFP)

h3cevtModuleSw-LSB1XP4LDB                  OBJECT IDENTIFIER ::= { h3cevtModuleSwitchType 244 } -- 4-Port 10GBase-R/W Ethernet XFP Optical Interface Line Speed Card(DB)

h3cevtModuleSw-LSB1XP4LDC                  OBJECT IDENTIFIER ::= { h3cevtModuleSwitchType 245 } -- 4-Port 10GBase-R/W Ethernet XFP Optical Interface Line Speed Card(DC)

h3cevtModuleSw-AHP4                        OBJECT IDENTIFIER ::= { h3cevtModuleSwitchType 246 } -- 2-Port OC-3 ATM and 2-Port OC-3/12 ATM Interface Module (SFP)

h3cevtModuleSw-LSB1AHP4GCA                 OBJECT IDENTIFIER ::= { h3cevtModuleSwitchType 247 } -- 2-Port OC-3 ATM and 2-Port OC-3/12 ATM and 8-Port 1000Base-X Ethernet Optical Interface Line Card(CA)

h3cevtModuleSw-CLP4                        OBJECT IDENTIFIER ::= { h3cevtModuleSwitchType 248 } -- 4 Ports OC-3/STM-1 CPOS Optical Interface Module (SFP)

h3cevtModuleSw-LSB1CLP4GCA                 OBJECT IDENTIFIER ::= { h3cevtModuleSwitchType 249 } -- 4 Ports OC-3/STM-1 CPOS Optical Interface and 4-Port 1000Base-X Ethernet Optical Interface Line Card(CA)

h3cevtModuleSw-ET32                        OBJECT IDENTIFIER ::= { h3cevtModuleSwitchType 250 } -- 32-Port Channelized E1/T1 Interface Module

h3cevtModuleSw-LSB1ET32GCA                 OBJECT IDENTIFIER ::= { h3cevtModuleSwitchType 251 } -- 32-Port Channelized E1/T1 Interface and 4-Port 1000Base-X Ethernet Optical Interface Line Card(CA)

h3cevtModuleSw-LSB1IDSDB                   OBJECT IDENTIFIER ::= { h3cevtModuleSwitchType 252 } -- Intrusion Detection Service Card(DB)

h3cevtModuleSw-LSB1SRP2N1                  OBJECT IDENTIFIER ::= { h3cevtModuleSwitchType 253 } -- Switching and Route Processing Board,8*LPU

h3cevtModuleSw-BOARD-LS82SRPB              OBJECT IDENTIFIER ::= { h3cevtModuleSwitchType 254 }

h3cevtModuleSw-BORAD-LS83SRPC              OBJECT IDENTIFIER ::= { h3cevtModuleSwitchType 255 }

h3cevtModuleSw-Main                        OBJECT IDENTIFIER ::= { h3cevtModuleSwitchType 256 }

h3cevtModuleSw-LSB1SRP2N2                  OBJECT IDENTIFIER ::= { h3cevtModuleSwitchType 257 } -- Switching and Route Processing Board,5*LPU

h3cevtModuleSw-LSB1NAMB                    OBJECT IDENTIFIER ::= { h3cevtModuleSwitchType 258 } -- NAM Service Processing Card (B)

h3cevtModuleSw-RSP2                        OBJECT IDENTIFIER ::= { h3cevtModuleSwitchType 259 } -- 2*2.5G Resilient Packet Ring Interface

h3cevtModuleSw-LSB1RSP2CA                  OBJECT IDENTIFIER ::= { h3cevtModuleSwitchType 260 } -- 2*2.5G Resilient Packet Ring Interface Line Card(CA)

h3cevtModuleSw-SR01XP4LVC                  OBJECT IDENTIFIER ::= { h3cevtModuleSwitchType 261 } -- 4-Port 10GBase-R/W Ethernet XFP Optical Interface Line Speed Card(VC)

h3cevtModuleSw-SR01AHP4GWA                 OBJECT IDENTIFIER ::= { h3cevtModuleSwitchType 262 } -- 2-Port OC-3 ATM and 2-Port OC-3/12 ATM and 8-Port 1000Base-X Ethernet Optical Interface Line Card(WA)

h3cevtModuleSw-SR01CLP4GWA                 OBJECT IDENTIFIER ::= { h3cevtModuleSwitchType 263 } -- 4 Ports OC-3/STM-1 CPOS Optical Interface and 4-Port 1000Base-X Ethernet Optical Interface Line Card(WA)

h3cevtModuleSw-SR01ET32GWA                 OBJECT IDENTIFIER ::= { h3cevtModuleSwitchType 264 } -- 32-Port Channelized E1/T1 Interface and 4-Port 1000Base-X Ethernet Optical Interface Line Card(WA)

h3cevtModuleSw-SR01IDSVB                   OBJECT IDENTIFIER ::= { h3cevtModuleSwitchType 265 } -- Intrusion Detection Service Card(VB)

h3cevtModuleSw-SR01SRPUF                   OBJECT IDENTIFIER ::= { h3cevtModuleSwitchType 266 } -- Switching and Route Processing Board,12*LPU

h3cevtModuleSw-SR01NAML                    OBJECT IDENTIFIER ::= { h3cevtModuleSwitchType 267 } -- NAM Service Processing Card (L)

h3cevtModuleSw-SR01RSP2WA                  OBJECT IDENTIFIER ::= { h3cevtModuleSwitchType 268 } -- 2*2.5G Resilient Packet Ring Interface Line Card(WA)

h3cevtModuleSw-LSPM1XP1P                   OBJECT IDENTIFIER ::= { h3cevtModuleSwitchType 269 } -- 1-Port 10G XFP Module

h3cevtModuleSw-LSPM1XP2P                   OBJECT IDENTIFIER ::= { h3cevtModuleSwitchType 270 } -- 2-Port 10G XFP Module

h3cevtModuleSw-LSPM1CX2P                   OBJECT IDENTIFIER ::= { h3cevtModuleSwitchType 271 } -- 2-Port 10G CX4 Module

h3cevtModuleSw-STK-1000BASE-T              OBJECT IDENTIFIER ::= { h3cevtModuleSwitchType 272 } -- Single Port 1000BASE-T Stack Ethernet Interface Card

--
-- 273 to 299 reserved for other product
--


--
-- 300 to 499 reserved for advanced switches
--
h3cevtModuleSw-LSB1SRP1M0                  OBJECT IDENTIFIER ::= { h3cevtModuleSwitchType 300 } -- Switching and Route Process Unit,2*LPU or 3*LPU

h3cevtModuleSw-LSB1SRP1M1                  OBJECT IDENTIFIER ::= { h3cevtModuleSwitchType 301 } -- Switching and Route Process Unit

h3cevtModuleSw-LSB1GP12DB                  OBJECT IDENTIFIER ::= { h3cevtModuleSwitchType 302 } -- 12 Ports 1000Base Ethernet Optical Interface Service Card(DB)

h3cevtModuleSw-LSB1GT12DB                  OBJECT IDENTIFIER ::= { h3cevtModuleSwitchType 303 } -- 12 Ports 1000Base-T Ethernet Interface Line Card(DB)

h3cevtModuleSw-LSB1XK1DB                   OBJECT IDENTIFIER ::= { h3cevtModuleSwitchType 304 } -- 10GBase-R Ethernet XENPAK Optical Interface Line Card(DB)

h3cevtModuleSw-LSB1XP2DB                   OBJECT IDENTIFIER ::= { h3cevtModuleSwitchType 305 } -- 2-Port 10GBase-R/W Ethernet XFP Optical Interface Card(DB)

h3cevtModuleSw-LSB1XP2DC                   OBJECT IDENTIFIER ::= { h3cevtModuleSwitchType 306 } -- 2-Port 10GBase-R/W Ethernet XFP Optical Interface Card(DC)

h3cevtModuleSw-LSB1GT48LDB                 OBJECT IDENTIFIER ::= { h3cevtModuleSwitchType 307 } -- 48-Port Gigabit Ethernet RJ45 Electrical Interface Card (DB)

h3cevtModuleSw-LSB1XP4TDB                  OBJECT IDENTIFIER ::= { h3cevtModuleSwitchType 308 } -- 4-Port 10GBase-R/W Ethernet XFP Optical Interface Line Speed Test Card(DB)

h3cevtModuleSw-LSB1XP4TDC                  OBJECT IDENTIFIER ::= { h3cevtModuleSwitchType 309 } -- 4-Port 10GBase-R/W Ethernet XFP Optical Interface Line Speed Test Card(DC)

h3cevtModuleSw-LSB1RSP2DC                  OBJECT IDENTIFIER ::= { h3cevtModuleSwitchType 310 } -- 2*2.5G Resilient Packet Ring Interface Line Card(DC)

h3cevtModuleSw-LSB1VP2DC                   OBJECT IDENTIFIER ::= { h3cevtModuleSwitchType 311 } -- 2*10G Resilient Packet Ring Process Unit(DC)

h3cevtModuleSw-LSB1XP4DB                   OBJECT IDENTIFIER ::= { h3cevtModuleSwitchType 312 } -- 4-Port 10GBase-R/X Ethernet Optical Interface Line Card(DB)

h3cevtModuleSw-LSB1SRP2E0                  OBJECT IDENTIFIER ::= { h3cevtModuleSwitchType 313 } -- Switching and Route Process Unit,12*LPU

h3cevtModuleSw-LSB1SRP2E1                  OBJECT IDENTIFIER ::= { h3cevtModuleSwitchType 314 } -- Switching and Route Process Unit,8*LPU

h3cevtModuleSw-LSB1SRP2E2                  OBJECT IDENTIFIER ::= { h3cevtModuleSwitchType 315 } -- Switching and Route Process Unit,5*LPU

h3cevtModuleSw-LSB1SRP2E3                  OBJECT IDENTIFIER ::= { h3cevtModuleSwitchType 316 } -- Switching and Route Process Unit, Clock module

h3cevtModuleSw-SR01SRPUQ                   OBJECT IDENTIFIER ::= { h3cevtModuleSwitchType 317 } -- Switching and Route Processing Unit Q

h3cevtModuleSw-AHP1                        OBJECT IDENTIFIER ::= { h3cevtModuleSwitchType 318 } -- 1-Port OC-12c(3c)/STM-4(1) ATM Optical Interface Module(SFP)

h3cevtModuleSw-AHP2                        OBJECT IDENTIFIER ::= { h3cevtModuleSwitchType 319 } -- 2-Port OC-12c(3c)/STM-4(1) ATM Optical Interface Module(SFP)

h3cevtModuleSw-CLP1                        OBJECT IDENTIFIER ::= { h3cevtModuleSwitchType 320 } -- 1-Port OC-3/STM-1 CPOS Optical Interface Module(SFP)

h3cevtModuleSw-CLP2                        OBJECT IDENTIFIER ::= { h3cevtModuleSwitchType 321 } -- 2-Port OC-3/STM-1 CPOS Optical Interface Module(SFP)

h3cevtModuleSw-ET16                        OBJECT IDENTIFIER ::= { h3cevtModuleSwitchType 322 } -- 16-Port Channelized E1/T1 Interface Module

h3cevtModuleSw-LSB1SRP1NA0                 OBJECT IDENTIFIER ::= { h3cevtModuleSwitchType 323 } -- Switching and Route Process Unit,12*LPU

h3cevtModuleSw-LSB1SRP1NA1                 OBJECT IDENTIFIER ::= { h3cevtModuleSwitchType 324 } -- Switching and Route Process Unit,8*LPU

h3cevtModuleSw-LSB1SRP1NA2                 OBJECT IDENTIFIER ::= { h3cevtModuleSwitchType 325 } -- Switching and Route Process Unit,5*LPU

h3cevtModuleSw-LSB1SRP1NA3                 OBJECT IDENTIFIER ::= { h3cevtModuleSwitchType 326 } -- Switching and Route Process Unit, Clock module

h3cevtModuleSw-SR01AHP1GWA                 OBJECT IDENTIFIER ::= { h3cevtModuleSwitchType 327 } -- 1-Port OC-12c(3c)/STM-4(1) ATM Optical Interface and 4-Port 1000Base-X Ethernet Optical Interface Line Card(WA)

h3cevtModuleSw-SR01AHP2GWA                 OBJECT IDENTIFIER ::= { h3cevtModuleSwitchType 328 } -- 2-Port OC-12c(3c)/STM-4(1) ATM Optical Interface and 4-Port 1000Base-X Ethernet Optical Interface Line Card(WA)

h3cevtModuleSw-SR01CLP1GWA                 OBJECT IDENTIFIER ::= { h3cevtModuleSwitchType 329 } -- 1-Port OC-3/STM-1 CPOS Optical Interface and 4-Port 1000Base-X Ethernet Optical Interface Line Card(WA)

h3cevtModuleSw-SR01CLP2GWA                 OBJECT IDENTIFIER ::= { h3cevtModuleSwitchType 330 } -- 2-Port OC-3/STM-1 CPOS Optical Interface and 4-Port 1000Base-X Ethernet Optical Interface Line Card(WA)

h3cevtModuleSw-SR01ET16GWA                 OBJECT IDENTIFIER ::= { h3cevtModuleSwitchType 331 } -- 16-Port Channelized E1/T1 Interface and  4-Port 1000Base-X Ethernet Optical Interface Line Card(WA)

h3cevtModuleSw-SR01GP12VB                  OBJECT IDENTIFIER ::= { h3cevtModuleSwitchType 332 } -- 12-Port Gigabit Ethernet Optical Interface Card(VB)

h3cevtModuleSw-SR01XK1VB                   OBJECT IDENTIFIER ::= { h3cevtModuleSwitchType 333 } -- 1-Port 10Gigabit Ethernet Optical Interface Card(VB)

h3cevtModuleSw-SR01XP2VC                   OBJECT IDENTIFIER ::= { h3cevtModuleSwitchType 334 } -- 2-Port 10GBase-RW Ethernet XFP Optical Interface Line Card(VC)

h3cevtModuleSw-SR01XP4LVB                  OBJECT IDENTIFIER ::= { h3cevtModuleSwitchType 335 } -- 4-Port 10GBase-R/W Ethernet XFP Optical Interface Line Speed Card(VB)

h3cevtModuleSw-SR01SRPUEA                  OBJECT IDENTIFIER ::= { h3cevtModuleSwitchType 336 } -- Switching and Route Process Unit, Clock Module

h3cevtModuleSw-LSB1SRP1N4                  OBJECT IDENTIFIER ::= { h3cevtModuleSwitchType 337 } -- Switching and Route Process Unit, 12*LPU

h3cevtModuleSw-LSB1SRP1N5                  OBJECT IDENTIFIER ::= { h3cevtModuleSwitchType 338 } -- Switching and Route Process Unit, 8*LPU

h3cevtModuleSw-LSB1SRP1N6                  OBJECT IDENTIFIER ::= { h3cevtModuleSwitchType 339 } -- Switching and Route Process Unit, 5*LPU

h3cevtModuleSw-LSB1SRP1N7                  OBJECT IDENTIFIER ::= { h3cevtModuleSwitchType 340 } -- Switching and Route Process Unit, Clock Module

h3cevtModuleSw-LSB1SRP2N4                  OBJECT IDENTIFIER ::= { h3cevtModuleSwitchType 341 } -- Switching and Route Process Unit, 12*LPU

h3cevtModuleSw-LSB1SRP2N5                  OBJECT IDENTIFIER ::= { h3cevtModuleSwitchType 342 } -- Switching and Route Process Unit, 8*LPU

h3cevtModuleSw-LSB1SRP2N6                  OBJECT IDENTIFIER ::= { h3cevtModuleSwitchType 343 } -- Switching and Route Process Unit, 5*LPU

h3cevtModuleSw-LSB1SRP2N7                  OBJECT IDENTIFIER ::= { h3cevtModuleSwitchType 344 } -- Switching and Route Process Unit, Clock Module

h3cevtModuleSw-LSB1SRP1NA4                 OBJECT IDENTIFIER ::= { h3cevtModuleSwitchType 345 } -- Switching and Route Process Unit, 12*LPU

h3cevtModuleSw-LSB1SRP1NA5                 OBJECT IDENTIFIER ::= { h3cevtModuleSwitchType 346 } -- Switching and Route Process Unit, 8*LPU

h3cevtModuleSw-LSB1SRP1NA6                 OBJECT IDENTIFIER ::= { h3cevtModuleSwitchType 347 } -- Switching and Route Process Unit, 5*LPU

h3cevtModuleSw-LSB1SRP1NA7                 OBJECT IDENTIFIER ::= { h3cevtModuleSwitchType 348 } -- Switching and Route Process Unit, Clock Module

h3cevtModuleSw-LSB2GV48DA                  OBJECT IDENTIFIER ::= { h3cevtModuleSwitchType 349 } -- 48-Ports 1000Base-T Ethernet Interface Line Card with POE(DA)

h3cevtModuleSw-LSB1RGP2GDB                 OBJECT IDENTIFIER ::= { h3cevtModuleSwitchType 350 } -- 2-Port GE RPR and 8-Port GE Optical Interface Service Card(DB)

h3cevtModuleSw-LSB1RGP4GDB                 OBJECT IDENTIFIER ::= { h3cevtModuleSwitchType 351 } -- 4-Port GE RPR and 8-Port GE Optical Interface Service Card(DB)

h3cevtModuleSw-LSB2GP24DB                  OBJECT IDENTIFIER ::= { h3cevtModuleSwitchType 352 } -- 24-Port 1000BASE-X  Interface Module(DB),(SFP,LC)

h3cevtModuleSw-LSB2GP24DC                  OBJECT IDENTIFIER ::= { h3cevtModuleSwitchType 353 } -- 24-Port 1000BASE-X  Interface Module(DC),(SFP,LC)

h3cevtModuleSw-LSB2GT24DB                  OBJECT IDENTIFIER ::= { h3cevtModuleSwitchType 354 } -- 24-Port 10/100/1000BASE-T Interface Module(DB),(RJ45)

h3cevtModuleSw-LSB2FW8DB                   OBJECT IDENTIFIER ::= { h3cevtModuleSwitchType 355 } -- 8-Port 1000BASE-X Interface Firewall Service Module(DB),(SFP,LC)

h3cevtModuleSw-LSB2IPSEC8DB                OBJECT IDENTIFIER ::= { h3cevtModuleSwitchType 356 } -- 8-Port 1000BASE-X Interface IPSEC Service Module(DB),(SFP,LC)

h3cevtModuleSw-LSB2GV48DB                  OBJECT IDENTIFIER ::= { h3cevtModuleSwitchType 357 } -- 48-Port 10/100/1000BASE-T Interface Module(DB),(PoE,RJ45)

h3cevtModuleSw-RGP2                        OBJECT IDENTIFIER ::= { h3cevtModuleSwitchType 358 } -- 2-Port GE Resilient Packet Ring Interface Module

h3cevtModuleSw-RGP4                        OBJECT IDENTIFIER ::= { h3cevtModuleSwitchType 359 } -- 4-Port GE Resilient Packet Ring Interface Module

h3cevtModuleSw-SR02FW8VB                   OBJECT IDENTIFIER ::= { h3cevtModuleSwitchType 360 } -- 8-Port 1000BASE-X Interface Firewall Service Module(VB),(SFP,LC)

h3cevtModuleSw-SR02IPSEC8VB                OBJECT IDENTIFIER ::= { h3cevtModuleSwitchType 361 } -- 8-Port 1000BASE-X Interface IPSEC Service Module(VB),(SFP,LC)

h3cevtModuleSw-LSB2SRP1N0                  OBJECT IDENTIFIER ::= { h3cevtModuleSwitchType 362 } -- Switching and Route Process Unit, 12*LPU

h3cevtModuleSw-LSB2SRP1N1                  OBJECT IDENTIFIER ::= { h3cevtModuleSwitchType 363 } -- Switching and Route Process Unit, 8*LPU

h3cevtModuleSw-LSB2SRP1N2                  OBJECT IDENTIFIER ::= { h3cevtModuleSwitchType 364 } -- Switching and Route Process Unit, 5*LPU

h3cevtModuleSw-LSB2SRP1N3                  OBJECT IDENTIFIER ::= { h3cevtModuleSwitchType 365 } -- Switching and Route Process Unit, Clock module

h3cevtModuleSw-LSB2SRP1N4                  OBJECT IDENTIFIER ::= { h3cevtModuleSwitchType 366 } -- Switching and Route Process Unit, 12*LPU

h3cevtModuleSw-LSB2SRP1N5                  OBJECT IDENTIFIER ::= { h3cevtModuleSwitchType 367 } -- Switching and Route Process Unit, 8*LPU

h3cevtModuleSw-LSB2SRP1N6                  OBJECT IDENTIFIER ::= { h3cevtModuleSwitchType 368 } -- Switching and Route Process Unit, 5*LPU

h3cevtModuleSw-LSB2SRP1N7                  OBJECT IDENTIFIER ::= { h3cevtModuleSwitchType 369 } -- Switching and Route Process Unit, Clock module

h3cevtModuleSw-SR02SRPUE                   OBJECT IDENTIFIER ::= { h3cevtModuleSwitchType 370 } -- Switching and Route Process Unit, Clock module

h3cevtModuleSw-SR01LN1BQH0                 OBJECT IDENTIFIER ::= { h3cevtModuleSwitchType 371 } -- Single XG Service Board(BQH)

h3cevtModuleSw-SR01DXP1L                   OBJECT IDENTIFIER ::= { h3cevtModuleSwitchType 372 } -- 1-Port 10GBASE-R/W Ethernet Optical Interface Card,(XFP,LC)

h3cevtModuleSw-SR01DGP10L                  OBJECT IDENTIFIER ::= { h3cevtModuleSwitchType 373 } -- 10-Port 1000BASE-X Optical Interface Card,(SFP,LC)

h3cevtModuleSw-SR01DRSP2L                  OBJECT IDENTIFIER ::= { h3cevtModuleSwitchType 374 } -- 2-Port 2.5G RPR Optical Interface Card,(SFP,LC)

h3cevtModuleSw-SR01DRUP1L                  OBJECT IDENTIFIER ::= { h3cevtModuleSwitchType 375 } -- 1-Port 10G RPR Optical Interface Card,(XFP,LC)

h3cevtModuleSw-SR01DGP20R                  OBJECT IDENTIFIER ::= { h3cevtModuleSwitchType 376 } -- 20-Port 1000BASE-X Optical Interface Card,(SFP,LC)

h3cevtModuleSw-SR01DPLP8L                  OBJECT IDENTIFIER ::= { h3cevtModuleSwitchType 377 } -- 8-Port 155M POS Optical Interface Card,(SFP,LC)

h3cevtModuleSw-SR01DXP2R                   OBJECT IDENTIFIER ::= { h3cevtModuleSwitchType 378 } -- 2-Port 10GBASE-R/W Ethernet Optical Interface Card,(XFP,LC)

h3cevtModuleSw-LSB1FW2A0                   OBJECT IDENTIFIER ::= { h3cevtModuleSwitchType 379 } -- Gigabit Firewall Card, 4 Gigabit Port for Management

h3cevtModuleSw-LSB1GP48LDB                 OBJECT IDENTIFIER ::= { h3cevtModuleSwitchType 380 } -- 48-Port Line Rate Gigabit Ethernet Optical Interface Card(DB)

h3cevtModuleSw-SR01LN1BNA0                 OBJECT IDENTIFIER ::= { h3cevtModuleSwitchType 381 } -- Single XG Service Board(BNA)

h3cevtModuleSw-SR01LN2BQH0                 OBJECT IDENTIFIER ::= { h3cevtModuleSwitchType 382 } -- Dual XG Service Board(BQH)

h3cevtModuleSw-SR01LN2BNA0                 OBJECT IDENTIFIER ::= { h3cevtModuleSwitchType 383 } -- Dual XG Service Board(BNA)

h3cevtModuleSw-SR01DGT20R                  OBJECT IDENTIFIER ::= { h3cevtModuleSwitchType 384 } -- 20-Port 10/100/1000BASE-T Electrical Interface Card,(RJ45)

h3cevtModuleSw-SR01DPSP4L                  OBJECT IDENTIFIER ::= { h3cevtModuleSwitchType 385 } -- 4-Port 2.5G POS Optical Interface Card(SFP,LC)

h3cevtModuleSw-SR01DPUP1L                  OBJECT IDENTIFIER ::= { h3cevtModuleSwitchType 386 } -- 1-Port 10G POS Optical Interface Card,(XFP,LC)

h3cevtModuleSw-SR01DPL2G6L                 OBJECT IDENTIFIER ::= { h3cevtModuleSwitchType 387 } -- 2-Port 155M POS Optical Interface(SFP,LC)+6-Port 1000BASE-X Optical Interface Card(SFP,LC)

h3cevtModuleSw-SR01DPH2G6L                 OBJECT IDENTIFIER ::= { h3cevtModuleSwitchType 388 } -- 2-Port 622M POS Optical Interface(SFP,LC)+6-Port 1000BASE-X Optical Interface Card(SFP,LC)

h3cevtModuleSw-SR01DPS2G4L                 OBJECT IDENTIFIER ::= { h3cevtModuleSwitchType 389 } -- 2-Port 2.5G POS Optical Interface(SFP,LC)+4-Port 1000BASE-X Optical Interface Card(SFP,LC)

h3cevtModuleSw-SR01DCL1G8L                 OBJECT IDENTIFIER ::= { h3cevtModuleSwitchType 390 } -- 1-Port 155M CPOS Optical Interface(SFP,LC)+8-Port 1000BASE-X Optical Interface Card(SFP,LC)

h3cevtModuleSw-SR01DCL2G8L                 OBJECT IDENTIFIER ::= { h3cevtModuleSwitchType 391 } -- 2-Port 155M CPOS Optical Interface(SFP,LC)+8-Port 1000BASE-X Optical Interface Card(SFP,LC)

h3cevtModuleSw-SR01DET8G8L                 OBJECT IDENTIFIER ::= { h3cevtModuleSwitchType 392 } -- 8-Port E1/T1 Electrical Interface(RJ45)+8-Port 1000BASE-X Optical Interface Card(SFP,LC)

h3cevtModuleSw-SR02SRP2E3                  OBJECT IDENTIFIER ::= { h3cevtModuleSwitchType 393 } -- Switching and Route Process Unit, Clock module

h3cevtModuleSw-SR02SRP1E3                  OBJECT IDENTIFIER ::= { h3cevtModuleSwitchType 394 } -- Switching and Route Process Unit, Clock module

h3cevtModuleSw-SR02SRP1M3                  OBJECT IDENTIFIER ::= { h3cevtModuleSwitchType 395 } -- Switching and Route Process Unit, Clock module

h3cevtModuleSw-SR01DQCP4L                  OBJECT IDENTIFIER ::= { h3cevtModuleSwitchType 396 } -- 4-Port OC-3c/OC-12c/OC-48c POS/GE Optical Interface Card,(SFP,LC)

h3cevtModuleSw-SR01DTCP8L                  OBJECT IDENTIFIER ::= { h3cevtModuleSwitchType 397 } -- 8-Port OC-3c/OC-12c POS/GE Optical Interface Card,(SFP,LC)

h3cevtModuleSw-LSB1AFC1A0                  OBJECT IDENTIFIER ::= { h3cevtModuleSwitchType 398 } -- Anomaly Flow Cleaner Board

h3cevtModuleSw-LSB1SSL1A0                  OBJECT IDENTIFIER ::= { h3cevtModuleSwitchType 399 } -- SSL VPN High-end Board

h3cevtModuleSw-IMNAM                       OBJECT IDENTIFIER ::= { h3cevtModuleSwitchType 400 } -- Net Analysis Service Processing Board

h3cevtModuleSw-IMNAT                       OBJECT IDENTIFIER ::= { h3cevtModuleSwitchType 401 } -- Network Address Translation Service Processing Board

h3cevtModuleSw-PICAHP1L                    OBJECT IDENTIFIER ::= { h3cevtModuleSwitchType 402 } -- 1-Port OC-12c/STM-4c ATM Optical Interface Card,(SFP,LC)

h3cevtModuleSw-PICALP4L                    OBJECT IDENTIFIER ::= { h3cevtModuleSwitchType 403 } -- 4-Port OC-3c/STM-1c ATM Optical Interface Card,(SFP,LC)

h3cevtModuleSw-PICCHP4L                    OBJECT IDENTIFIER ::= { h3cevtModuleSwitchType 404 } -- 4-Port 622M CPOS Optical Interface Card(SFP,LC)

h3cevtModuleSw-PICCHS1G4L                  OBJECT IDENTIFIER ::= { h3cevtModuleSwitchType 405 } -- 1-Port 622M CPOS Optical Interface(Channelized to E3/T3)+4-Port 1000BASE-X Optical Interface Card(SFP,LC)

h3cevtModuleSw-PICCLS4G4L                  OBJECT IDENTIFIER ::= { h3cevtModuleSwitchType 406 } -- 4-Port 155M CPOS Optical Interface(Channelized to E3/T3)+4-Port 1000BASE-X Optical Interface Card(SFP,LC)

h3cevtModuleSw-PICCSP1L                    OBJECT IDENTIFIER ::= { h3cevtModuleSwitchType 407 } -- 1-Port 2.5G CPOS Optical Interface Card(SFP,LC)

h3cevtModuleSw-LSB1ACG1A0                  OBJECT IDENTIFIER ::= { h3cevtModuleSwitchType 408 } -- Application Control Gateway Board

h3cevtModuleSw-LST1MRPNC1                  OBJECT IDENTIFIER ::= { h3cevtModuleSwitchType 409 } -- Management and Route Process Unit

h3cevtModuleSw-LST1SF18B1                  OBJECT IDENTIFIER ::= { h3cevtModuleSwitchType 410 } -- S12518 Switch Fabric Card

h3cevtModuleSw-LST1SF08B1                  OBJECT IDENTIFIER ::= { h3cevtModuleSwitchType 411 } -- S12508 Switch Fabric Card

h3cevtModuleSw-LST1GT48LEC1                OBJECT IDENTIFIER ::= { h3cevtModuleSwitchType 412 } -- 48-Port 10/100/1000BASE-T Interface Module(LEC),(RJ45)

h3cevtModuleSw-LST1GP48LEC1                OBJECT IDENTIFIER ::= { h3cevtModuleSwitchType 413 } -- 48-Port 1000BASE-X Interface Module (LEC),(SFP,LC)

h3cevtModuleSw-LST1XP4LEC1                 OBJECT IDENTIFIER ::= { h3cevtModuleSwitchType 414 } -- 4-Port 10GBASE-R/W Interface Module (LEC),(XFP,LC)

h3cevtModuleSw-LST1XP8LEC1                 OBJECT IDENTIFIER ::= { h3cevtModuleSwitchType 415 } -- 8-Port 10GBASE-R/W Interface Module (LEC),(XFP,LC)

h3cevtModuleSw-LSR1SRP2B1                  OBJECT IDENTIFIER ::= { h3cevtModuleSwitchType 416 } -- Switching and Route Process Unit

h3cevtModuleSw-LSR1SRP2C1                  OBJECT IDENTIFIER ::= { h3cevtModuleSwitchType 417 } -- Switching and Route Process Unit

h3cevtModuleSw-LSR1SRP2B2                  OBJECT IDENTIFIER ::= { h3cevtModuleSwitchType 418 } -- Switching and Route Process Unit

h3cevtModuleSw-LSR1SRP2C2                  OBJECT IDENTIFIER ::= { h3cevtModuleSwitchType 419 } -- Switching and Route Process Unit

h3cevtModuleSw-LSR1GT24LEC1                OBJECT IDENTIFIER ::= { h3cevtModuleSwitchType 420 } -- 16-Port 10/100/1000BASE-T Interface and 8-port 1000BASE-T/1000BASE-X Combo Interface Service Card(LEC)

h3cevtModuleSw-LSR1GP24LEB1                OBJECT IDENTIFIER ::= { h3cevtModuleSwitchType 421 } -- 16-Port 1000BASE-X Interface and 8-port 1000BASE-T/1000BASE-X Combo Interface Service Card(LEB)

h3cevtModuleSw-LSR1GP24LEC1                OBJECT IDENTIFIER ::= { h3cevtModuleSwitchType 422 } -- 16-Port 1000BASE-X Interface and 8-port 1000BASE-T/1000BASE-X Combo Interface Service Card(LEC)

h3cevtModuleSw-LSR1GT48LEB1                OBJECT IDENTIFIER ::= { h3cevtModuleSwitchType 423 } -- 48-Port 10/100/1000BASE-T Interface Module(LEB),(RJ45)

h3cevtModuleSw-LSR1GT48LEC1                OBJECT IDENTIFIER ::= { h3cevtModuleSwitchType 424 } -- 48-Port 10/100/1000BASE-T Interface Module(LEC),(RJ45)

h3cevtModuleSw-LSR1GP48LEB1                OBJECT IDENTIFIER ::= { h3cevtModuleSwitchType 425 } -- 48-Port 1000BASE-X Interface Module(LEB),(SFP,LC)

h3cevtModuleSw-LSR1GP48LEC1                OBJECT IDENTIFIER ::= { h3cevtModuleSwitchType 426 } -- 48-Port 1000BASE-X Interface Module(LEC),(SFP,LC)

h3cevtModuleSw-LSR2GV48REB1                OBJECT IDENTIFIER ::= { h3cevtModuleSwitchType 427 } -- 48-Port 10/100/1000BASE-T Interface Module(REB),(PoE,RJ45)

h3cevtModuleSw-LSR1XP2LEB1                 OBJECT IDENTIFIER ::= { h3cevtModuleSwitchType 428 } -- 2-Port 10GBase-R/W Interface Module (LEB),(XFP,LC)

h3cevtModuleSw-LSR1XP2LEC1                 OBJECT IDENTIFIER ::= { h3cevtModuleSwitchType 429 } -- 2-Port 10GBase-R/W Interface Module (LEC),(XFP,LC)

h3cevtModuleSw-LSR1XP4LEB1                 OBJECT IDENTIFIER ::= { h3cevtModuleSwitchType 430 } -- 4-Port 10GBase-R/W Interface Module (LEB),(XFP,LC)

h3cevtModuleSw-LSR1XP4LEC1                 OBJECT IDENTIFIER ::= { h3cevtModuleSwitchType 431 } -- 4-Port 10GBase-R/W Interface Module (LEC),(XFP,LC)

h3cevtModuleSw-IMFW                        OBJECT IDENTIFIER ::= { h3cevtModuleSwitchType 432 } -- Firewall Service Processing Board

h3cevtModuleSw-LSB1LB1A0                   OBJECT IDENTIFIER ::= { h3cevtModuleSwitchType 433 } -- Load Balance Board

h3cevtModuleSw-LSB1IPS1A0                  OBJECT IDENTIFIER ::= { h3cevtModuleSwitchType 434 } -- Gigabit IPS Card

h3cevtModuleSw-LST1GT48LEB1                OBJECT IDENTIFIER ::= { h3cevtModuleSwitchType 435 } -- 48-Port 10/100/1000BASE-T Interface Module(LEB),(RJ45)

h3cevtModuleSw-LST1GP48LEB1                OBJECT IDENTIFIER ::= { h3cevtModuleSwitchType 436 } -- 48-Port 1000BASE-X Interface Module (LEB),(SFP,LC)

h3cevtModuleSw-LST1XP4LEB1                 OBJECT IDENTIFIER ::= { h3cevtModuleSwitchType 437 } -- 4-Port 10GBASE-R/W Interface Module (LEB),(XFP,LC)

h3cevtModuleSw-LST1XP8LEB1                 OBJECT IDENTIFIER ::= { h3cevtModuleSwitchType 438 } -- 8-Port 10GBASE-R/W Interface Module (LEB),(XFP,LC)

h3cevtModuleSw-LST1XP32REB1                OBJECT IDENTIFIER ::= { h3cevtModuleSwitchType 439 } -- 32-Port 10GBASE-R Interface Module (REB),(SFP+,LC)

h3cevtModuleSw-LST1XP32REC1                OBJECT IDENTIFIER ::= { h3cevtModuleSwitchType 440 } -- 32-Port 10GBASE-R Interface Module (REC),(SFP+,LC)

h3cevtModuleSw-LSR1FW2A1                   OBJECT IDENTIFIER ::= { h3cevtModuleSwitchType 441 } -- Firewall Service Module

h3cevtModuleSw-LSR1SSL1A1                  OBJECT IDENTIFIER ::= { h3cevtModuleSwitchType 442 } -- SSL VPN Service Module

h3cevtModuleSw-SR01DET32G2L                OBJECT IDENTIFIER ::= { h3cevtModuleSwitchType 443 } -- 32-Port E1/T1 75ohm Electrical Interface(DB56 Female Socket)+2-Port 1000BASE-X Optical Interface Card(SFP,LC)

h3cevtModuleSw-LSR1GP24LEF1                OBJECT IDENTIFIER ::= { h3cevtModuleSwitchType 444 } -- 16-Port 1000BASE-X Interface and 8-port 1000BASE-T/1000BASE-X Combo Interface Service Card(LEF)

h3cevtModuleSw-LSR1XP4LEF1                 OBJECT IDENTIFIER ::= { h3cevtModuleSwitchType 445 } -- 4-Port 10GBASE-R/W Interface Module (LEF),(XFP,LC)

--
-- 500 to 699 reserved for secondary switches
--
h3cevtModuleSw-LS81GP16TM                  OBJECT IDENTIFIER ::= { h3cevtModuleSwitchType 500 } -- 12-port 1000BASE-X SFP Interface and 4-port 1000BASE-T/1000BASE-X Combo Interface Metro Switch and Route Processing Board

h3cevtModuleSw-LS81VP4C                    OBJECT IDENTIFIER ::= { h3cevtModuleSwitchType 501 } -- 4-port 1000BASE-X SFP Interface Virtual Daughter Card

h3cevtModuleSw-LS8M1PT8P0                  OBJECT IDENTIFIER ::= { h3cevtModuleSwitchType 502 } -- 8-Port 1000BASE-PX Optical Line Interface Board, SFP Req

h3cevtModuleSw-LS8M1PT8GB0                 OBJECT IDENTIFIER ::= { h3cevtModuleSwitchType 503 } -- 8-Port 1000BASE-PX20 Gigabit Passive Optical Line Interface Board B(20km, SFF), SC Connector

h3cevtModuleSw-LS8M1PT4GB0                 OBJECT IDENTIFIER ::= { h3cevtModuleSwitchType 504 } -- 4-Port 1000BASE-PX20 Gigabit Passive Optical Line Interface Board B(20km, SFF), SC Connector

h3cevtModuleSw-LS81GP2R                    OBJECT IDENTIFIER ::= { h3cevtModuleSwitchType 505 } -- 2-port 1000M Ethernet Optical Interface RPR Board

h3cevtModuleSw-LS81GP4R                    OBJECT IDENTIFIER ::= { h3cevtModuleSwitchType 506 } -- 4-port 1000M Ethernet Optical Interface RPR Board

h3cevtModuleSw-LS81IPSECA                  OBJECT IDENTIFIER ::= { h3cevtModuleSwitchType 507 } -- IPSec Service Board

h3cevtModuleSw-LS81FWA                     OBJECT IDENTIFIER ::= { h3cevtModuleSwitchType 508 } -- Firewall Service Board

h3cevtModuleSw-LS82VSNP                    OBJECT IDENTIFIER ::= { h3cevtModuleSwitchType 509 } -- Versatile Network Processing Service Module (PBR/NAT/NetStream) with 12-port 1000BASE-X SFP, XGBUS Uplink

h3cevtModuleSw-LSQ1GV48SA                  OBJECT IDENTIFIER ::= { h3cevtModuleSwitchType 510 } -- 48-Port 1000Base-T Gigabit Ethernet Interface Board(RJ45)

h3cevtModuleSw-LSQ1SRPB                    OBJECT IDENTIFIER ::= { h3cevtModuleSwitchType 511 } -- Salience VI

h3cevtModuleSw-LSQ1SRP2XB                  OBJECT IDENTIFIER ::= { h3cevtModuleSwitchType 512 } -- Salience VI-10GE

h3cevtModuleSw-LSQ1SRP1CB                  OBJECT IDENTIFIER ::= { h3cevtModuleSwitchType 513 } -- Salience VI-Turbo

h3cevtModuleSw-LSQ1FV48SA                  OBJECT IDENTIFIER ::= { h3cevtModuleSwitchType 514 } -- 48-Port 100M Ethernet Electrical Interface Switch Unit(RJ45)

h3cevtModuleSw-LSD1MPUA                    OBJECT IDENTIFIER ::= { h3cevtModuleSwitchType 515 } -- Main Control Unit

h3cevtModuleSw-LSD1GP20A0                  OBJECT IDENTIFIER ::= { h3cevtModuleSwitchType 516 } -- 16-port 1000BASE-X SFP Interface and 4-port 1000BASE-T/1000BASE-X Combo Interface Line Card

h3cevtModuleSw-LSD1GP20TA0                 OBJECT IDENTIFIER ::= { h3cevtModuleSwitchType 517 } -- 16-port 1000BASE-X SFP Interface and 4-port 1000BASE-T/1000BASE-X Combo Interface and 16 1000BASE-T Interface Line Card

h3cevtModuleSw-LSD1GP36A0                  OBJECT IDENTIFIER ::= { h3cevtModuleSwitchType 518 } -- 32-port 1000BASE-X SFP Interface and 4-port 1000BASE-T/1000BASE-X Combo Interface Line Card

h3cevtModuleSw-LSD1GP20XA0                 OBJECT IDENTIFIER ::= { h3cevtModuleSwitchType 519 } -- 16-port 1000BASE-X SFP Interface and 4-port 1000BASE-T/1000BASE-X Combo Interface and 2-port 10GBASE-X XFP Interface Line Card

h3cevtModuleSw-LSD1GP20EA0                 OBJECT IDENTIFIER ::= { h3cevtModuleSwitchType 520 } -- 16-port 1000BASE-X SFP Interface and 4-port 1000BASE-T/1000BASE-X Combo Interface and 2-port GE RPR Interface Line Card

h3cevtModuleSw-LSD1GP20RA0                 OBJECT IDENTIFIER ::= { h3cevtModuleSwitchType 521 } -- 16-port 1000BASE-X SFP Interface and 4-port 1000BASE-T/1000BASE-X Combo Interface and 2-port OC48 RPR Interface Line Card

h3cevtModuleSw-LSD1GP16A0                  OBJECT IDENTIFIER ::= { h3cevtModuleSwitchType 522 } -- 16-port 1000BASE-X SFP Ethernet Interface SubCard

h3cevtModuleSw-LSD1GT16A0                  OBJECT IDENTIFIER ::= { h3cevtModuleSwitchType 523 } -- 16-port 1000BASE-T Ethernet Interface SubCard

h3cevtModuleSw-LSD1XP2A0                   OBJECT IDENTIFIER ::= { h3cevtModuleSwitchType 524 } -- 2-port 10GBASE-X XFP Ethernet Interface SubCard

h3cevtModuleSw-LSD1EP2A0                   OBJECT IDENTIFIER ::= { h3cevtModuleSwitchType 525 } -- 2-port 1000BASE-T Ethernet RPR Interface SubCard

h3cevtModuleSw-LSD1RP2A0                   OBJECT IDENTIFIER ::= { h3cevtModuleSwitchType 526 } -- 2-port OC48 RPR Interface SubCard

h3cevtModuleSw-LSQ1GV48SC                  OBJECT IDENTIFIER ::= { h3cevtModuleSwitchType 527 } -- 48-Port 1000Base-T Gigabit Ethernet Interface Board(RJ45)-POE

h3cevtModuleSw-LSQ1FP48SA                  OBJECT IDENTIFIER ::= { h3cevtModuleSwitchType 528 } -- 48 Port 100M Ethernet Optical Interface Board(SFP,LC)

h3cevtModuleSw-LSQ1GP24SC                  OBJECT IDENTIFIER ::= { h3cevtModuleSwitchType 529 } -- 24 Port 1000BASE-X Ethernet Optical Interface Board(SFP,LC)

h3cevtModuleSw-LSQ1GT24SC                  OBJECT IDENTIFIER ::= { h3cevtModuleSwitchType 530 } -- 24-Port 1000BASE-T Ethernet Interface Board (RJ45)

h3cevtModuleSw-LSQ1TGX2SC                  OBJECT IDENTIFIER ::= { h3cevtModuleSwitchType 531 } -- 2-Port 10GBASE Ethernet Optical Interface Board(XFP,LC)

h3cevtModuleSw-LSQ1GP12EA                  OBJECT IDENTIFIER ::= { h3cevtModuleSwitchType 532 } -- 12-Port 1000BASE-X Ethernet Optical Interface Board(SFP,LC)

h3cevtModuleSw-LSQ1TGX1EA                  OBJECT IDENTIFIER ::= { h3cevtModuleSwitchType 533 } -- 1-Port 10GBASE Ethernet Optical Interface Module(XFP,LC)

h3cevtModuleSw-LSQ1P24XGSC                 OBJECT IDENTIFIER ::= { h3cevtModuleSwitchType 534 } -- 24-Port 1000BASE-X Gigabit Ethernet Optical Interface(SFP,LC)+2-Port 10GBASE Ethernet Optical Interface Board(XFP,LC)

h3cevtModuleSw-LSQ1T24XGSC                 OBJECT IDENTIFIER ::= { h3cevtModuleSwitchType 535 } -- 24-Port 1000BASE-T Gigabit Ethernet Interface(RJ45)+2-Port 10GBASE Ethernet Optical Interface Board(XFP,LC)

h3cevtModuleSw-LS81TGX1B                   OBJECT IDENTIFIER ::= { h3cevtModuleSwitchType 536 } -- 1 Port 10GBase-R Ethernet Interface Board(XENPAK,SC)

h3cevtModuleSw-LSQ1PT4PSC0                 OBJECT IDENTIFIER ::= { h3cevtModuleSwitchType 537 } -- 4-Port 1000Base-PX Optical Line Terminal(EPON OLT SFP,SC)+8-Port 1000BASE-X Optical Interface Board(SFP,LC)

h3cevtModuleSw-LS81SRPG13                  OBJECT IDENTIFIER ::= { h3cevtModuleSwitchType 538 } -- Salience V, Switch and Route Processing Board

h3cevtModuleSw-LS81SRPG14                  OBJECT IDENTIFIER ::= { h3cevtModuleSwitchType 539 } -- Salience V Edge

h3cevtModuleSw-LS81SRPG15                  OBJECT IDENTIFIER ::= { h3cevtModuleSwitchType 540 } -- Salience V Plus

h3cevtModuleSw-LSQ1GP48SC0                 OBJECT IDENTIFIER ::= { h3cevtModuleSwitchType 541 } -- 48-Port 1000BASE Ethernet Optical Interface Board(SFP,LC)

h3cevtModuleSw-LSQ1GP12SC0                 OBJECT IDENTIFIER ::= { h3cevtModuleSwitchType 542 } -- 12-Port 1000BASE-X Ethernet Optical Interface Board(SFP,LC)

h3cevtModuleSw-LSD1SRPA                    OBJECT IDENTIFIER ::= { h3cevtModuleSwitchType 543 } -- Salience VIII 160

h3cevtModuleSw-LSD1SRPB                    OBJECT IDENTIFIER ::= { h3cevtModuleSwitchType 544 } -- Salience VIII 480

h3cevtModuleSw-LSD1SRPC                    OBJECT IDENTIFIER ::= { h3cevtModuleSwitchType 545 } -- Salience VIII 800

h3cevtModuleSw-LSD1GT16PES0                OBJECT IDENTIFIER ::= { h3cevtModuleSwitchType 546 } -- 16-Port 10/100/1000BASE-T and 8-Port 100/1000BASE-X SFP Interface Card

h3cevtModuleSw-LSD1GP24ES0                 OBJECT IDENTIFIER ::= { h3cevtModuleSwitchType 547 } -- 24-Port 1000BASE-X Ethernet SFP Interface Card

h3cevtModuleSw-LSD1GT24XES0                OBJECT IDENTIFIER ::= { h3cevtModuleSwitchType 548 } -- 24-Port 10/100/1000BASE-T and 2-port 10GBASE-X Ethernet XFP Optical Interface Card

h3cevtModuleSw-LSD1GP24XES0                OBJECT IDENTIFIER ::= { h3cevtModuleSwitchType 549 } -- 24-Port 1000BASE-X Ethernet SFP interface and 2-port 10GBASE-X Ethernet XFP Optical Interface Card

h3cevtModuleSw-LSD1XP2ES0                  OBJECT IDENTIFIER ::= { h3cevtModuleSwitchType 550 } -- 2-Port 10GBASE-X Ethernet XFP Optical Interface Card

h3cevtModuleSw-LSD1GP48ES0                 OBJECT IDENTIFIER ::= { h3cevtModuleSwitchType 551 } -- 48-Port 1000BASE-X Ethernet SFP Interface Card

h3cevtModuleSw-LSQ1MPUA0                   OBJECT IDENTIFIER ::= { h3cevtModuleSwitchType 552 } -- Master Process Board

h3cevtModuleSw-LSQ1MPUA1                   OBJECT IDENTIFIER ::= { h3cevtModuleSwitchType 553 } -- Master Process Unit

h3cevtModuleSw-LSQ1FWBSC0                  OBJECT IDENTIFIER ::= { h3cevtModuleSwitchType 554 } -- Gigabit Firewall Cardú¼4 Gigabit Port for Management

h3cevtModuleSw-LSQ1PT8PSC0                 OBJECT IDENTIFIER ::= { h3cevtModuleSwitchType 555 } -- 8-Port 1000Base-PX Optical Line Terminal(EPON OLT SFP,SC)+8-Port 1000BASE-X Optical Interface Board(SFP,LC)

h3cevtModuleSw-LSQ1PT16PSC0                OBJECT IDENTIFIER ::= { h3cevtModuleSwitchType 556 } -- 16-Port 1000Base-PX Optical Line Terminal(EPON OLT SFP,SC)+8-Port 1000BASE-X Optical Interface Board(SFP,LC)

h3cevtModuleSw-SA11MPUA0                   OBJECT IDENTIFIER ::= { h3cevtModuleSwitchType 557 } -- SmartEngine I-Lite

h3cevtModuleSw-SA11MPUB0                   OBJECT IDENTIFIER ::= { h3cevtModuleSwitchType 558 } -- SmartEngine I

h3cevtModuleSw-LSQ1AFCBSC0                 OBJECT IDENTIFIER ::= { h3cevtModuleSwitchType 559 } -- Anomaly Flow Cleaner Board Interface Board(SFP,LC)

h3cevtModuleSw-LSQ1MPUB0                   OBJECT IDENTIFIER ::= { h3cevtModuleSwitchType 560 } -- Salience VI-Lite

h3cevtModuleSw-LSQ1MPUB1                   OBJECT IDENTIFIER ::= { h3cevtModuleSwitchType 561 } -- Salience VI-Lite

h3cevtModuleSw-LSQ1PT4PSC1                 OBJECT IDENTIFIER ::= { h3cevtModuleSwitchType 562 } -- 4-Port 1000Base-PX Optical Line Terminal(EPON OLT SFP,SC)+8-Port 1000BASE-X Optical Interface Board(SFP,LC)

h3cevtModuleSw-LSQ1PT8PSC1                 OBJECT IDENTIFIER ::= { h3cevtModuleSwitchType 563 } -- 8-Port 1000Base-PX Optical Line Terminal(EPON OLT SFP,SC)+8-Port 1000BASE-X Optical Interface Board(SFP,LC)

h3cevtModuleSw-LSQ1PT16PSC1                OBJECT IDENTIFIER ::= { h3cevtModuleSwitchType 564 } -- 16-Port 1000Base-PX Optical Line Terminal(EPON OLT SFP,SC)+8-Port 1000BASE-X Optical Interface Board(SFP,LC)

h3cevtModuleSw-LSQ1FP48USA0                OBJECT IDENTIFIER ::= { h3cevtModuleSwitchType 565 } -- 48-Port 100M Ethernet Optical Interface Switch Unit(SFP,LC)

h3cevtModuleSw-LSQ1FP48USA1                OBJECT IDENTIFIER ::= { h3cevtModuleSwitchType 566 } -- 48-Port 100M Ethernet Optical Interface Switch Unit(SFP,LC)

h3cevtModuleSw-LSQ1FV48USA0                OBJECT IDENTIFIER ::= { h3cevtModuleSwitchType 567 } -- 48-Port 100M Ethernet Electrical Interface Switch Unit(RJ45),PoE

h3cevtModuleSw-LSQ1FV48USA1                OBJECT IDENTIFIER ::= { h3cevtModuleSwitchType 568 } -- 48-Port 100M Ethernet Electrical Interface Switch Unit(RJ45),PoE

h3cevtModuleSw-LSQ1SRPD0                   OBJECT IDENTIFIER ::= { h3cevtModuleSwitchType 569 } -- Switch and Route Processing Unit, Salience VI-Plus

h3cevtModuleSw-LSQ1CGP24TSC0               OBJECT IDENTIFIER ::= { h3cevtModuleSwitchType 570 } -- Switching and Routing Processing Unit with 24 1000BASE-X Gigabit Ethernet Optical Ports,including 8 Combo Ports,SFP Req.

h3cevtModuleSw-LSQ1GP24TSC0                OBJECT IDENTIFIER ::= { h3cevtModuleSwitchType 571 } -- 16-Port 1000BASE-X Gigabit Ethernet Optical(SFP,LC) And 8-Port 10/100/1000BASE-T RJ45/1000BASE-X SFP Combo Interface Board

h3cevtModuleSw-LSQ1ACGASC0                 OBJECT IDENTIFIER ::= { h3cevtModuleSwitchType 572 } -- Application Control Gateway Board

h3cevtModuleSw-LSD1XP1ES0                  OBJECT IDENTIFIER ::= { h3cevtModuleSwitchType 573 } -- 1-Port 10GBASE-X Ethernet XFP Optical Interface Card

h3cevtModuleSw-LSD1GP12ES0                 OBJECT IDENTIFIER ::= { h3cevtModuleSwitchType 574 } -- 12-Port 1000BASE-X Ethernet SFP Interface Card

h3cevtModuleSw-LSQ1SRP12GB0                OBJECT IDENTIFIER ::= { h3cevtModuleSwitchType 575 } -- Switch And Route Processing Unit with 12 1000BASE Ethernet Optical Interfaces(SFP,LC),Salience VI-GE

h3cevtModuleSw-LSQ1GV40PSC0                OBJECT IDENTIFIER ::= { h3cevtModuleSwitchType 576 } -- 40-Port 10/100/1000BASE-T Electrical(RJ45) And 8-Port 1000BASE-X Optical Ethernet Interface Board(SFP,LC),PoE

h3cevtModuleSw-LSQ1FWBSC1                  OBJECT IDENTIFIER ::= { h3cevtModuleSwitchType 577 } -- Firewall Board

h3cevtModuleSw-LSQ1NSMSC0                  OBJECT IDENTIFIER ::= { h3cevtModuleSwitchType 578 } -- NetStream Board

h3cevtModuleSw-LSQ1NSMSC1                  OBJECT IDENTIFIER ::= { h3cevtModuleSwitchType 579 } -- NetStream Board

h3cevtModuleSw-LSQ1AFDBSC0                 OBJECT IDENTIFIER ::= { h3cevtModuleSwitchType 580 } -- Anomaly Flow Detector Board

h3cevtModuleSw-LS81MPUB                    OBJECT IDENTIFIER ::= { h3cevtModuleSwitchType 581 } -- Salience IV

h3cevtModuleSw-LS81FP48XL                  OBJECT IDENTIFIER ::= { h3cevtModuleSwitchType 582 } -- 48-Port 100M Ethernet Optical Interface Module,(SFP,LC)

h3cevtModuleSw-LS81FT48XL                  OBJECT IDENTIFIER ::= { h3cevtModuleSwitchType 583 } -- 48-Port 10/100M Ethernet Electrical Interface Module(RJ45)

h3cevtModuleSw-LS81GP12XL                  OBJECT IDENTIFIER ::= { h3cevtModuleSwitchType 584 } -- 12-Port 1000/100M Ethernet Optical Interface Module(SFP,LC)

h3cevtModuleSw-LS81GP24XL                  OBJECT IDENTIFIER ::= { h3cevtModuleSwitchType 585 } -- 24-Port 1000/100M Ethernet Optical Interface Module(SFP,LC)

h3cevtModuleSw-LS81GP48XL                  OBJECT IDENTIFIER ::= { h3cevtModuleSwitchType 586 } -- 48-Port 1000/100M Ethernet Optical Interface Module(SFP,LC)

h3cevtModuleSw-LS81GT24XL                  OBJECT IDENTIFIER ::= { h3cevtModuleSwitchType 587 } -- 24-Port 10/100/1000M Ethernet Electrical Interface Module(RJ45)

h3cevtModuleSw-LS81GT48XL                  OBJECT IDENTIFIER ::= { h3cevtModuleSwitchType 588 } -- 48-Port 10/100/1000M Ethernet Electrical Interface Module(RJ45)

h3cevtModuleSw-LS81TGX2XL                  OBJECT IDENTIFIER ::= { h3cevtModuleSwitchType 589 } -- 2-Port 10GBASE Ethernet Optical Interface Module(XFP,LC)

h3cevtModuleSw-LSQ1GV48SD0                 OBJECT IDENTIFIER ::= { h3cevtModuleSwitchType 590 } -- 48-Port 1000Base-T Gigabit Ethernet Interface Board(RJ45),PoE

h3cevtModuleSw-LSQ1GP48EB0                 OBJECT IDENTIFIER ::= { h3cevtModuleSwitchType 591 } -- 48-Port Enhanced 1000BASE-X Ethernet Optical Interface Board(SFP,LC)

h3cevtModuleSw-LSQ1IPSSC0                  OBJECT IDENTIFIER ::= { h3cevtModuleSwitchType 592 } -- Gigabit IPS Card

h3cevtModuleSw-LSQ1GV48SD1                 OBJECT IDENTIFIER ::= { h3cevtModuleSwitchType 593 } -- 48-Port 1000Base-T Gigabit Ethernet Interface Board(RJ45),PoE

h3cevtModuleSw-LSQ1GP48SD0                 OBJECT IDENTIFIER ::= { h3cevtModuleSwitchType 594 } -- 48-Port 1000BASE-X Gigabit Ethernet Optical Interface(SFP,LC) Interface Board

h3cevtModuleSw-LSQ1GP48SD1                 OBJECT IDENTIFIER ::= { h3cevtModuleSwitchType 595 } -- 48-Port 1000BASE-X Gigabit Ethernet Optical Interface(SFP,LC) Interface Board

h3cevtModuleSw-LSQ1SRPA0                   OBJECT IDENTIFIER ::= { h3cevtModuleSwitchType 596 } -- Salience VI-Smart

h3cevtModuleSw-LSQ1SRPA1                   OBJECT IDENTIFIER ::= { h3cevtModuleSwitchType 597 } -- Salience VI-Smart

h3cevtModuleSw-LSQ2FP48SA0                 OBJECT IDENTIFIER ::= { h3cevtModuleSwitchType 598 } -- 48 Port 100M Ethernet Optical Interface Board(SFP,LC)

h3cevtModuleSw-LSQ2FP48SA1                 OBJECT IDENTIFIER ::= { h3cevtModuleSwitchType 599 } -- 48 Port 100M Ethernet Optical Interface Board(SFP,LC)

h3cevtModuleSw-LSQ2FT48SA0                 OBJECT IDENTIFIER ::= { h3cevtModuleSwitchType 600 } -- 48-Port 100M Ethernet Electrical Interface Switch Unit(RJ45)

h3cevtModuleSw-LSQ2FT48SA1                 OBJECT IDENTIFIER ::= { h3cevtModuleSwitchType 601 } -- 48-Port 100M Ethernet Electrical Interface Switch Unit(RJ45)

h3cevtModuleSw-LSQ1GV24PSC0                OBJECT IDENTIFIER ::= { h3cevtModuleSwitchType 602 } -- 24-Port 10/100/1000BASE-T Electrical(RJ45) Interface Board,including 4 Combo Ports,SFP Req,PoE,No Spell

h3cevtModuleSw-LSQ1GV24PSC1                OBJECT IDENTIFIER ::= { h3cevtModuleSwitchType 603 } -- 24-Port 10/100/1000BASE-T Electrical(RJ45) Interface Board,including 4 Combo Ports,SFP Req,PoE,No Spell

h3cevtModuleSw-LSQ1CGV24PSC0               OBJECT IDENTIFIER ::= { h3cevtModuleSwitchType 604 } -- Switching and Routing Processing Unit with 24 10/100/1000BASE-T Electrical Ports(RJ45),including 4 Combo Ports,SFP Req,PoE,No Spell

h3cevtModuleSw-LSQ1CGV24PSC1               OBJECT IDENTIFIER ::= { h3cevtModuleSwitchType 605 } -- Switching and Routing Processing Unit with 24 10/100/1000BASE-T Electrical Ports(RJ45),including 4 Combo Ports,SFP Req,PoE,No Spell

h3cevtModuleSw-LSQ1GP24TEB0                OBJECT IDENTIFIER ::= { h3cevtModuleSwitchType 606 } -- 16-Port 1000BASE-X Gigabit Ethernet Optical Interface(SFP,LC)+8-Port Combo Interface Board

h3cevtModuleSw-LSQ1GP24TEB1                OBJECT IDENTIFIER ::= { h3cevtModuleSwitchType 607 } -- 16-Port 1000BASE-X Gigabit Ethernet Optical Interface(SFP,LC)+8-Port Combo Interface Board

h3cevtModuleSw-LSQ1GP24TSD0                OBJECT IDENTIFIER ::= { h3cevtModuleSwitchType 608 } -- 16-Port 1000BASE-X Gigabit Ethernet Optical Interface(SFP,LC)+8-Port Combo Interface Board

h3cevtModuleSw-LSQ1GP24TSD1                OBJECT IDENTIFIER ::= { h3cevtModuleSwitchType 609 } -- 16-Port 1000BASE-X Gigabit Ethernet Optical Interface(SFP,LC)+8-Port Combo Interface Board

h3cevtModuleSw-LSQ1GP24TXSD0               OBJECT IDENTIFIER ::= { h3cevtModuleSwitchType 610 } -- 16-Port GE Optical Interface(SFP,LC)+8-Port Combo Interface+2-Port 10GE Optical Interface Board(XFP,LC)

h3cevtModuleSw-LSQ1GP24TXSD1               OBJECT IDENTIFIER ::= { h3cevtModuleSwitchType 611 } -- 16-Port GE Optical Interface(SFP,LC)+8-Port Combo Interface+2-Port 10GE Optical Interface Board(XFP,LC)

h3cevtModuleSw-LSQ1TGX2EB0                 OBJECT IDENTIFIER ::= { h3cevtModuleSwitchType 612 } -- 2-Port 10GBASE Ethernet Optical Interface Board(XFP,LC)

h3cevtModuleSw-LSQ1TGX2EB1                 OBJECT IDENTIFIER ::= { h3cevtModuleSwitchType 613 } -- 2-Port 10GBASE Ethernet Optical Interface Board(XFP,LC)

h3cevtModuleSw-LSQ1TGX2SD0                 OBJECT IDENTIFIER ::= { h3cevtModuleSwitchType 614 } -- 2-Port 10GBASE Ethernet Optical Interface Board(XFP,LC)

h3cevtModuleSw-LSQ1TGX2SD1                 OBJECT IDENTIFIER ::= { h3cevtModuleSwitchType 615 } -- 2-Port 10GBASE Ethernet Optical Interface Board(XFP,LC)

h3cevtModuleSw-LSQ1TGX4SD0                 OBJECT IDENTIFIER ::= { h3cevtModuleSwitchType 616 } -- 4-Port 10GBASE Ethernet Optical Interface Board(XFP,LC)

h3cevtModuleSw-LSQ1TGX4SD1                 OBJECT IDENTIFIER ::= { h3cevtModuleSwitchType 617 } -- 4-Port 10GBASE Ethernet Optical Interface Board(XFP,LC)

h3cevtModuleSw-LSQ1TGX8SD0                 OBJECT IDENTIFIER ::= { h3cevtModuleSwitchType 618 } -- 8-Port 10GBASE Ethernet Optical Interface Board(XFP,LC)

h3cevtModuleSw-LSQ1TGX8SD1                 OBJECT IDENTIFIER ::= { h3cevtModuleSwitchType 619 } -- 8-Port 10GBASE Ethernet Optical Interface Board(XFP,LC)

h3cevtModuleSw-LSQ1GP48EB1                 OBJECT IDENTIFIER ::= { h3cevtModuleSwitchType 620 } -- 48-Port Enhanced 1000BASE-X Ethernet Optical Interface Board(SFP,LC)

h3cevtModuleSw-LSQ1TGX4EB0                 OBJECT IDENTIFIER ::= { h3cevtModuleSwitchType 621 } -- 4-Port 10GBASE Ethernet Optical Interface Board(XFP,LC)

h3cevtModuleSw-LSQ1TGX4EB1                 OBJECT IDENTIFIER ::= { h3cevtModuleSwitchType 622 } -- 4-Port 10GBASE Ethernet Optical Interface Board(XFP,LC)

--
-- 700 to 799 reserved for primary switches
--
h3cevtModuleSw-1000BASE-X-COMBO            OBJECT IDENTIFIER ::= { h3cevtModuleSwitchType 701 } -- Single port 10/100/1000BASE-T/1000BASE-X Combo Interface Board

h3cevtModuleSw-EPON-1000M                  OBJECT IDENTIFIER ::= { h3cevtModuleSwitchType 702 } -- Optical Network Unit Interface Board

h3cevtModuleSw-1000BASE-FIXED-2SFP-T-2RJ45         OBJECT IDENTIFIER ::= { h3cevtModuleSwitchType 703 } -- 2 port 10/100/1000BASE-T and 2 port 1000BASE-X Interface Board

h3cevtModuleSw-100M-1550-BIDI              OBJECT IDENTIFIER ::= { h3cevtModuleSwitchType 704 }  -- 100BASE-X BIDI Interface Board, Tx 1550nm, Rx 1310nm

h3cevtModuleSw-100M-1310-BIDI              OBJECT IDENTIFIER ::= { h3cevtModuleSwitchType 705 }  -- 100BASE-X reverse Interface Board, Tx 1310nm, Rx 1550nm

h3cevtModuleSw-1000BASE-FIXED-4RJ45-4SFP-COMBO     OBJECT IDENTIFIER ::= { h3cevtModuleSwitchType 706 } -- 4 port 10/100/1000BASE-T and 4 port 1000BASE-X COMBO Interface Board

h3cevtModuleSw-LSH1PK2T                    OBJECT IDENTIFIER ::= { h3cevtModuleSwitchType 707 } -- OSM Interface Board

h3cevtModuleSw-LSPM2GP2P                   OBJECT IDENTIFIER ::= { h3cevtModuleSwitchType 708 } -- 2-Port 1000BASE-X SFP Module

h3cevtModuleSw-LSWM1GT16P                  OBJECT IDENTIFIER ::= { h3cevtModuleSwitchType 709 } -- 16-Port 10/100/1000BASE-T Ethernet Electrical Interface Module

h3cevtModuleSw-LSWM1GP16P                  OBJECT IDENTIFIER ::= { h3cevtModuleSwitchType 710 } -- 16-Port 100/1000BASE-X Ethernet Optical Interface Module

h3cevtModuleSw-LSWM1XP2P                   OBJECT IDENTIFIER ::= { h3cevtModuleSwitchType 711 } -- 2-Port 10G Ethernet XFP Optical Interface Module

h3cevtModuleSw-LSWM1XP4P                   OBJECT IDENTIFIER ::= { h3cevtModuleSwitchType 712 } -- 4-Port 10G Ethernet XFP Optical Interface Module

h3cevtModuleSw-LSWM1SP2P                   OBJECT IDENTIFIER ::= { h3cevtModuleSwitchType 713 } -- 2-Port 10G Ethernet SFP PLUS Optical Interface Module

h3cevtModuleSw-LSWM1SP4P                   OBJECT IDENTIFIER ::= { h3cevtModuleSwitchType 714 } -- 4-Port 10G Ethernet SFP PLUS Optical Interface Module

h3cevtModuleSw-LSWM148POEM                 OBJECT IDENTIFIER ::= { h3cevtModuleSwitchType 715 } -- 48 Port Mid Power PoE Module

h3cevtModuleSw-LSWM1FW10                   OBJECT IDENTIFIER ::= { h3cevtModuleSwitchType 716 } -- RMI CPU XLR 732, with Firewall software

h3cevtModuleSw-LSWM1WCM10                  OBJECT IDENTIFIER ::= { h3cevtModuleSwitchType 717 } -- RMI CPU XLR 732, with Wireless Access Controller software

h3cevtModuleSw-LSWM1IPS10                  OBJECT IDENTIFIER ::= { h3cevtModuleSwitchType 718 } -- RMI CPU XLR 732, with IPS/AV software

h3cevtModuleSw-IPS-T1000-M                 OBJECT IDENTIFIER ::= { h3cevtModuleSwitchType 720 } -- IPS for T1000-M mainboardú¡module

h3cevtModuleSw-IPS-T1000-A                 OBJECT IDENTIFIER ::= { h3cevtModuleSwitchType 721 } -- IPS for T1000-A mainboardú¡module

h3cevtModuleSw-IPS-T1000-S                 OBJECT IDENTIFIER ::= { h3cevtModuleSwitchType 722 } -- IPS for T1000-S mainboardú¡module

h3cevtModuleSw-IPS-GX4C                    OBJECT IDENTIFIER ::= { h3cevtModuleSwitchType 723 } -- four-port-gigabit-fiber-boardú¡module

h3cevtModuleSw-IPS-GT4C                    OBJECT IDENTIFIER ::= { h3cevtModuleSwitchType 724 } -- four-port-1000BASET-boardú¡module

h3cevtModuleSw-LSPM2SP2P                   OBJECT IDENTIFIER ::= { h3cevtModuleSwitchType 725 } -- 2-Port 10G Ethernet SFP PLUS Optical Interface Module


-- 800 to 899 reserved for WLAN products
h3cevtModuleSw-WX5002MPU                   OBJECT IDENTIFIER ::= { h3cevtModuleSwitchType 800 } -- Wireless Lan Control Board with 2-port 1000BASE-T/1000BASE-X Combo Interface

h3cevtModuleSw-LS8M1WCMA                   OBJECT IDENTIFIER ::= { h3cevtModuleSwitchType 801 } -- Wireless Lan Service Board

h3cevtModuleSw-EWPX1G24XA0                 OBJECT IDENTIFIER ::= { h3cevtModuleSwitchType 802 } -- 24-Port 1000BASE-T Gigabit Ethernet Interface(RJ45) and 4-port 1000BASE-T/1000BASE-X Combo Interface and 2-port 10GBASE Interface Line Card

h3cevtModuleSw-LSQ1WCMB0                   OBJECT IDENTIFIER ::= { h3cevtModuleSwitchType 803 } -- 1 Port 10GBASE Interface Board

h3cevtModuleSw-LSB1WCM2A0                  OBJECT IDENTIFIER ::= { h3cevtModuleSwitchType 804 } -- Wireless Controller Module Board

h3cevtModuleSw-EWPX1WCMB0                  OBJECT IDENTIFIER ::= { h3cevtModuleSwitchType 805 } -- 1 Port 10GBASE Interface Board

h3cevtModuleSw-EWPX1G24XC0                 OBJECT IDENTIFIER ::= { h3cevtModuleSwitchType 806 } -- 24-Port 1000BASE-T Gigabit Ethernet Interface(RJ45) and 4-port 1000BASE-T/1000BASE-X Combo Interface Line Card

h3cevtModuleSw-EWPX1WCMC0                  OBJECT IDENTIFIER ::= { h3cevtModuleSwitchType 807 } -- 1-Port 1000BASE-T Gigabit Ethernet of wireless Lan Service Board

h3cevtModuleSw-EWPX1FWA0                   OBJECT IDENTIFIER ::= { h3cevtModuleSwitchType 808 } -- Firewall Service Board

h3cevtModuleSw-EWPX1G10XC0                 OBJECT IDENTIFIER ::= { h3cevtModuleSwitchType 809 } -- 8-Port 1000BASE-T Gigabit Ethernet Interface(RJ45) and 2-port 1000BASE-X SFP Interface Line Card

h3cevtModuleSw-EWPX1WCM10C0                OBJECT IDENTIFIER ::= { h3cevtModuleSwitchType 810 } -- 1-Port 1000BASE-T Gigabit Ethernet of wireless Lan Service Board

h3cevtModuleSw-LSR1WCM2A1                  OBJECT IDENTIFIER ::= { h3cevtModuleSwitchType 811 } -- 1-Port 1000BASE-T Gigabit Ethernet of wireless Lan Service Board


-- Here define submodule for routers
h3cevtSubModuleRouter       OBJECT IDENTIFIER ::= { h3cevtModule 5 }


-- Here define submodule for switches
h3cevtSubModuleSwitch       OBJECT IDENTIFIER ::= { h3cevtModule 6 }

--
-- h3cevtPort section:
--

h3cevtPort          OBJECT IDENTIFIER ::= { h3cEntityVendortypeObjects 10 }
h3cevtPortUnknownPorts      OBJECT IDENTIFIER ::= { h3cevtPort 1 }
h3cevtPortCommonPorts       OBJECT IDENTIFIER ::= { h3cevtPort 2 }
h3cevtPortRouterType        OBJECT IDENTIFIER ::= { h3cevtPort 3 }
h3cevtPortSwitchType        OBJECT IDENTIFIER ::= { h3cevtPort 4 }


-- Below are ports used to router
h3cevtPortRt-Async          OBJECT IDENTIFIER ::= { h3cevtPortRouterType 1 }    -- Async interface

h3cevtPortRt-Analogmodem    OBJECT IDENTIFIER ::= { h3cevtPortRouterType 2 }    -- Analog modem interface

h3cevtPortRt-Atm            OBJECT IDENTIFIER ::= { h3cevtPortRouterType 3 }    --

h3cevtPortRt-AtmAdsl        OBJECT IDENTIFIER ::= { h3cevtPortRouterType 4 }    --

h3cevtPortRt-AtmShdsl       OBJECT IDENTIFIER ::= { h3cevtPortRouterType 5 }    --

h3cevtPortRt-AtmE1          OBJECT IDENTIFIER ::= { h3cevtPortRouterType 6 }    --

h3cevtPortRt-AtmT1          OBJECT IDENTIFIER ::= { h3cevtPortRouterType 7 }    --

h3cevtPortRt-AtmE3          OBJECT IDENTIFIER ::= { h3cevtPortRouterType 8 }    --

h3cevtPortRt-AtmT3          OBJECT IDENTIFIER ::= { h3cevtPortRouterType 9 }    --

h3cevtPortRt-Atm622M        OBJECT IDENTIFIER ::= { h3cevtPortRouterType 10 }   --

h3cevtPortRt-AtmImaE1       OBJECT IDENTIFIER ::= { h3cevtPortRouterType 11 }   --

h3cevtPortRt-AtmImaT1       OBJECT IDENTIFIER ::= { h3cevtPortRouterType 12 }   --

h3cevtPortRt-Atm25M         OBJECT IDENTIFIER ::= { h3cevtPortRouterType 13 }   --

h3cevtPortRt-Bri            OBJECT IDENTIFIER ::= { h3cevtPortRouterType 14 }   --

h3cevtPortRt-Console        OBJECT IDENTIFIER ::= { h3cevtPortRouterType 15 }   --

h3cevtPortRt-E1             OBJECT IDENTIFIER ::= { h3cevtPortRouterType 16 }   --

h3cevtPortRt-E3             OBJECT IDENTIFIER ::= { h3cevtPortRouterType 17 }   --

h3cevtPortRt-T1             OBJECT IDENTIFIER ::= { h3cevtPortRouterType 18 }   --

h3cevtPortRt-T3             OBJECT IDENTIFIER ::= { h3cevtPortRouterType 19 }   --

h3cevtPortRt-Cpos           OBJECT IDENTIFIER ::= { h3cevtPortRouterType 20 }   --

h3cevtPortRt-Ethernet       OBJECT IDENTIFIER ::= { h3cevtPortRouterType 21 }   --

h3cevtPortRt-Serial         OBJECT IDENTIFIER ::= { h3cevtPortRouterType 22 }   --

h3cevtPortRt-E1f            OBJECT IDENTIFIER ::= { h3cevtPortRouterType 23 }   --

h3cevtPortRt-T1f            OBJECT IDENTIFIER ::= { h3cevtPortRouterType 24 }   --

h3cevtPortRt-Pos            OBJECT IDENTIFIER ::= { h3cevtPortRouterType 25 }   --

h3cevtPortRt-Ge             OBJECT IDENTIFIER ::= { h3cevtPortRouterType 26 }   --

h3cevtPortRt-Aux            OBJECT IDENTIFIER ::= { h3cevtPortRouterType 27 }   --

--h3cevtPortRt-Null         OBJECT IDENTIFIER ::= { h3cevtPortRouterType 28 }   reserved

--h3cevtPortRt-Max          OBJECT IDENTIFIER ::= { h3cevtPortRouterType 29 }   reserved

h3cevtPortRt-VG-Fxs         OBJECT IDENTIFIER ::= { h3cevtPortRouterType 30 }   --

h3cevtPortRt-VG-Fxo         OBJECT IDENTIFIER ::= { h3cevtPortRouterType 31 }   --

h3cevtPortRt-VG-E1vi        OBJECT IDENTIFIER ::= { h3cevtPortRouterType 32 }   --

h3cevtPortRt-VG-T1vi        OBJECT IDENTIFIER ::= { h3cevtPortRouterType 33 }   --

h3cevtPortRt-Usb            OBJECT IDENTIFIER ::= { h3cevtPortRouterType 34 }   --

h3cevtPortRt-Ndec           OBJECT IDENTIFIER ::= { h3cevtPortRouterType 35 }   -- NDEC port, Encrypt card version 1.0

h3cevtPortRt-Cavium         OBJECT IDENTIFIER ::= { h3cevtPortRouterType 36 }   -- NDEC port, Encrypt card version 2.0

h3cevtPortRt-Fcm            OBJECT IDENTIFIER ::= { h3cevtPortRouterType 37 }   -- POS/Fast connect module port

h3cevtPortRt-E1vi           OBJECT IDENTIFIER ::= { h3cevtPortRouterType 38 }   -- E1VI port

h3cevtPortRt-T1vi           OBJECT IDENTIFIER ::= { h3cevtPortRouterType 39 }   -- T1VI port

h3cevtPortRt-Vi             OBJECT IDENTIFIER ::= { h3cevtPortRouterType 40 }   -- Voice port

h3cevtPortRt-Adls2Plus      OBJECT IDENTIFIER ::= { h3cevtPortRouterType 41 }   -- ADSL2Plus port

h3cevtPortRt-RADIO-AG       OBJECT IDENTIFIER ::= { h3cevtPortRouterType 42 }   -- 802.11ag Radio port

h3cevtPortRt-1exp           OBJECT IDENTIFIER ::= { h3cevtPortRouterType 43 }   -- 10GBASE-R/W Ethernet port

h3cevtPortRt-G-SHDSL-BIS    OBJECT IDENTIFIER ::= { h3cevtPortRouterType 44 }   -- 4 wire G.SHDSL.BIS interface

h3cevtPortRt-ONU-1000BASE-BX-SFF-SC    OBJECT IDENTIFIER ::= { h3cevtPortRouterType 45 }   -- 1000 BASE-BX SFF SC ONU Interface

h3cevtPortRt-CELLULAR       OBJECT IDENTIFIER ::= { h3cevtPortRouterType 46 }   -- 3G Wireless WAN Interface

-- Below are ports used to switches
--h3cevtPortSw-Unknown              OBJECT IDENTIFIER ::= { h3cevtPortSwitchType 0 }

h3cevtPortSw-10or100M               OBJECT IDENTIFIER ::= { h3cevtPortSwitchType 1 }    --

h3cevtPortSw-1000BaseLxSm           OBJECT IDENTIFIER ::= { h3cevtPortSwitchType 2 }    --

h3cevtPortSw-1000BaseSxMm           OBJECT IDENTIFIER ::= { h3cevtPortSwitchType 3 }    --

h3cevtPortSw-1000BaseTx             OBJECT IDENTIFIER ::= { h3cevtPortSwitchType 4 }    --

h3cevtPortSw-100MSinglemodeFx       OBJECT IDENTIFIER ::= { h3cevtPortSwitchType 5 }    --

h3cevtPortSw-100MMultimodeFx        OBJECT IDENTIFIER ::= { h3cevtPortSwitchType 6 }    --

h3cevtPortSw-100M100BaseTx          OBJECT IDENTIFIER ::= { h3cevtPortSwitchType 7 }    --

h3cevtPortSw-100MHub                OBJECT IDENTIFIER ::= { h3cevtPortSwitchType 8 }    --

h3cevtPortSw-Vdsl                   OBJECT IDENTIFIER ::= { h3cevtPortSwitchType 9 }    --

h3cevtPortSw-Stack                  OBJECT IDENTIFIER ::= { h3cevtPortSwitchType 10 }   --

h3cevtPortSw-1000BaseZenithFx       OBJECT IDENTIFIER ::= { h3cevtPortSwitchType 11 }   --

h3cevtPortSw-1000BaseLongFx         OBJECT IDENTIFIER ::= { h3cevtPortSwitchType 12 }   --

h3cevtPortSw-Adsl                   OBJECT IDENTIFIER ::= { h3cevtPortSwitchType 13 }   --

h3cevtPortSw-10or100MDb             OBJECT IDENTIFIER ::= { h3cevtPortSwitchType 14 }   --

h3cevtPortSw-10GBaseLrSm            OBJECT IDENTIFIER ::= { h3cevtPortSwitchType 15 }   --

h3cevtPortSw-10GBaseLx4Mm           OBJECT IDENTIFIER ::= { h3cevtPortSwitchType 16 }   --

h3cevtPortSw-10GBaseLx4Sm           OBJECT IDENTIFIER ::= { h3cevtPortSwitchType 17 }   --

h3cevtPortSw-100MLongFx             OBJECT IDENTIFIER ::= { h3cevtPortSwitchType 18 }   --

h3cevtPortSw-1000BaseCx             OBJECT IDENTIFIER ::= { h3cevtPortSwitchType 19 }   --

h3cevtPortSw-1000BaseZenithFxLc     OBJECT IDENTIFIER ::= { h3cevtPortSwitchType 20 }   --

h3cevtPortSw-1000BaseLongFxLc       OBJECT IDENTIFIER ::= { h3cevtPortSwitchType 21 }   --

h3cevtPortSw-100MSmFxSc             OBJECT IDENTIFIER ::= { h3cevtPortSwitchType 22 }   --

h3cevtPortSw-100MMmFxSc             OBJECT IDENTIFIER ::= { h3cevtPortSwitchType 23 }   --

h3cevtPortSw-100MSmFxLc             OBJECT IDENTIFIER ::= { h3cevtPortSwitchType 24 }   --

h3cevtPortSw-100MMmFxLc             OBJECT IDENTIFIER ::= { h3cevtPortSwitchType 25 }   --

h3cevtPortSw-GbicNoConnector        OBJECT IDENTIFIER ::= { h3cevtPortSwitchType 26 }   --

h3cevtPortSw-Gbic1000BaseT          OBJECT IDENTIFIER ::= { h3cevtPortSwitchType 27 }   --

h3cevtPortSw-Gbic1000BaseLx         OBJECT IDENTIFIER ::= { h3cevtPortSwitchType 28 }   --

h3cevtPortSw-Gbic1000BaseSx         OBJECT IDENTIFIER ::= { h3cevtPortSwitchType 29 }   --

h3cevtPortSw-Gbic1000BaseZx         OBJECT IDENTIFIER ::= { h3cevtPortSwitchType 30 }   --

h3cevtPortSw-ComboNoConnector       OBJECT IDENTIFIER ::= { h3cevtPortSwitchType 31 }   --

h3cevtPortSw-Combo1000BaseLx        OBJECT IDENTIFIER ::= { h3cevtPortSwitchType 32 }   --

h3cevtPortSw-Combo1000BaseLxFiber   OBJECT IDENTIFIER ::= { h3cevtPortSwitchType 33 }   --

h3cevtPortSw-Combo1000BaseLxCopper  OBJECT IDENTIFIER ::= { h3cevtPortSwitchType 34 }   --

h3cevtPortSw-Combo1000BaseSx        OBJECT IDENTIFIER ::= { h3cevtPortSwitchType 35 }   --

h3cevtPortSw-Combo1000BaseSxFiber   OBJECT IDENTIFIER ::= { h3cevtPortSwitchType 36 }   --

h3cevtPortSw-Combo1000BaseSxCopper  OBJECT IDENTIFIER ::= { h3cevtPortSwitchType 37 }   --

h3cevtPortSw-Combo1000BaseZx        OBJECT IDENTIFIER ::= { h3cevtPortSwitchType 38 }   --

h3cevtPortSw-Combo1000BaseZxFiber   OBJECT IDENTIFIER ::= { h3cevtPortSwitchType 39 }   --

h3cevtPortSw-Combo1000BaseZxCopper  OBJECT IDENTIFIER ::= { h3cevtPortSwitchType 40 }   --

h3cevtPortSw-155PosSxMmf            OBJECT IDENTIFIER ::= { h3cevtPortSwitchType 41 }   --

h3cevtPortSw-155PosLxSmf            OBJECT IDENTIFIER ::= { h3cevtPortSwitchType 42 }   --

-- added by Garibaldi

h3cevtPortSw-1000BASE-T             OBJECT IDENTIFIER ::= { h3cevtPortSwitchType 43 }   -- 1000 Base-T Port

h3cevtPortSw-1000BASE-SX-SFP        OBJECT IDENTIFIER ::= { h3cevtPortSwitchType 44 }   -- 1000 Base-SX SFP Port

h3cevtPortSw-1000BASE-LX-SFP        OBJECT IDENTIFIER ::= { h3cevtPortSwitchType 45 }   -- 1000 Base-LX SFP Port

h3cevtPortSw-1000BASE-T-AN-SFP      OBJECT IDENTIFIER ::= { h3cevtPortSwitchType 46 }   -- 1000 Base-T AN SFP Port

h3cevtPortSw-10GBASE-LX4-XENPAK     OBJECT IDENTIFIER ::= { h3cevtPortSwitchType 47 }   -- 10G Base-LX4 XENPAK Port

h3cevtPortSw-10GBASE-LR-XENPAK      OBJECT IDENTIFIER ::= { h3cevtPortSwitchType 48 }   -- 10G Base-LR XENPAK Port

h3cevtPortSw-10GBASE-CX4            OBJECT IDENTIFIER ::= { h3cevtPortSwitchType 49 }   -- 10G Base-CX4 Port

h3cevtPortSw-1000BASE-ZX-SFP        OBJECT IDENTIFIER ::= { h3cevtPortSwitchType 50 }    -- 1000 Base-ZX SFP Port

h3cevtPortSw-1000BASE-MM-SFP        OBJECT IDENTIFIER ::= { h3cevtPortSwitchType 51 }    -- 1000 Base-MM SFP Port

h3cevtPortSw-100BASE-SX-SFP         OBJECT IDENTIFIER ::= { h3cevtPortSwitchType 52 }    -- 100 Base-SX SFP Port

h3cevtPortSw-100BASE-LX-SFP         OBJECT IDENTIFIER ::= { h3cevtPortSwitchType 53 }    -- 100 Base-LX SFP Port

h3cevtPortSw-100BASE-T-AN-SFP       OBJECT IDENTIFIER ::= { h3cevtPortSwitchType 54 }    -- 100 Base-T SFP Port

h3cevtPortSw-100BASE-ZX-SFP         OBJECT IDENTIFIER ::= { h3cevtPortSwitchType 55 }    -- 100 Base-ZX SFP Port

h3cevtPortSw-100BASE-MM-SFP         OBJECT IDENTIFIER ::= { h3cevtPortSwitchType 56 }    -- 100 Base-MM SFP Port

h3cevtPortSw-SFP-NO-CONNECTOR       OBJECT IDENTIFIER ::= { h3cevtPortSwitchType 57 }    -- No Connector SFP Port

h3cevtPortSw-SFP-UNKNOWN-CONNECTOR  OBJECT IDENTIFIER ::= { h3cevtPortSwitchType 58 }    -- Unknown SFP Port

h3cevtPortSw-POS-NO-CONNECTOR       OBJECT IDENTIFIER ::= { h3cevtPortSwitchType 59 }    -- POS no connector

h3cevtPortSw-10G-BASE-SR            OBJECT IDENTIFIER ::= { h3cevtPortSwitchType 60 }    -- 10GBASE-SR Fiber Optic Transceivers with SC Connector

h3cevtPortSw-10G-BASE-ER            OBJECT IDENTIFIER ::= { h3cevtPortSwitchType 61 }    -- 10GBASE-ER Fiber Optic Transceivers with SC Connector

h3cevtPortSw-10G-BASE-LX4           OBJECT IDENTIFIER ::= { h3cevtPortSwitchType 62 }    -- 10GBASE-LX4 Fiber Optic Transceivers with SC Connector

h3cevtPortSw-10G-BASE-SW            OBJECT IDENTIFIER ::= { h3cevtPortSwitchType 63 }    -- 10GBASE-SW Fiber Optic Transceivers with SC Connector

h3cevtPortSw-10G-BASE-LW            OBJECT IDENTIFIER ::= { h3cevtPortSwitchType 64 }    -- 10GBASE-LW Fiber Optic Transceivers with SC Connector

h3cevtPortSw-10G-BASE-EW            OBJECT IDENTIFIER ::= { h3cevtPortSwitchType 65 }    -- 10GBASE-EW Fiber Optic Transceivers with SC Connector

h3cevtPortSw-10G-LR-SM-LC           OBJECT IDENTIFIER ::= { h3cevtPortSwitchType 66 }    -- 10GBASE-LR Single Mode Fiber Optic Transceivers with LC Connector

h3cevtPortSw-10G-SR-MM-LC           OBJECT IDENTIFIER ::= { h3cevtPortSwitchType 67 }    -- 10GBASE-SR Multi Mode Fiber Optic Transceivers with LC Connector

h3cevtPortSw-10G-ER-SM-LC           OBJECT IDENTIFIER ::= { h3cevtPortSwitchType 68 }    -- 10GBASE-ER Single Mode Fiber Optic Transceivers with LC Connector

h3cevtPortSw-10G-LW-SM-LC           OBJECT IDENTIFIER ::= { h3cevtPortSwitchType 69 }    -- 10GBASE-LW Single Mode Fiber Optic Transceivers with LC Connector

h3cevtPortSw-10G-SW-MM-LC           OBJECT IDENTIFIER ::= { h3cevtPortSwitchType 70 }    -- 10GBASE-SW Multi Mode Fiber Optic Transceivers with LC Connector

h3cevtPortSw-10G-EW-SM-LC           OBJECT IDENTIFIER ::= { h3cevtPortSwitchType 71 }    -- 10GBASE-EW Single Mode Fiber Optic Transceivers with LC Connector

h3cevtPortSw-100BASE-SM-MTRJ        OBJECT IDENTIFIER ::= { h3cevtPortSwitchType 72 }    -- 100 Base-SM MTRJ Port

h3cevtPortSw-100BASE-MM-MTRJ        OBJECT IDENTIFIER ::= { h3cevtPortSwitchType 73 }    -- 100 Base-MM MTRJ Port

h3cevtPortSw-XFP-NO-CONNECTOR       OBJECT IDENTIFIER ::= { h3cevtPortSwitchType 74 }    -- XFP without Transceiver

h3cevtPortSw-XFP-10GBASE-SR         OBJECT IDENTIFIER ::= { h3cevtPortSwitchType 75 }    -- 10GBASE-SR XFP Transceiver

h3cevtPortSw-XFP-10GBASE-LR         OBJECT IDENTIFIER ::= { h3cevtPortSwitchType 76 }    -- 10GBASE-LR XFP Transceiver

h3cevtPortSw-XFP-10GBASE-ER         OBJECT IDENTIFIER ::= { h3cevtPortSwitchType 77 }    -- 10GBASE-ER XFP Transceiver

h3cevtPortSw-XFP-10GBASE-SW         OBJECT IDENTIFIER ::= { h3cevtPortSwitchType 78 }    -- 10GBASE-SW XFP Transceiver

h3cevtPortSw-XFP-10GBASE-LW         OBJECT IDENTIFIER ::= { h3cevtPortSwitchType 79 }    -- 10GBASE-LW XFP Transceiver

h3cevtPortSw-XFP-10GBASE-EW         OBJECT IDENTIFIER ::= { h3cevtPortSwitchType 80 }    -- 10GBASE-EW XFP Transceiver

h3cevtPortSw-XFP-10GBASE-CX4        OBJECT IDENTIFIER ::= { h3cevtPortSwitchType 81 }    -- 10GBASE-CX4 XFP Transceiver

h3cevtPortSw-XFP-10GBASE-LX4        OBJECT IDENTIFIER ::= { h3cevtPortSwitchType 82 }    -- 10GBASE-LX4 XFP Transceiver

h3cevtPortSw-XFP-UNKNOWN            OBJECT IDENTIFIER ::= { h3cevtPortSwitchType 83 }    -- Unknown  XFP Transceiver

h3cevtPortSw-XPK-NOCONNECTOR        OBJECT IDENTIFIER ::= { h3cevtPortSwitchType 84 }    -- Xenpak without Transceiver

h3cevtPortSw-XPK-10GBASE-SR         OBJECT IDENTIFIER ::= { h3cevtPortSwitchType 85 }    -- 10GBASE-SR Xenpak Transceiver

h3cevtPortSw-XPK-10GBASE-LR         OBJECT IDENTIFIER ::= { h3cevtPortSwitchType 86 }    -- 10GBASE-LR Xenpak Transceiver

h3cevtPortSw-XPK-10GBASE-ER         OBJECT IDENTIFIER ::= { h3cevtPortSwitchType 87 }    -- 10GBASE-ER Xenpak Transceiver

h3cevtPortSw-XPK-10GBASE-SW         OBJECT IDENTIFIER ::= { h3cevtPortSwitchType 88 }    -- 10GBASE-SW Xenpak Transceiver

h3cevtPortSw-XPK-10GBASE-LW         OBJECT IDENTIFIER ::= { h3cevtPortSwitchType 89 }    -- 10GBASE-LW Xenpak Transceiver

h3cevtPortSw-XPK-10GBASE-EW         OBJECT IDENTIFIER ::= { h3cevtPortSwitchType 90 }    -- 10GBASE-EW Xenpak Transceiver

h3cevtPortSw-XPK-10GBASE-CX4        OBJECT IDENTIFIER ::= { h3cevtPortSwitchType 91 }    -- 10GBASE-CX4 Xenpak Transceiver

h3cevtPortSw-XPK-10GBASE-LX4        OBJECT IDENTIFIER ::= { h3cevtPortSwitchType 92 }    -- 10GBASE-LX4 Xenpak Transceiver

h3cevtPortSw-XPK-UNKNOWN            OBJECT IDENTIFIER ::= { h3cevtPortSwitchType 93 }    -- Unknown Xenpak Transceiver

h3cevtPortSw-POS-OC48-SR-SM-LC      OBJECT IDENTIFIER ::= { h3cevtPortSwitchType 94 }    -- OC48-SR Single Mode Fiber Optic Transceivers with LC Connector

h3cevtPortSw-POS-OC48-IR-SM-LC      OBJECT IDENTIFIER ::= { h3cevtPortSwitchType 95 }    -- OC48-IR Single Mode Fiber Optic Transceivers with LC Connector

h3cevtPortSw-POS-OC48-LR-SM-LC      OBJECT IDENTIFIER ::= { h3cevtPortSwitchType 96 }    -- OC48-LR Single Mode Fiber Optic Transceivers with LC Connector

h3cevtPortSw-10G-BASE-CX4           OBJECT IDENTIFIER ::= { h3cevtPortSwitchType 97 }    -- 10G BASE-CX4 Electrical Interface

h3cevtPortSw-OLT-1000BASE-BX-SFF-SC OBJECT IDENTIFIER ::= { h3cevtPortSwitchType 98 }   -- 1000 BASE-BX SFF SC OLT Interface

h3cevtPortSw-ONU-1000BASE-BX-SFF-SC OBJECT IDENTIFIER ::= { h3cevtPortSwitchType 99 }   -- 1000 BASE-BX SFF SC ONU Interface

h3cevtPortSw-24G-CASCADE            OBJECT IDENTIFIER ::= { h3cevtPortSwitchType 100 }  -- 24G Cascade port

h3cevtPortSw-POS-OC3-SR-MM          OBJECT IDENTIFIER ::= { h3cevtPortSwitchType 101 }  --  STM1/OC3 Short Reach Multi Mode Fiber Optic Transceivers with LC Connector

h3cevtPortSw-POS-OC3-IR-SM          OBJECT IDENTIFIER ::= { h3cevtPortSwitchType 102 }  --  STM1/OC3 Intermediate Reach Single Mode Fiber Optic Transceivers with LC Connector

h3cevtPortSw-POS-OC3-IR-1-SM        OBJECT IDENTIFIER ::= { h3cevtPortSwitchType 103 }  --  STM1/OC3 Intermediate Reach Single Mode Fiber Optic Transceivers with LC Connector(variation 1)

h3cevtPortSw-POS-OC3-IR-2-SM        OBJECT IDENTIFIER ::= { h3cevtPortSwitchType 104 }  --  STM1/OC3 Intermediate Reach Single Mode Fiber Optic Transceivers with LC Connector(variation 2)

h3cevtPortSw-POS-OC3-LR-SM          OBJECT IDENTIFIER ::= { h3cevtPortSwitchType 105 }  --  STM1/OC3 Long Reach Single Mode Fiber Optic Transceivers with LC Connector

h3cevtPortSw-POS-OC3-LR-1-SM        OBJECT IDENTIFIER ::= { h3cevtPortSwitchType 106 }  --  STM1/OC3 Long Reach Single Mode Fiber Optic Transceivers with LC Connector(variation 1)

h3cevtPortSw-POS-OC3-LR-2-SM        OBJECT IDENTIFIER ::= { h3cevtPortSwitchType 107 }  --  STM1/OC3 Long Reach Single Mode Fiber Optic Transceivers with LC Connector(variation 2)

h3cevtPortSw-POS-OC3-LR-3-SM        OBJECT IDENTIFIER ::= { h3cevtPortSwitchType 108 }  --  STM1/OC3 Long Reach Single Mode Fiber Optic Transceivers with LC Connector(variation 3)

h3cevtPortSw-POS-OC12-SR-MM         OBJECT IDENTIFIER ::= { h3cevtPortSwitchType 109 }  --  STM4/OC12 Short Reach Multi Mode Fiber Optic Transceivers with LC Connector

h3cevtPortSw-POS-OC12-IR-SM         OBJECT IDENTIFIER ::= { h3cevtPortSwitchType 110 }  --  STM4/OC12 Intermediate Reach Single Mode Fiber Optic Transceivers with LC Connector

h3cevtPortSw-POS-OC12-IR-1-SM       OBJECT IDENTIFIER ::= { h3cevtPortSwitchType 111 }  --  STM4/OC12 Intermediate Reach Single Mode Fiber Optic Transceivers with LC Connector(variation 1)

h3cevtPortSw-POS-OC12-IR-2-SM       OBJECT IDENTIFIER ::= { h3cevtPortSwitchType 112 }  --  STM4/OC12 Intermediate Reach Single Mode Fiber Optic Transceivers with LC Connector(variation 2)

h3cevtPortSw-POS-OC12-LR-SM         OBJECT IDENTIFIER ::= { h3cevtPortSwitchType 113 }  --  STM4/OC12 Long Reach Single Mode Fiber Optic Transceivers with LC Connector

h3cevtPortSw-POS-OC12-LR-1-SM       OBJECT IDENTIFIER ::= { h3cevtPortSwitchType 114 }  --  STM4/OC12 Long Reach Single Mode Fiber Optic Transceivers with LC Connector(variation 1)

h3cevtPortSw-POS-OC12-LR-2-SM       OBJECT IDENTIFIER ::= { h3cevtPortSwitchType 115 }  --  STM4/OC12 Long Reach Single Mode Fiber Optic Transceivers with LC Connector(variation 2)

h3cevtPortSw-POS-OC12-LR-3-SM       OBJECT IDENTIFIER ::= { h3cevtPortSwitchType 116 }  --  STM4/OC12 Long Reach Single Mode Fiber Optic Transceivers with LC Connector(variation 3)

h3cevtPortSw-POS-OC48-SR-SM         OBJECT IDENTIFIER ::= { h3cevtPortSwitchType 117 }  --  STM16/OC48 Short Reach Single Mode Fiber Optic Transceivers with LC Connector

h3cevtPortSw-POS-OC48-IR-SM         OBJECT IDENTIFIER ::= { h3cevtPortSwitchType 118 }  --  STM16/OC48 Intermediate Reach Single Mode Fiber Optic Transceivers with LC Connector

h3cevtPortSw-POS-OC48-IR-1-SM       OBJECT IDENTIFIER ::= { h3cevtPortSwitchType 119 }  --  STM16/OC48 Intermediate Reach Single Mode Fiber Optic Transceivers with LC Connector(variation 1)

h3cevtPortSw-POS-OC48-IR-2-SM       OBJECT IDENTIFIER ::= { h3cevtPortSwitchType 120 }  --  STM16/OC48 Intermediate Reach Single Mode Fiber Optic Transceivers with LC Connector(variation 2)

h3cevtPortSw-POS-OC48-LR-SM         OBJECT IDENTIFIER ::= { h3cevtPortSwitchType 121 }  --  STM16/OC48 Long Reach Single Mode Fiber Optic Transceivers with LC Connector

h3cevtPortSw-POS-OC48-LR-1-SM       OBJECT IDENTIFIER ::= { h3cevtPortSwitchType 122 }  --  STM16/OC48 Long Reach Single Mode Fiber Optic Transceivers with LC Connector(variation 1)

h3cevtPortSw-POS-OC48-LR-2-SM       OBJECT IDENTIFIER ::= { h3cevtPortSwitchType 123 }  --  STM16/OC48 Long Reach Single Mode Fiber Optic Transceivers with LC Connector(variation 2)

h3cevtPortSw-POS-OC48-LR-3-SM       OBJECT IDENTIFIER ::= { h3cevtPortSwitchType 124 }  --  STM16/OC48 Long Reach Single Mode Fiber Optic Transceivers with LC Connector(variation 3)

h3cevtPortSw-POS-I-64-1             OBJECT IDENTIFIER ::= { h3cevtPortSwitchType 125 }  --  STM64/OC192 Interconnect Fiber Optic Transceivers with LC Connector(wavelength 1310nm G.652 fiber)

h3cevtPortSw-POS-I-64-2             OBJECT IDENTIFIER ::= { h3cevtPortSwitchType 126 }  --  STM64/OC192 Interconnect Fiber Optic Transceivers with LC Connector(wavelength 1550nm G.652 fiber)

h3cevtPortSw-POS-I-64-3             OBJECT IDENTIFIER ::= { h3cevtPortSwitchType 127 }  --  STM64/OC192 Interconnect Fiber Optic Transceivers with LC Connector(wavelength 1550nm G.653 fiber)

h3cevtPortSw-POS-I-64-5             OBJECT IDENTIFIER ::= { h3cevtPortSwitchType 128 }  --  STM64/OC192 Interconnect Fiber Optic Transceivers with LC Connector(wavelength 1550nm G.655 fiber)

h3cevtPortSw-POS-S-64-1             OBJECT IDENTIFIER ::= { h3cevtPortSwitchType 129 }  --  STM64/OC192 Short Haul Fiber Optic Transceivers with LC Connector(wavelength 1310nm G.652 fiber)

h3cevtPortSw-POS-S-64-2             OBJECT IDENTIFIER ::= { h3cevtPortSwitchType 130 }  --  STM64/OC192 Short Haul Fiber Optic Transceivers with LC Connector(wavelength 1550nm G.652 fiber)

h3cevtPortSw-POS-S-64-3             OBJECT IDENTIFIER ::= { h3cevtPortSwitchType 131 }  --  STM64/OC192 Short Haul Fiber Optic Transceivers with LC Connector(wavelength 1550nm G.653 fiber)

h3cevtPortSw-POS-S-64-5             OBJECT IDENTIFIER ::= { h3cevtPortSwitchType 132 }  --  STM64/OC192 Short Haul Fiber Optic Transceivers with LC Connector(wavelength 1550nm G.655 fiber)

h3cevtPortSw-POS-L-64-1             OBJECT IDENTIFIER ::= { h3cevtPortSwitchType 133 }  --  STM64/OC192 Long Haul Fiber Optic Transceivers with LC Connector(wavelength 1310nm G.652 fiber)

h3cevtPortSw-POS-L-64-2             OBJECT IDENTIFIER ::= { h3cevtPortSwitchType 134 }  --  STM64/OC192 Long Haul Fiber Optic Transceivers with LC Connector(wavelength 1550nm G.652 fiber)

h3cevtPortSw-POS-L-64-3             OBJECT IDENTIFIER ::= { h3cevtPortSwitchType 135 }  --  STM64/OC192 Long Haul Fiber Optic Transceivers with LC Connector(wavelength 1550nm G.653 fiber)

h3cevtPortSw-POS-V-64-2             OBJECT IDENTIFIER ::= { h3cevtPortSwitchType 136 }  --  STM64/OC192 Very Long Haul Fiber Optic Transceivers with LC Connector(wavelength 1550nm G.652 fiber)

h3cevtPortSw-POS-V-64-3             OBJECT IDENTIFIER ::= { h3cevtPortSwitchType 137 }  --  STM64/OC192 Very Long Haul Fiber Optic Transceivers with LC Connector(wavelength 1550nm G.653 fiber)

h3cevtPortSw-100BASE-FX-BIDI        OBJECT IDENTIFIER ::= { h3cevtPortSwitchType 138 }  --  100 BASE-FX BIDI Port

h3cevtPortSw-100BASE-BX10-U-SFP     OBJECT IDENTIFIER ::= { h3cevtPortSwitchType 139 }  --  100 BASE-BX10-U-SFP Port

h3cevtPortSw-100BASE-BX10-D-SFP     OBJECT IDENTIFIER ::= { h3cevtPortSwitchType 140 }  --  100 BASE-BX10-D-SFP Port

h3cevtPortSw-1000BASE-BX10-U-SFP    OBJECT IDENTIFIER ::= { h3cevtPortSwitchType 141 }  --  1000 BASE-BX10-U-SFP Port

h3cevtPortSw-1000BASE-BX10-D-SFP    OBJECT IDENTIFIER ::= { h3cevtPortSwitchType 142 }  --  1000 BASE-BX10-D-SFP Port

h3cevtPortSw-STK-1000BASE-T         OBJECT IDENTIFIER ::= { h3cevtPortSwitchType 143 }  --  1000 BASE-T Stack Port

h3cevtPortSw-RPR-PHYPOS-CONNECTOR     OBJECT IDENTIFIER ::= { h3cevtPortSwitchType 144 }  --  Resilient Packet Ring POS physical port

h3cevtPortSw-RPR-PHY10GE-CONNECTOR    OBJECT IDENTIFIER ::= { h3cevtPortSwitchType 145 }  --  10G Resilient Packet Ring physical port

h3cevtPortSw-RPR-LOGICPOS-CONNECTOR   OBJECT IDENTIFIER ::= { h3cevtPortSwitchType 146 }  --  Resilient Packet Ring POS logical port

h3cevtPortSw-RPR-LOGIC10GE-CONNECTOR  OBJECT IDENTIFIER ::= { h3cevtPortSwitchType 147 }  --  10G Resilient Packet Ring logical port

h3cevtPortSw-10GBASE-ZR               OBJECT IDENTIFIER ::= { h3cevtPortSwitchType 148 }  --  Fiber Optic Transceivers with SC Connector, XENPAK

h3cevtPortSw-TYPE-ERROR-CONNECTOR     OBJECT IDENTIFIER ::= { h3cevtPortSwitchType 149 }  --  Error Optic Transceivers type

h3cevtPortSw-10G-STACK                OBJECT IDENTIFIER ::= { h3cevtPortSwitchType 150 }  --  10G Stack Port

h3cevtPortSw-155-ATM-SX-MMF             OBJECT IDENTIFIER ::= { h3cevtPortSwitchType 151 }  -- ATM OC-3 Multi-mode Short Reach Optical Transceiver

h3cevtPortSw-155-ATM-LX-SMF             OBJECT IDENTIFIER ::= { h3cevtPortSwitchType 152 }  -- ATM OC-3 Single Mode Long Reach Optical Transceiver

h3cevtPortSw-622-ATM-SX-MMF             OBJECT IDENTIFIER ::= { h3cevtPortSwitchType 153 }  -- ATM OC-12 Multi-mode Short Reach Optical Transceiver

h3cevtPortSw-622-ATM-LX-SMF             OBJECT IDENTIFIER ::= { h3cevtPortSwitchType 154 }  -- ATM OC-12 Single Mode Long Reach Optical Transceiver

h3cevtPortSw-155-ATM-NO-CONNECTOR       OBJECT IDENTIFIER ::= { h3cevtPortSwitchType 155 }  -- ATM OC-3 No Connector

h3cevtPortSw-622-ATM-NO-CONNECTOR       OBJECT IDENTIFIER ::= { h3cevtPortSwitchType 156 }  -- ATM OC-12 No Connector

h3cevtPortSw-155-CPOS-E1-NO-CONNECTOR   OBJECT IDENTIFIER ::= { h3cevtPortSwitchType 157 }  -- CPOS(E1) OC-3 No Connector

h3cevtPortSw-155-CPOS-T1-NO-CONNECTOR   OBJECT IDENTIFIER ::= { h3cevtPortSwitchType 158 }  -- CPOS(T1) OC-3 No Connector

h3cevtPortSw-622-CPOS-E1-NO-CONNECTOR   OBJECT IDENTIFIER ::= { h3cevtPortSwitchType 159 }  -- CPOS(E1) OC-12 No Connector

h3cevtPortSw-622-CPOS-T1-NO-CONNECTOR   OBJECT IDENTIFIER ::= { h3cevtPortSwitchType 160 }  -- CPOS(T1) OC-12 No Connector

h3cevtPortSw-155-CPOS-E1-SX-MMF         OBJECT IDENTIFIER ::= { h3cevtPortSwitchType 161 }  -- CPOS(E1) OC-3 Multi-mode Short Reach Optical Transceiver

h3cevtPortSw-155-CPOS-T1-SX-MMF         OBJECT IDENTIFIER ::= { h3cevtPortSwitchType 162 }  -- CPOS(T1) OC-3 Multi-mode Short Reach Optical Transceiver

h3cevtPortSw-155-CPOS-E1-LX-SMF         OBJECT IDENTIFIER ::= { h3cevtPortSwitchType 163 }  -- CPOS(E1) OC-3 Single Mode Long Reach Optical Transceiver

h3cevtPortSw-155-CPOS-T1-LX-SMF         OBJECT IDENTIFIER ::= { h3cevtPortSwitchType 164 }  -- CPOS(T1) OC-3 Single Mode Long Reach Optical Transceiver

h3cevtPortSw-622-CPOS-E1-SX-MMF         OBJECT IDENTIFIER ::= { h3cevtPortSwitchType 165 }  -- CPOS(E1) OC-12 Multi-mode Short Reach Optical Transceiver

h3cevtPortSw-622-CPOS-T1-SX-MMF         OBJECT IDENTIFIER ::= { h3cevtPortSwitchType 166 }  -- CPOS(T1) OC-12 Multi-mode Short Reach Optical Transceiver

h3cevtPortSw-622-CPOS-E1-LX-SMF         OBJECT IDENTIFIER ::= { h3cevtPortSwitchType 167 }  -- CPOS(E1) OC-12 Multi-mode Short Reach Optical Transceiver

h3cevtPortSw-622-CPOS-T1-LX-SMF         OBJECT IDENTIFIER ::= { h3cevtPortSwitchType 168 }  -- CPOS(T1) OC-12 Single Mode Long Reach Optical Transceiver

h3cevtPortSw-E1-CONNECTOR               OBJECT IDENTIFIER ::= { h3cevtPortSwitchType 169 }  -- E1 RJ45 Transceiver

h3cevtPortSw-T1-CONNECTOR               OBJECT IDENTIFIER ::= { h3cevtPortSwitchType 170 }  -- T1 RJ45 Transceiver

h3cevtPortSw-1000BASE-STK-SFP           OBJECT IDENTIFIER ::= { h3cevtPortSwitchType 171 } -- 1-port 1000 Base-STK SFP Module

h3cevtPortSw-1000BASE-BIDI-SFP          OBJECT IDENTIFIER ::= { h3cevtPortSwitchType 172 } -- 1-port 1000 Base-BIDI SFP Module

h3cevtPortSw-1000BASE-CWDM-SFP          OBJECT IDENTIFIER ::= { h3cevtPortSwitchType 173 } -- 1-port 1000 Base-CWDM SFP Module

h3cevtPortSw-100BASE-BIDI-SFP           OBJECT IDENTIFIER ::= { h3cevtPortSwitchType 174 } -- 1-port 100 Base-BIDI SFP Module

h3cevtPortSw-OLT-1000BASE-PX-SFP        OBJECT IDENTIFIER ::= { h3cevtPortSwitchType 175 }  -- 1000BASE-PX SFP OLT Interface

h3cevtPortSw-OLT-1000BASE-NO-CONNECTOR  OBJECT IDENTIFIER ::= { h3cevtPortSwitchType 176 }  -- 1000BASE OLT No Connector

h3cevtPortSw-RPR-PHYGE-CONNECTOR        OBJECT IDENTIFIER ::= { h3cevtPortSwitchType 177 }  --  Resilient Packet Ring GE physical port

h3cevtPortSw-RPR-LOGICGE-CONNECTOR      OBJECT IDENTIFIER ::= { h3cevtPortSwitchType 178 }  --  Resilient Packet Ring GE logical port

h3cevtPortSw-100M-1550-BIDI             OBJECT IDENTIFIER ::= { h3cevtPortSwitchType 179 }  -- Single Port 100M Ethernet Bi-direction Optical Interface Module(TX1550nm, RX1310nm, 15km, SC)

h3cevtPortSw-100M-1310-BIDI             OBJECT IDENTIFIER ::= { h3cevtPortSwitchType 180 }  -- Single Port 100M Ethernet Bi-direction Optical reverse Interface Module(TX1310nm, RX1550nm, 15km, SC)

h3cevtPortSw-RPR-PHYOC48-CONNECTOR      OBJECT IDENTIFIER ::= { h3cevtPortSwitchType 181 }  -- Resilient Packet Ring OC48 physical port

h3cevtPortSw-RPR-LOGICOC48-CONNECTOR    OBJECT IDENTIFIER ::= { h3cevtPortSwitchType 182 }  -- Resilient Packet Ring OC48 logical port

h3cevtPortSw-100-1000-BASE-LX-SMF       OBJECT IDENTIFIER ::= { h3cevtPortSwitchType 183 }  -- 100BASE-LX/1000BASE-LX Single Mode Fiber Optic Transceivers

h3cevtPortSw-10G-ZW-SM-LC               OBJECT IDENTIFIER ::= { h3cevtPortSwitchType 184 }  -- 10GBASE-ZW Single Mode Fiber Optic Transceivers with LC Connector

h3cevtPortSw-10G-ZR-SM-LC               OBJECT IDENTIFIER ::= { h3cevtPortSwitchType 185 }  -- 10GBASE-ZR Single Mode Fiber Optic Transceivers with LC Connector

h3cevtPortSw-XPK-10GBASE-ZR             OBJECT IDENTIFIER ::= { h3cevtPortSwitchType 186 }  -- 10GBASE-ZR Xenpak Transceiver:LH80,SM1550

h3cevtPortSw-SGMII-100-BASE-LX-SFP      OBJECT IDENTIFIER ::= { h3cevtPortSwitchType 187 }  -- SGMII-100-BASE-LX-SFP Transceiver

h3cevtPortSw-SGMII-100-BASE-FX-SFP      OBJECT IDENTIFIER ::= { h3cevtPortSwitchType 188 }  -- SGMII-100-BASE-FX-SFP Transceiver

h3cevtPortSw-WLAN-RADIO                 OBJECT IDENTIFIER ::= { h3cevtPortSwitchType 189 }  -- WLAN-RADIO Transceiver

h3cevtPortSw-CABLE                      OBJECT IDENTIFIER ::= { h3cevtPortSwitchType 190 }  -- Cable Port

h3cevtPortSw-SFP-PLUS-NO-CONNECTOR      OBJECT IDENTIFIER ::= { h3cevtPortSwitchType 191 }  -- SFP+ without Transceiver

h3cevtPortSw-SFP-PLUS-10GBASE-SR        OBJECT IDENTIFIER ::= { h3cevtPortSwitchType 192 }  -- 10GBASE-SR SFP+ Transceiver

h3cevtPortSw-SFP-PLUS-10GBASE-LR        OBJECT IDENTIFIER ::= { h3cevtPortSwitchType 193 }  -- 10GBASE-LR SFP+ Transceiver

h3cevtPortSw-SFP-PLUS-10GBASE-LRM       OBJECT IDENTIFIER ::= { h3cevtPortSwitchType 194 }  -- 10GBASE-LRM SFP+ Transceiver

h3cevtPortSw-SFP-PLUS-10GBASE-Cu        OBJECT IDENTIFIER ::= { h3cevtPortSwitchType 195 }  -- 10GBASE-Cu SFP+ Transceiver

h3cevtPortSw-SFP-PLUS-UNKNOWN           OBJECT IDENTIFIER ::= { h3cevtPortSwitchType 196 }  -- Unknown SFP+ Transceiver

h3cevtPortSw-SFP-PLUS-STACK-CONNECTOR   OBJECT IDENTIFIER ::= { h3cevtPortSwitchType 197 }  -- SFP+ STACK Transceiver

--
-- h3cevtStack section:
--

h3cevtStack     OBJECT IDENTIFIER ::= { h3cEntityVendortypeObjects 11 }


END
