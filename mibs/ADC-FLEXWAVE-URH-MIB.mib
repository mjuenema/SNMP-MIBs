--*****************************************************************
-- ADC-FLEXWAVE-URH.mib : MIB file name
--
-- Copyright (c) 2007, 2008, 2009, 2010 by ADC Telecommunications, Inc.
-- Copyright (c) 2011, 2012 by TE Connectivity.
-- All rights reserved.
--
--*****************************************************************

ADC-FLEXWAVE-URH-MIB	DEFINITIONS ::= BEGIN
	IMPORTS
		DateAndTime, TEXTUAL-CONVENTION, DisplayString, RowStatus
			FROM SNMPv2-TC
		enterprises, MODULE-IDENTITY, OBJECT-TYPE, NOTIFICATION-TYPE, IpAddress, TimeTicks, Integer32, Unsigned32, Counter32, Counter64, OBJECT-IDENTITY
			FROM SNMPv2-SMI
		MODULE-COMPLIANCE, OBJECT-GROUP, NOTIFICATION-GROUP
			FROM SNMPv2-CONF
		ALARMType, BANDType, LNAType, DuplexerType, OPTICSType, MODEType, CONTACTType, GAINType, DELAYType, ALARMManage,MODULEType, ENETType, CATALOGType, RauBandType, UnitID2, UnitID3, UnitType, ALARMEnable
			FROM ADC-FWU-URH-TC-MIB;
	
	flexwaveURHMibModule	MODULE-IDENTITY
		LAST-UPDATED	"201210030000Z"
		ORGANIZATION	"TE Connectivity"
		CONTACT-INFO	"PHONE
                                 U.S.A. or CANADA:
                                        Sales: 1-800-366-3891 Extn: 73000
                                        Technical Assistance: 1-800-530-9960 
                                                Connectivity Extn: 73475 
                                                Wireless Extn: 73476
                                 
                                 EUROPE:
                                        Sales Administration: +32-2-712-65 00
                                        Technical Assistance: +32-2-712-65 42
                                 
                                 EUROPEAN TOLL FREE NUMBERS:
                                 Germany: 0180 2232923
                                 UK: 0800 960236
                                 Spain: 900 983291
                                 France: 0800 914032
                                 Italy: 0800 782374

                                 ASIA/PACIFIC:
                                        Sales Administration: +65-6294-9948
                                        Technical Assistance: +65-6393-0739
                                 
                                 ELSEWHERE:
                                 Sales Administration: +1-952-917-3000
                                 Technical Assistance: +1-952-917-3475 

                                 EMAIL:
                                 Connectivity Products
                                        United States: Connectivity.Tac@te.com
                                        Europe: Euro.Tac@te.com
                                        Asia/Pacific: AsiaPacific.Tac@te.com
                                 All Wireless Products:
                                        WirelessSupport@te.com

                                 ONLINE ACCESS: 
                                 Customer Portal: http://www.adc.com/Americas/en_US/1268116693520
                                 Online Customer Support Request: https://nssales.adc.com/ftr/ftrhome1.asp"


                DESCRIPTION     "This is the MIB for managing entities associated with FlexWave Prism & InterReach SPECTRUM products for SW Version 8.1"
                
		   REVISION	"201210030000Z"
		DESCRIPTION     "Commenting HstLinkingMode as deprecated."   

		   REVISION     "201208240000Z"
		DESCRIPTION     "This is for SW Version 8.0. Noted relationships among objects in the descriptions."
		   

		::=  {  flexwaveurh  1  }

-- .1.3.6.1.4.1.2014
adc					OBJECT IDENTIFIER		::=  { enterprises  2014 }
flexwave			OBJECT IDENTIFIER		::=  { adc  15 }
flexwaveurh			OBJECT IDENTIFIER		::=  { flexwave  2 }

-- 15.2.1.3
fwuGeneralObjects	OBJECT IDENTIFIER		::=  { flexwaveURHMibModule  3 }

-- +++++++++++++++++++++++++++++++++++++++++++++++++++++++++++++++++++++++++++++
-- Notification Objects  (.15.2.1.3.1) --
-- +++++++++++++++++++++++++++++++++++++++++++++++++++++++++++++++++++++++++++++
fwuNotifObjects      OBJECT IDENTIFIER  ::=  {  fwuGeneralObjects  1  }

fwuTrapSequenceNumber   OBJECT-TYPE
   SYNTAX         Counter32
   MAX-ACCESS     accessible-for-notify
   STATUS         current
   DESCRIPTION    "Count of the total number of traps (including this trap), raised by the agent."
   ::=  {  fwuNotifObjects  1  }

fwuTrapTimeStamp  OBJECT-TYPE
   SYNTAX         DateAndTime
   MAX-ACCESS     accessible-for-notify
   STATUS         current
   DESCRIPTION    "The trap time stamp."
   ::=  {  fwuNotifObjects  2  }

fwuNotificationStatus   OBJECT-TYPE
   SYNTAX         ALARMType
   MAX-ACCESS     accessible-for-notify
   STATUS         current
   DESCRIPTION    "The severity of the fault."
   ::=  {  fwuNotifObjects  3  }

fwuModuleType  OBJECT-TYPE
   SYNTAX         MODULEType
   MAX-ACCESS     accessible-for-notify
   STATUS         current
   DESCRIPTION    "The module type reporting alarm."
   ::=  {  fwuNotifObjects  4  }

fwuModuleNumber   OBJECT-TYPE
   SYNTAX         Integer32
   MAX-ACCESS     accessible-for-notify
   STATUS         current
   DESCRIPTION    "The numerical Id of module, for the above module type, reporting the alarm."
   ::=  {  fwuNotifObjects  5  }

fwuTrapCode     OBJECT-TYPE
   SYNTAX         INTEGER 
   MAX-ACCESS     accessible-for-notify
   STATUS         current
   DESCRIPTION    "The unique ID of the trap."
   ::= { fwuNotifObjects 6 }

fwuTrapNodeAddress   OBJECT-TYPE
   SYNTAX         Integer32 (1..2147483647)
   MAX-ACCESS     accessible-for-notify
   STATUS         current
   DESCRIPTION    "Unit from which the trap originated."
   ::= { fwuNotifObjects 7 }

fwuAlarmedModuleName  OBJECT-TYPE
   SYNTAX         DisplayString 
   MAX-ACCESS     accessible-for-notify
   STATUS         current
   DESCRIPTION    "Name of the hardware module where the trap originated."
   ::= { fwuNotifObjects 8 }

-- +++++++++++++++++++++++++++++++++++++++++++++++++++++++++++++++++++++++++++++
-- Host Unit Objects; 
--	OID: 15.2.1.1
-- +++++++++++++++++++++++++++++++++++++++++++++++++++++++++++++++++++++++++++++
fwuHostUnitObjects			OBJECT IDENTIFIER		::=  { flexwaveURHMibModule  1 }	
fwuHstSystemLevelObjects	OBJECT IDENTIFIER		::=  { fwuHostUnitObjects  1 }
fwuHstSystemLevelInfo		OBJECT IDENTIFIER		::=  { fwuHstSystemLevelObjects  1 }

fwuHstGeneral				OBJECT IDENTIFIER		::=  { fwuHstSystemLevelInfo  1 }
	-- .1.1.1.1 
fwuHstNumber		OBJECT-TYPE
	SYNTAX			INTEGER (1)
	MAX-ACCESS		read-only
	STATUS			current
	DESCRIPTION		"Host Number."
	DEFVAL			{ 1 }
	::=  {  fwuHstGeneral  1  }
	
	-- .1.1.1.2
fwuHstName			OBJECT-TYPE	
	SYNTAX			DisplayString  (SIZE(0 .. 64))
	MAX-ACCESS		read-write
	STATUS			current
	DESCRIPTION		"User defined name of the host unit. All characters except angular brackets, single and double quotes are allowed. Minimum length of the name is 1 character. Maximum length of the name 64 characters."
	DEFVAL  		{ "Host" }
	::=  {  fwuHstGeneral  2  }
	
	-- .1.1.1.3 
fwuHstUnitReset		OBJECT-TYPE
	SYNTAX			INTEGER { normal(0), reset(1) }
	MAX-ACCESS		read-write
	STATUS			current
	DESCRIPTION		"Use to reset the Host. Do this by changing from normal(0) to reset(1). After the operation has completed the state automatically changes to normal."
	DEFVAL  		{ 0 }
	::=  {  fwuHstGeneral  3  }
	
	-- .1.1.1.4
fwuHstBackPlaneRev	OBJECT-TYPE	
	SYNTAX			DisplayString
	MAX-ACCESS		read-only
	STATUS			current
	DESCRIPTION		"The back plane revision of the Host (It is the three pin version number of the chassis back plane)."
	::=  {  fwuHstGeneral  4  }

	-- .1.1.1.5
fwuHstAlarmStatusSummary	OBJECT-TYPE	
	SYNTAX			ALARMType
	MAX-ACCESS		read-only
	STATUS			current
	DESCRIPTION		"Summary of alarm status on the Host."
	::=  {  fwuHstGeneral  5  }
	
	-- .1.1.1.6
fwuHstTempMeas		OBJECT-TYPE	
	SYNTAX			DisplayString 
	MAX-ACCESS		read-only
	STATUS			current
	DESCRIPTION		"Host system temperature value in Celsius."
	::=  {  fwuHstGeneral  6  }
	
	-- .1.1.1.7
fwuSystemAlarmStatusSummary		OBJECT-TYPE	
	SYNTAX			ALARMType
	MAX-ACCESS		read-only
	STATUS			current
	DESCRIPTION		"Summary of alarm status on the System. If there a unit in the system (Host and all remotes) with a fault condition, it will be reflected here. Severity is summarised by the highest severity of the alarms in the system. i.e. If there is at least one Major alarm, the summary will indicate Major Alarm. The severities supported are Major, Minor and OK."
	::=  {  fwuHstGeneral  7  }
	
	-- .1.1.1.8 
--fwuHstLinkingMode	OBJECT-TYPE
--	SYNTAX			INTEGER  { automated(1), manual(2)} 
--	MAX-ACCESS		read-write
--	STATUS			current
--	DESCRIPTION		"The DART Linking mode of the system. Only the automated mode is supported. The manual mode is obsolete. "
--	DEFVAL  		{ 1 }
--	::=  {  fwuHstGeneral  8  }
 
fwuHstSystemDateAndTime		OBJECT-TYPE	
	SYNTAX			OCTET STRING (SIZE(0 .. 20))
	MAX-ACCESS		read-write
	STATUS			current
	DESCRIPTION		"Date and Time settings on the system."
	::=  {  fwuHstGeneral  9  }
	 
fwuAlarmAck			OBJECT-TYPE
	SYNTAX			INTEGER  { acknowledgeAll(0) } 
	MAX-ACCESS		read-write
	STATUS			current
	DESCRIPTION		"Provision to acknowledgement one or all alarms in the system. Set 0 to acknowledge all alarms or the alarm code (numeric ID) of the alarm to be acknowledged. This is a integer greater than 0."
	DEFVAL  		{ 0 }
	::=  {  fwuHstGeneral  11  }
	
fwuAlarmLevel		OBJECT-TYPE	
	SYNTAX			ALARMType 
	MAX-ACCESS		read-write
	STATUS			current
	DESCRIPTION		"Alarm status summary of system."
	DEFVAL  		{ 1 }
	::=  {  fwuHstGeneral  12  }

fwuUserCommLinkTest		OBJECT-TYPE	
	SYNTAX			INTEGER  { inactive(0), start(1) } 
	MAX-ACCESS		read-write
	STATUS			current
	DESCRIPTION		"Provision to perform the system test manually. Set the value to 1 to initiate the test. Once started, the test cannot be cancelled. User has to wait for completion. On completion of the test, the value reverts back to 0. Use fwuUserCommLinkTestDartBandType or fwuUserCommLinkTestDartId to provide parameters for the test."
	DEFVAL  			{ 0 }
	::=  {  fwuHstGeneral  13  }
	
fwuUserLinkTestStatus	OBJECT-TYPE	
	SYNTAX			DisplayString
	MAX-ACCESS		read-only
	STATUS			current
	DESCRIPTION		"Provides the status of the System/Link test, once the test has started. Start the test using fwuUserCommLinkTest. Status is reported in the format X;Y where X is the test status (number) and Y is the unit number. The valid values of the test status and their associated meaning. 
					(0) - Test has not started. This is the default value.
					(1) - Test started.
					(2,3,4,5,6,7,8,9,10,11,12,13,14) - Test is in progress. 
					(15) - Test completed. 
					(16) - Test Failed."
	DEFVAL  		{ "0" }
	::=  {  fwuHstGeneral  14  }

fwuUserCommLinkTestDartBandType		OBJECT-TYPE	
	SYNTAX			BANDType 
	MAX-ACCESS		read-write
	STATUS			current
	DESCRIPTION		"Bands on which the system test is to be run. Refer TC BANDType for list. 0 to select all provisioned bands for the test. If a non-zero value is provided here then fwuUserCommLinkTestDartId must be empty. If zero is provided here then fwuUserCommLinkTestDartId may be set to 0 or empty. "
	DEFVAL  		{ -1 }
	::=  {  fwuHstGeneral  15  }

fwuUserCommLinkTestDartId	OBJECT-TYPE
	SYNTAX			Integer32(0 .. 8)
	MAX-ACCESS		read-write
	STATUS			current
	DESCRIPTION		"Identify the DARTs on which the system test is to be run. It is the DART slot number on Host unit. Use 0 to select all provisioned DARTs for the test. Other valid values are 1 to 8 and -1. If a non-zero value is provided here then fwuUserCommLinkTestDartBandType must be empty. If zero is provided here then fwuUserCommLinkTestDartBandType may be set to 0 or empty. "
	DEFVAL  		{ 0 }
	::=  {  fwuHstGeneral  16  }

fwuClearSysConfig	OBJECT-TYPE	
	SYNTAX			INTEGER {disable(0), enable(1)} 
	MAX-ACCESS		read-write
	STATUS			current
	DESCRIPTION		"To Clear System Configuration. Change the value from 0 to 1 to clear all the settings on the system. Also, known as Restore To Factory Defaults (RTFD)."
	DEFVAL  		{ 0 }			 
	::=  {  fwuHstGeneral  17  }
	
--fwuPwrUpLinkTest	OBJECT-TYPE	
--	SYNTAX			INTEGER { disable(0), enable(1) } 
--	MAX-ACCESS		read-write
--	STATUS			current
--	DESCRIPTION		"System/Link Test on Power Up. (Link Test)."
--	DEFVAL  		{ 0 }			 
--	::=  {  fwuHstGeneral  18  }

fwuLinkTestLastRuntime	OBJECT-TYPE	
	SYNTAX			DateAndTime
	MAX-ACCESS		read-only
	STATUS			current
	DESCRIPTION		"Time indicating the most recent execution of System/Link Test."	
	::=  {  fwuHstGeneral  19  }

fwuNTPServerIP  OBJECT-TYPE
	SYNTAX                  DisplayString
	MAX-ACCESS              read-write
	STATUS                  current
	DESCRIPTION             "IP address of NTP Server. Use internet dot-decimal notation when providing the address."
	DEFVAL                  { "0.0.0.0" }
	::=  {  fwuHstGeneral  20  }

fwuSyncNTPServer  OBJECT-TYPE 
	SYNTAX                  INTEGER  { disable(0), enable(1) }
        MAX-ACCESS              read-write
        STATUS                  current
        DESCRIPTION             "Enable synchronization with NTP server. Change the value from 0 to 1 to enable synchronization with the NTP Server."
        DEFVAL                  { 0 }
	::=  {  fwuHstGeneral  21  }

	-- .15.2.1.1.1.1.2
fwuHstExt			OBJECT IDENTIFIER	::=  {  fwuHstSystemLevelInfo  2 }

fwuHstMajorContactAlarmOutput	OBJECT-TYPE	
	SYNTAX			CONTACTType
	MAX-ACCESS		read-only
	STATUS			current
	DESCRIPTION		"Host Major contact output port state. Not present, OK and faulted are the supported states."
	::=  {  fwuHstExt  1  }

fwuHstMinorContactAlarmOutput OBJECT-TYPE	
	SYNTAX			CONTACTType
	MAX-ACCESS		read-only
	STATUS			current
	DESCRIPTION		"Host Minor contact output port state. Not present, OK and faulted are the supported states."
	::=  {  fwuHstExt  2  }

fwuRmtMajorContactAlarmOutput OBJECT-TYPE	
	SYNTAX			CONTACTType
	MAX-ACCESS		read-only
	STATUS			current
	DESCRIPTION		"Remote Major contact output port state. Not present, OK and faulted are the supported states."
	::=  {  fwuHstExt  3  }

fwuRmtMinorContactAlarmOutput OBJECT-TYPE	
	SYNTAX			CONTACTType
	MAX-ACCESS		read-only
	STATUS			current
	DESCRIPTION		"Remote Minor contact output port state. Not present, OK and faulted are the supported states."
	::=  {  fwuHstExt  4  }

fwuSystemActiveAlarms		OBJECT IDENTIFIER	::=  {  fwuHstSystemLevelInfo  3 }

fwuSystemActiveAlarmTable	OBJECT-TYPE
	SYNTAX			SEQUENCE  OF  FwuSystemActiveAlarmEntry
	MAX-ACCESS		not-accessible
	STATUS			current
	DESCRIPTION		"This table lists all the outstanding (active) alarms in the system. 
				Alarms are removed from this table when the alarm condition is cleared (i.e. When CLEAR is sent out)."
					
	::=  { fwuSystemActiveAlarms  1 }
	
fwuSystemActiveAlarmEntry	OBJECT-TYPE
	SYNTAX			FwuSystemActiveAlarmEntry
	MAX-ACCESS		not-accessible
	STATUS			current
	DESCRIPTION		"Entries for active alarms."
	INDEX			{  fwuSystemAlarmSequenceNumber  }
	::=  { fwuSystemActiveAlarmTable 1 }

FwuSystemActiveAlarmEntry	::=  SEQUENCE {
	fwuSystemAlarmSequenceNumber	Unsigned32,
	fwuSystemAlarmTrapNodeAddress	UnitID2,
	fwuSystemlabel				DisplayString,
	fwuSystemAlarmRmtName		DisplayString,
	fwuSystemAlarmRmtType		UnitType,
	fwuSystemAlarmModuleType	MODULEType,
	fwuSystemAlarmModuleNumber	Unsigned32,
	fwuSystemAlarmModuleName	DisplayString,
	fwuSystemAlarmSeverity		ALARMType,
	fwuSystemAlarmRFBand		DisplayString,
	fwuSystemAlarmTimeStamp		DateAndTime,
	fwuSystemAlarmCode			Unsigned32,
	fwuSystemAlarmHstNbr		Unsigned32,
	fwuSystemAlarmAnalogAddress	UnitID3	}

fwuSystemAlarmSequenceNumber	OBJECT-TYPE	
	SYNTAX			Unsigned32 (0..4294967295)
	MAX-ACCESS		not-accessible
	STATUS			current
	DESCRIPTION		"The number of the alarm table entry which is defined by this row."
	::=  {  fwuSystemActiveAlarmEntry  1  }

fwuSystemAlarmTrapNodeAddress	OBJECT-TYPE	
	SYNTAX			UnitID2
	MAX-ACCESS		read-only
	STATUS			current
	DESCRIPTION	    "System Node Address, where the alarm originated."
	::=  {  fwuSystemActiveAlarmEntry  2  }
	
fwuSystemlabel		OBJECT-TYPE	
	SYNTAX			DisplayString
	MAX-ACCESS		read-only
	STATUS			current
	DESCRIPTION		"The name used to identify the system. Since the Host name is used to identify the system, the Host name is reflected here."
	::=  {  fwuSystemActiveAlarmEntry  3  }

fwuSystemAlarmRmtName	OBJECT-TYPE	
	SYNTAX			DisplayString
	MAX-ACCESS		read-only
	STATUS			current
	DESCRIPTION		"Name of the unit from which the alarm originated."
	::=  {  fwuSystemActiveAlarmEntry  4  }

fwuSystemAlarmRmtType	OBJECT-TYPE
	SYNTAX			UnitType
	MAX-ACCESS		read-only
	STATUS			current
	DESCRIPTION		"Type of the unit from which the alarm originated. fwuSystemAlarmRmtName is the user provided name of this unit."
	::=  {  fwuSystemActiveAlarmEntry  5  }

fwuSystemAlarmModuleType	OBJECT-TYPE	
	SYNTAX			MODULEType
	MAX-ACCESS		read-only
	STATUS			current
	DESCRIPTION		"Type of the Module from which the alarm originated. e.g SeRF, DART, SFP. To be read with fwuSystemAlarmRmtType. Then, it identifies the module on that (fwuSystemAlarmRmtType) unit."
	::=  {  fwuSystemActiveAlarmEntry  6  }

fwuSystemAlarmModuleNumber	OBJECT-TYPE	
	SYNTAX			Unsigned32 (1..8)
	MAX-ACCESS		read-only
	STATUS			current
	DESCRIPTION		"Number of the module from which the alarm originated. To be used in conjuction with the object fwuSystemAlarmModuleType. So, if module type indicated DART and module number reported 3, then it means that the alarm originated from the third DART."
	::=  {  fwuSystemActiveAlarmEntry  7  }

fwuSystemAlarmModuleName	OBJECT-TYPE	
	SYNTAX			DisplayString
	MAX-ACCESS		read-only
	STATUS			current
	DESCRIPTION		"Name of the Module from which the alarm originated. The user provided name of the module identified by fwuSystemAlarmModuleNumber. "
	::=  {  fwuSystemActiveAlarmEntry  8  }

fwuSystemAlarmSeverity	OBJECT-TYPE	
	SYNTAX			ALARMType
	MAX-ACCESS		read-only
	STATUS			current
	DESCRIPTION		"Severity of the alarm."
	::=  {  fwuSystemActiveAlarmEntry  9  }

fwuSystemAlarmRFBand  OBJECT-TYPE	
	SYNTAX			DisplayString
	MAX-ACCESS		read-only
	STATUS			current
	DESCRIPTION	        "The RF band affected by this alarm condition."
	::=  {  fwuSystemActiveAlarmEntry  10  }

fwuSystemAlarmTimeStamp	OBJECT-TYPE	
	SYNTAX			DateAndTime
	MAX-ACCESS		read-only
	STATUS			current
	DESCRIPTION		"Time when the alarm is raised."
	::=  {  fwuSystemActiveAlarmEntry  11  }

fwuSystemAlarmCode	OBJECT-TYPE	
	SYNTAX			Unsigned32
	MAX-ACCESS		read-only
	STATUS			current
	DESCRIPTION		"A positive number which uniquely identifies an alarm."
	::=  {  fwuSystemActiveAlarmEntry  12  }

fwuSystemAlarmHstNbr	OBJECT-TYPE	
	SYNTAX			Unsigned32
	MAX-ACCESS		read-only
	STATUS			current
	DESCRIPTION		"Number identifying the host in the system."
	::=  {  fwuSystemActiveAlarmEntry  13  }

fwuSystemAlarmAnalogAddress		OBJECT-TYPE	
	SYNTAX			UnitID3
	MAX-ACCESS		read-only
	STATUS			current
	DESCRIPTION		"Analog Portion of the node address."
	::=  {  fwuSystemActiveAlarmEntry  14  }

-- .15.2.1.1.1.2
fwuHstSystemLevelTraps			OBJECT IDENTIFIER 		::=  {  fwuHstSystemLevelObjects  2  }	

--.1.3.6.1.4.1.2014.15.2.1.1.1.2.2
fwuHstModuleMissingFault	NOTIFICATION-TYPE
	OBJECTS	{	fwuTrapSequenceNumber,
				fwuTrapTimeStamp,
				fwuModuleNumber,
				fwuModuleType, 
                                fwuAlarmedModuleName,
				fwuHstNumber, 
				fwuHstName,
                                fwuTrapCode,
				fwuNotificationStatus	}
	STATUS		current
	DESCRIPTION	"Missing Host pluggable module."
	::=  {  fwuHstSystemLevelTraps  2  }

--.1.3.6.1.4.1.2014.15.2.1.1.1.2.3		
fwuHstOverTempFault		NOTIFICATION-TYPE
	OBJECTS	{	fwuTrapSequenceNumber,
				fwuTrapTimeStamp,
				fwuModuleNumber,
				fwuModuleType, 
                               fwuAlarmedModuleName,
				fwuHstNumber, 
				fwuHstName, 
				fwuTrapCode,
				fwuNotificationStatus }
	STATUS		current
	DESCRIPTION	"Host Temperature above operating limit."
	::=  {  fwuHstSystemLevelTraps  3  }

--.1.3.6.1.4.1.2014.15.2.1.1.1.2.4		
fwuHstUnderTempFault	NOTIFICATION-TYPE
	OBJECTS	{	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"Host Temperature below operating limit."
	::=  {  fwuHstSystemLevelTraps  4  }

-- +++++++++++++++++++++++++++++++++++++++++++++++++++++++++++++++++++++++++++++
-- Rev-7 : System/Link Traps   --
-- +++++++++++++++++++++++++++++++++++++++++++++++++++++++++++++++++++++++++++++
-- .15.2.1.1.1.2.5 --		
fwuHstBTSUnderPowerFault	NOTIFICATION-TYPE
	OBJECTS	{	fwuTrapSequenceNumber,
				fwuTrapTimeStamp, 
				fwuModuleNumber,
				fwuModuleType, 
                               fwuAlarmedModuleName,
				fwuHstNumber, 
				fwuHstName, 
				fwuTrapCode,
				fwuNotificationStatus 	}
	STATUS		current
	DESCRIPTION	"Band specific alarm FLM raised when unit connected to BTS."
	::=  {  fwuHstSystemLevelTraps  5  }

-- .15.2.1.1.1.2.6 --
fwuHstFLMDownconvertFailureFault	NOTIFICATION-TYPE
	OBJECTS	{	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"Forward Link Monitor (FLM) fault active."
	::=  {  fwuHstSystemLevelTraps  6  }

-- .15.2.1.1.1.2.7 --
fwuHstRLMUpconvertFailureFault	NOTIFICATION-TYPE
	OBJECTS	{	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"Band specific alarm RLM raised when unit connected to BTS."
	::=  {  fwuHstSystemLevelTraps  7  }
	
-- .15.2.1.1.1.2.8 --
fwuHstRLMUpConIndetFault	NOTIFICATION-TYPE
	OBJECTS	{	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"Unable to run RLM due to Host Reverse gain being set too low."
	::=  {  fwuHstSystemLevelTraps  8  }

-- .15.2.1.1.1.2.9 --
fwuHstIamAliveFault 	NOTIFICATION-TYPE
	OBJECTS	{	fwuTrapSequenceNumber, 
				fwuTrapTimeStamp, 
				fwuHstNumber, 
				fwuHstName, 
				fwuNotificationStatus	}
	STATUS		current
	DESCRIPTION	"The Host I am alive Trap"
	::=  {  fwuHstSystemLevelTraps  9  }

fwuHstSERFObjects			OBJECT IDENTIFIER 		::=  {  fwuHostUnitObjects  2 }
fwuHstSERFInfo				OBJECT IDENTIFIER 		::=  {  fwuHstSERFObjects  1 }
fwuHstSERFGeneral			OBJECT IDENTIFIER 		::=  {  fwuHstSERFInfo  1 }

fwuHstSERFLinuxKernelVer	OBJECT-TYPE	
	SYNTAX			DisplayString
	MAX-ACCESS		read-only
	STATUS			current
	DESCRIPTION		"Linux Kernel version on host."
	::=  {  fwuHstSERFGeneral  1  }

fwuHstSERFLinuxBootLoaderVer	OBJECT-TYPE	
	SYNTAX			DisplayString
	MAX-ACCESS		read-only
	STATUS			current
	DESCRIPTION		"Boot Loader1 version on host."
	::=  {  fwuHstSERFGeneral  2  }
	
fwuHstSERFCompactFlashSWVer	OBJECT-TYPE	
	SYNTAX			DisplayString
	MAX-ACCESS		read-only
	STATUS			current
	DESCRIPTION		"Compact Flash version on host."
	::=  {  fwuHstSERFGeneral  3  }
	
fwuHstSERFFPGAVer	OBJECT-TYPE	
	SYNTAX			DisplayString
	MAX-ACCESS		read-only
	STATUS			current
	DESCRIPTION		"FPGA version loaded on Host SeRF."
	::=  {  fwuHstSERFGeneral  4  }

fwuHstSERFPPCSNMPAgentSWVer	OBJECT-TYPE	
	SYNTAX			DisplayString
	MAX-ACCESS		read-only
	STATUS			current
	DESCRIPTION		"SNMP agent version on host."
	::=  {  fwuHstSERFGeneral  5  }

fwuHstSERFPPCHWMonSWVer	OBJECT-TYPE	
	SYNTAX			DisplayString
	MAX-ACCESS		read-only
	STATUS			current
	DESCRIPTION		"Hardware Monitor process version on host."
	::=  {  fwuHstSERFGeneral  6 }

fwuHstSERFPPCAPPMonSWVer	OBJECT-TYPE	
	SYNTAX			DisplayString
	MAX-ACCESS		read-only
	STATUS			current
	DESCRIPTION		"Application Monitor process version on host."
	::=  {  fwuHstSERFGeneral  7  }

fwuHstSERFPPCMATEMonSWVer	OBJECT-TYPE	
	SYNTAX			DisplayString
	MAX-ACCESS		read-only
	STATUS			current
	DESCRIPTION		"Mate Monitor process version on host."
	::=  {  fwuHstSERFGeneral  8  }

fwuHstSERFPPCENETMonSWVer	OBJECT-TYPE	
	SYNTAX			DisplayString
	MAX-ACCESS		read-only
	STATUS			current
	DESCRIPTION		"Ethernet Monitor process version on host."
	::=  {  fwuHstSERFGeneral  9  }

fwuHstSERFPPCFPGAMonSWVer	OBJECT-TYPE	
	SYNTAX			DisplayString
	MAX-ACCESS		read-only
	STATUS			current
	DESCRIPTION		"FPGA Monitor process version on host."
	::=  {  fwuHstSERFGeneral  10  }

fwuHstSERFRIDateCode	OBJECT-TYPE	
	SYNTAX			DisplayString
	MAX-ACCESS		read-only
	STATUS			current
	DESCRIPTION		"Host SeRF Inventory - Date Code."
	::=  {  fwuHstSERFGeneral  11  }
	
fwuHstSERFRIHWVer	OBJECT-TYPE	
	SYNTAX			DisplayString
	MAX-ACCESS		read-only
	STATUS			current
	DESCRIPTION		"Host SeRF Inventory - Hardware version."
	::=  {  fwuHstSERFGeneral  12  }

fwuHstSERFRISerialNumber	OBJECT-TYPE	
	SYNTAX			DisplayString
	MAX-ACCESS		read-only
	STATUS			current
	DESCRIPTION		"Host SeRF Inventory - Serial Number."
	::=  {  fwuHstSERFGeneral  13  }

fwuHstSERFRIADCPartNumber	OBJECT-TYPE	
	SYNTAX			DisplayString
	MAX-ACCESS		read-only
	STATUS			current
	DESCRIPTION		"Host SeRF Inventory - TE PartNumber."
	::=  {  fwuHstSERFGeneral  14  }

fwuHstSERFRIHWGen	OBJECT-TYPE	
	SYNTAX			INTEGER  { firstGeneration(0), secondGeneration(1) }
	MAX-ACCESS		read-only
	STATUS			current
	DESCRIPTION		"Host SeRF Hardware Generation."
	::=  {  fwuHstSERFGeneral  15  }

fwuHstSERFLinuxBootLoaderFirstVer	OBJECT-TYPE	
	SYNTAX			DisplayString
	MAX-ACCESS		read-only
	STATUS			current
	DESCRIPTION		"Boot Loader2 version of the host system."
	::=  {  fwuHstSERFGeneral  16  }

fwuHstpThreadSWVer 	OBJECT-TYPE	
	SYNTAX			DisplayString
	MAX-ACCESS		read-only
	STATUS			current
	DESCRIPTION		"The version number of pThread process. If blank then pThread does not run here."
	::=  {  fwuHstSERFGeneral  17  }

fwuHstSubagentSWVer OBJECT-TYPE	
	SYNTAX			DisplayString
	MAX-ACCESS		read-only
	STATUS			current
	DESCRIPTION		"The version number of the subagent."
	::=  {  fwuHstSERFGeneral  18  }

fwuHstWebServerSWVer 	OBJECT-TYPE	
	SYNTAX			DisplayString
	MAX-ACCESS		read-only
	STATUS			current
	DESCRIPTION		"The version number of web server."
	::=  {  fwuHstSERFGeneral  19  }

--+++++++++++++++++++++++++++++++++++++++++++++++++++++++++++++++++++++++++++++
-- Host SeRF Optical Objects; 
--	OID: .15.2.1.1.2.1.2
-- +++++++++++++++++++++++++++++++++++++++++++++++++++++++++++++++++++++++++++++
	
fwuHstSERFOptObjects		OBJECT IDENTIFIER 		::=  {  fwuHstSERFInfo  2 }

fwuHstSERFOptTable	OBJECT-TYPE
	SYNTAX			SEQUENCE  OF  FwuHstSERFOptEntry
	MAX-ACCESS		not-accessible
	STATUS			current
	DESCRIPTION		"This table maintains Information of Host SERF Optical Objects."
	::=  { fwuHstSERFOptObjects  1 }

fwuHstSERFOptEntry	OBJECT-TYPE
	SYNTAX			FwuHstSERFOptEntry
	MAX-ACCESS		not-accessible
	STATUS			current
	DESCRIPTION		"Each entry in this table refers to Host SERF Optical objects."
	INDEX			{  fwuHstSERFOptSFPNumber  }
	::=  { fwuHstSERFOptTable 1 }

FwuHstSERFOptEntry  ::=  SEQUENCE {
	fwuHstSERFOptSFPNumber		Integer32,
	fwuHstSERFOptSFPName 	 	DisplayString,
	fwuHstSERFOptSFPType  		OPTICSType,
	fwuHstSERFOptSFPTxColor		Integer32,
	fwuHstSERFOptRevLaunchPowerMeas	DisplayString,
	fwuHstSERFOptFwdLaunchPowerMeas DisplayString,
	fwuHstSERFOptMateName 		DisplayString,
	fwuHstSERFIPEnable		INTEGER,
	fwuHstSERFOptMateId		UnitID2,
	fwuHstSERFOptMateSfpId	Integer32 }

fwuHstSERFOptSFPNumber OBJECT-TYPE	
	SYNTAX			Integer32 (1 .. 8) 
	MAX-ACCESS		read-only
	STATUS			current
	DESCRIPTION		"SFP Number - Optical Port number."
	::=  {  fwuHstSERFOptEntry  1  }

fwuHstSERFOptSFPName OBJECT-TYPE	
	SYNTAX			DisplayString ( SIZE(0 .. 64) ) 
	MAX-ACCESS		read-write
	STATUS			current
	DESCRIPTION		"User defined name of each Host SFP. All characters except angular brackets, single and double quotes are allowed. Minimum length of the name is 1 character. Maximum length of the name 64 characters."
	DEFVAL  		{ "SFP" }
	::=  {  fwuHstSERFOptEntry  2  }

fwuHstSERFOptSFPType OBJECT-TYPE	
	SYNTAX			OPTICSType
	MAX-ACCESS		read-only
	STATUS			current
	DESCRIPTION		"SFP Type - Optical Port Type. Identifies whether the SFP is short(1)/intermediate(2)/long(3) range. It may also be unidentified (-1)."
	::=  {  fwuHstSERFOptEntry  3  }

fwuHstSERFOptSFPTxColor	OBJECT-TYPE	
	SYNTAX			Integer32
	MAX-ACCESS		read-only
	STATUS			current
	DESCRIPTION		"Wavelength of light used in the SFP (in nanometers)."
	::=  {  fwuHstSERFOptEntry  4  }

fwuHstSERFOptRevLaunchPowerMeas	OBJECT-TYPE	
	SYNTAX			DisplayString
	MAX-ACCESS		read-only
	STATUS			current
	DESCRIPTION		"Value of the optical power, in dBm received at the host."
	::=  {  fwuHstSERFOptEntry  5 }

fwuHstSERFOptFwdLaunchPowerMeas	OBJECT-TYPE	
	SYNTAX			DisplayString
	MAX-ACCESS		read-only
	STATUS			current
	DESCRIPTION		"Value of the optical power, in dBm transmitted by the host."
	::=  {  fwuHstSERFOptEntry  6  }

fwuHstSERFOptMateName	OBJECT-TYPE
	SYNTAX			DisplayString
	MAX-ACCESS		read-only
	STATUS			current
	DESCRIPTION		"Name of Host Mates."
	::=  {  fwuHstSERFOptEntry  7  }

fwuHstSERFIPEnable 	OBJECT-TYPE
	SYNTAX			INTEGER  { iPEnable(1), iPDisable(2) }
	MAX-ACCESS		read-only
	STATUS			current
	DESCRIPTION		"Indicates whether IP is enabled(1) or not(2)."
	::=  {  fwuHstSERFOptEntry  8  }

fwuHstSERFOptMateId	OBJECT-TYPE	
	SYNTAX			UnitID2
	MAX-ACCESS		read-only
	STATUS			current
	DESCRIPTION		"Identifier of (companion) mate unit."
	::=  {  fwuHstSERFOptEntry  9  }

fwuHstSERFOptMateSfpId	OBJECT-TYPE	
	SYNTAX			Integer32
	MAX-ACCESS		read-only
	STATUS			current
	DESCRIPTION		"SFP slot number used at remote end."
	::=  {  fwuHstSERFOptEntry  10  }
	
fwuHstSERFTraps			OBJECT IDENTIFIER		 ::=  {  fwuHstSERFObjects  2 }

--.1.3.6.1.4.1.2014.15.2.1.1.2.2.2		
fwuHstSERFSynthAlarmFault	NOTIFICATION-TYPE
	OBJECTS	{	fwuTrapSequenceNumber, 
				fwuTrapTimeStamp, 
				fwuModuleNumber,
				fwuModuleType, 
				fwuAlarmedModuleName,
				fwuHstNumber, 
				fwuHstName,
				fwuTrapCode, 
				fwuNotificationStatus }
	STATUS		current
	DESCRIPTION	"Host SeRF synthesizer unlocked."
	::=  {  fwuHstSERFTraps  2  }

-- .1.3.6.1.4.1.2014.15.2.1.1.2.2.3
fwuHstSERFFault		NOTIFICATION-TYPE
	OBJECTS {	fwuTrapSequenceNumber, 
				fwuTrapTimeStamp, 
				fwuModuleNumber,
				fwuModuleType, 
				fwuAlarmedModuleName,
				fwuHstNumber, 
				fwuHstName, 
				fwuTrapCode,
				fwuNotificationStatus 	}
	STATUS		current
	DESCRIPTION	"Summary of SeRF Synthesizer Unlocked alarm and SeRF FPGA status. The system may not be communicating with the Ethernet Switch. This fault is also precipitated by the I2C Bus Fault."
	::=  {  fwuHstSERFTraps  3  }

--	.1.3.6.1.4.1.2014.15.2.1.1.2.2.4
fwuHstSERFRmtLostFault	NOTIFICATION-TYPE
	OBJECTS	{	fwuTrapSequenceNumber, 
				fwuTrapTimeStamp, 
				fwuModuleNumber,
				fwuModuleType, 
				fwuAlarmedModuleName,
				fwuHstNumber, 
				fwuHstName, 
				fwuRmtNumber, 
				fwuRmtName, 
				fwuTrapCode,
				fwuNotificationStatus	}
	STATUS		current
	DESCRIPTION	"Remote is not communicating with Host."
	::=  {  fwuHstSERFTraps  4  }

-- .1.3.6.1.4.1.2014.15.2.1.1.2.2.5 --
fwuHstSERFOptRxBERFault		NOTIFICATION-TYPE
	OBJECTS {	fwuTrapSequenceNumber, 
				fwuTrapTimeStamp, 
				fwuModuleNumber,
				fwuModuleType, 
				fwuAlarmedModuleName,
				fwuHstNumber, 
				fwuHstName, 
				fwuTrapCode,
				fwuNotificationStatus 	}
	STATUS		current
	DESCRIPTION	"High bit error rate (BER) detected by fiber optic receiver."
	::=  {  fwuHstSERFTraps  5  }

-- .1.3.6.1.4.1.2014.15.2.1.1.2.2.6 --
fwuHstSERFOptRxNoLightFault	NOTIFICATION-TYPE
	OBJECTS	{	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"No signal detected by optical receiver."
	::=  {  fwuHstSERFTraps  6  }

-- .1.3.6.1.4.1.2014.15.2.1.1.2.2.7 --
fwuHstSERFOptLaserFault	NOTIFICATION-TYPE
	OBJECTS {	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"SFP optical transmitter failed."
	::=  {  fwuHstSERFTraps  7  }

--.1.3.6.1.4.1.2014.15.2.1.1.2.2.8 --
fwuHstSERFOptOverDriveFault	NOTIFICATION-TYPE
	OBJECTS {	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"SFP optical receive input power above specification."
	::=  {  fwuHstSERFTraps  8  }

-- .1.3.6.1.4.1.2014.15.2.1.1.2.2.9 --	
fwuHstSERFOptUnderDriveFault	NOTIFICATION-TYPE
	OBJECTS {	fwuTrapSequenceNumber, 
				fwuTrapTimeStamp, 
				fwuModuleNumber,
				fwuModuleType, 
                               fwuAlarmedModuleName,
				fwuHstNumber, 
				fwuHstName, 
				fwuTrapCode,
				fwuNotificationStatus	}
	STATUS		current
	DESCRIPTION	"SFP optical receive input power below specification."
	::=  {  fwuHstSERFTraps  9  }
	
-- .1.3.6.1.4.1.2014.15.2.1.1.2.2.10 --
fwuHstSERFOptIpEnableFault	NOTIFICATION-TYPE
	OBJECTS	{	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"Host SFP IPEnable Fault."
	::=  {  fwuHstSERFTraps  10  }

-- .1.3.6.1.4.1.2014.15.2.1.1.2.2.11 --
fwuMastClockPriorityLvlConflict      NOTIFICATION-TYPE
        OBJECTS {       fwuTrapSequenceNumber,
                                fwuTrapTimeStamp,
                                fwuModuleNumber,
                                fwuModuleType,
                               fwuAlarmedModuleName,
                                fwuHstNumber,
                                fwuHstName,
				fwuTrapCode,
                                fwuNotificationStatus   }
        STATUS          current
        DESCRIPTION     "More than one Host has the same Master Clock Priority Level. All Hosts in conflict raise the alarm."
        ::=  {  fwuHstSERFTraps  11  }

-- .1.3.6.1.4.1.2014.15.2.1.1.2.2.12 --
fwuHstI2CBus1Fault NOTIFICATION-TYPE
        OBJECTS {       fwuTrapSequenceNumber,
                                fwuTrapTimeStamp,
                                fwuModuleNumber,
                                fwuModuleType,
                               fwuAlarmedModuleName,
                                fwuHstNumber,
                                fwuHstName,
                                fwuTrapCode,
                                fwuNotificationStatus   }
        STATUS          current
        DESCRIPTION     "Indicates an I2C communication problem."
        ::=  {  fwuHstSERFTraps  12  }

-- .1.3.6.1.4.1.2014.15.2.1.1.2.2.13 --
fwuHstI2CBus2Fault NOTIFICATION-TYPE
        OBJECTS {       fwuTrapSequenceNumber,
                                fwuTrapTimeStamp,       
                                fwuModuleNumber,
                                fwuModuleType,
                               fwuAlarmedModuleName,
                                fwuHstNumber, 
                                fwuHstName,
                                fwuTrapCode,
                                fwuNotificationStatus   }
        STATUS          current
        DESCRIPTION     "Indicates an I2C communication problem."
        ::=  {  fwuHstSERFTraps  13  }

fwuHstSERFEthPortObjects	OBJECT IDENTIFIER	::=  {  fwuHostUnitObjects  3  }
fwuHstSERFEthPortInfo		OBJECT IDENTIFIER	::=  {  fwuHstSERFEthPortObjects  1  }

fwuHstSERFEthPortTable	OBJECT-TYPE
	SYNTAX			SEQUENCE  OF  FwuHstSERFEthPortEntry
	MAX-ACCESS		not-accessible
	STATUS			current
	DESCRIPTION		"This table maintains information of Host Ethernet Ports."
	::=  { fwuHstSERFEthPortInfo  1 }

fwuHstSERFEthPortEntry	OBJECT-TYPE
	SYNTAX			FwuHstSERFEthPortEntry
	MAX-ACCESS		not-accessible
	STATUS			current
	DESCRIPTION		"Each entry in this table refers to Host SERF Ethernet port objects."
	INDEX			{  fwuHstSERFEthPortNumber  }
	::=  { fwuHstSERFEthPortTable 1 }

FwuHstSERFEthPortEntry  ::=  SEQUENCE {
	fwuHstSERFEthPortNumber  Unsigned32,
	fwuHstSERFEthPortType  ENETType,
	fwuHstSERFEthPortRxBytes  Counter64,
	fwuHstSERFEthPortRxPkts  Counter64,
	fwuHstSERFEthPortRxFcsErrors  Counter64,
	fwuHstSERFEthPortRxBroadcastPkts  Counter64,
	fwuHstSERFEthPortRxMulticastPkts  Counter64,
	fwuHstSERFEthPortRxFragmtdFrames  Counter64,
	fwuHstSERFEthPortRxJabbersFrames  Counter64,
	fwuHstSERFEthPortTxByteCounter  Counter64,
	fwuHstSERFEthPortTxPkts  Counter64,
	fwuHstSERFEthPortTxBroadcastPkts  Counter64,
	fwuHstSERFEthPortTxMulticastPkts  Counter64,
	fwuHstSERFEthPortSFPId  Integer32	}

fwuHstSERFEthPortNumber	OBJECT-TYPE	
	SYNTAX			Unsigned32  (1 .. 12) 
	MAX-ACCESS		read-only
	STATUS			current
	DESCRIPTION		"A unique identifier for each Ethernet port."
	::=  {  fwuHstSERFEthPortEntry  1  }

fwuHstSERFEthPortType	OBJECT-TYPE	
	SYNTAX			ENETType
	MAX-ACCESS		read-only
	STATUS			current
	DESCRIPTION		"An identifier for the type of Ethernet port. The port types are network(1), craft(2) , management(3) , switch(4) , SFP(5). It may be unknown (-1)."
	::=  {  fwuHstSERFEthPortEntry  2  }

fwuHstSERFEthPortRxBytes	OBJECT-TYPE	
	SYNTAX			Counter64
	MAX-ACCESS		read-only
	STATUS			current
	DESCRIPTION		"Count of the number of recieved bytes at this ethernet port."
	::=  {  fwuHstSERFEthPortEntry  3  }

fwuHstSERFEthPortRxPkts	OBJECT-TYPE	
	SYNTAX			Counter64
	MAX-ACCESS		read-only
	STATUS			current
	DESCRIPTION		"The number of packets recieved at this ethernet port."
	::=  {  fwuHstSERFEthPortEntry  4  }

fwuHstSERFEthPortRxFcsErrors	OBJECT-TYPE	
	SYNTAX			Counter64
	MAX-ACCESS		read-only
	STATUS			current
	DESCRIPTION		"The number of FCS errors recieved at this ethernet port."
	::=  {  fwuHstSERFEthPortEntry  5  }

fwuHstSERFEthPortRxBroadcastPkts	OBJECT-TYPE	
	SYNTAX			Counter64
	MAX-ACCESS		read-only
	STATUS			current
	DESCRIPTION		"The number of broadcast packets recieved at this ethernet port."
	::=  {  fwuHstSERFEthPortEntry  6  }

fwuHstSERFEthPortRxMulticastPkts	OBJECT-TYPE	
	SYNTAX			Counter64
	MAX-ACCESS		read-only
	STATUS			current
	DESCRIPTION		"The number of multicast packets at this ethernet port."
	::=  {  fwuHstSERFEthPortEntry  7  }

fwuHstSERFEthPortRxFragmtdFrames	OBJECT-TYPE	
	SYNTAX			Counter64
	MAX-ACCESS		read-only
	STATUS			current
	DESCRIPTION		"The number of fragmented frames received at this ethernet port."
	::=  {  fwuHstSERFEthPortEntry  8  }

fwuHstSERFEthPortRxJabbersFrames	OBJECT-TYPE	
	SYNTAX			Counter64
	MAX-ACCESS		read-only
	STATUS			current
	DESCRIPTION		"The number of jabber frames received at this ethernet port."
	::=  {  fwuHstSERFEthPortEntry  9 }

fwuHstSERFEthPortTxByteCounter	OBJECT-TYPE	
	SYNTAX			Counter64
	MAX-ACCESS		read-only
	STATUS			current
	DESCRIPTION		"The number of bytes transmitted from this ethernet port."
	::=  {  fwuHstSERFEthPortEntry  10  }

fwuHstSERFEthPortTxPkts	OBJECT-TYPE	
	SYNTAX			Counter64
	MAX-ACCESS		read-only
	STATUS			current
	DESCRIPTION		"The number of packets transmitted from this ethernet port."
	::=  {  fwuHstSERFEthPortEntry  11  }

fwuHstSERFEthPortTxBroadcastPkts	OBJECT-TYPE	
	SYNTAX			Counter64
	MAX-ACCESS		read-only
	STATUS			current
	DESCRIPTION		"The number of broadcast packets transmitted from this ethernet port."
	::=  {  fwuHstSERFEthPortEntry  12  }

fwuHstSERFEthPortTxMulticastPkts	OBJECT-TYPE	
	SYNTAX			Counter64
	MAX-ACCESS		read-only
	STATUS			current
	DESCRIPTION		"The number of multicast packets transmitted from this ethernet port."
	::=  {  fwuHstSERFEthPortEntry  13  }

fwuHstSERFEthPortSFPId	OBJECT-TYPE	
	SYNTAX			Integer32
	MAX-ACCESS		read-only
	STATUS			current
	DESCRIPTION		"Identifies the SFP number to which this ethernet port connects."
	::=  {  fwuHstSERFEthPortEntry  14  }

fwuHstSERFEthPortTraps		OBJECT IDENTIFIER		::=  {  fwuHstSERFEthPortObjects  2  }
fwuHstSERFFPGAObjects		OBJECT IDENTIFIER		::=  {  fwuHostUnitObjects  4  }
fwuHstSERFFPGAInfo			OBJECT IDENTIFIER		::=  {  fwuHstSERFFPGAObjects  1  }	

fwuHstSERFFPGAStatus	OBJECT-TYPE	
	SYNTAX			INTEGER  { ppcCanTalkToFPGA(0), ppcCanNotTalkToFPGA(1) } 
	MAX-ACCESS		read-only
	STATUS			current
	DESCRIPTION		"Provides the SERF Card FPGA status. The status may be PPC can communicate with the FPGA (0) or not (1)."
	DEFVAL  		{ 0 }
	::=  {  fwuHstSERFFPGAInfo  1  }

fwuHstSERFFPGATraps		OBJECT IDENTIFIER	::=  {  fwuHstSERFFPGAObjects  2  }	

fwuHstMateMonObjects	OBJECT IDENTIFIER	::=  {  fwuHostUnitObjects  5  }
fwuHstMateMonInfo		OBJECT IDENTIFIER	::=  {  fwuHstMateMonObjects  1  }	

fwuHstMateMonTable	OBJECT-TYPE
	SYNTAX			SEQUENCE  OF  FwuHstMateMonEntry
	MAX-ACCESS		not-accessible
	STATUS			current
	DESCRIPTION		"This table maintains Information of Host Mate Monitor."
	::=  { fwuHstMateMonInfo  1 }

fwuHstMateMonEntry	OBJECT-TYPE
	SYNTAX			FwuHstMateMonEntry
	MAX-ACCESS		not-accessible
	STATUS			current
	DESCRIPTION		"Each entry in this table refers to host Mate monitor objects."
	INDEX			{  fwuHMmonRmtID  }
	::=  { fwuHstMateMonTable 1 }
		
FwuHstMateMonEntry  ::=  SEQUENCE {
	fwuHMmonRmtID  UnitID2,
	fwuHMmonRmtIPAddress  OCTET STRING }
 
fwuHMmonRmtID		OBJECT-TYPE	
	SYNTAX			UnitID2
	MAX-ACCESS		read-only
	STATUS			current
	DESCRIPTION		"ID of companion remote unit as Index of mate monitor table."
	::=  {  fwuHstMateMonEntry  1  }

fwuHMmonRmtIPAddress	OBJECT-TYPE	
	SYNTAX			OCTET STRING (SIZE (0..16))
	MAX-ACCESS		read-only
	STATUS			current
	DESCRIPTION		"IP addresses of remote mate. This is a link-local address."
	::=  {  fwuHstMateMonEntry  2  }


fwuHstDARTObjects	OBJECT IDENTIFIER	::=  {  fwuHostUnitObjects  6  }
fwuHstDARTInfo		OBJECT IDENTIFIER	::=  {  fwuHstDARTObjects  1  }

fwuHstDARTGeneral	OBJECT IDENTIFIER	::=  {  fwuHstDARTInfo  1  }

fwuHstDARTGeneralTable	OBJECT-TYPE
	SYNTAX			SEQUENCE  OF  FwuHstDARTGeneralEntry
	MAX-ACCESS		not-accessible
	STATUS			current
	DESCRIPTION		"This table maintains Information of Host DART Card."
	::=  { fwuHstDARTGeneral  1 }

fwuHstDARTGeneralEntry	OBJECT-TYPE
	SYNTAX			FwuHstDARTGeneralEntry
	MAX-ACCESS		not-accessible
	STATUS			current
	DESCRIPTION		"Each entry in this table refers to host DART Card objects."
	INDEX			{  fwuHstDARTNumber  }
	::=  { fwuHstDARTGeneralTable 1 }

FwuHstDARTGeneralEntry  ::=  SEQUENCE {
	fwuHstDARTNumber  Integer32,
	fwuHstDARTName  DisplayString,
	fwuHstDARTBandType  BANDType,
	fwuHstDARTPassBand  OCTET STRING,
	fwuHstDARTOperatingMode  MODEType,
	fwuHstDARTDiversityStatus  INTEGER,
	fwuHstDARTForwardGain  GAINType,
	fwuHstDARTReverseGain  GAINType,
	fwuHstDARTFPGAStatus INTEGER,
	fwuHstDARTFPGAProgramVer  DisplayString,
	fwuHstDARTRIADCPartNumber  DisplayString,
	fwuHstDARTRISerialNumber  DisplayString,
	fwuHstDARTRIDateCode  DisplayString,
	fwuHstDARTRIHWVer  DisplayString,
	fwuHstDARTRowStatus RowStatus, 
	fwuHstDARTPeakInputPwrLvl1 DisplayString,
	fwuHstDARTPeakInputPwrLvl2 DisplayString,
	fwuHstDARTPeakAvgInputPwrLvl1 DisplayString,
	fwuHstDARTPeakAvgInputPwrLvl2 DisplayString,
	fwuHstDARTMinAvgInputPwrLvl1 DisplayString,
	fwuHstDARTMinAvgInputPwrLvl2 DisplayString,
	fwuHstDARTInputPowerMode INTEGER,
	fwuHstDARTPwrLevelMaxHoldReset INTEGER, 
	fwuHstDARTLastMaxHoldResetTime OCTET STRING,
	fwuHstDARTInputSrc INTEGER	}

fwuHstDARTNumber	OBJECT-TYPE	
	SYNTAX			Integer32  (1 .. 8) 
	MAX-ACCESS		read-only
	STATUS			current
	DESCRIPTION		"A unique identifier for each DART. As there are eight DART slots, the number may be any of 1 to 8."
	::=  {  fwuHstDARTGeneralEntry  1  }

fwuHstDARTName	OBJECT-TYPE	
	SYNTAX			DisplayString  (SIZE(0..64))
	MAX-ACCESS		read-create
	STATUS			current
	DESCRIPTION		"A user defined name for each DART Card object of host. All characters except angular brackets, single and double quotes are allowed. Minimum length of the name is 1 character. Maximum length of the name 64 characters."
	DEFVAL 			{ "DART" }	 
	::=  {  fwuHstDARTGeneralEntry  2  }

fwuHstDARTBandType	OBJECT-TYPE	
	SYNTAX			BANDType
	MAX-ACCESS		read-only
	STATUS			current
	DESCRIPTION		"Band type of host DART card."
	DEFVAL 			{ -1 }	 	
	::=  {  fwuHstDARTGeneralEntry  3  }

fwuHstDARTPassBand	OBJECT-TYPE	
	SYNTAX			OCTET STRING (SIZE (0..40))
	MAX-ACCESS		read-create
	STATUS			current
	DESCRIPTION		"This is for configuration of Pass-band type for host DART card. 
					Following input formats are supported for Classic and SuperDart
					passband configuration. 
					1. For Classic Darts only, 
						User input string would be enumeration value ( i.e., 'x'), ranging from 1 to 134. 
						See below in section 3. for valid values. 
					2. For SuperDarts only,
						a. BandType_SubBand1+SubBand2 
							This is applicable only for contiguous passband selection,
							applicable only for PCS & AWS. (e.g., 'PCS_A1+A2+A3')
						b. BandType_SubBand1+SubBand2:SubBand5+SubBand6
							This is applicable for noncontiguous passband selection,
							applicable only for PCS & AWS. (e.g., 'PCS_A1+A2:C2+C1')
						c. BandType_StartFrequency-StartFrequency
							This is applicable only for contiguous passband frequency range. (e.g.,, PCS_1930-1945) 
						d. BandType_StartFrequency1-StartFrequency1:StartFrequency2-StartFrequency2
							This is applicable only for noncontiguous passband frequency ranges.
							(e.g., PCS_1930-1940.5:1960.7-1970.6). Where BandType is 'PCS', 'AWS', 'UMTS','EGSM900','GSM1800', 'UC700', 'LABC700'.
					3. Valid enumeration value for classic dart:- undefined(-1), cellularA2A(1),cellularA(2),cellularAA1A2(3),cellularA1(4),
						cellularB(5),cellularB1(6),cellularBB1(7), pcsA1(8),pcsA2(9),pcsA3(10),pcsB1(11),pcsB2(12),pcsB3(13),
						pcsC3(14),pcsC4(15),pcsC5(16),pcsD(17),pcsE(18),pcsF(19), pcsG(20),awsH(21),pcsC2(22), pcsC1(23), 								
						pcsA1A2(24),pcsA2A3(25),pcsA3D(26),pcsDB1(27),pcsB1B2(28),pcsB2B3(29), pcsB3E(30),pcsEF(31),pcsFC3(32),
						pcsC3C4(33),pcsC4C5(34), pcsC5G(35),pcsGawsH(36),pcsFC2(37),pcsC1G(38),pcsA(39), pcsA2A3D(40),pcsA3DB1(41),
						pcsDB1B2(42),pcsB(43),pcsB2B3E(44), pcsB3EF(45),pcsEFC3(46),pcsFC3C4(47),pcsC(48), pcsC4C5G(49),
						pcsC5GawsH(50),pcsEFC2(51),pcsC1GawsH(52), pcsAD(53),pcsA2A3DB1(54),pcsA3DB1B2(55),pcsDB(56),pcsBE(57), 
						pcsB2B3EF(58),pcsB3EFC3(59),pcsEFC3C4(60),pcsFC(61), pcsCG(62),pcsC4C5GawsH(63),pcsB3EFC2(64), 
						pcsADB1(65),pcsA2A3DB1B2(66),pcsA3DB(67),pcsDBE(68), pcsBEF(69),pcsB2B3EFC3(70),pcsB3EFC3C4(71),pcsEFC(72),
						pcsFCG(73),pcsCGawsH(74),pcsB2B3EFC2(75), pcsADB1B2(76),pcsA2A3DB(77),pcsA3DBE(78),pcsDBEF(79),
						pcsBEFC3(80),pcsB2B3EFC3C4(81),pcsB3EFC(82), pcsEFCG(83),pcsFCGawsH(84),pcsADB(85), pcsA2A3DBE(86),pcsA3DBEF(87),
						pcsDBEFC3(88), pcsBEFC3C4(89),pcsB2B3EFC(90),pcsB3EFCG(91), pcsEFCGawsH(92),smrLow(93) , smrHigh( 94),
						awsA(95), awsAB(96), awsABC(97), awsABCD(98), awsABCDE(99), awsB(100), awsBC(101), awsBCD(102), awsBCDE(103), 
						awsBCDEF(104), awsC(105), awsCD(106), awsCDE(107), awsCDEF(108), awsD(109), awsDE(110), awsDEF(111), 
						awsE(112), awsEF(113), awsF(114), smrLowWide(115), cellularA2ABA1B1(116), GSM1800Low(117), GSM1800Middle(118), 
						GSM1800High(119), umtsLow(120), umtsMiddle(121), umtsHigh(122), cellularAB(133), apac800iDEN(134)."
	::=  {  fwuHstDARTGeneralEntry  4  }

fwuHstDARTOperatingMode	OBJECT-TYPE	
	SYNTAX			MODEType
	MAX-ACCESS		read-create
	STATUS			current
	DESCRIPTION		"Operating mode of the Host DART. The DART may be operating normally (1) or on standby (2). The mode may be undefined (-1)."
	DEFVAL 			{ 1 }
	::=  {  fwuHstDARTGeneralEntry  5  }

fwuHstDARTDiversityStatus	OBJECT-TYPE	
	SYNTAX			INTEGER  { nonDiversity(0) , diversity(1) } 
	MAX-ACCESS		read-create
	STATUS			current
	DESCRIPTION		"Diversity Status of host DART."
	DEFVAL 			{ 0 }
	::=  {  fwuHstDARTGeneralEntry  6  }

fwuHstDARTForwardGain	OBJECT-TYPE	
	SYNTAX			GAINType
	MAX-ACCESS		read-create
	STATUS			current
	DESCRIPTION		"Primary Gain in the forward path of Host DART. The range is 0-31dB with increments in steps of 1dB."
	DEFVAL 			{ 0 }
	::=  {  fwuHstDARTGeneralEntry  7  }

fwuHstDARTReverseGain	OBJECT-TYPE	
	SYNTAX			GAINType
	MAX-ACCESS		read-create
	STATUS			current
	DESCRIPTION		"Primary Gain in the reverse path of Host DART. The range is 0-31dB with increments in steps of 1dB."
	DEFVAL 			{ 0 }
	::=  {  fwuHstDARTGeneralEntry  8  }

fwuHstDARTFPGAStatus	OBJECT-TYPE	
	SYNTAX			INTEGER { serfFpgaCanTalkToDARTFpga(0), serfFpgaCannotTalkToDARTFpga(1) }
	MAX-ACCESS		read-only
	STATUS			current
	DESCRIPTION		"Host DART FPGA Status. It indicates whether the SeRF FPGA can talk to DART FPGA(0) or not (1)."
	DEFVAL 			{ 0 }	
	::=  {  fwuHstDARTGeneralEntry  9  }

fwuHstDARTFPGAProgramVer	OBJECT-TYPE	
	SYNTAX			DisplayString
	MAX-ACCESS		read-only
	STATUS			current
	DESCRIPTION		"FPGA Version on the Host DART card."
	::=  {  fwuHstDARTGeneralEntry  10  }

fwuHstDARTRIADCPartNumber	OBJECT-TYPE	
	SYNTAX			DisplayString
	MAX-ACCESS		read-only
	STATUS			current
	DESCRIPTION		"Host DART Inventory Data - TE Part Number."
	::=  {  fwuHstDARTGeneralEntry  11  }

fwuHstDARTRISerialNumber	OBJECT-TYPE	
	SYNTAX			DisplayString
	MAX-ACCESS		read-only
	STATUS			current
	DESCRIPTION		"Host DART Inventory Data - Serial Number."
	::=  {  fwuHstDARTGeneralEntry  12  }

fwuHstDARTRIDateCode	OBJECT-TYPE	
	SYNTAX			DisplayString
	MAX-ACCESS		read-only
	STATUS			current
	DESCRIPTION		"Host DART Inventory Data - DateCode."
	::=  {  fwuHstDARTGeneralEntry  13  }

fwuHstDARTRIHWVer	OBJECT-TYPE	
	SYNTAX			DisplayString
	MAX-ACCESS		read-only
	STATUS			current
	DESCRIPTION		"Host DART Inventory Data - HW version."
	::=  {  fwuHstDARTGeneralEntry  14  }

fwuHstDARTRowStatus OBJECT-TYPE
	SYNTAX	 		RowStatus
	MAX-ACCESS   	read-create
	STATUS       	current
	DESCRIPTION 	"The status of this conceptual row. It may be active or inactive."
	::= { fwuHstDARTGeneralEntry 15 }

fwuHstDARTPeakInputPwrLvl1	OBJECT-TYPE
	SYNTAX	 		DisplayString
	MAX-ACCESS   	read-only
	STATUS       	current
	DESCRIPTION 	"Peak Input Power Level 1 to a Host DART."
	DEFVAL 		{ "NA" }	
	::= { fwuHstDARTGeneralEntry 16 }

fwuHstDARTPeakInputPwrLvl2	OBJECT-TYPE
	SYNTAX	 		DisplayString
	MAX-ACCESS   	read-only
	STATUS       	current
	DESCRIPTION 	"Peak Input Power Level 2 to a Host DART. Incase of diversity, this value will be NA."
	DEFVAL 			{ "NA" }
	::= { fwuHstDARTGeneralEntry 17 }

fwuHstDARTPeakAvgInputPwrLvl1	OBJECT-TYPE
	SYNTAX	 		DisplayString
	MAX-ACCESS   	read-only
	STATUS       	current
	DESCRIPTION 	"Peak Average Input Power Level1 to a Host DART."
	DEFVAL 			{ "NA" }	
	::= { fwuHstDARTGeneralEntry 18 }

fwuHstDARTPeakAvgInputPwrLvl2	OBJECT-TYPE
	SYNTAX			DisplayString
	MAX-ACCESS   	read-only
	STATUS       	current
	DESCRIPTION 	"Peak Average Input Power Level 2 to a Host DART. Incase of diversity, this value will be NA."
	DEFVAL 			{ "NA" }	
	::= { fwuHstDARTGeneralEntry 19 }

fwuHstDARTMinAvgInputPwrLvl1	OBJECT-TYPE
	SYNTAX	 		DisplayString
	MAX-ACCESS   	read-only
	STATUS       	current
	DESCRIPTION 	"Minimum Average Input Power Level 1 to a Host DART."
	DEFVAL 			{ "NA" }	
	::= { fwuHstDARTGeneralEntry 20 }

fwuHstDARTMinAvgInputPwrLvl2	OBJECT-TYPE
	SYNTAX	 		DisplayString
	MAX-ACCESS   	read-only
	STATUS       	current
	DESCRIPTION 	"Minimum Average Input Power Level 2 to a Host DART. Incase of diversity, this value will be NA."
	DEFVAL 			{ "NA" }	
	::= { fwuHstDARTGeneralEntry 21 }

fwuHstDARTInputPowerMode	OBJECT-TYPE
	SYNTAX	 		INTEGER  { snapShot(0) , maxHold(1) }
	MAX-ACCESS   	read-write
	STATUS       	current
	DESCRIPTION 	"Host DART Input Power Level Mode. The supported modes are Snapshot(0) and Max Hold(1). When setting Max Hold, ensure that the status (fwuHstDARTDiversityStatus) is not diversity."
	DEFVAL 			{ 0 }	
	::= { fwuHstDARTGeneralEntry 22 }

fwuHstDARTPwrLevelMaxHoldReset	OBJECT-TYPE
	SYNTAX	 		INTEGER { notApplicable(-1), normal(0) , reset(1) }
	MAX-ACCESS   	read-write
	STATUS       	current
	DESCRIPTION 	"Provision to reset the Max Hold reading. Used when the input power mode is Max hold. Reset by changing from normal (0) to reset (1). Status will revert to normal once the reset is done. In snapshot mode (see fwuHstDARTInputPowerMode) this object is not applicable (-1)."
	DEFVAL 			{ -1 }	
	::= { fwuHstDARTGeneralEntry 23 }

fwuHstDARTLastMaxHoldResetTime	OBJECT-TYPE
	SYNTAX	 		OCTET STRING (SIZE (0..40)) 
	MAX-ACCESS   	read-only
	STATUS       	current
	DESCRIPTION 	"Date and Time of the last Max Hold reset on the host DART."
	::= { fwuHstDARTGeneralEntry 24 }
		 
fwuHstDARTInputSrc	OBJECT-TYPE
	SYNTAX	 		INTEGER { bts ( 1 ), bda ( 2 ) }
	MAX-ACCESS   	read-write
	STATUS       	current
	DESCRIPTION 	"To identify the input source; BTS(1) or BDA(2) and change it, if required."
	DEFVAL 			{ 1 }	
	::= { fwuHstDARTGeneralEntry 25 }

fwuHstDARTTraps			OBJECT IDENTIFIER		::=  {  fwuHstDARTObjects  2  }

fwuHstDARTDwnCon1SynLockFault	NOTIFICATION-TYPE
	OBJECTS	{	fwuTrapSequenceNumber, 
				fwuTrapTimeStamp, 
				fwuModuleNumber,
				fwuModuleType, 
				fwuAlarmedModuleName,
				fwuHstNumber, 
				fwuHstName,
				fwuTrapCode,
				fwuNotificationStatus	}
	STATUS		current
	DESCRIPTION	"DART downconverter 1 synthesizer unlocked."
	::=  {  fwuHstDARTTraps  2  }

fwuHstDARTDwnCon2SynLockFault	NOTIFICATION-TYPE
	OBJECTS	{	fwuTrapSequenceNumber, 
				fwuTrapTimeStamp, 
				fwuModuleNumber,
				fwuModuleType, 
				fwuAlarmedModuleName,
				fwuHstNumber, 
				fwuHstName, 
				fwuTrapCode,
				fwuNotificationStatus 	}
	STATUS		current
	DESCRIPTION	"DART downconverter 2 synthesizer unlocked."
	::=  {  fwuHstDARTTraps  3  }

fwuHstDARTUpConSynLockFault	NOTIFICATION-TYPE
	OBJECTS	{	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"DART upconverter synthesizer unlocked."
	::=  {  fwuHstDARTTraps  4  }

fwuHstDARTOverDriveFault	NOTIFICATION-TYPE
	OBJECTS {	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"DART forward RF input too high."
	::=  {  fwuHstDARTTraps  5  }

fwuHstDARTUnderDriveFault	NOTIFICATION-TYPE
	OBJECTS {	fwuTrapSequenceNumber, 
				fwuTrapTimeStamp, 
				fwuModuleNumber,
				fwuModuleType, 
                               fwuAlarmedModuleName,
				fwuHstNumber, 
				fwuHstName, 
				fwuTrapCode,
				fwuNotificationStatus	}
	STATUS		current
	DESCRIPTION	"DART forward RF input signal below the normal operating limit."
	::=  {  fwuHstDARTTraps  6  }

fwuHstDARTFault	NOTIFICATION-TYPE
	OBJECTS {	fwuTrapSequenceNumber, 
				fwuTrapTimeStamp, 
				fwuModuleNumber,
				fwuModuleType, 
                               fwuAlarmedModuleName,
				fwuHstNumber, 
				fwuHstName, 
				fwuTrapCode,
				fwuNotificationStatus 	}
	STATUS		current
	DESCRIPTION	"Summary of DART Downconverter 1 Synthesizer Unlocked, Downconverter 2 Synthesizer Unlocked, Upconverter Synthesizer Unlocked, DC Supply Fault alarms, and DART FPGA status."
	::=  {  fwuHstDARTTraps  7  }

fwuHstDARTDCSupplyFault	NOTIFICATION-TYPE
	OBJECTS {	fwuTrapSequenceNumber, 
				fwuTrapTimeStamp, 
				fwuModuleNumber,
				fwuModuleType, 
				fwuAlarmedModuleName,
				fwuHstNumber, 
				fwuHstName, 
				fwuTrapCode,
				fwuNotificationStatus	}
	STATUS		current
	DESCRIPTION	"DART card DC supply voltages outside specification."
	::=  {  fwuHstDARTTraps  8  }

fwuHstDARTHardwareMismatchFault	NOTIFICATION-TYPE
	OBJECTS {	fwuTrapSequenceNumber, 
				fwuTrapTimeStamp, 
				fwuModuleNumber,
				fwuModuleType, 
				fwuAlarmedModuleName,
				fwuHstNumber, 
				fwuHstName,  
				fwuRmtNumber, 
				fwuRmtName, 
				fwuTrapCode,
				fwuNotificationStatus 	}
	STATUS		current
	DESCRIPTION	"Host DART does not support the selected passband.  Fault occurs when a Host DART is replaced with another DART of the incorrect type."
	::=  {  fwuHstDARTTraps  9  }

fwuHstDARTALCLimitingFault	NOTIFICATION-TYPE
	OBJECTS	{	fwuTrapSequenceNumber, 
				fwuTrapTimeStamp, 
				fwuModuleNumber,
				fwuModuleType, 
                               fwuAlarmedModuleName,
				fwuHstNumber, 
				fwuHstName, 
				fwuTrapCode,
				fwuNotificationStatus	}
	STATUS		current
	DESCRIPTION	"Host DART forward path Automatic Level Control is active."
	::=  {  fwuHstDARTTraps  10  }

fwuHstDARTLinkingConflictFault      NOTIFICATION-TYPE
        OBJECTS {       fwuTrapSequenceNumber,
                                fwuTrapTimeStamp,
                                fwuModuleNumber,
                                fwuModuleType,
                               fwuAlarmedModuleName,
                                fwuHstNumber,
                                fwuHstName,
				fwuTrapCode,
                                fwuNotificationStatus   }
        STATUS          current
        DESCRIPTION     "Host comes back up and finds that it cannot restore a link with a remote DART to which it was linked."
        ::=  {  fwuHstDARTTraps  11  }

-- +++++++++++++++++++++++++++++++++++++++++++++++++++++++++++++++++++++++++++++
--   (.15.2.1.4) --
fwuHstSystemCardObjects	OBJECT IDENTIFIER			::=  {  fwuHostUnitObjects  7  }
-- +++++++++++++++++++++++++++++++++++++++++++++++++++++++++++++++++++++++++++++

fwuHstSystemCardInfo	OBJECT IDENTIFIER			::=  {  fwuHstSystemCardObjects  1  }

fwuHstSysCardRIADCPartNumber	OBJECT-TYPE	
	SYNTAX			DisplayString
	MAX-ACCESS		read-only
	STATUS			current
	DESCRIPTION		"Host Inventory Data - TE Part Number."
	::=  {  fwuHstSystemCardInfo  1  }

fwuHstSysCardRISerialNumber	OBJECT-TYPE	
	SYNTAX			DisplayString
	MAX-ACCESS		read-only
	STATUS			current
	DESCRIPTION		"Host Inventory Data - Serial Number."
	::=  {  fwuHstSystemCardInfo  2  }

fwuHstSysCardRIDateCode	OBJECT-TYPE	
	SYNTAX			DisplayString
	MAX-ACCESS		read-only
	STATUS			current
	DESCRIPTION		"Host Inventory Data - Date Code."
	::=  {  fwuHstSystemCardInfo  3  }

fwuHstSysCardRIHWVer	OBJECT-TYPE	
	SYNTAX			DisplayString
	MAX-ACCESS		read-only
	STATUS			current
	DESCRIPTION		"Host Inventory Data - Hardware version."
	::=  {  fwuHstSystemCardInfo  4  }

fwuHstSysCard10MhzRefClock	OBJECT-TYPE	
	SYNTAX			INTEGER  { internal(0) , external(1) } 
	MAX-ACCESS		read-write
	STATUS			current
	DESCRIPTION		"System Card Reference clock. It may be set to internal (0) or external(1)."
	::=  {  fwuHstSystemCardInfo  5  }

--	Added Clock Priority Level Object for Multi Host URH
fwuHstSysCardCPLevel	OBJECT-TYPE	
	SYNTAX			Integer32   (1 .. 14) 
	MAX-ACCESS		read-write
	STATUS			current
	DESCRIPTION		"System Card Master Clock Priority Level prioritizes the system card clock using values 1 through 14 (Lower value is higher priority). This is primarily used in multihost systems. In such system, all hosts should have different priority levels, and the system inherently assures this. This entity allows the user to change the system set prioritization. Changeing values in a single host system has no change."
	::=  {  fwuHstSystemCardInfo  6  }

fwuHstSysCardOutputRefClock		OBJECT-TYPE	
	SYNTAX			INTEGER  { off (0), clock10mhz(1) , clock30mhz(2) } 
	MAX-ACCESS		read-write
	STATUS			current
	DESCRIPTION		"System Card Reference clock. System Board I supports only 10 MHz and 
					System Board II supports both 10 MHz and 30 MHz Clock output. Default value is 1 for Host and 2 for DRU."
	DEFVAL 			{ 1 }
	::=  {  fwuHstSystemCardInfo  7  }

fwuHstSysCardRIHWGen OBJECT-TYPE	
	SYNTAX			INTEGER  { firstGeneration(0), secondGeneration(1) }
	MAX-ACCESS		read-only
	STATUS			current
	DESCRIPTION		"Host System Card Hardware Generation. Presently, there are two generations; first Generation(0), second Generation(1)"
	::=  {  fwuHstSystemCardInfo  8  }
	
fwuHstSystemCardTraps	OBJECT IDENTIFIER			::=  {  fwuHstSystemCardObjects  2  }

fwuHstSysCardFanFault	NOTIFICATION-TYPE
	OBJECTS {	fwuTrapSequenceNumber, 
				fwuTrapTimeStamp, 
				fwuModuleNumber, 
				fwuModuleType, 
                               fwuAlarmedModuleName,
				fwuHstNumber, 
				fwuHstName, 
				fwuTrapCode,
				fwuNotificationStatus 	}
	STATUS		current
	DESCRIPTION	"Fan not functioning."
	::=  {  fwuHstSystemCardTraps  2  }
		
fwuHstSysCardClockMismatchFault 	NOTIFICATION-TYPE
	OBJECTS	{ 	fwuTrapSequenceNumber, 
				fwuTrapTimeStamp, 
				fwuModuleNumber, 
				fwuModuleType, 
                               fwuAlarmedModuleName,
				fwuHstNumber, 
				fwuHstName, 
				fwuTrapCode,
				fwuNotificationStatus }
	STATUS			current
	DESCRIPTION		"System Card output clock not supported."
	::=  {  fwuHstSystemCardTraps  3  }

-- +++++++++++++++++++++++++++++++++++++++++++++++++++++++++++++++++++++++++++++
-- Remote Unit Objects; 
--	OID: 15.2.1.2
-- +++++++++++++++++++++++++++++++++++++++++++++++++++++++++++++++++++++++++++++
fwuRemoteUnitObjects		OBJECT IDENTIFIER  		::=  {  flexwaveURHMibModule  2  }
fwuRmtSystemLevelObjects	OBJECT IDENTIFIER		::=  {  fwuRemoteUnitObjects  1  }
fwuRmtSystemLevelInfo		OBJECT IDENTIFIER		::=  {  fwuRmtSystemLevelObjects  1 }
fwuRmtGeneral				OBJECT IDENTIFIER		::=  {  fwuRmtSystemLevelInfo  1 }
				
fwuRmtGeneralTable	OBJECT-TYPE
	SYNTAX			SEQUENCE  OF  FwuRmtGeneralEntry
	MAX-ACCESS		not-accessible
	STATUS			current
	DESCRIPTION		"This table maintains Information of remote."
	::=  { fwuRmtGeneral  1 }
						
fwuRmtGeneralEntry	OBJECT-TYPE
	SYNTAX			FwuRmtGeneralEntry
	MAX-ACCESS		not-accessible
	STATUS			current
	DESCRIPTION		"Each entry in this table refers to remote objects."
	INDEX			{  fwuRmtNumber  }
	::=  { fwuRmtGeneralTable 1 }
						
FwuRmtGeneralEntry  ::=  SEQUENCE {
	fwuRmtNumber	UnitID2,	
	fwuRmtCatalogState	CATALOGType,
	fwuRmtName	DisplayString,
	fwuRmtAlarmStatusSummary	ALARMType,
	fwuRmtTempMeasurement	DisplayString,
	fwuRmtGeneralTableRowStatus	RowStatus,
	fwuRmtType	UnitType,
	fwuDruIfCombinerReboot 	Unsigned32, 
	fwuUsrCommLinkTestIFBr	INTEGER,
	fwuUsrCommLinkTestIFBrDType	BANDType,
	fwuUsrCommLinkTestDartId	Unsigned32,
	fwuDruBackPlaneRev	OCTET STRING,
	fwuPrismUnitReset 	INTEGER
	}
						
fwuRmtNumber		OBJECT-TYPE	
	SYNTAX			UnitID2
	MAX-ACCESS		read-only
	STATUS			current
	DESCRIPTION		"The Node address of connected remote."	
	::=  {  fwuRmtGeneralEntry  1  }

fwuRmtCatalogState	OBJECT-TYPE	
	SYNTAX			CATALOGType
	MAX-ACCESS		read-only
	STATUS			current
	DESCRIPTION		"Catalog state of remote. If fwuRmtCatalogState is commission(2),
					then start commissioning on remote, else if it in normal, do not commission the remote."
	::=  {  fwuRmtGeneralEntry  2  }
						
fwuRmtName	OBJECT-TYPE
	SYNTAX			DisplayString  ( SIZE (0 .. 64) ) 
	MAX-ACCESS		read-create
	STATUS			current
	DESCRIPTION		"User defined name of the remote unit. All characters except angular brackets, single and double quotes are allowed. Minimum length of the name is 1 character. Maximum length of the name 64 characters."
	DEFVAL 			{ "Remote" }	
	::=  {  fwuRmtGeneralEntry  3  }	 

fwuRmtAlarmStatusSummary	OBJECT-TYPE	
	SYNTAX			ALARMType
	MAX-ACCESS		read-only
	STATUS			current
	DESCRIPTION		"Summary of alarm status of all connected remote units."
	::=  {  fwuRmtGeneralEntry  4  }

fwuRmtTempMeasurement	OBJECT-TYPE	
	SYNTAX			DisplayString
	MAX-ACCESS		read-only
	STATUS			current
	DESCRIPTION		"Temperature of each remote unit in Celsius. This value comes from the RSI."
	::=  {  fwuRmtGeneralEntry  5  }

fwuRmtGeneralTableRowStatus OBJECT-TYPE
	SYNTAX			RowStatus
	MAX-ACCESS   	read-create
	STATUS       	current
	DESCRIPTION 	"The status of this conceptual row. It may be active or inactive."
	::= { fwuRmtGeneralEntry 6 }

fwuRmtType	OBJECT-TYPE	
	SYNTAX			UnitType
	MAX-ACCESS		read-only
	STATUS			current
	DESCRIPTION		"The type of Remote. e.g. Prism, DRU, HEU, IRU."
	::=  {  fwuRmtGeneralEntry  7  }

fwuDruIfCombinerReboot 	OBJECT-TYPE	
	SYNTAX			Unsigned32 (0..1)
	MAX-ACCESS		read-write
	STATUS			current
	DESCRIPTION		"Reboot an IF-combiner and all the units connected to it. Only 
					applicable to DRU-IFs Change Value from 0 to 1 to reboot."
	::=  {  fwuRmtGeneralEntry  8  }

fwuUsrCommLinkTestIFBr	OBJECT-TYPE	
	SYNTAX			INTEGER  { inactive(0), start(1) , inprogress(2) } 
	MAX-ACCESS		read-write
	STATUS			current
	DESCRIPTION		"Provision to perform system test on an IF branch. Change from inactive(0) to start(1) to initiate the test. For the duration of the test inprogress(2) is displayed. On completion, inactive is displayed."
	DEFVAL 			{ 0 }
	::=  {  fwuRmtGeneralEntry  9  }

fwuUsrCommLinkTestIFBrDType	OBJECT-TYPE	
	SYNTAX			BANDType
	MAX-ACCESS		read-write
	STATUS			current
	DESCRIPTION		"Selected Bands i.e. RF DARTs on units when performing system test."
	::=  {  fwuRmtGeneralEntry  10  }

fwuUsrCommLinkTestDartId	OBJECT-TYPE	
	SYNTAX			Unsigned32
	MAX-ACCESS		read-write
	STATUS			current
	DESCRIPTION		"To identify the DART ."
	::=  {  fwuRmtGeneralEntry  11  }

fwuDruBackPlaneRev	OBJECT-TYPE	
	SYNTAX			OCTET STRING (SIZE (1..40))
	MAX-ACCESS		read-only
	STATUS			current
	DESCRIPTION		"Provides the back plane revision of the DRU (Three pin version Number of the Chassis back plane)"
	::=  {  fwuRmtGeneralEntry  12  }

fwuPrismUnitReset	OBJECT-TYPE	
	SYNTAX			INTEGER { normal(0), reset(1)}
	MAX-ACCESS		read-write
	STATUS			current
	DESCRIPTION		"Provides a way to reset the Remote SERF card. SET this to reset(1) to trigger a remote unit reset."
	::=  {  fwuRmtGeneralEntry  13  }
	
	
fwuRmtSystemLevelTraps		OBJECT IDENTIFIER	::=  {  fwuRmtSystemLevelObjects  2  }

fwuRmtAcPowerSupplyFault	NOTIFICATION-TYPE
	OBJECTS	{	fwuTrapSequenceNumber,
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS			current
	DESCRIPTION		"Summary of AC Power Supply 1, AC Power Supply 2, AC Power Supply 3, and AC Power Supply 4 alarms."
	::=  {  fwuRmtSystemLevelTraps  2  }

fwuRmtMajorExtAlarmInputFault	NOTIFICATION-TYPE
	OBJECTS	{ 	fwuTrapSequenceNumber, 
				fwuTrapTimeStamp, 
				fwuModuleNumber,
				fwuModuleType,
                               fwuAlarmedModuleName,
				fwuHstNumber,
				fwuHstName,
				fwuRmtNumber, 
				fwuRmtName,
				fwuTrapCode,
				fwuNotificationStatus 	}
	STATUS			current
	DESCRIPTION		"The remote Major Ext Alarm Input Fault."
	::=  {  fwuRmtSystemLevelTraps  3  }

fwuRmtMinorExtAlarmInputFault	NOTIFICATION-TYPE
	OBJECTS	{ 	fwuTrapSequenceNumber, 
				fwuTrapTimeStamp, 
				fwuModuleNumber,
				fwuModuleType,
                               fwuAlarmedModuleName,
				fwuHstNumber,
				fwuHstName,
				fwuRmtNumber,
				fwuRmtName,
				fwuTrapCode,
				fwuNotificationStatus 	}
	STATUS		current
	DESCRIPTION		"The remote Minor Ext Alarm Input Fault."
	::=  {  fwuRmtSystemLevelTraps  4  }
					
fwuRmtModuleMissingFault	NOTIFICATION-TYPE
	OBJECTS	{ 	fwuTrapSequenceNumber, 
				fwuTrapTimeStamp, 
				fwuModuleNumber,
				fwuModuleType,  
                               fwuAlarmedModuleName,
				fwuHstNumber,
				fwuHstName,
				fwuRmtNumber, 
				fwuRmtName,
				fwuTrapCode,
				fwuNotificationStatus 	}
	STATUS			current
	DESCRIPTION		"A Remote (DRU/PRU/URU) pluggable module is missing (if DRU: DART or SFP.  If PRU/URU: DART, SFP, LNA, LPA, or PD)."
	::=  {  fwuRmtSystemLevelTraps  5 }

fwuRmtOverTempFault	NOTIFICATION-TYPE
	OBJECTS	{	fwuTrapSequenceNumber, 
				fwuTrapTimeStamp, 
				fwuModuleNumber,
				fwuModuleType,  
                               fwuAlarmedModuleName,
				fwuHstNumber,
				fwuHstName,
				fwuRmtNumber, 
				fwuRmtName, 
				fwuTrapCode,
				fwuNotificationStatus 	}
	STATUS			current
	DESCRIPTION		"Remote Temperature above operating limit."
	::=  {  fwuRmtSystemLevelTraps  6  }
	
fwuRmtUnderTempFault	NOTIFICATION-TYPE
	OBJECTS	{ 	fwuTrapSequenceNumber, 
				fwuTrapTimeStamp, 
				fwuModuleNumber,
				fwuModuleType,
                               fwuAlarmedModuleName,
				fwuHstNumber,
				fwuHstName,
				fwuRmtNumber, 
				fwuRmtName, 
				fwuTrapCode,
				fwuNotificationStatus 	}
	STATUS			current
	DESCRIPTION		"Temperature below operating limit."
	::=  {  fwuRmtSystemLevelTraps  7  }

fwuRmtOpenDoorFault		NOTIFICATION-TYPE
	OBJECTS	{ 	fwuTrapSequenceNumber, 
				fwuTrapTimeStamp, 
				fwuModuleNumber,
				fwuModuleType,  
                               fwuAlarmedModuleName,
				fwuHstNumber, 
				fwuHstName, 
				fwuRmtNumber, 
				fwuRmtName, 
				fwuTrapCode,
				fwuNotificationStatus 	}
	STATUS		current
	DESCRIPTION	"Door open on PRU."
	::=  {  fwuRmtSystemLevelTraps  8  }

fwuRmtFanOverSpeedFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Fans operating above expected RPM."
	::=  {  fwuRmtSystemLevelTraps  9  }

fwuRmtFanUnderSpeedFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Fans operating below expected RPM."
	::=  {  fwuRmtSystemLevelTraps  10  }

-- +++++++++++++++++++++++++++++++++++++++++++++++++++++++++++++++++++++++++++++
-- Rev-7 : System/Link Traps   --
-- +++++++++++++++++++++++++++++++++++++++++++++++++++++++++++++++++++++++++++++
-- 15.2.1.2.1.2.11 --	
fwuRmtDownLinkCalToneFailureFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Forward calibration tone not at expected level."
	::=  {  fwuRmtSystemLevelTraps  11  }

-- 15.2.1.2.1.2.12 --
fwuRmtUplinkFailureDetectLowFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Reverse test tone not at expected level."
	::=  {  fwuRmtSystemLevelTraps  12  }

-- 15.2.1.2.1.2.13 --	
fwuRmtUpConvertFailureFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Band specific alarm raised during Forward Link Monitoring on PRU/URU."
	::=  {  fwuRmtSystemLevelTraps  13  }

-- 15.2.1.2.1.2.14 --	
fwuRmtUnderPowerFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Band specific alarm raised during Forward Link Monitoring on PRU/URU."
	::=  {  fwuRmtSystemLevelTraps  14  }

-- 15.2.1.2.1.2.15 --
fwuRmtDownConvertFailureFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Band specific alarm raised during Reverse Link Monitoring on PRU/URU."
	::=  {  fwuRmtSystemLevelTraps  15  }

-- 15.2.1.2.1.2.16 --
fwuRmtUpconIndetFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION	"Band specific alarm raised during Forward Link Monitoring on PRU/URU."
	::=  {  fwuRmtSystemLevelTraps  16  }

-- 15.2.1.2.1.2.17 --
fwuRmtFiberConnMismatchFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Fiber optic cable connections between cascaded DRU/PRUs not following SFP connection rules."
	::=  {  fwuRmtSystemLevelTraps  17  }

-- 15.2.1.2.1.2.18 --
fwuRmtExcessConnFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"Two or more DRU/PRU/URU connected to a single cascaded DRU/PRU/URU, or a ninth DRU/PRU/URU connected in cascade."
	::=  {  fwuRmtSystemLevelTraps  18  }	
	
-- 15.2.1.2.1.2.19 --
fwuRmtInvalidDevConnFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION	"PRU/URU connected to a DRU or vice versa."
	::=  {  fwuRmtSystemLevelTraps  19  }	
	
-- 15.2.1.2.1.2.20 --
fwuDruSysCardClockMismatchFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"System Card output clock not supported."
	::=  {  fwuRmtSystemLevelTraps  20  }		

-- 15.2.1.2.1.2.21 --
fwuDruNoCommsFault 	NOTIFICATION-TYPE
	OBJECTS	{ 	fwuTrapSequenceNumber, 
				fwuTrapTimeStamp, 
				fwuModuleNumber,
				fwuModuleType, 
                               fwuAlarmedModuleName,
				fwuHstNumber, 
				fwuHstName, 
				fwuRmtNumber, 
				fwuRmtName, 
				fwuTrapCode,
				fwuNotificationStatus	}
	STATUS		current
	DESCRIPTION		"DRU has lost communication with IFEU Or IFEU is disconnected from the DRU."
	::=  {  fwuRmtSystemLevelTraps  21  }

fwuSWVersionMismatchFault	NOTIFICATION-TYPE
	OBJECTS	{	fwuTrapSequenceNumber,
			fwuTrapTimeStamp,
			fwuModuleNumber,
			fwuModuleType,
                               fwuAlarmedModuleName,
			fwuHstNumber,
			fwuHstName,
			fwuRmtNumber,
			fwuRmtName,
			fwuTrapCode,
			fwuNotificationStatus	}
	STATUS		current
	DESCRIPTION	"Software Version Mismatch Fault. SW Versions on the Host and Remote do not match."
	::=  {  fwuRmtSystemLevelTraps  22  }

fwuDruSysCardFanFault	NOTIFICATION-TYPE
	OBJECTS	{	fwuTrapSequenceNumber,
			fwuTrapTimeStamp,
			fwuModuleNumber,
			fwuModuleType,
                               fwuAlarmedModuleName,
			fwuHstNumber,
			fwuHstName,
			fwuRmtNumber,
			fwuRmtName,
			fwuTrapCode,
			fwuNotificationStatus	}
	STATUS		current
	DESCRIPTION	"Fan not functioning."
	::=  {  fwuRmtSystemLevelTraps  23  }

fwuDruOverTempFault	NOTIFICATION-TYPE
	OBJECTS	{	fwuTrapSequenceNumber,
			fwuTrapTimeStamp,
			fwuModuleNumber,
			fwuModuleType,
                               fwuAlarmedModuleName,
			fwuHstNumber,
			fwuHstName,
			fwuRmtNumber,
			fwuRmtName,
			fwuTrapCode,
			fwuNotificationStatus	}
	STATUS		current
	DESCRIPTION	"DRU Temperature above operating limit."
	::=  {  fwuRmtSystemLevelTraps  24  }	

fwuDruUnderTempFault	NOTIFICATION-TYPE
	OBJECTS	{	fwuTrapSequenceNumber,
			fwuTrapTimeStamp,
			fwuModuleNumber,
			fwuModuleType,
                               fwuAlarmedModuleName,
			fwuHstNumber,
			fwuHstName,
			fwuRmtNumber,
			fwuRmtName,
			fwuTrapCode,
			fwuNotificationStatus	}
	STATUS		current
	DESCRIPTION	"DRU Temperature below operating limit."
	::=  {  fwuRmtSystemLevelTraps  25  }


fwuRmtSERFObjects			OBJECT IDENTIFIER		::=  {  fwuRemoteUnitObjects  2  }
fwuRmtSERFInfo				OBJECT IDENTIFIER		::=  {  fwuRmtSERFObjects  1  }
fwuRmtSERFGeneral			OBJECT IDENTIFIER		::=  {  fwuRmtSERFInfo  1  }

fwuRmtSERFGeneralTable	OBJECT-TYPE
	SYNTAX			SEQUENCE  OF  FwuRmtSERFGeneralEntry
	MAX-ACCESS		not-accessible
	STATUS			current
	DESCRIPTION		"This table maintains Information of remote SERF Card."
	::=  { fwuRmtSERFGeneral  1 }

fwuRmtSERFGeneralEntry	OBJECT-TYPE
	SYNTAX			FwuRmtSERFGeneralEntry
	MAX-ACCESS		not-accessible
	STATUS			current
	DESCRIPTION		"Each entry in this table refers to SERF Card objects."
	INDEX			{  fwuRmtNumber  }
	::=  { fwuRmtSERFGeneralTable 1 }

FwuRmtSERFGeneralEntry  ::=  SEQUENCE {
	fwuRmtSERFLinuxKernelVer  DisplayString,
	fwuRmtSERFLinuxBootLoaderVer  DisplayString,
	fwuRmtSERFCompactFlashSWVer  DisplayString,
	fwuRmtSERFFPGAVer  DisplayString,		
	fwuRmtSERFPPCHWMonSWVer  DisplayString,
	fwuRmtSERFPPCAPPMonSWVer  DisplayString,
	--fwuRmtSERFPPCGPSMonSWVer  DisplayString,
	--fwuRmtSERFPPCSNMPAgentSWVer  DisplayString,
	fwuRmtSERFPPCMATEMonSWVer  DisplayString,
	fwuRmtSERFPPCENETMonSWVer  DisplayString,
	fwuRmtSERFPPCFPGAMonSWVer  DisplayString,
	fwuRmtSERFRIDateCode  DisplayString,
	fwuRmtSERFRIHWVer  DisplayString,
	fwuRmtSERFRISerialNumber  DisplayString,
	fwuRmtSERFRIADCPartNumber  DisplayString,
	fwuRmtSERFRIHWGen	INTEGER,
	fwuRmtpThreadSWVer  DisplayString,
	fwuRmtWebServerSWVer  DisplayString	}

fwuRmtSERFLinuxKernelVer	OBJECT-TYPE	
	SYNTAX			DisplayString
	MAX-ACCESS		read-only
	STATUS			current
	DESCRIPTION		"Linux Kernel version on remote."
	::=  {  fwuRmtSERFGeneralEntry  1  }

fwuRmtSERFLinuxBootLoaderVer	OBJECT-TYPE	
	SYNTAX			DisplayString
	MAX-ACCESS		read-only
	STATUS			current
	DESCRIPTION		"Linux Boot loader version on remote."
	::=  {  fwuRmtSERFGeneralEntry  2  }

fwuRmtSERFCompactFlashSWVer	OBJECT-TYPE	
	SYNTAX			DisplayString
	MAX-ACCESS		read-only
	STATUS			current
	DESCRIPTION		"Compact Flash version on remote."
	::=  {  fwuRmtSERFGeneralEntry  3  }
		
fwuRmtSERFFPGAVer	OBJECT-TYPE	
	SYNTAX			DisplayString
	MAX-ACCESS		read-only
	STATUS			current
	DESCRIPTION		"Version of FPGA loaded on remote SeRF."
	::=  {  fwuRmtSERFGeneralEntry  4  }

fwuRmtSERFPPCHWMonSWVer	OBJECT-TYPE	
	SYNTAX			DisplayString
	MAX-ACCESS		read-only
	STATUS			current
	DESCRIPTION		"Hardware monitor process version on remote."
	::=  {  fwuRmtSERFGeneralEntry  5  }

fwuRmtSERFPPCAPPMonSWVer	OBJECT-TYPE	
	SYNTAX			DisplayString
	MAX-ACCESS		read-only
	STATUS			current
	DESCRIPTION		"Application monitor process version on remote."
	::=  {  fwuRmtSERFGeneralEntry  6  }

-- In Rel 6.0 this attribute is removed, as GPS is never supported.
--fwuRmtSERFPPCGPSMonSWVer	OBJECT-TYPE	
--	SYNTAX			DisplayString
--	MAX-ACCESS		read-only
--	STATUS			deprecated
--	DESCRIPTION		"GPS monitor process  Software Version of the remote system."
--	::=  {  fwuRmtSERFGeneralEntry  7  }

--fwuRmtSERFPPCSNMPAgentSWVer	OBJECT-TYPE	
--	SYNTAX			DisplayString
--	MAX-ACCESS		read-only
--	STATUS			current
--	DESCRIPTION		"SNMP agent version on remote."
--	::=  {  fwuRmtSERFGeneralEntry  8  }

fwuRmtSERFPPCMATEMonSWVer	OBJECT-TYPE	
	SYNTAX			DisplayString
	MAX-ACCESS		read-only
	STATUS			current
	DESCRIPTION		"Mate monitor process version on remote."
	::=  {  fwuRmtSERFGeneralEntry  9  }

fwuRmtSERFPPCENETMonSWVer	OBJECT-TYPE	
	SYNTAX			DisplayString
	MAX-ACCESS		read-only
	STATUS			current
	DESCRIPTION		"ENET monitor process version on remote."
	::=  {  fwuRmtSERFGeneralEntry  10  }

fwuRmtSERFPPCFPGAMonSWVer	OBJECT-TYPE	
	SYNTAX			DisplayString
	MAX-ACCESS		read-only
	STATUS			current
	DESCRIPTION		"FPGA monitor process version on remote."
	::=  {  fwuRmtSERFGeneralEntry  11  }

fwuRmtSERFRIDateCode	OBJECT-TYPE	
	SYNTAX			DisplayString
	MAX-ACCESS		read-only
	STATUS			current
	DESCRIPTION		"Remote SERF Inventory - Date Code of the Remote system."
	::=  {  fwuRmtSERFGeneralEntry  12  }

fwuRmtSERFRIHWVer	OBJECT-TYPE	
	SYNTAX			DisplayString
	MAX-ACCESS		read-only
	STATUS			current
	DESCRIPTION		"Remote SERF Inventory - HardWare version of the remote system."
	::=  {  fwuRmtSERFGeneralEntry  13  }

fwuRmtSERFRISerialNumber	OBJECT-TYPE	
	SYNTAX			DisplayString
	MAX-ACCESS		read-only
	STATUS			current
	DESCRIPTION		"Remote SERF Inventory -  Serial Number."
	::=  {  fwuRmtSERFGeneralEntry  14  }

fwuRmtSERFRIADCPartNumber	OBJECT-TYPE	
	SYNTAX			DisplayString
	MAX-ACCESS		read-only
	STATUS			current
	DESCRIPTION		"Remote SERF Inventory -  TE PartNumber."
	::=  {  fwuRmtSERFGeneralEntry  15  }

-- Rel 6.0
fwuRmtSERFRIHWGen OBJECT-TYPE	
	SYNTAX			INTEGER  { firstGeneration(0), secondGeneration(1) }
	MAX-ACCESS		read-only
	STATUS			current
	DESCRIPTION		"Remote SERF Hardware Generation. Presently, there are two generations first generation(0), second generation(1) "
	::=  {  fwuRmtSERFGeneralEntry  16  }

fwuRmtpThreadSWVer	OBJECT-TYPE	
	SYNTAX			DisplayString
	MAX-ACCESS		read-only
	STATUS			current
	DESCRIPTION		"The version number of pThread Process. If blank then pThread is not running."
	::=  {  fwuRmtSERFGeneralEntry  17  }
	
fwuRmtWebServerSWVer		OBJECT-TYPE	
	SYNTAX			DisplayString
	MAX-ACCESS		read-only
	STATUS			current
	DESCRIPTION		"The version number of Web Server on remote."
	::=  {  fwuRmtSERFGeneralEntry  18  }


fwuRmtSERFOptObjects		OBJECT IDENTIFIER		::=  {  fwuRmtSERFInfo  2  }

fwuRmtSERFOptTable	OBJECT-TYPE
	SYNTAX			SEQUENCE  OF  FwuRmtSERFOptEntry
	MAX-ACCESS		not-accessible
	STATUS			current
	DESCRIPTION		"This table maintains Information of remote units SFP objects."
	::=  { fwuRmtSERFOptObjects  1 }

fwuRmtSERFOptEntry	OBJECT-TYPE
	SYNTAX			FwuRmtSERFOptEntry
	MAX-ACCESS		not-accessible
	STATUS			current
	DESCRIPTION		"Each entry in this table refers to remote units SFP objects."
	INDEX			{  fwuRmtNumber, fwuRmtSERFOptSFPNumber  }
	::=  { fwuRmtSERFOptTable 1 }

FwuRmtSERFOptEntry  ::=  SEQUENCE {
	fwuRmtSERFOptSFPNumber  Integer32,
	fwuRmtSERFOptSFPName	DisplayString,
	fwuRmtSERFOptSFPType  OPTICSType,
	fwuRmtSERFOptSFPColor	Integer32,
	fwuRmtSERFOptRevLaunchPowerMeas  DisplayString,
	fwuRmtSERFOptFwdLaunchPowerMeas  DisplayString,
	fwuRmtSERFOptMateName 	DisplayString,
	fwuRmtSERFIPEnable	INTEGER,
	fwuRmtSERFOptMateId		UnitID2,
	fwuRmtSERFOptMateSfpId	Integer32,	
	fwuRmtSERFOptMateSfpDir	INTEGER,
        fwuRmtSERFOptHostIP     DisplayString } 

fwuRmtSERFOptSFPNumber	OBJECT-TYPE	
	SYNTAX			Integer32  (1 .. 8) 
	MAX-ACCESS		read-only
	STATUS			current
	DESCRIPTION		"A unique identifier of each SFP. The identifier is the SFP slot number. There are eight slots. Therefore, the valid values are 1 to 8."
	::=  {  fwuRmtSERFOptEntry  1  }

fwuRmtSERFOptSFPName	OBJECT-TYPE	
	SYNTAX			DisplayString (SIZE(0..64))
	MAX-ACCESS		read-write
	STATUS			current
	DESCRIPTION		"User defined name of each Remote SFP. All characters except angular brackets, single and double quotes are allowed. Minimum length of the name is 1 character. Maximum length of the name 64 characters."
	DEFVAL  		{ "SFP" }
	::=  {  fwuRmtSERFOptEntry  2  }

fwuRmtSERFOptSFPType	OBJECT-TYPE	
	SYNTAX			OPTICSType
	MAX-ACCESS		read-only
	STATUS			current
	DESCRIPTION		"SFP Type - Optical Port Type. Identifies whether the SFP is short(1)/intermediate(2)/long(3) range. It may also be unidentified (-1)."
	::=  {  fwuRmtSERFOptEntry  3  }

fwuRmtSERFOptSFPColor	OBJECT-TYPE	
	SYNTAX			Integer32
	MAX-ACCESS		read-only
	STATUS			current
	DESCRIPTION		"Wavelength of light used in the SFP (in nanometers)."
	::=  {  fwuRmtSERFOptEntry  4  }

fwuRmtSERFOptRevLaunchPowerMeas	OBJECT-TYPE	
	SYNTAX			DisplayString
	MAX-ACCESS		read-only
	STATUS			current
	DESCRIPTION		"Value of the optical power, in dBm received at the remote."				
	::=  {  fwuRmtSERFOptEntry  5  }

fwuRmtSERFOptFwdLaunchPowerMeas	OBJECT-TYPE	
	SYNTAX			DisplayString
	MAX-ACCESS		read-only
	STATUS			current
	DESCRIPTION		"Value of the optical power, in dBm transmitted by the remote."
	::=  {  fwuRmtSERFOptEntry  6  }

fwuRmtSERFOptMateName 		OBJECT-TYPE	
 	SYNTAX			DisplayString
 	MAX-ACCESS		read-only
	STATUS			current
	DESCRIPTION		"Name of Remote mate."
	::=  {  fwuRmtSERFOptEntry  7  }

fwuRmtSERFIPEnable 		OBJECT-TYPE	
	SYNTAX			INTEGER  { iPEnable(1), iPDisable(2) }
	MAX-ACCESS		read-only
	STATUS			current
	DESCRIPTION		"IP enable mode."
	DEFVAL 			{ 2 }	
	::=  {  fwuRmtSERFOptEntry   8 }
	
fwuRmtSERFOptMateId	OBJECT-TYPE	
	SYNTAX			UnitID2
	MAX-ACCESS		read-only
	STATUS			current
	DESCRIPTION		"Identifier of (companion) mate unit."
	::=  {  fwuRmtSERFOptEntry  9  }

fwuRmtSERFOptMateSfpId	OBJECT-TYPE	
	SYNTAX			Integer32
	MAX-ACCESS		read-only
	STATUS			current
	DESCRIPTION		"Identifier of SFP to which the mate connects."
	::=  {  fwuRmtSERFOptEntry  10  }
	
fwuRmtSERFOptMateSfpDir	OBJECT-TYPE	
	SYNTAX			INTEGER  { notDirection(-1) , reverse(0) , forwad(1) }
	MAX-ACCESS		read-only
	STATUS			current
	DESCRIPTION		"Indicates whether the fiber is incoming(from the direction of the host) (0) or outgoing (away from the unit)(1)  on this SFP port."
	::=  {  fwuRmtSERFOptEntry  11  }

fwuRmtSERFOptHostIP     OBJECT-TYPE
        SYNTAX                  OCTET STRING ( SIZE (0..16) )
        MAX-ACCESS              read-only
        STATUS                  current
        DESCRIPTION             "IP addresses of Host. If 'NA', then it means that no host is connected."
        DEFVAL          { "NA" }
        ::=  {  fwuRmtSERFOptEntry  12  }

fwuRmtSERFTraps				OBJECT IDENTIFIER		::=  {  fwuRmtSERFObjects  2  }

fwuRmtSERFHstLostFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS		current
	DESCRIPTION		"Host not communicating with DRU/PRU/URU."
	::=  {  fwuRmtSERFTraps  2  }

fwuRmtSERFOptRxBERFault	NOTIFICATION-TYPE
	OBJECTS	{	fwuTrapSequenceNumber, 
				fwuTrapTimeStamp, 
				fwuModuleNumber,
				fwuModuleType,
                               fwuAlarmedModuleName,
				fwuHstNumber,
				fwuHstName,
				fwuRmtNumber,
				fwuRmtName,
				fwuTrapCode,
				fwuNotificationStatus 	}
	STATUS		current
	DESCRIPTION		"High bit error rate (BER) detected by fiber optic receiver."
	::=  {  fwuRmtSERFTraps  3  }

fwuRmtSERFOptRxNoLightFault	NOTIFICATION-TYPE
	OBJECTS	{ 	fwuTrapSequenceNumber,
				fwuTrapTimeStamp, 
				fwuModuleNumber,
				fwuModuleType,  
                               fwuAlarmedModuleName,
				fwuHstNumber, 
				fwuHstName,  
				fwuRmtNumber, 
				fwuRmtName,
				fwuTrapCode,
				fwuNotificationStatus 	}
	STATUS		current
	DESCRIPTION		"No signal detected by optical receiver."
	::=  {  fwuRmtSERFTraps  4  }

fwuRmtSERFOptLaserFault	NOTIFICATION-TYPE
	OBJECTS	{ 	fwuTrapSequenceNumber,
				fwuTrapTimeStamp, 
				fwuModuleNumber,
				fwuModuleType,  
                               fwuAlarmedModuleName,
				fwuHstNumber, 
				fwuHstName,  
				fwuRmtNumber, 
				fwuRmtName,
				fwuTrapCode, 
				fwuNotificationStatus 	}
	STATUS		current
	DESCRIPTION		"SFP optical transmitter failed."
	::=  {  fwuRmtSERFTraps  5  }

fwuRmtSERFOptOverDriveFault	NOTIFICATION-TYPE
	OBJECTS	{ 	fwuTrapSequenceNumber, 
				fwuTrapTimeStamp,
				fwuModuleNumber,
				fwuModuleType,  
                               fwuAlarmedModuleName,
				fwuHstNumber, 
				fwuHstName,  
				fwuRmtNumber,
				fwuRmtName,
				fwuTrapCode,
				fwuNotificationStatus 	}
	STATUS		current
	DESCRIPTION	"SFP optical receive input power above specification."
	::=  {  fwuRmtSERFTraps  6  }
	
fwuRmtSERFOptUnderDriveFault	NOTIFICATION-TYPE
	OBJECTS	{ 	fwuTrapSequenceNumber, 
				fwuTrapTimeStamp,
				fwuModuleNumber,
				fwuModuleType,
                               fwuAlarmedModuleName,
				fwuHstNumber,
				fwuHstName,
				fwuRmtNumber, 
				fwuRmtName, 
				fwuTrapCode,
				fwuNotificationStatus 	}
	STATUS		current
	DESCRIPTION		"SFP optical receive input power below specification."
	::=  {  fwuRmtSERFTraps  7  }
		
fwuRmtSERFSynthAlarmFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName,
				fwuTrapCode, 
				fwuNotificationStatus 	}
	STATUS		current
	DESCRIPTION		"SeRF synthesizer unlocked."
	::=  {  fwuRmtSERFTraps  8  }

fwuRmtSERFFault	NOTIFICATION-TYPE
	OBJECTS	{ 	fwuTrapSequenceNumber, 
				fwuTrapTimeStamp,
				fwuModuleNumber,
				fwuModuleType,
                               fwuAlarmedModuleName,
				fwuHstNumber,
				fwuHstName,
				fwuRmtNumber,
				fwuRmtName,
				fwuTrapCode,
				fwuNotificationStatus	}
	STATUS		current
	DESCRIPTION		"Summary of SeRF Synthesizer Unlocked alarm and SeRF FPGA status. Possibly, the system may not be communicating with the Ethernet Switch. This is also precipitated by the I2C Bus Fault."
	::=  {  fwuRmtSERFTraps  9  }

fwuRmtI2CBus1Fault NOTIFICATION-TYPE
        OBJECTS {       fwuTrapSequenceNumber,
                                fwuTrapTimeStamp,
                                fwuModuleNumber,
                                fwuModuleType,
                               fwuAlarmedModuleName,
                                fwuHstNumber,
                                fwuHstName,
                                fwuRmtNumber,
                                fwuRmtName,
                                fwuTrapCode,
                                fwuNotificationStatus   }
        STATUS          current
        DESCRIPTION             "Indicates an I2C communication problem."
        ::=  {  fwuRmtSERFTraps  10  }

fwuRmtI2CBus2Fault NOTIFICATION-TYPE
        OBJECTS {       fwuTrapSequenceNumber,
                                fwuTrapTimeStamp,               
                                fwuModuleNumber,
                                fwuModuleType,
                               fwuAlarmedModuleName,
                                fwuHstNumber,
                                fwuHstName,
                                fwuRmtNumber,
                                fwuRmtName,
                                fwuTrapCode,
                                fwuNotificationStatus   }
        STATUS          current
        DESCRIPTION             "Indicates an I2C communication problem."
        ::=  {  fwuRmtSERFTraps  11  }

fwuRmtSERFEthPortObjects	OBJECT IDENTIFIER		::=  {  fwuRemoteUnitObjects  3  }
fwuRmtSERFEthPortInfo		OBJECT IDENTIFIER		::=  {  fwuRmtSERFEthPortObjects  1  }

fwuRmtSERFEthPortTable	OBJECT-TYPE
	SYNTAX			SEQUENCE  OF  FwuRmtSERFEthPortEntry
	MAX-ACCESS		not-accessible
	STATUS			current
	DESCRIPTION		
		"This table maintains information of Host Ethernet Ports."
	::=  { fwuRmtSERFEthPortInfo  1 }

fwuRmtSERFEthPortEntry	OBJECT-TYPE
	SYNTAX			FwuRmtSERFEthPortEntry
	MAX-ACCESS		not-accessible
	STATUS			current
	DESCRIPTION		
		"Each entry in this table refers to Host SERF Ethernet port objects."
	INDEX			{  fwuRmtNumber, fwuRmtSERFEthPortNumber  }
	::=  { fwuRmtSERFEthPortTable 1 }

FwuRmtSERFEthPortEntry  ::=  SEQUENCE {
	fwuRmtSERFEthPortNumber  Unsigned32,
	fwuRmtSERFEthPortType  ENETType,
	fwuRmtSERFEthPortRxBytes  Counter64,
	fwuRmtSERFEthPortRxPkts  Counter64,
	fwuRmtSERFEthPortRxFcsErrors  Counter64,
	fwuRmtSERFEthPortRxBroadcastPkts  Counter64,
	fwuRmtSERFEthPortRxMulticastPkts  Counter64,
	fwuRmtSERFEthPortRxFragmtdFrames  Counter64,
	fwuRmtSERFEthPortRxJabbersFrames  Counter64,
	fwuRmtSERFEthPortTxByteCounter  Counter64,
	fwuRmtSERFEthPortTxPkts  Counter64,
	fwuRmtSERFEthPortTxBroadcastPkts  Counter64,
	fwuRmtSERFEthPortTxMulticastPkts  Counter64,
	fwuRmtSERFEthPortSFPId  Integer32	}

fwuRmtSERFEthPortNumber	OBJECT-TYPE	
	SYNTAX			Unsigned32  (1 .. 12) 
	MAX-ACCESS		read-only
	STATUS			current
	DESCRIPTION		"A unique identifier for each Ethernet port. There are twelve ports."
	::=  {  fwuRmtSERFEthPortEntry  1  }

fwuRmtSERFEthPortType	OBJECT-TYPE	
	SYNTAX			ENETType 
	MAX-ACCESS		read-only
	STATUS			current
	DESCRIPTION		"An identifier for the type of Ethernet port. The port types are network(1), craft(2) , management(3) , switch(4) , SFP(5). It may be unknown (-1)."
	::=  {  fwuRmtSERFEthPortEntry  2  }

fwuRmtSERFEthPortRxBytes	OBJECT-TYPE	
	SYNTAX			Counter64
	MAX-ACCESS		read-only
	STATUS			current
	DESCRIPTION		"The number of bytes recieved at this ethernet port."
	::=  {  fwuRmtSERFEthPortEntry  3  }

fwuRmtSERFEthPortRxPkts	OBJECT-TYPE	
	SYNTAX			Counter64
	MAX-ACCESS		read-only
	STATUS			current
	DESCRIPTION		"The number of packets recieved at this ethernet port."
	::=  {  fwuRmtSERFEthPortEntry  4  }

fwuRmtSERFEthPortRxFcsErrors	OBJECT-TYPE	
	SYNTAX			Counter64
	MAX-ACCESS		read-only
	STATUS			current
	DESCRIPTION		"The number of FCS errors recieved at this ethernet port."
	::=  {  fwuRmtSERFEthPortEntry  5  }

fwuRmtSERFEthPortRxBroadcastPkts	OBJECT-TYPE	
	SYNTAX			Counter64
	MAX-ACCESS		read-only
	STATUS			current
	DESCRIPTION		"The number of broadcast packets recieved at this ethernet port."
	::=  {  fwuRmtSERFEthPortEntry  6  }

fwuRmtSERFEthPortRxMulticastPkts	OBJECT-TYPE	
	SYNTAX			Counter64
	MAX-ACCESS		read-only
	STATUS			current
	DESCRIPTION		"The number of multicast packets recieved at this ethernet port."
	::=  {  fwuRmtSERFEthPortEntry  7  }

fwuRmtSERFEthPortRxFragmtdFrames	OBJECT-TYPE	
	SYNTAX			Counter64
	MAX-ACCESS		read-only
	STATUS			current
	DESCRIPTION		"The number of fragmented frames received at this ethernet port."
	::=  {  fwuRmtSERFEthPortEntry  8  }

fwuRmtSERFEthPortRxJabbersFrames	OBJECT-TYPE	
	SYNTAX			Counter64
	MAX-ACCESS		read-only
	STATUS			current
	DESCRIPTION		"The number of jabber frames received at this ethernet port."
	::=  {  fwuRmtSERFEthPortEntry  9  }

fwuRmtSERFEthPortTxByteCounter	OBJECT-TYPE	
	SYNTAX			Counter64
	MAX-ACCESS		read-only
	STATUS			current
	DESCRIPTION		"The number of bytes transmitted from this ethernet port."
	::=  {  fwuRmtSERFEthPortEntry  10  }

fwuRmtSERFEthPortTxPkts	OBJECT-TYPE	
	SYNTAX			Counter64
	MAX-ACCESS		read-only
	STATUS			current
	DESCRIPTION		"The number of packets transmitted from this ethernet port."
	::=  {  fwuRmtSERFEthPortEntry  11  }

fwuRmtSERFEthPortTxBroadcastPkts	OBJECT-TYPE	
	SYNTAX			Counter64
	MAX-ACCESS		read-only
	STATUS			current
	DESCRIPTION		"The number of broadcast packets transmitted from this ethernet port."
	::=  {  fwuRmtSERFEthPortEntry  12  }

fwuRmtSERFEthPortTxMulticastPkts	OBJECT-TYPE	
	SYNTAX			Counter64
	MAX-ACCESS		read-only
	STATUS			current
	DESCRIPTION		"The number of multicast packets transmitted from this ethernet port."
	::=  {  fwuRmtSERFEthPortEntry  13  }
	  
fwuRmtSERFEthPortSFPId	OBJECT-TYPE	
	SYNTAX			Integer32
	MAX-ACCESS		read-only
	STATUS			current
	DESCRIPTION		"Identifier of SFP to which this ethernet port connects to."
	::=  {  fwuRmtSERFEthPortEntry  14  }

fwuRmtSERFEthPortTraps		OBJECT IDENTIFIER		::=  {  fwuRmtSERFEthPortObjects  2  }

fwuRmtSERFFPGAObjects		OBJECT IDENTIFIER		::=  {  fwuRemoteUnitObjects  4  }
fwuRmtSERFFPGAInfo			OBJECT IDENTIFIER		::=  {  fwuRmtSERFFPGAObjects  1 }

fwuRmtSERFFPGAInfoTable		OBJECT-TYPE
	SYNTAX			SEQUENCE  OF  FwuRmtSERFFPGAInfoEntry
	MAX-ACCESS		not-accessible
	STATUS			current
	DESCRIPTION		"This table maintains Information of remote SERF FPGA objects."
	::=  { fwuRmtSERFFPGAInfo  1 }

fwuRmtSERFFPGAInfoEntry	OBJECT-TYPE
	SYNTAX			FwuRmtSERFFPGAInfoEntry
	MAX-ACCESS		not-accessible
	STATUS			current
	DESCRIPTION		"Each entry in this table refers to SERF FPGA information."
	INDEX			{  fwuRmtNumber }
	::=  { fwuRmtSERFFPGAInfoTable 1 }

FwuRmtSERFFPGAInfoEntry  ::=  SEQUENCE { 
	fwuRmtSERFFPGAStatus  INTEGER
	}

fwuRmtSERFFPGAStatus	OBJECT-TYPE	
	SYNTAX			INTEGER  { ppcCanTalkToFPGA(0) , ppcCannotTalkToFPGA(1) } 
	MAX-ACCESS		read-only
	STATUS			current
	DESCRIPTION		"Remote SERF Card FPGA status. Either the ppc can talk to FPGA(0) or not(1)"
	DEFVAL 			{ 0 }	
	::=  {  fwuRmtSERFFPGAInfoEntry  1  }

fwuRmtSERFFPGATraps			OBJECT IDENTIFIER		::=  {  fwuRmtSERFFPGAObjects  2 }

--fwuRmtMateMonObjects		OBJECT IDENTIFIER		::=  {  fwuRemoteUnitObjects  5  }
--fwuRmtMateMonInfo			OBJECT IDENTIFIER		::=  {  fwuRmtMateMonObjects  1  }

--fwuRmtMateMonTable	OBJECT-TYPE
--	SYNTAX			SEQUENCE  OF  FwuRmtMateMonEntry
--	MAX-ACCESS		not-accessible
--	STATUS			current
--	DESCRIPTION		"This table maintains Information of Remote Mate Monitor."
--	::=  { fwuRmtMateMonInfo  1 }

--fwuRmtMateMonEntry	OBJECT-TYPE
--	SYNTAX			FwuRmtMateMonEntry
--	MAX-ACCESS		not-accessible
--	STATUS			current
--	DESCRIPTION		"Each entry in this table refers to remote Mate monitor objects."
--	INDEX			{  fwuRMmonIndex  }
--	::=  { fwuRmtMateMonTable 1 }
			
--FwuRmtMateMonEntry  ::=  SEQUENCE {
--		fwuRMmonIndex  Integer32,
--		fwuRMmonHstIPAddress  IpAddress,
--		fwuRMmonHstID  UnitType, 
--		fwuRMmonRmtID  UnitID2 }
--	 
--fwuRMmonIndex	OBJECT-TYPE	
--	SYNTAX			Integer32 (1..2147483647)
--	MAX-ACCESS		read-only
--	STATUS			current
--	DESCRIPTION		"Index of mate monitor table. "
--	::=  {  fwuRmtMateMonEntry  1  }
--
--fwuRMmonHstIPAddress	OBJECT-TYPE	
--	SYNTAX			IpAddress
--	MAX-ACCESS		read-only
--	STATUS			current
--	DESCRIPTION		"IP addresses of host mate."
--	::=  {  fwuRmtMateMonEntry  2  }
--
--fwuRMmonHstID	OBJECT-TYPE	
--	SYNTAX			UnitType
--	MAX-ACCESS		read-only
--	STATUS			current
--	DESCRIPTION		"ID of companion host unit."
--	::=  {  fwuRmtMateMonEntry  3  }
--
--fwuRMmonRmtID	OBJECT-TYPE	
--	SYNTAX			UnitID2
--	MAX-ACCESS		read-only
--	STATUS			current
--	DESCRIPTION		"ID of companion remote unit."
--	::=  {  fwuRmtMateMonEntry  4  }
		
fwuRmtDARTObjects		OBJECT IDENTIFIER		::=  {  fwuRemoteUnitObjects  6  }
fwuRmtDARTInfo			OBJECT IDENTIFIER		::=  {  fwuRmtDARTObjects  1  }
fwuRmtDARTGeneral		OBJECT IDENTIFIER		::=  {  fwuRmtDARTInfo  1  }

fwuRmtDARTGeneralTable	OBJECT-TYPE
	SYNTAX			SEQUENCE  OF  FwuRmtDARTGeneralEntry
	MAX-ACCESS		not-accessible
	STATUS			current
	DESCRIPTION		"This table maintains Information of Remote DART Card."
	::=  { fwuRmtDARTGeneral  1 }

fwuRmtDARTGeneralEntry	OBJECT-TYPE
	SYNTAX			FwuRmtDARTGeneralEntry
	MAX-ACCESS		not-accessible
	STATUS			current
	DESCRIPTION		"Each entry in this table refers to remote DART Card objects."
	INDEX			{  fwuRmtNumber, fwuRmtDARTNumber  }
	::=  { fwuRmtDARTGeneralTable 1 }

FwuRmtDARTGeneralEntry  ::=  SEQUENCE {
	fwuRmtDARTNumber  Integer32,
	fwuRmtDARTName	DisplayString,
	fwuRmtDARTBandType  BANDType,
	fwuRmtDARTPassBand  OCTET STRING,
	fwuRmtDARTOperatingMode  MODEType,
	fwuRmtDARTDiversityStatus  INTEGER,
	fwuRmtDARTForwardGain  GAINType,
	fwuRmtDARTReverseGain  GAINType,
	fwuRmtDARTForwardDelay  DELAYType,
	fwuRmtDARTReverseDelay  DELAYType,
	fwuRmtDARTTempMeas  DisplayString,
	fwuRmtDARTFPGAStatus INTEGER,
	fwuRmtDARTFPGAProgramVer  DisplayString,
	fwuRmtDARTRIADCPartNumber  DisplayString,
	fwuRmtDARTRISerialNumber  DisplayString,
	fwuRmtDARTRIDateCode  DisplayString,
	fwuRmtDARTRIHWVer  DisplayString,
	fwuRmtDARTGeneralTableRowStatus RowStatus,	
	fwuRmtDARTActualForwardDelay  Integer32,
	fwuRmtDARTForwardLowerboundDelay  Integer32,
	fwuRmtDARTForwardUpperboundDelay  Integer32,
	fwuRmtDARTActualReverseDelay  Integer32,
	fwuRmtDARTReverseLowerboundDelay  Integer32,
	fwuRmtDARTReverseUpperboundDelay  Integer32,
	fwuRmtDARTPeakInputPwrLvl1 DisplayString,
	fwuRmtDARTPeakInputPwrLvl2 DisplayString,
	fwuRmtDARTPeakAvgInputPwrLvl1 DisplayString,
	fwuRmtDARTPeakAvgInputPwrLvl2 DisplayString,
	fwuRmtDARTMinAvgInputPwrLvl1 DisplayString,
	fwuRmtDARTMinAvgInputPwrLvl2 DisplayString,
	fwuRmtDARTInputPowerMode INTEGER,
	fwuRmtDARTPwrLevelMaxHoldReset INTEGER, 
	fwuRmtDARTLastMaxHoldResetTime OCTET STRING,
	fwuRmtDARTReverseGainMode  INTEGER,
	fwuRmtDARTTxRIADCPartNumber DisplayString,
	fwuRmtDARTTxRISerialNumber DisplayString,
	fwuRmtDARTTxRIDateCode DisplayString,
	fwuRmtDARTTxRIHWVer DisplayString,
        fwuRmtDARTLinkedStatus INTEGER,
        fwuRmtDARTAvailable INTEGER,
        fwuRmtDARTUsedSFP INTEGER }

fwuRmtDARTNumber	OBJECT-TYPE	
	SYNTAX			Integer32  (1 .. 8) 
	MAX-ACCESS		read-only
	STATUS			current
	DESCRIPTION		"A unique identifier for each DART Card Object of remote. Since there are eight DART slots the valid values are 1 to 8."
	::=  {  fwuRmtDARTGeneralEntry  1  }

fwuRmtDARTName	OBJECT-TYPE	
	SYNTAX			DisplayString (SIZE(0..64))
	MAX-ACCESS		read-create
	STATUS			current
	DESCRIPTION		"A user defined name for each DART Card object of remote. All characters except angular brackets, single and double quotes are allowed. Minimum length of the name is 1 character. Maximum length of the name 64 characters."
	DEFVAL 			{ "DART" }
	::=  {  fwuRmtDARTGeneralEntry  2  }

fwuRmtDARTBandType	OBJECT-TYPE	
	SYNTAX			BANDType
	MAX-ACCESS		read-only
	STATUS			current
	DESCRIPTION		"Band type of remote DART card."
	DEFVAL 			{ -1 }
	::=  {  fwuRmtDARTGeneralEntry  3 }

fwuRmtDARTPassBand	OBJECT-TYPE	
	SYNTAX			OCTET STRING (SIZE (0..40))
	MAX-ACCESS		read-create
	STATUS			current
	DESCRIPTION		"This is for configuration of Pass-band type for Remote DART card. 
			 Following input formats are supported for Classic and SuperDart
			 passband configuration.
 			 1. For Classic Darts only, 
				User input string would be enumeration value ( i.e., 'x'), 
				ranging from 1 to 134. See below in section 3. for valid values. 
			 2. For SuperDarts only,
				a. BandType_SubBand1+SubBand2 
				  This is applicable only for contiguous passband selection,
					applicable only for PCS & AWS. (e.g., 'PCS_A1+A2+A3')
				b. BandType_SubBand1+SubBand2:SubBand5+SubBand6
				  This is applicable for noncontiguous passband selection,
					applicable only for PCS & AWS. (e.g., 'PCS_A1+A2:C2+C1')
				c. BandType_StartFrequency-StartFrequency
				  This is applicable only for contiguous passband frequency range.
				  (e.g.,, PCS_1930-1945) 
				d. BandType_StartFrequency1-StartFrequency1:StartFrequency2-StartFrequency2
				  This is applicable only for noncontiguous passband frequency ranges.
				  (e.g., PCS_1930-1940.5:1960.7-1970.6).
				  Where BandType is 'PCS', 'AWS', 'UMTS','EGSM900','GSM1800', 'UC700'.
			3. Valid enumeration value for classic dart:- undefined ( -1 ),
					cellularA2A(1),cellularA(2),cellularAA1A2(3),cellularA1(4),
					cellularB(5),cellularB1(6),cellularBB1(7),
					pcsA1(8),pcsA2(9),pcsA3(10),pcsB1(11),pcsB2(12),pcsB3(13),
					pcsC3(14),pcsC4(15),pcsC5(16),pcsD(17),pcsE(18),pcsF(19),
					pcsA1A2(24),pcsA2A3(25),pcsA3D(26),pcsDB1(27),pcsB1B2(28),pcsB2B3(29),
					pcsB3E(30),pcsEF(31),pcsFC3(32),pcsC3C4(33),pcsC4C5(34),
					pcsC5G(35),pcsGawsH(36),pcsFC2(37),pcsC1G(38),pcsA(39),
					pcsA2A3D(40),pcsA3DB1(41),pcsDB1B2(42),pcsB(43),pcsB2B3E(44),
					pcsB3EF(45),pcsEFC3(46),pcsFC3C4(47),pcsC(48), pcsC4C5G(49),
					pcsC5GawsH(50),pcsEFC2(51),pcsC1GawsH(52),
					pcsAD(53),pcsA2A3DB1(54),pcsA3DB1B2(55),pcsDB(56),pcsBE(57),
					pcsB2B3EF(58),pcsB3EFC3(59),pcsEFC3C4(60),pcsFC(61),
					pcsCG(62),pcsC4C5GawsH(63),pcsB3EFC2(64),
					pcsADB1(65),pcsA2A3DB1B2(66),pcsA3DB(67),pcsDBE(68),
					pcsBEF(69),pcsB2B3EFC3(70),pcsB3EFC3C4(71),pcsEFC(72),
					pcsFCG(73),pcsCGawsH(74),pcsB2B3EFC2(75),
					pcsADB1B2(76),pcsA2A3DB(77),pcsA3DBE(78),pcsDBEF(79),
					pcsBEFC3(80),pcsB2B3EFC3C4(81),pcsB3EFC(82),
					pcsEFCG(83),pcsFCGawsH(84),pcsADB(85),
					pcsA2A3DBE(86),pcsA3DBEF(87),pcsDBEFC3(88),
					pcsBEFC3C4(89),pcsB2B3EFC(90),pcsB3EFCG(91),
					pcsEFCGawsH(92),smrLow(93) , smrHigh( 94),
					awsA(95), awsAB(96), awsABC(97), awsABCD(98), awsABCDE(99), awsB(100),
					awsBC(101), awsBCD(102), awsBCDE(103), awsBCDEF(104), 
					awsC(105), awsCD(106), awsCDE(107),
					awsCDEF(108), awsD(109), awsDE(110), awsDEF(111), 
					awsE(112), awsEF(113), awsF(114), smrLowWide(115), cellularA2ABA1B1(116), 
					GSM1800Low(117), GSM1800Middle(118), GSM1800High(119), umtsLow(120), umtsMiddle(121), umtsHigh(122), cellularAB(133), apac800iDEN(134) " 
	DEFVAL 			{ "-1" }
	::=  {  fwuRmtDARTGeneralEntry  4  }

fwuRmtDARTOperatingMode	OBJECT-TYPE	
	SYNTAX			MODEType
	MAX-ACCESS		read-create
	STATUS			current
	DESCRIPTION		"Operating mode of remote DART card. The DART may be operating normally (1) or on standby (2). The mode may be undefined (-1)."
	DEFVAL 			{ 1 }
	::=  {  fwuRmtDARTGeneralEntry  5  }

fwuRmtDARTDiversityStatus	OBJECT-TYPE	
	SYNTAX			INTEGER  { nonDiversity(0), diversity(1) } 
	MAX-ACCESS		read-create
	STATUS			current
	DESCRIPTION		"Diversity Status of remote DART card."
	DEFVAL 			{ 0 }
	::=  {  fwuRmtDARTGeneralEntry  6 }

fwuRmtDARTForwardGain	OBJECT-TYPE	
	SYNTAX			GAINType
	MAX-ACCESS		read-create
	STATUS			current
	DESCRIPTION		"Primary Gain in forward path of remote DART card. The range is 0-31dB with increments in steps of 1dB."
	DEFVAL 			{ 0 }
	::=  {  fwuRmtDARTGeneralEntry  7  }

fwuRmtDARTReverseGain	OBJECT-TYPE	
	SYNTAX			GAINType
	MAX-ACCESS		read-only
	STATUS			current
	DESCRIPTION		"Primary Gain in reverse path of remote DART card."
	DEFVAL 			{ 0 }
	::=  {  fwuRmtDARTGeneralEntry  8  }

fwuRmtDARTForwardDelay	OBJECT-TYPE	
	SYNTAX			DELAYType
	MAX-ACCESS		read-create
	STATUS			current
	DESCRIPTION		"Forward delay in micro seconds on the remote DART. If the delay setting is outside the valid range of delay values then ranging fault will be raised if the Remote Dart is Linked."
	::=  {  fwuRmtDARTGeneralEntry  9  }

fwuRmtDARTReverseDelay	OBJECT-TYPE	
	SYNTAX			DELAYType
	MAX-ACCESS		read-create
	STATUS			current
	DESCRIPTION		"Reverse delay in micro seconds on the remote DART. If the delay setting is outside the valid range of delay values then ranging fault will be raised if the Remote Dart is Linked."
	::=  {  fwuRmtDARTGeneralEntry  10  }

fwuRmtDARTTempMeas	OBJECT-TYPE	
	SYNTAX			DisplayString 
	MAX-ACCESS		read-only
	STATUS			current
	DESCRIPTION		"Temperature of Remote DART in degree Celsius."
	::=  {  fwuRmtDARTGeneralEntry  11  }
		
fwuRmtDARTFPGAStatus	OBJECT-TYPE	
	SYNTAX			INTEGER { serfFpgaCanTalkToDARTFpga(0), serfFpgaCannotTalkToDARTFpga(1) }
	MAX-ACCESS		read-only
	STATUS			current
	DESCRIPTION		"Remote DART FPGA Status. It indicates if the SERF FPGA can talk(0) or not talk(1)to DART FPGA ."
	::=  {  fwuRmtDARTGeneralEntry  12  }

fwuRmtDARTFPGAProgramVer	OBJECT-TYPE	
	SYNTAX			DisplayString
	MAX-ACCESS		read-only
	STATUS			current
	DESCRIPTION		"FPGA version on the remote DART."
	::=  {  fwuRmtDARTGeneralEntry  13  }

fwuRmtDARTRIADCPartNumber	OBJECT-TYPE	
	SYNTAX			DisplayString
	MAX-ACCESS		read-only
	STATUS			current
	DESCRIPTION		"Remote DART Inventory Data - TE Part Number."
	::=  {  fwuRmtDARTGeneralEntry  14  }

fwuRmtDARTRISerialNumber	OBJECT-TYPE	
	SYNTAX			DisplayString
	MAX-ACCESS		read-only
	STATUS			current
	DESCRIPTION		"Remote DART Inventory Data - Serial Number."
	::=  {  fwuRmtDARTGeneralEntry  15  }

fwuRmtDARTRIDateCode	OBJECT-TYPE	
	SYNTAX			DisplayString
	MAX-ACCESS		read-only
	STATUS			current
	DESCRIPTION		"Remote DART Inventory Data - DateCode."
	::=  {  fwuRmtDARTGeneralEntry  16  }

fwuRmtDARTRIHWVer	OBJECT-TYPE	
	SYNTAX			DisplayString
	MAX-ACCESS		read-only
	STATUS			current
	DESCRIPTION		"Remote DART Inventory Data - HW version."
	::=  {  fwuRmtDARTGeneralEntry  17  }
        
fwuRmtDARTGeneralTableRowStatus OBJECT-TYPE
	SYNTAX	     	RowStatus
	MAX-ACCESS   	read-create
	STATUS       	current
	DESCRIPTION 	"The status of this conceptual row."
	::= { fwuRmtDARTGeneralEntry    18 }

fwuRmtDARTActualForwardDelay	OBJECT-TYPE	
	SYNTAX			Integer32
	MAX-ACCESS		read-only
	STATUS			current
	DESCRIPTION		"This is the forward delay on Remote DART."
	::=  {  fwuRmtDARTGeneralEntry  19  }

fwuRmtDARTForwardLowerboundDelay	OBJECT-TYPE	
	SYNTAX			Integer32
	MAX-ACCESS		read-only
	STATUS			current
	DESCRIPTION		"This is the lower bound of the Forward Delay values."
	::=  {  fwuRmtDARTGeneralEntry  20  }

fwuRmtDARTForwardUpperboundDelay	OBJECT-TYPE	
	SYNTAX			Integer32
	MAX-ACCESS		read-only
	STATUS			current
	DESCRIPTION		"This is the upper bound of the Forward Delay values."
	::=  {  fwuRmtDARTGeneralEntry  21 }

fwuRmtDARTActualReverseDelay	OBJECT-TYPE	
	SYNTAX			Integer32
	MAX-ACCESS		read-only
	STATUS			current
	DESCRIPTION		"This  is the Reverse delay on Remote DART."
	::=  {  fwuRmtDARTGeneralEntry  22 }

fwuRmtDARTReverseLowerboundDelay	OBJECT-TYPE	
	SYNTAX			Integer32
	MAX-ACCESS		read-only
	STATUS			current
	DESCRIPTION		"This is the lower bound of the Reverse delay values."
	::=  {  fwuRmtDARTGeneralEntry  23 }

fwuRmtDARTReverseUpperboundDelay	OBJECT-TYPE	
	SYNTAX			Integer32
	MAX-ACCESS		read-only
	STATUS			current
	DESCRIPTION		"This is the upper bound of the Reverse delay values."
	::=  {  fwuRmtDARTGeneralEntry  24 }

fwuRmtDARTPeakInputPwrLvl1	OBJECT-TYPE
	SYNTAX	 		DisplayString
	MAX-ACCESS   	read-only
	STATUS       	current
	DESCRIPTION 	"Peak Input Power Level 1 to a Remote DART."
	::= { fwuRmtDARTGeneralEntry 25 }

fwuRmtDARTPeakInputPwrLvl2	OBJECT-TYPE
	SYNTAX	 		DisplayString
	MAX-ACCESS   	read-only
	STATUS       	current
	DESCRIPTION 	"Peak Input Power Level 2 to the Remote DART."
	::= { fwuRmtDARTGeneralEntry 26 }

fwuRmtDARTPeakAvgInputPwrLvl1	OBJECT-TYPE
	SYNTAX	 		DisplayString
	MAX-ACCESS   	read-only
	STATUS       	current
	DESCRIPTION 	"Peak Average Input Power Level 1 to the Remote DART."
	::= { fwuRmtDARTGeneralEntry 27 }

fwuRmtDARTPeakAvgInputPwrLvl2	OBJECT-TYPE
	SYNTAX	 		DisplayString
	MAX-ACCESS   	read-only
	STATUS       	current
	DESCRIPTION 	"Peak Average Input Power Level 2 to the Remote DART."
	::= { fwuRmtDARTGeneralEntry 28 }

fwuRmtDARTMinAvgInputPwrLvl1	OBJECT-TYPE
	SYNTAX	 		DisplayString
	MAX-ACCESS   	read-only
	STATUS       	current
	DESCRIPTION 	"Minimum Average Input Power Level 1 to the Remote DART."
	::= { fwuRmtDARTGeneralEntry 29 }

fwuRmtDARTMinAvgInputPwrLvl2	OBJECT-TYPE
	SYNTAX	 		DisplayString
	MAX-ACCESS   	read-only
	STATUS       	current
	DESCRIPTION 	"Minimum Average Input Power Level 2 to the Remote DART."
	::= { fwuRmtDARTGeneralEntry 30 }

fwuRmtDARTInputPowerMode	OBJECT-TYPE
	SYNTAX	 		INTEGER  { snapShot(0), maxHold(1) }
	MAX-ACCESS   	read-write
	STATUS       	current
	DESCRIPTION 	"Remote DART Input Power Level Mode. Two modes are supported Snapshot(0) and Max Hold(1)."
	DEFVAL 			{ 0 }
	::= { fwuRmtDARTGeneralEntry 31 }

fwuRmtDARTPwrLevelMaxHoldReset	OBJECT-TYPE
	SYNTAX	 		INTEGER { notApplicable(-1), normal(0) , reset(1) }
	MAX-ACCESS   	read-write
	STATUS       	current
	DESCRIPTION 	"Provision to reset the Max Hold reading. Used when the input power mode is Max hold. Reset by changing from normal (0) to reset (1). Status will revert to normal once the reset is done. In snapshot mode (see fwuRmtDARTInputPowerMode) this object is not applicable (-1)."
	DEFVAL 			{ -1 }
	::= { fwuRmtDARTGeneralEntry 32 }

fwuRmtDARTLastMaxHoldResetTime	OBJECT-TYPE
	SYNTAX	 		OCTET STRING (SIZE (0..40))
	MAX-ACCESS   	read-only
	STATUS       	current
	DESCRIPTION 	"Date and Time of the last maxHold reset on the remote DART."
	::= { fwuRmtDARTGeneralEntry 33 }

fwuRmtDARTReverseGainMode	OBJECT-TYPE
	SYNTAX	 		INTEGER { normal(0) , high(1) }
	MAX-ACCESS   	read-write
	STATUS       	current
	DESCRIPTION 	"The gain modes on the Reverse Path. Two modes are supported, Normal(0) and High(1). It is applicable to all RF modules but not to IF DARTs."
	DEFVAL 			{ 0 }
	::= { fwuRmtDARTGeneralEntry 34 }

fwuRmtDARTTxRIADCPartNumber	OBJECT-TYPE
	SYNTAX	 		DisplayString
	MAX-ACCESS   	read-only
	STATUS       	current
	DESCRIPTION 	"Remote Inventory Data - TE Part Number [Tx Board]. 
                     Field will have value only if Tx Board is present."
	::= { fwuRmtDARTGeneralEntry 35 }
	
fwuRmtDARTTxRISerialNumber	OBJECT-TYPE
	SYNTAX	 		DisplayString
	MAX-ACCESS   	read-only
	STATUS       	current
	DESCRIPTION 	"Remote Inventory Data - Serial Number [Tx Board].
                     Field will have value only if Tx Board is present."
	::= { fwuRmtDARTGeneralEntry 36 }
	
fwuRmtDARTTxRIDateCode	OBJECT-TYPE
	SYNTAX	 		DisplayString
	MAX-ACCESS   	read-only
	STATUS       	current
	DESCRIPTION 	"Remote Inventory Data - DateCode [Tx Board].
                     Field will have value only if Tx Board is present."
	::= { fwuRmtDARTGeneralEntry 37 }
	
fwuRmtDARTTxRIHWVer		OBJECT-TYPE
	SYNTAX	 		DisplayString
	MAX-ACCESS   	read-only
	STATUS       	current
	DESCRIPTION 	"Remote Inventory Data - HW version [Tx Board].
                     Field will have value only if Tx Board is present."
	::= { fwuRmtDARTGeneralEntry 38 }
	
fwuRmtDARTLinkedStatus          OBJECT-TYPE
        SYNTAX                  INTEGER { notLinked(0) , linked(1) }
        MAX-ACCESS      read-only
        STATUS          current
        DESCRIPTION     "Indicates if the DART is linked (1) or not (0)."
        ::= { fwuRmtDARTGeneralEntry 39 }

fwuRmtDARTAvailable             OBJECT-TYPE
        SYNTAX                  INTEGER { notAvailable(0) , available(1) }
        MAX-ACCESS      read-only
        STATUS          current
        DESCRIPTION     "Indicates if the DART is available for use (1) or not (0)."
        ::= { fwuRmtDARTGeneralEntry 40 }

fwuRmtDARTUsedSFP               OBJECT-TYPE
        SYNTAX                  INTEGER (1 .. 8)
        MAX-ACCESS      read-only
        STATUS          current
        DESCRIPTION     "Indicates the SFP (number) used by a DART to link. There are eight possible SFP numbers. Therefore, the valid values are 1 to 8."
        ::= { fwuRmtDARTGeneralEntry 41 }

fwuRmtDARTTraps		OBJECT IDENTIFIER		::=  {  fwuRmtDARTObjects  2  }

fwuRmtDARTDwnCon1SynLockFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS		current
	DESCRIPTION		"Lock state of the first down converter synthesizer."
	::=  {  fwuRmtDARTTraps  2  }

fwuRmtDARTDwnCon2SynLockFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS		current
	DESCRIPTION		"DART downconverter 2 synthesizer unlocked."
	::=  {  fwuRmtDARTTraps  3  }

fwuRmtDARTUpConSynLockFault	NOTIFICATION-TYPE
	OBJECTS	{ 	fwuTrapSequenceNumber, 
				fwuTrapTimeStamp, 
				fwuModuleNumber,
				fwuModuleType,
                               fwuAlarmedModuleName,
				fwuHstNumber, 
				fwuHstName,  
				fwuRmtNumber, 
				fwuRmtName, 
				fwuTrapCode,
				fwuNotificationStatus 	}
	STATUS		current
	DESCRIPTION		"DART downconverter 2 synthesizer unlocked."
	::=  {  fwuRmtDARTTraps  4  }

fwuRmtDARTDCSupplyFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS		current
	DESCRIPTION		"DART card DC supply voltages outside specification."
	::=  {  fwuRmtDARTTraps  5  }

fwuRmtDARTFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS		current
	DESCRIPTION		"Summary of DART Downconverter 1 Synthesizer Unlocked, Downconverter 2 Synthesizer Unlocked, Upconverter Synthesizer Unlocked, DC Supply Fault alarms, and DART FPGA status."
	::=  {  fwuRmtDARTTraps  6  }

fwuRmtDARTHardwareMismatchFault	NOTIFICATION-TYPE
	OBJECTS	{ 	fwuTrapSequenceNumber,
				fwuTrapTimeStamp, 
				fwuModuleNumber,
				fwuModuleType,
                               fwuAlarmedModuleName,
				fwuHstNumber,
				fwuHstName,
				fwuRmtNumber, 
				fwuRmtName, 
				fwuTrapCode,
				fwuNotificationStatus 	}
	STATUS		current
	DESCRIPTION		"Remote DART does not support the selected passband.  Fault occurs when a Remote DART is replaced with another DART of the incorrect type."
	::=  {  fwuRmtDARTTraps  7  }

fwuRmtRangingFault	NOTIFICATION-TYPE
	OBJECTS	{ 	fwuTrapSequenceNumber, 
				fwuTrapTimeStamp, 
				fwuModuleNumber,
				fwuModuleType,  
				fwuAlarmedModuleName,
				fwuHstNumber, 
				fwuHstName,  
				fwuRmtNumber, 
				fwuRmtName, 
				fwuTrapCode,
				fwuNotificationStatus	}
	STATUS		current
	DESCRIPTION		"DRU/PRU/URU delay settings outside the valid range."
	::=  {  fwuRmtDARTTraps  8  }

fwuRmtDARTOverTempFault	NOTIFICATION-TYPE
	OBJECTS	{ 	fwuTrapSequenceNumber, 
				fwuTrapTimeStamp, 
				fwuModuleNumber,
				fwuModuleType,  
				fwuAlarmedModuleName,
				fwuHstNumber, 
				fwuHstName,  
				fwuRmtNumber, 
				fwuRmtName, 
				fwuTrapCode,
				fwuNotificationStatus	}
	STATUS		current
	DESCRIPTION		"Remote DART temperature above operating limit."
	::=  {  fwuRmtDARTTraps  9  }

fwuRmtDARTLowTempFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS		current
	DESCRIPTION		"Remote DART temperature below operating limit."
	::=  {  fwuRmtDARTTraps  10  }
	
fwuRmtDARTUplinkInactivityFault NOTIFICATION-TYPE
	OBJECTS {   fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS		current
	DESCRIPTION		"No uplink activity is detected for one hour."
	::=  {  fwuRmtDARTTraps  11  }
 	
fwuRmtDARTCommsFault NOTIFICATION-TYPE
	OBJECTS {   fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS		current
	DESCRIPTION		"The Remote DART communication path is missing or incorrect."
	::=  {  fwuRmtDARTTraps  12  }

-- In Rel 6.0 this attribute is removed, as GPS is never supported. 
-- While modification take care of this OID.
--fwuRmtGPSObjects		OBJECT IDENTIFIER		::=  {  fwuRemoteUnitObjects  7  }
--fwuRmtGPSInfo			OBJECT IDENTIFIER		::=  {  fwuRmtGPSObjects  1  }
--fwuRmtGPSTraps		OBJECT IDENTIFIER		::=  {  fwuRmtGPSObjects  2  }

fwuRmtLPAObjects		OBJECT IDENTIFIER		::=  {  fwuRemoteUnitObjects  8  }
fwuRmtLPAInfo			OBJECT IDENTIFIER		::=  {  fwuRmtLPAObjects  1  }

fwuRmtLPAInfoTable	OBJECT-TYPE
	SYNTAX			SEQUENCE  OF  FwuRmtLPAInfoEntry
	MAX-ACCESS		not-accessible
	STATUS			current
	DESCRIPTION		"This table maintains Information of remote LPA objects."
	::=  { fwuRmtLPAInfo  1 }

fwuRmtLPAInfoEntry	OBJECT-TYPE
	SYNTAX			FwuRmtLPAInfoEntry
	MAX-ACCESS		not-accessible
	STATUS			current
	DESCRIPTION		"Each entry in this table refers to LPA objects."
	INDEX			{  fwuRmtNumber, fwuRmtLPANumber  }
	::=  { fwuRmtLPAInfoTable 1 }

FwuRmtLPAInfoEntry  ::=  SEQUENCE {
	fwuRmtLPANumber  Integer32,
	fwuRmtLPAReset  INTEGER,
	fwuRmtLPAOpState  INTEGER,
	fwuRmtLPAPartNum DisplayString,
	fwuRmtLPASerialNum DisplayString,
	fwuRmtLPAHWVer DisplayString,
	fwuRmtLPASWVer DisplayString,
	fwuRmtLPADescr DisplayString,
	fwuRmtLPAControl INTEGER,
	fwuRmtLPAMaxOpPwr DisplayString,
	fwuRmtLPABandType DuplexerType }

fwuRmtLPANumber	OBJECT-TYPE	
	SYNTAX			Integer32  (1 .. 4) 
	MAX-ACCESS		read-only
	STATUS			current
	DESCRIPTION		"A unique identifier for an LPA."
	::=  {  fwuRmtLPAInfoEntry  1  }

fwuRmtLPAReset	OBJECT-TYPE	
	SYNTAX			INTEGER  { normal(0) , reset(1) } 
	MAX-ACCESS		read-write
	STATUS			current
	DESCRIPTION		"Provision to reset the LPA. Change from normal(0) to reset(1) to perform a reset of the LPA. Resetting the LPA when it is offline will place in an operating state."
	DEFVAL 			{ 0 }
	::=  {  fwuRmtLPAInfoEntry  2  }

fwuRmtLPAOpState	OBJECT-TYPE	
	SYNTAX			INTEGER  { operating(0) , offline(1) } 
	MAX-ACCESS		read-only
	STATUS			current
	DESCRIPTION		"Identifies the LPA Operating mode. The modes are operating (0) and offline (1). The operating state is controlled by fwuRmtLPAControl. Also, see fwuRmtLPAReset."
	DEFVAL 			{ 1 }
	::=  {  fwuRmtLPAInfoEntry  3  }

fwuRmtLPAPartNum	OBJECT-TYPE	
	SYNTAX			DisplayString
	MAX-ACCESS		read-only
	STATUS			current
	DESCRIPTION		"Remote LPA Part Number."
	::=  {  fwuRmtLPAInfoEntry  4  }

fwuRmtLPASerialNum	OBJECT-TYPE	
	SYNTAX			DisplayString
	MAX-ACCESS		read-only
	STATUS			current
	DESCRIPTION		"Remote LPA Serial Number."
	::=  {  fwuRmtLPAInfoEntry  5  }

fwuRmtLPAHWVer	OBJECT-TYPE	
	SYNTAX			DisplayString
	MAX-ACCESS		read-only
	STATUS			current
	DESCRIPTION		"Remote LPA Hardware version."
	::=  {  fwuRmtLPAInfoEntry  6  }
	
fwuRmtLPASWVer	OBJECT-TYPE	
	SYNTAX			DisplayString
	MAX-ACCESS		read-only
	STATUS			current
	DESCRIPTION		"Remote LPA Software version."
	::=  {  fwuRmtLPAInfoEntry  7  }

fwuRmtLPADescr 	OBJECT-TYPE	
	SYNTAX			DisplayString
	MAX-ACCESS		read-only
	STATUS			current
	DESCRIPTION		"Remote LPA Description."
	::=  {  fwuRmtLPAInfoEntry  8  }

fwuRmtLPAControl 	OBJECT-TYPE	
	SYNTAX			INTEGER  { normal(0), standby(1) } 
	MAX-ACCESS		read-write	
	STATUS			current
	DESCRIPTION		"Provision to control the operating mode of remote LPA. When the control is set to normal (0), the operating mode is operating. When the control is set to offline (1), the operating mode is standby. fwuRmtLPAOpState will reflect the change in state/mode when the values are changed for this entity."
	DEFVAL 			{ 1 }
	::=  {  fwuRmtLPAInfoEntry  9  }

fwuRmtLPAMaxOpPwr 	OBJECT-TYPE	
	SYNTAX			DisplayString
	MAX-ACCESS		read-only
	STATUS			current
	DESCRIPTION		"Maximum Output power for the LPA. This object is applicable for HDMs also."
	::=  {  fwuRmtLPAInfoEntry  10  }
fwuRmtLPABandType	OBJECT-TYPE	
	SYNTAX			DuplexerType
	MAX-ACCESS		read-only
	STATUS			current
	DESCRIPTION		" LPA hardware type. Valid LPA Types are cellularA(1), cellularB(2), smrLow(3), smrHigh(4),
					pcs(5), aws(6), smrLowWide(7), fullCellular(8),	gsm1800(9), umts(10), egsm900(11), lowerABC(12), 
					upperC700(13), apac800iDEN(14), prismSmr800and900(15), prismSmr900and800(16), prismSmr800(17),
					cellularApac(18), apacEgsm900(19), pGsmEgsm900(20) "					
	::=  {  fwuRmtLPAInfoEntry  11  }


fwuRmtLPATraps		OBJECT IDENTIFIER		::=  {  fwuRmtLPAObjects  2  }

fwuRmtLPADisableFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS		current
	DESCRIPTION		"PRU/URU Linear Power Amplifier (LPA) disabled due to an internally detected problem.  (VSWR, DC, Loop Fault, Low Power, or Temperature High alarm)."
	::=  {  fwuRmtLPATraps  2  }

fwuRmtLPAOverPowerFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS		current
	DESCRIPTION		"PRU/URU Linear Power Amplifier (LPA) output power level above operating limit."
	::=  {  fwuRmtLPATraps  3  }

fwuRmtLPAHighTempFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS		current
	DESCRIPTION		"LPA High Temperature Fault."
	::=  {  fwuRmtLPATraps  4  }

fwuRmtLPAVswrFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS		current
	DESCRIPTION		"PRU/URU Linear Power Amplifier (LPA) VSWR fault."
	::=  {  fwuRmtLPATraps  5  }

fwuRmtLPADcFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS		current
	DESCRIPTION		"PRU/URU Linear Power Amplifier (LPA) DC fault."
	::=  {  fwuRmtLPATraps  6  }

fwuRmtLPALoopFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS			current
	DESCRIPTION		"PRU/URU Linear Power Amplifier (LPA) Loop fault."
	::=  {  fwuRmtLPATraps  7  }

fwuRmtLPALowPowerFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS			current
	DESCRIPTION		"Internal low power fault state of linear power amplifier (the gain of one or more 
					internal amplifiers does not meet specification)."
	::=  {  fwuRmtLPATraps  8  }

fwuRmtLPADetectFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS			current
	DESCRIPTION		"Linear Power Amplifier (LPA) detection fault.  LPA missing from remote."
	::=  {  fwuRmtLPATraps  9  }

fwuRmtPaOverCurrentFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus	}
	STATUS			current
	DESCRIPTION		"PA reported fault."
	::=  {  fwuRmtLPATraps  10  }
	
fwuRmtPwrDetectorBoardObjects		OBJECT IDENTIFIER		::=  {  fwuRemoteUnitObjects  9  }
fwuRmtPwrDetectorBoardInfo			OBJECT IDENTIFIER		::=  {  fwuRmtPwrDetectorBoardObjects  1  }

fwuRmtPwrDetectorBoardInfoTable	OBJECT-TYPE
	SYNTAX			SEQUENCE  OF  FwuRmtPwrDetectorBoardInfoEntry
	MAX-ACCESS		not-accessible
	STATUS			current
	DESCRIPTION		"This table maintains Information of remote power detector board objects."
	::=  { fwuRmtPwrDetectorBoardInfo  1 }

fwuRmtPwrDetectorBoardInfoEntry	OBJECT-TYPE
	SYNTAX			FwuRmtPwrDetectorBoardInfoEntry
	MAX-ACCESS		not-accessible
	STATUS			current
	DESCRIPTION		"Each entry in this table refers to power detector board objects."
	INDEX			{  fwuRmtNumber,fwuRmtPowerDetectorNumber  }
	::=  { fwuRmtPwrDetectorBoardInfoTable 1 }

FwuRmtPwrDetectorBoardInfoEntry  ::=  SEQUENCE {
	fwuRmtPowerDetectorNumber  Integer32,
	fwuRmtSystemVswrMeas  DisplayString,
	fwuRmtRFPowerOutputMeas  DisplayString,
	fwuRmtPwrDetectorBoardRIADCPartNum  DisplayString,
	fwuRmtPwrDetectorBoardRISerialNum  DisplayString,
	fwuRmtPwrDetectorBoardRIDateCode  DisplayString,
	fwuRmtPwrDetectorBoardRIHWVer  DisplayString,
	fwuRmtPwrDetectorNoRfPowerThershold DisplayString,
	fwuRmtSystemVSWRThreshold DisplayString }

fwuRmtPowerDetectorNumber	OBJECT-TYPE	
	SYNTAX			Integer32 (1.. 4)
	MAX-ACCESS		read-only
	STATUS			current
	DESCRIPTION		"A unique identifier for each power detector."
	::=  {  fwuRmtPwrDetectorBoardInfoEntry  1  }

fwuRmtSystemVswrMeas	OBJECT-TYPE	
	SYNTAX			DisplayString
	MAX-ACCESS		read-only
	STATUS			current
	DESCRIPTION		"VSWR (Voltage Standing Wave Ratio) measured in the system."
	::=  {  fwuRmtPwrDetectorBoardInfoEntry  2  }

fwuRmtRFPowerOutputMeas	OBJECT-TYPE	
	SYNTAX			DisplayString
	MAX-ACCESS		read-only
	STATUS			current
	DESCRIPTION		"The value of Remote RF Power Output, in dBm."
	::=  {  fwuRmtPwrDetectorBoardInfoEntry  3  }

fwuRmtPwrDetectorBoardRIADCPartNum	OBJECT-TYPE	
	SYNTAX			DisplayString
	MAX-ACCESS		read-only
	STATUS			current
	DESCRIPTION		"Power Detector Inventory - TE Part Number."
	::=  {  fwuRmtPwrDetectorBoardInfoEntry  4  }

fwuRmtPwrDetectorBoardRISerialNum	OBJECT-TYPE	
	SYNTAX			DisplayString
	MAX-ACCESS		read-only
	STATUS			current
	DESCRIPTION		"Power Detector Inventory - Serial Number."
	::=  {  fwuRmtPwrDetectorBoardInfoEntry  5  }

fwuRmtPwrDetectorBoardRIDateCode	OBJECT-TYPE	
	SYNTAX			DisplayString
	MAX-ACCESS		read-only
	STATUS			current
	DESCRIPTION		"Power Detector Inventory - Date Code."
	::=  {  fwuRmtPwrDetectorBoardInfoEntry  6  }

fwuRmtPwrDetectorBoardRIHWVer	OBJECT-TYPE	
	SYNTAX			DisplayString
	MAX-ACCESS		read-only
	STATUS			current
	DESCRIPTION		"Power Detector Inventory - HW version."
	::=  {  fwuRmtPwrDetectorBoardInfoEntry  7  }

fwuRmtPwrDetectorNoRfPowerThershold OBJECT-TYPE	
	SYNTAX			DisplayString
	MAX-ACCESS		read-write
	STATUS			current
	DESCRIPTION		"Threshold value for RF No Power. The minimum threshold value is 0dBm and maximum threshold value is 100dBm."
	::=  {  fwuRmtPwrDetectorBoardInfoEntry  8  }

fwuRmtSystemVSWRThreshold OBJECT-TYPE	
	SYNTAX			DisplayString
	MAX-ACCESS		read-write
	STATUS			current
	DESCRIPTION		"User set VSWR threshold value. User is to provide the VSWR value in the form x.y:1. If the value is provided as x:1 then it will be represented as x.0:1. The minimum threshold value is 2.0 and maximum threshold value is 9.0."
	::=  {  fwuRmtPwrDetectorBoardInfoEntry  9  }


fwuRmtPwrDetectorBoardTraps			OBJECT IDENTIFIER		::=  {  fwuRmtPwrDetectorBoardObjects  2  }

fwuRmtSystemVswrFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS			current
	DESCRIPTION		"PRU/URU VSWR measurement above specification."
	::=  {  fwuRmtPwrDetectorBoardTraps  2  }

fwuRmtRFPowerFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS		current
	DESCRIPTION		"PRU/URU RF Output Power below minimum threshold."
	::=  {  fwuRmtPwrDetectorBoardTraps  3  }

fwuRmtLNAObjects			OBJECT IDENTIFIER		::=  {  fwuRemoteUnitObjects  10  }
fwuRmtLNAInfo				OBJECT IDENTIFIER		::=  {  fwuRmtLNAObjects  1  }

fwuRmtLNAInfoTable	OBJECT-TYPE
	SYNTAX			SEQUENCE  OF  FwuRmtLNAInfoEntry
	MAX-ACCESS		not-accessible
	STATUS			current
	DESCRIPTION		"This table maintains Information of remote LNA objects."
	::=  { fwuRmtLNAInfo  1 }

fwuRmtLNAInfoEntry	OBJECT-TYPE
	SYNTAX			FwuRmtLNAInfoEntry
	MAX-ACCESS		not-accessible
	STATUS			current
	DESCRIPTION		"Each entry in this table refers to LNA information."
	INDEX			{  fwuRmtNumber, fwuRmtLNANumber  }
	::=  { fwuRmtLNAInfoTable 1 }

FwuRmtLNAInfoEntry  ::=  SEQUENCE {
	fwuRmtLNANumber  Integer32,
	fwuRmtLNAType  LNAType,
	fwuRmtLNARIADCPartNumber  DisplayString,
	fwuRmtLNARISerialNumber  DisplayString,
	fwuRmtLNARIDateCode  DisplayString,
	fwuRmtLNARIHWVer  DisplayString,
	fwuRmtDuplexerType DuplexerType	}

fwuRmtLNANumber	OBJECT-TYPE	
	SYNTAX			Integer32  (1 .. 8) 
	MAX-ACCESS		read-only
	STATUS			current
	DESCRIPTION		"A unique identifier for LNA Objects."
	::=  {  fwuRmtLNAInfoEntry  1  }
	
fwuRmtLNAType	OBJECT-TYPE	
	SYNTAX			LNAType
	MAX-ACCESS		read-only
	STATUS			current
	DESCRIPTION		"Remote LNA card type. Valid LNA types are Cellular A(1), Cellular B(2), SMR Low(3), 
					SMR High(4), PCS(5), AWS(6), SMR Low Wide(7), Full Cellular(8), GSM1800(9), UMTS(10), EGSM900(11), 
					Lower ABC 700(12), Upper C 700(13), APAC 800 iDEN(14), Prism SMR 800 and 900(15), 
					Prism SMR 900 and 800(16), Prism SMR 800(17)."
	::=  {  fwuRmtLNAInfoEntry  2  }

fwuRmtLNARIADCPartNumber	OBJECT-TYPE	
	SYNTAX			DisplayString
	MAX-ACCESS		read-only
	STATUS			current
	DESCRIPTION		"LNA Inventory Data - TE Part Number."
	::=  {  fwuRmtLNAInfoEntry  3  }

fwuRmtLNARISerialNumber	OBJECT-TYPE	
	SYNTAX			DisplayString
	MAX-ACCESS		read-only
	STATUS			current
	DESCRIPTION		"LNA Inventory Data - Serial Number."
	::=  {  fwuRmtLNAInfoEntry  4  }

fwuRmtLNARIDateCode	OBJECT-TYPE	
	SYNTAX			DisplayString
	MAX-ACCESS		read-only
	STATUS			current
	DESCRIPTION		"LNA Inventory Data - Date Code."
	::=  {  fwuRmtLNAInfoEntry  5  }

fwuRmtLNARIHWVer	OBJECT-TYPE	
	SYNTAX			DisplayString
	MAX-ACCESS		read-only
	STATUS			current
	DESCRIPTION		"LNA Inventory Data - HW version."
	::=  {  fwuRmtLNAInfoEntry  6  }

fwuRmtDuplexerType	OBJECT-TYPE	
	SYNTAX			DuplexerType
	MAX-ACCESS		read-only
	STATUS			current
	DESCRIPTION		" Duplexer hardware type. Valid Duplexer Types are cellularA(1), cellularB(2), smrLow(3), smrHigh(4),
					pcs(5), aws(6), smrLowWide(7), fullCellular(8),	gsm1800(9), umts(10), egsm900(11), lowerABC(12), 
					upperC700(13), apac800iDEN(14), prismSmr800and900(15), prismSmr900and800(16), prismSmr800(17),
					cellularApac(18), apacEgsm900(19), pGsmEgsm900(20) "					
	::=  {  fwuRmtLNAInfoEntry  7  }

fwuRmtLNATraps				OBJECT IDENTIFIER		::=  {  fwuRmtLNAObjects  2  }

fwuRmtLNAPowerFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS			current
	DESCRIPTION		"PRU/URU Low Noise Amplifier (LNA) Power fault."
	::=  {  fwuRmtLNATraps  2  }

fwuRmtDuplexerFreqMismatchFault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS		current
	DESCRIPTION	"Configured frequency range not supported by Duplexer."
	::=  {  fwuRmtLNATraps  3  }

fwuRmtRDIObjects			OBJECT IDENTIFIER		::=  {  fwuRemoteUnitObjects  11  }
fwuRmtRDIInfo				OBJECT IDENTIFIER		::=  {  fwuRmtRDIObjects  1  }

fwuRmtRDIInfoTable	OBJECT-TYPE
	SYNTAX			SEQUENCE  OF  FwuRmtRDIInfoEntry
	MAX-ACCESS		not-accessible
	STATUS			current
	DESCRIPTION		"This table maintains Information of remote RDI objects."
	::=  { fwuRmtRDIInfo  1 }

fwuRmtRDIInfoEntry	OBJECT-TYPE
	SYNTAX			FwuRmtRDIInfoEntry
	MAX-ACCESS		not-accessible
	STATUS			current
	DESCRIPTION		"Each entry in this table refers to RDI information."
	INDEX			{  fwuRmtNumber, fwuRmtRDINumber  }
	::=  { fwuRmtRDIInfoTable 1 }

FwuRmtRDIInfoEntry  ::=  SEQUENCE {
	fwuRmtRDINumber  Integer32,
	fwuRmtRDIRIADCPartNumber  DisplayString,
	fwuRmtRDIRISerialNumber  DisplayString,
	fwuRmtRDIRIDateCode  DisplayString,
	fwuRmtRDIRIHWVer  DisplayString,
	fwuRmtRDIRIHWType INTEGER
		}

fwuRmtRDINumber	OBJECT-TYPE	
	SYNTAX			Integer32  (1 .. 4) 
	MAX-ACCESS		read-only
	STATUS			current
	DESCRIPTION		"A unique identifier for each RDI."
	::=  {  fwuRmtRDIInfoEntry  1  }

fwuRmtRDIRIADCPartNumber	OBJECT-TYPE	
	SYNTAX			DisplayString
	MAX-ACCESS		read-only
	STATUS			current
	DESCRIPTION		"RDI Inventory Data - TE Part Number."
	::=  {  fwuRmtRDIInfoEntry  2  }

fwuRmtRDIRISerialNumber	OBJECT-TYPE	
	SYNTAX			DisplayString
	MAX-ACCESS		read-only
	STATUS			current
	DESCRIPTION		"RDI Inventory Data - Serial Number."
	::=  {  fwuRmtRDIInfoEntry  3  }

fwuRmtRDIRIDateCode	OBJECT-TYPE	
	SYNTAX			DisplayString
	MAX-ACCESS		read-only
	STATUS			current
	DESCRIPTION		"RDI Inventory Data - Date Code."
	::=  {  fwuRmtRDIInfoEntry  4  }

fwuRmtRDIRIHWVer	OBJECT-TYPE	
	SYNTAX			DisplayString
	MAX-ACCESS		read-only
	STATUS			current
	DESCRIPTION		"RDI Inventory Data - HW version."
	::=  {  fwuRmtRDIInfoEntry  5  }

fwuRmtRDIRIHWType	OBJECT-TYPE	
	SYNTAX			INTEGER { unknown(0), rdi(1), alpaca(2) }
	MAX-ACCESS		read-only
	STATUS			current
	DESCRIPTION		"Identifies if RDI(1) or ALPACA(2) board. It may be unknown(0)."
	DEFVAL 			{ 0 }	
	::=  {  fwuRmtRDIInfoEntry  6  }	

fwuRmtRDITraps				OBJECT IDENTIFIER		::=  {  fwuRmtRDIObjects  2  }

fwuRmtACPowerSupplyMon1Fault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS			current
	DESCRIPTION		"AC Power monitor 1 Fault."
	::=  {  fwuRmtRDITraps  1  }
		
fwuRmtACPowerSupplyMon2Fault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS			current
	DESCRIPTION		"AC Power monitor 2 Fault."
	::=  {  fwuRmtRDITraps  2  }
		
fwuRmtACPowerSupplyMon3Fault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS			current
	DESCRIPTION		"AC Power monitor 3 Fault."
	::=  {  fwuRmtRDITraps  3  }


fwuRmtRSIObjects			OBJECT IDENTIFIER		::=  {  fwuRemoteUnitObjects  12  }
fwuRmtRSIInfo				OBJECT IDENTIFIER		::=  {  fwuRmtRSIObjects  1  }

fwuRmtRSIInfoTable	OBJECT-TYPE
	SYNTAX			SEQUENCE  OF  FwuRmtRSIInfoEntry
	MAX-ACCESS		not-accessible
	STATUS			current
	DESCRIPTION		"This table maintains Information of Remote RSI objects."
	::=  { fwuRmtRSIInfo  1 }

fwuRmtRSIInfoEntry	OBJECT-TYPE
	SYNTAX			FwuRmtRSIInfoEntry
	MAX-ACCESS		not-accessible
	STATUS			current
	DESCRIPTION		"Each entry in this table refers to RSI information."
	INDEX			{  fwuRmtNumber }
	::=  { fwuRmtRSIInfoTable 1 }

FwuRmtRSIInfoEntry  ::=  SEQUENCE {
	fwuRmtRSIRIADCPartNumber  DisplayString,
	fwuRmtRSIRISerialNumber  DisplayString,
	fwuRmtRSIRIDateCode  DisplayString,
	fwuRmtRSIRIHWVer  DisplayString,
	fwuRmtCapacity	Unsigned32	}

fwuRmtRSIRIADCPartNumber	OBJECT-TYPE	
	SYNTAX			DisplayString
	MAX-ACCESS		read-only
	STATUS			current
	DESCRIPTION		"Remote Inventory Data - TE Part Number."
	::=  {  fwuRmtRSIInfoEntry  1  }

fwuRmtRSIRISerialNumber	OBJECT-TYPE	
	SYNTAX			DisplayString
	MAX-ACCESS		read-only
	STATUS			current
	DESCRIPTION		"Remote Inventory Data - Serial Number."
	::=  {  fwuRmtRSIInfoEntry  2  }

fwuRmtRSIRIDateCode	OBJECT-TYPE	
	SYNTAX			DisplayString
	MAX-ACCESS		read-only
	STATUS			current
	DESCRIPTION		"Remote Inventory Data - Date Code."
	::=  {  fwuRmtRSIInfoEntry  3 }

fwuRmtRSIRIHWVer	OBJECT-TYPE	
	SYNTAX			DisplayString
	MAX-ACCESS		read-only
	STATUS			current
	DESCRIPTION		"Remote Inventory Data - Hardware version."
	::=  {  fwuRmtRSIInfoEntry  4  }

fwuRmtCapacity		OBJECT-TYPE		
	SYNTAX			Unsigned32(1 .. 4) 
	MAX-ACCESS		read-only
	STATUS			current
	DESCRIPTION		"The number of RF modules that can be installed in the remote."
	::=  {  fwuRmtRSIInfoEntry  5  }

fwuRmtRSITraps				OBJECT IDENTIFIER		::=  {  fwuRmtRSIObjects  2  }	

fwuRmtACPowerSupplyMon4Fault	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName, 
				fwuTrapCode,
				fwuNotificationStatus 	}
	STATUS			current
	DESCRIPTION		"AC Power monitor 4 Fault."
	::=  {  fwuRmtRSITraps  1  }

-- +++++++++++++++++++++++++++++++++++++++++++++++++++++++++++++++++++++++++++++
-- Dart Mapping Table Objects  (.15.2.1.3.2) --
-- +++++++++++++++++++++++++++++++++++++++++++++++++++++++++++++++++++++++++++++
fwuDARTMappingObjects		OBJECT IDENTIFIER		::=  {  fwuGeneralObjects  2  }	
fwuDARTMappingInfo			OBJECT IDENTIFIER		::=  {  fwuDARTMappingObjects  1  }	

fwuDARTMappingTable	OBJECT-TYPE
	SYNTAX			SEQUENCE  OF  FwuDARTMappingEntry
	MAX-ACCESS		not-accessible
	STATUS			current
	DESCRIPTION		"This table maintains Information of DART Mapping Objects."
	::=  { fwuDARTMappingInfo  1 }

fwuDARTMappingEntry	OBJECT-TYPE
	SYNTAX			FwuDARTMappingEntry
	MAX-ACCESS		not-accessible
	STATUS			current
	DESCRIPTION		"Each entry in this table refers to DART Mapping Objects."
	INDEX			{  fwuDARTMappingIndex  }
	::=  { fwuDARTMappingTable 1 }

FwuDARTMappingEntry  ::=  SEQUENCE {
	fwuDARTMappingIndex  Unsigned32,
	fwuUnitID  UnitID2,
	fwuUnitDARTID  Integer32,
	fwuUnitSFPID  Integer32 ,
	fwuUnitDartPassBand  OCTET STRING,
	fwuMateID UnitID2,
	fwuMateDARTID Integer32,
	fwuMateSFPID  Integer32,
	fwuMateDartPassband OCTET STRING,
	fwuSFPStartTimeSlot  Integer32,
	fwuSFPEndTimeSlot  Integer32,
	fwuMappingStatus  RowStatus	}

fwuDARTMappingIndex	OBJECT-TYPE	
	SYNTAX			Unsigned32
	MAX-ACCESS		read-only
	STATUS			current
	DESCRIPTION		"DART  Mapping Table Index."
	::=  {  fwuDARTMappingEntry  1  }

fwuUnitID	OBJECT-TYPE	
	SYNTAX			UnitID2
	MAX-ACCESS		read-create
	STATUS			current
	DESCRIPTION		"Identifier for the unit."
	::=  {  fwuDARTMappingEntry  2  }

fwuUnitDARTID	OBJECT-TYPE	
	SYNTAX			Integer32 (1..8)
	MAX-ACCESS		read-create
	STATUS			current
	DESCRIPTION		"Identifier of DART on the unit. Since there is a maximum of 8 DARTs, the valid values are one to eight."
	::=  {  fwuDARTMappingEntry  3  }
	
fwuUnitSFPID	OBJECT-TYPE	
	SYNTAX			Integer32 (1..8)
	MAX-ACCESS		read-create
	STATUS			current
	DESCRIPTION		"Identifier of unit SFP connected to the mate DART (outgoing; away from the Host). Since there is a maximum of 8 SFPs, the valid values are one to eight."
	::=  {  fwuDARTMappingEntry  4  }

fwuUnitDartPassBand	OBJECT-TYPE	
	SYNTAX			OCTET STRING (SIZE (0..40)) 
	MAX-ACCESS		read-only
	STATUS			current
	DESCRIPTION		"Band-Passband information of the linked DART on the host side."
	::=  {  fwuDARTMappingEntry  5  }
	
fwuMateID	OBJECT-TYPE	
	SYNTAX			UnitID2
	MAX-ACCESS		read-create
	STATUS			current
	DESCRIPTION		"Identifier of (companion) mate unit."
	::=  {  fwuDARTMappingEntry  6  }

fwuMateDARTID	OBJECT-TYPE	
	SYNTAX			Integer32  (1..8)
	MAX-ACCESS		read-create
	STATUS			current
	DESCRIPTION		"Identifies the (companion) DART on mate unit. Since there is a maximum of 8 DARTs, the valid values are one to eight."
	::=  {  fwuDARTMappingEntry  7  }

fwuMateSFPID	OBJECT-TYPE	
	SYNTAX			Integer32 (1..8)
	MAX-ACCESS		read-create
	STATUS			current
	DESCRIPTION		"Identifies the remote SFP connected to the unit DART(incoming from direction of the Host)."
	::=  {  fwuDARTMappingEntry  8  }
	
fwuMateDartPassband	OBJECT-TYPE	
	SYNTAX			OCTET STRING (SIZE (0..40))
	MAX-ACCESS		read-only
	STATUS			current
	DESCRIPTION		"Band-Passband information of the linked DART on the Mate side."
	::=  {  fwuDARTMappingEntry  9  }

fwuSFPStartTimeSlot	OBJECT-TYPE	
	SYNTAX			Integer32
	MAX-ACCESS		read-create
	STATUS			current
	DESCRIPTION		"Value of the first time slot used on the fiber carrying RF from unit DART to mate DART. Though this is a read-write object, the end user can only read the value. This and the next object are pair of values for a fiber. Depending on the DART type there may be a maximum of six or twelve time slots."
	::=  {  fwuDARTMappingEntry  10  }

fwuSFPEndTimeSlot	OBJECT-TYPE	
	SYNTAX			Integer32
	MAX-ACCESS		read-create
	STATUS			current
	DESCRIPTION		"Value of the last time slot used on the fiber carrying RF from unit DART to mate DART. Though this is a read-write object, the end user can only read the value. This and the previous object are pair of values for a fiber."
	::=  {  fwuDARTMappingEntry  11  }

fwuMappingStatus	OBJECT-TYPE	
	SYNTAX			RowStatus 
	MAX-ACCESS		read-create
	STATUS			current
	DESCRIPTION		"The status of the conceptual row. The status may be active or inactive."
	::=  {  fwuDARTMappingEntry  12  }	

fwuSystemAlarmManagement		OBJECT IDENTIFIER	::=  {  fwuGeneralObjects  3  }
 
fwuSystemAlarmManagementTable	OBJECT-TYPE
	SYNTAX			SEQUENCE  OF  FwuSystemAlarmManagementEntry
	MAX-ACCESS		not-accessible
	STATUS			current
	DESCRIPTION		"This table maintains alarm managing property and threshold information of all alarms."
        ::=  { fwuSystemAlarmManagement  1 }
 
fwuSystemAlarmManagementEntry	OBJECT-TYPE
	SYNTAX			FwuSystemAlarmManagementEntry
	MAX-ACCESS		not-accessible
	STATUS			current
	DESCRIPTION		"Each entry in this table refers to Alarm management table Objects."
	INDEX			{ fwuSystemAlarmcode}
	::=  { fwuSystemAlarmManagementTable 1 }
 
FwuSystemAlarmManagementEntry  ::=  SEQUENCE {
	fwuSystemAlarmcode Unsigned32,
	fwuSystemAlarmManageable ALARMManage,
	fwuSystemAlarmThreshold  DisplayString,
	fwuSystemAlarmModType Integer32	}
 
fwuSystemAlarmcode	OBJECT-TYPE
	SYNTAX			Unsigned32
	MAX-ACCESS		read-only
	STATUS			current
	DESCRIPTION		"The alarm code.It is used as Table Index."
	::=  {  fwuSystemAlarmManagementEntry  1  }
 
fwuSystemAlarmManageable	OBJECT-TYPE
	SYNTAX			ALARMManage
	MAX-ACCESS		read-only
	STATUS			current
	DESCRIPTION		"Indicates if the alarm is manageble(0) or not (1). If manageable, use fwuSystemAlarmEnabled, see below, to enable or disable the alarm."
        ::=  {  fwuSystemAlarmManagementEntry  2  }
 
fwuSystemAlarmThreshold		OBJECT-TYPE
	SYNTAX			DisplayString
	MAX-ACCESS		read-only
	STATUS			current
	DESCRIPTION		"Alarm Threshold value."
        ::=  {  fwuSystemAlarmManagementEntry  3  }
 
fwuSystemAlarmModType		OBJECT-TYPE
	SYNTAX			Integer32
	MAX-ACCESS		read-only
	STATUS			current
	DESCRIPTION		"Identifies the module type which raised the alarm."
	::=  {  fwuSystemAlarmManagementEntry  4  }
 
fwuSystemModuleAlarmEnableTable OBJECT-TYPE
	SYNTAX			SEQUENCE  OF  FwuSystemModuleAlarmEnableEntry
	MAX-ACCESS		not-accessible
	STATUS			current
	DESCRIPTION		"This table will allow the user to enable or disable an alarm. Use the fwuSystemAlarmManagementTable to check if the alarm is manageable or not."
	::=  { fwuSystemAlarmManagement  2 }
 
fwuSystemModuleAlarmEnableEntry		OBJECT-TYPE
	SYNTAX			FwuSystemModuleAlarmEnableEntry
	MAX-ACCESS		not-accessible
	STATUS			current
	DESCRIPTION		"Each entry in this table refers to Module alarm enable table Objects."
	INDEX			{ fwuSystemTrapNodeAddress,fwuSystemAlarmModuleNo,fwuSystemModuleAlarmcode }
	::=  { fwuSystemModuleAlarmEnableTable 1 }
 
FwuSystemModuleAlarmEnableEntry  ::=  SEQUENCE {
	fwuSystemTrapNodeAddress Unsigned32,
	fwuSystemAlarmModuleNo Unsigned32,
	fwuSystemModuleAlarmcode  Unsigned32,
	fwuSystemAlarmEnabled ALARMEnable	}
 
fwuSystemTrapNodeAddress     OBJECT-TYPE
	SYNTAX			Unsigned32
	MAX-ACCESS		read-write
	STATUS			current
	DESCRIPTION		"The unit which raised the alarm."
	::=  {  fwuSystemModuleAlarmEnableEntry 1  }
 
fwuSystemAlarmModuleNo	OBJECT-TYPE
	SYNTAX			Unsigned32
	MAX-ACCESS		read-write
	STATUS			current
	DESCRIPTION		"The module which raised the alarm."
	::=  {  fwuSystemModuleAlarmEnableEntry 2  }
 
fwuSystemModuleAlarmcode	OBJECT-TYPE
	SYNTAX			Unsigned32
	MAX-ACCESS		read-write
	STATUS			current
	DESCRIPTION		"The alarm code."
        ::=  {  fwuSystemModuleAlarmEnableEntry 3  }

fwuSystemAlarmEnabled	OBJECT-TYPE
	SYNTAX			ALARMEnable
	MAX-ACCESS		read-write
	STATUS			current
	DESCRIPTION		"This is used to enable or disable the alarm. Alarms is enabled by default, except the Uplink inactivity fault."
	::=  {  fwuSystemModuleAlarmEnableEntry 4  }

fwuGeoObjects				OBJECT IDENTIFIER		::=  {  fwuGeneralObjects  4  }	

--fwuGeoHeartbeatTimer	OBJECT-TYPE	
--	SYNTAX			Integer32 (1..30)
--	MAX-ACCESS		read-write
--	STATUS			current
--	DESCRIPTION	
--		"Heartbeat can be sent at the timer specified here."
--	DEFVAL 			{ 20 }
--	::=  {  fwuGeoObjects  1  }

fwuGeoTable	OBJECT-TYPE
	SYNTAX			SEQUENCE  OF  FwuGeoEntry
	MAX-ACCESS		not-accessible
	STATUS			current
	DESCRIPTION		"This table maintains Information of Geo Objects."
	::=  { fwuGeoObjects  2 }

fwuGeoEntry	OBJECT-TYPE
	SYNTAX			FwuGeoEntry
	MAX-ACCESS		not-accessible
	STATUS			current
	DESCRIPTION		"Each entry in this table refers to Geo Objects."
	INDEX			{  fwuGeoIndex  }
	::=  { fwuGeoTable 1 }

FwuGeoEntry  ::=  SEQUENCE {
	fwuGeoIndex  Unsigned32,
	fwuGeoLatitude  DisplayString,
	fwuGeoLongitude  DisplayString,
	fwuGeoRmtName  DisplayString,
	fwuGeoStatus  INTEGER	}

fwuGeoIndex		OBJECT-TYPE	
	SYNTAX			Unsigned32
	MAX-ACCESS		read-write
	STATUS			current
	DESCRIPTION		"Geo objects Table Index."
	::=  {  fwuGeoEntry  1  }

fwuGeoLatitude		OBJECT-TYPE	
	SYNTAX			DisplayString
	MAX-ACCESS		read-write
	STATUS			current
	DESCRIPTION		"Identifies the Latitude of remote unit."
	::=  {  fwuGeoEntry  2 }

fwuGeoLongitude		OBJECT-TYPE	
	SYNTAX			DisplayString
	MAX-ACCESS		read-write
	STATUS			current
	DESCRIPTION		"Identifies the Longitude of remote unit."
	::=  {  fwuGeoEntry  3 }

fwuGeoRmtName		OBJECT-TYPE	
	SYNTAX			DisplayString
	MAX-ACCESS		read-only
	STATUS			current
	DESCRIPTION		"The Remote name."
	::=  {  fwuGeoEntry  4 }

fwuGeoStatus		OBJECT-TYPE	
	SYNTAX			INTEGER { notPresent(0), active(1), inActive(2) }
	MAX-ACCESS		read-only
	STATUS			current
	DESCRIPTION		"Standard SNMP row status for this table."
	::=  {  fwuGeoEntry  5 }

-- +++++++++++++++++++++++++++++++++++++++++++++++++++++++++++++++++++++++++++++
-- SNMP Specific parameters  [Rev-7] (.15.2.1.3.5) --
fwuSnmpSettings OBJECT IDENTIFIER::= {fwuGeneralObjects 5}	
-- +++++++++++++++++++++++++++++++++++++++++++++++++++++++++++++++++++++++++++++
fwuV1TrapAgentAddrOverrideMode OBJECT-TYPE
	SYNTAX 			INTEGER  { disable(0), enable(1) }
	MAX-ACCESS 		read-write
  	STATUS 			current
  	DESCRIPTION		"Provision to overide the default (1) or use default (0) agent address in v1 trap PDU. Use fwuV1TrapAgentAddrOverrideIPAddr to set the overriding agent address."
	DEFVAL 			{ 0 }
	::= { fwuSnmpSettings 1 }

fwuV1TrapAgentAddrOverrideIPAddr	OBJECT-TYPE
	SYNTAX 			OCTET STRING ( SIZE (0..16) )
	MAX-ACCESS 		read-write
	STATUS 			current
	DESCRIPTION		"The overriding agent IP address in v1 trap PDU. Use Internet standard dot-decimal notation. Enable its use by setting fwuV1TrapAgentAddrOverrideMode."
	::= { fwuSnmpSettings 2 }

fwuSnmpTrapResendInterval OBJECT-TYPE
  	SYNTAX 		Integer32 (0..600)
  	MAX-ACCESS 	read-write
  	STATUS 		current
  	DESCRIPTION	"Time, in seconds, to resend unacknowledged traps. The trap will not be
		resent if this is set to zero(0). Acknowledgement is not needed if resend is
		not required, therefore, no trap entry will be entered into fwuSystemActiveAlarmTable."
    DEFVAL          { 0 }	
	::= { fwuSnmpSettings 3 }

fwuSnmpTrapResendMaximum OBJECT-TYPE
	SYNTAX 		Integer32 (0..10)
	MAX-ACCESS 	read-write
	STATUS 		current
	DESCRIPTION
		"Maximum number of times traps will be resent before removal if not acknowledged. If set to zero, it will not be resent."
    DEFVAL          { 2 }		
	::= { fwuSnmpSettings 4 }

--fwuImAliveTrapInterval OBJECT-TYPE
--	SYNTAX Integer32 (-86400..-1 | 0 | 1..60)
--	MAX-ACCESS read-write
--	STATUS current
--	DESCRIPTION
--		"This is the time interval for sending I'm Alive traps. If the number (T) is
--		less than 0, then the interval is abs(T) seconds. If the number is greater
--		than 0, then the interval is (T) days. If the number is 0, it will stop sending
--		the I'm Alive traps. No acknowledgement is required."
--	::= { fwuSnmpSettings 5 }

--fwuEthernetModemWakeUp	OBJECT-TYPE
--  	SYNTAX 		INTEGER { false(0), true(1)}
--  	MAX-ACCESS 	read-write
--  	STATUS 		current
--  	DESCRIPTION
--		"To send a wake up to external modem if used."
--	::= { fwuSnmpSettings 6 }


-- ++++++++++++++++++++++++++++++++++++++++++++++++++++++++++++++++++++++++++++
-- Snmp Trap Dest Table  [Rev-7] (.15.2.1.3.5.7) --
-- Rearranged the OIDs in order to minimize MIB compatibility issues
-- ++++++++++++++++++++++++++++++++++++++++++++++++++++++++++++++++++++++++++++
fwuSnmpTrapMgrConfigTable	OBJECT-TYPE
	SYNTAX			SEQUENCE OF FwuSnmpTrapMgrConfigEntry
	MAX-ACCESS		not-accessible
	STATUS			current
	DESCRIPTION		"Table containing information about the trap destinations.  For changes
					to take effect, a (Host) reboot is	required."
	::= { fwuSnmpSettings 7}

fwuSnmpTrapMgrConfigEntry	OBJECT-TYPE
	SYNTAX			FwuSnmpTrapMgrConfigEntry
	MAX-ACCESS		not-accessible
	STATUS			current
	DESCRIPTION		"An entry in the fwuSnmpTrapMgrConfigTable."
	INDEX			{ fwuTrapMgrRowId }
	::= { fwuSnmpTrapMgrConfigTable 1 }

FwuSnmpTrapMgrConfigEntry ::= SEQUENCE {
	fwuTrapMgrRowId 	INTEGER,
	fwuTrapMgrIpAddress 	OCTET STRING,
	fwuTrapMgrListeningPort	Unsigned32,
	fwuTrapMgrCommunity	DisplayString,
	fwuTrapVersion 		INTEGER,
	fwuTrapMgrRowStatus 	RowStatus	}

fwuTrapMgrRowId		OBJECT-TYPE
	SYNTAX			INTEGER (1..16)
	MAX-ACCESS		not-accessible
	STATUS			current
	DESCRIPTION		"The unique index of this trap destination."		
	::= {fwuSnmpTrapMgrConfigEntry 1}

fwuTrapMgrIpAddress OBJECT-TYPE
	SYNTAX 			OCTET STRING ( SIZE (0..16) )
	MAX-ACCESS 		read-create
	STATUS			current
	DESCRIPTION		"Provision to set the IP address of the trap manager. Use Internet standard dot-decimal notation."
	DEFVAL  { "127.0.0.1" } 	
	::= {fwuSnmpTrapMgrConfigEntry 2}

fwuTrapMgrListeningPort	OBJECT-TYPE	
	SYNTAX			Unsigned32
	MAX-ACCESS		read-create
	STATUS			current
	DESCRIPTION		"Provision to set the port at which the trap manager is listening for the traps. The default port for SNMP traps is 162."
	DEFVAL			{ 162 }
	::= {fwuSnmpTrapMgrConfigEntry 3}
	
fwuTrapMgrCommunity	OBJECT-TYPE	
	SYNTAX			DisplayString ( SIZE(6..20))
	MAX-ACCESS		read-create
	STATUS			current
	DESCRIPTION		"The community used by the agent to send traps or informs to this manager."
	DEFVAL			{ "public" }
	::=  {  fwuSnmpTrapMgrConfigEntry  4 }	

fwuTrapVersion		OBJECT-TYPE
	SYNTAX			INTEGER  { v1(0),  v2c(1), inform(2) }
	MAX-ACCESS 		read-create
	STATUS			current
	DESCRIPTION		"The SNMP version used for this trap destination. The available versions are v1(0),  v2c(1), inform(2) with v2c being set as default."
	DEFVAL			{ 1 }
	::= {fwuSnmpTrapMgrConfigEntry 5}

fwuTrapMgrRowStatus OBJECT-TYPE
	SYNTAX 			RowStatus		
	MAX-ACCESS 		read-create
	STATUS 			current
	DESCRIPTION		"The status of this conceptual row.
					This is used to manage the creation and deletion of this trap destination table."
	DEFVAL			{ notInService }	
	::= {fwuSnmpTrapMgrConfigEntry 6}
	
fwuEnableNotifHysteresis OBJECT-TYPE
    SYNTAX      INTEGER {disable(0), enable(1)}
    MAX-ACCESS  read-write
    STATUS      current
    DESCRIPTION
        "Provision to enable(1) or disable(0) event hysteresis. If disabled notification is sent out on occurance of the event. If enabled set the hysteresis value using fwuEventNotifHysteresis."
    DEFVAL          { 0 }
    ::= { fwuSnmpSettings 8 }

fwuEventNotifHysteresis OBJECT-TYPE
    SYNTAX      Integer32 (10..600)
    MAX-ACCESS  read-write
    STATUS      current
    DESCRIPTION
        "Time period, in seconds, for which an event has to persist before a notification is sent. For this value to be useable, ensure that fwuEnableNotifHysteresis is enabled."
    ::= { fwuSnmpSettings 9 }

fwuEnableNotifInterval OBJECT-TYPE
    SYNTAX      INTEGER {disable(0), enable(1)}
    MAX-ACCESS  read-write
    STATUS      current
    DESCRIPTION
        "Provision to enable(1) or disable(0) a time lag before sending out an event notification. If disabled, 
         notification is sent out on the occurance of the event. If enabled, use fwuEventNotifInterval to set the lag."
    DEFVAL          { 0 }
    ::= { fwuSnmpSettings 10 }

fwuEventNotifInterval OBJECT-TYPE
    SYNTAX      Integer32 (5..60)
    MAX-ACCESS  read-write
    STATUS      current
    DESCRIPTION
        "Provision to set the time lag in seconds between the successive event notifications. For this value to be useable, ensure that fwuEnableNotifInterval is enabled."
    ::= { fwuSnmpSettings 11 }

-- ++++++++++++++++++++++++++++++++++++++++++++++++++++++++++++++++++++++++++++
-- Scheduler Table objects (.15.2.1.3.5.12) --
-- ++++++++++++++++++++++++++++++++++++++++++++++++++++++++++++++++++++++++++++
fwuSchedulerTable	OBJECT-TYPE
	SYNTAX			SEQUENCE OF FwuSchedulerEntry
	MAX-ACCESS		not-accessible
	STATUS			current
	DESCRIPTION		"Table containing information about the trap destinations.  For changes
					to take effect, a (Host) reboot is required."
	::= { fwuSnmpSettings 12}

fwuSchedulerEntry	OBJECT-TYPE
	SYNTAX			FwuSchedulerEntry
	MAX-ACCESS		not-accessible
	STATUS			current
	DESCRIPTION		"An entry in the fwuSchedulerTable."
	INDEX			{ fwuTaskId }
	::= { fwuSchedulerTable 1 }

FwuSchedulerEntry ::= SEQUENCE {
    fwuTaskId  INTEGER,
    fwuTaskType  INTEGER,
    fwuScheduleStatus  INTEGER,
    fwuTaskStartTime  DisplayString,
    fwuOccurrences  INTEGER,
    fwuRecurrence  DisplayString,
    fwuFunctionArgs  DisplayString,
    fwuRowStatus 	RowStatus}

fwuTaskId		    OBJECT-TYPE
	SYNTAX			INTEGER (0 .. 2147483647) 
	MAX-ACCESS		not-accessible
	STATUS			current
	DESCRIPTION		"The unique index of the Scheduler table. Range limited to
	                 machine integer size(32 bit) restriction."		
	::= {fwuSchedulerEntry 1}

fwuTaskType		    OBJECT-TYPE
	SYNTAX			INTEGER { systemTest(2), iamAliveTrap(5) }
	MAX-ACCESS 		read-create
	STATUS			current
	DESCRIPTION		"The task to be scheduled. If System Test is the task being scheduled it requires some more arguments. Use fwuFunctionArgs to provide them. After specifying a task, enable the task using fwuScheduleStatus."
	::= {fwuSchedulerEntry 2}

fwuScheduleStatus	OBJECT-TYPE
	SYNTAX			INTEGER { notEnabled(0), enabled(1) }
	MAX-ACCESS 		read-create
	STATUS			current
	DESCRIPTION		"Provision to enable(1) or disable(0) the scheduled task (defined by fwuTaskType)."
	DEFVAL			{ 0 }
	::= {fwuSchedulerEntry 3}

	
fwuTaskStartTime	OBJECT-TYPE	
	SYNTAX			DisplayString
	MAX-ACCESS		read-create
	STATUS			current
	DESCRIPTION		"The start time of the scheduled activity."
	::=  {fwuSchedulerEntry  4}	

fwuOccurrences		OBJECT-TYPE
	SYNTAX			INTEGER
	MAX-ACCESS 		read-create
	STATUS			current
	DESCRIPTION		"Provision to set the number of times the task is to be executed. Set a value greater than 0 for a finite number of executions. 
	                 To keep executing forever, set value to -1."
	DEFVAL			{ -1 }
	::= {fwuSchedulerEntry 5}

fwuRecurrence		OBJECT-TYPE
	SYNTAX			DisplayString
	MAX-ACCESS 		read-create
	STATUS			current
	DESCRIPTION		"Provision to set the periodicity of the scheduled task. Eg. S5 is 5 Sec, H6 is 6 Hours, M8 is 8 Min. 
	                 Note: This is also used for the time interval for sending I am alive traps."
	DEFVAL			{ "0" }
	::= {fwuSchedulerEntry 6}

fwuFunctionArgs	    OBJECT-TYPE	
	SYNTAX			DisplayString
	MAX-ACCESS		read-create
	STATUS			current
	DESCRIPTION		"Colon separated string of arguments required for the given task type. 
	                 Can be empty depending on the task type."
	::=  { fwuSchedulerEntry  7}
	
fwuRowStatus        OBJECT-TYPE
	SYNTAX 			RowStatus		
	MAX-ACCESS 		read-create
	STATUS 			current
	DESCRIPTION		"The status of the conceptual row.
					This is used to manage the creation and deletion of the rows in scheduler table."
	DEFVAL			{ notInService }	
	::= {fwuSchedulerEntry 8}	
	
-- +++++++++++++++++++++++++++++++++++++++++++++++++++++++++++++++++++++++++++++
-- Contact Alarm Objects  [Rev-7] (.15.2.1.3.6)  fwuContactAlarmTraps --
fwuContactAlarmObjects OBJECT IDENTIFIER::= {fwuGeneralObjects 6}	
-- +++++++++++++++++++++++++++++++++++++++++++++++++++++++++++++++++++++++++++++

fwuContactAlarmInfo	OBJECT IDENTIFIER::=  {  fwuContactAlarmObjects  1  }

fwuSystemContactAlarmMgmtTable	OBJECT-TYPE
	SYNTAX			SEQUENCE  OF  FwuSystemContactAlarmMgmtEntry
	MAX-ACCESS		not-accessible
	STATUS			current
	DESCRIPTION		"Entities in this table are applicable to all Prism and URH remote units. 
				For Host and DRU, entities are applicable only for 2nd generation system 
				cards and onwards."
	::=  { fwuContactAlarmInfo  1 }

fwuSystemContactAlarmMgmtEntry OBJECT-TYPE
	SYNTAX			FwuSystemContactAlarmMgmtEntry
	MAX-ACCESS		not-accessible
	STATUS			current
	DESCRIPTION		"An entry (conceptual row) in the fwuSnmpTrapMgrConfigTable."
	INDEX			{  fwuUnitIndex, fwuSYstemAlarmCode}
	::= { fwuSystemContactAlarmMgmtTable 1 }

FwuSystemContactAlarmMgmtEntry ::= SEQUENCE {
	fwuUnitIndex UnitID2,
	fwuSYstemAlarmCode	Unsigned32,
	fwuContactAlarm	DisplayString,
	fwuContactAlarmMode	INTEGER, 
	fwuContactAlarmName	DisplayString,
	fwuContactAlarmEnable	ALARMEnable,
	fwuContactAlarmSeverity INTEGER }

fwuUnitIndex		OBJECT-TYPE
	SYNTAX			UnitID2
	MAX-ACCESS		read-only
	STATUS			current
	DESCRIPTION		"The number of the connected unit."	
	::= {fwuSystemContactAlarmMgmtEntry 1}

fwuSYstemAlarmCode	OBJECT-TYPE
	SYNTAX			Unsigned32
	MAX-ACCESS		read-only
	STATUS			current
	DESCRIPTION	
		"A code that uniquely identifies an alarm."
	::=  {fwuSystemContactAlarmMgmtEntry 2}

fwuContactAlarm OBJECT-TYPE
	SYNTAX			DisplayString
	MAX-ACCESS		read-only
	STATUS			current
	DESCRIPTION		"Hardware Assigned Name."	
	::= {fwuSystemContactAlarmMgmtEntry 3}

fwuContactAlarmMode OBJECT-TYPE
	SYNTAX			INTEGER { normallyClose(1) ,  normallyOpen(2) } 
	MAX-ACCESS		read-write
	STATUS			current
	DESCRIPTION		"Provision to set the mode of the alarm as normally closed (1) or normally open  (2)."	
	::= {fwuSystemContactAlarmMgmtEntry 4}

fwuContactAlarmName	OBJECT-TYPE
	SYNTAX			DisplayString (SIZE(0..40))
	MAX-ACCESS		read-write
	STATUS			current
	DESCRIPTION		"User defined name of the host unit. All characters except angular brackets, single and double quotes are allowed. Minimum length of the name is 0 character  (It may be empty.). Maximum length of the name is 64 characters."	
	::= {fwuSystemContactAlarmMgmtEntry 5}

fwuContactAlarmEnable OBJECT-TYPE
	SYNTAX			ALARMEnable 
	MAX-ACCESS		read-write
	STATUS			current
	DESCRIPTION		"Provision to enable (1) or disable (0) the contact alarm. The alarm is enabled by default."
	DEFVAL 			{1}
	::= {fwuSystemContactAlarmMgmtEntry 6}

fwuContactAlarmSeverity OBJECT-TYPE
	SYNTAX			INTEGER { minor (2) ,  major(3) } 
	MAX-ACCESS		read-write
	STATUS			current
	DESCRIPTION		"Severity of the alarm."	
	::= {fwuSystemContactAlarmMgmtEntry 7}

fwuContactAlarmTraps	OBJECT IDENTIFIER	::=  {  fwuContactAlarmObjects  2  }

fwuHstContactAlarmOutput1	NOTIFICATION-TYPE
	OBJECTS	{ 	fwuTrapSequenceNumber, 
				fwuTrapTimeStamp, 
				fwuModuleNumber,
				fwuModuleType,  
                               fwuAlarmedModuleName,
				fwuHstNumber, 
				fwuHstName, 
				fwuTrapCode, 
				fwuNotificationStatus 	}
	STATUS			current
	DESCRIPTION		"Host contact output port state."
	::=  {  fwuContactAlarmTraps  1  }

fwuHstContactAlarmOutput2	NOTIFICATION-TYPE
	OBJECTS	{ 	fwuTrapSequenceNumber, 
				fwuTrapTimeStamp, 
				fwuModuleNumber,
				fwuModuleType,  
                               fwuAlarmedModuleName,
				fwuHstNumber, 
				fwuHstName,
				fwuTrapCode,  
				fwuNotificationStatus 	}
	STATUS			current
	DESCRIPTION		"Host contact output port state."
	::=  {  fwuContactAlarmTraps  2  }

fwuHstContactAlarmInput1	NOTIFICATION-TYPE
	OBJECTS	{ 	fwuTrapSequenceNumber, 
				fwuTrapTimeStamp, 
				fwuModuleNumber,
				fwuModuleType,  
                               fwuAlarmedModuleName,
				fwuHstNumber, 
				fwuHstName,
				fwuTrapCode,  
				fwuNotificationStatus 	}
	STATUS		current
	DESCRIPTION		"Host contact input port state."
	::=  {  fwuContactAlarmTraps  3  }

fwuHstContactAlarmInput2	NOTIFICATION-TYPE
	OBJECTS	{ 	fwuTrapSequenceNumber, 
				fwuTrapTimeStamp, 
				fwuModuleNumber,
				fwuModuleType,  
                               fwuAlarmedModuleName,
				fwuHstNumber, 
				fwuHstName,
				fwuTrapCode,  
				fwuNotificationStatus 	}
	STATUS			current
	DESCRIPTION		"Host contact input port state."
	::=  {  fwuContactAlarmTraps  4  }

fwuRmtContactAlarmInput1	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName,
				fwuTrapCode, 
				fwuNotificationStatus 	}
	STATUS			current
	DESCRIPTION		"Remote contact input port state- Summary of all connected remotes."
	::=  {  fwuContactAlarmTraps  5  }

fwuRmtContactAlarmInput2	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName,
				fwuTrapCode,	 
				fwuNotificationStatus 	}
	STATUS			current
	DESCRIPTION		"Remote contact input port state- Summary of all connected remotes."
	::=  {  fwuContactAlarmTraps  6  }

fwuRmtContactAlarmOutput1	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName,
				fwuTrapCode, 
				fwuNotificationStatus 	}
	STATUS		current
	DESCRIPTION		"Remote contact output port state- Summary of all connected remotes."
	::=  {  fwuContactAlarmTraps  7  }

fwuRmtContactAlarmOutput2	NOTIFICATION-TYPE
	OBJECTS	{ 	fwuTrapSequenceNumber, 
				fwuTrapTimeStamp, 
				fwuModuleNumber,
				fwuModuleType,  
                               fwuAlarmedModuleName,
				fwuHstNumber, 
				fwuHstName,  
				fwuRmtNumber, 
				fwuRmtName,
				fwuTrapCode,	 
				fwuNotificationStatus 	}
	STATUS		current
	DESCRIPTION	"Remote contact output port state- Summary of all connected remotes."
	::=  {  fwuContactAlarmTraps  8  }

-- +++++++++++++++++++++++++++++++++++++++++++++++++++++++++++++++++++++++++++++
-- Static Alarms Table [Rev-7] (.15.2.1.3.7)  fwuStaticAlarmsTable --
fwuSystemStaticAlarms OBJECT IDENTIFIER ::= { fwuGeneralObjects 7 }	
-- +++++++++++++++++++++++++++++++++++++++++++++++++++++++++++++++++++++++++++++

fwuSystemStaticAlarmsTable OBJECT-TYPE
	SYNTAX			SEQUENCE OF FwuSystemStaticAlarmsEntry
	MAX-ACCESS		not-accessible
	STATUS			current
	DESCRIPTION		"This is a static alarm table containing the statistics of units in the system.
					The major and minor alarms will be grouped separately for each of the units."
	::=  { fwuSystemStaticAlarms  1 }

fwuSystemStaticAlarmsEntry OBJECT-TYPE
	SYNTAX			FwuSystemStaticAlarmsEntry
	MAX-ACCESS		not-accessible
	STATUS			current
	DESCRIPTION		"Entries for units which can be either alarmed or not alarmed or not-discovered."
	INDEX			{ fwuSystemUnitID, fwuSystemUnitType }
	::=  { fwuSystemStaticAlarmsTable 1 }

FwuSystemStaticAlarmsEntry  ::=  SEQUENCE {		
	fwuSystemUnitID		UnitID2,
	fwuSystemUnitType	UnitType,
	fwuUnitMajorAlarms	DisplayString,
	fwuUnitMinorAlarms	DisplayString	}

fwuSystemUnitID 	OBJECT-TYPE
	SYNTAX			UnitID2
	MAX-ACCESS		read-only	
	STATUS			current
	DESCRIPTION		"The ID of the unit from which the alarms has been raised."
	::=  {  fwuSystemStaticAlarmsEntry  1  }

fwuSystemUnitType 	OBJECT-TYPE	
	SYNTAX			UnitType	
	MAX-ACCESS		read-only
	STATUS			current
	DESCRIPTION		"The type of the from which the alarm has been raised."
	::=  {  fwuSystemStaticAlarmsEntry  2  }

fwuUnitMajorAlarms 	OBJECT-TYPE	
	SYNTAX			DisplayString
	MAX-ACCESS		read-only
	STATUS			current
	DESCRIPTION		"The major alarm name of the unit."
	::=  {  fwuSystemStaticAlarmsEntry  3  }

fwuUnitMinorAlarms	OBJECT-TYPE	
	SYNTAX			DisplayString		
	MAX-ACCESS		read-only
	STATUS			current
	DESCRIPTION		"The minor alarm name of the unit."
	::=  {  fwuSystemStaticAlarmsEntry  4  }


-- +++++++++++++++++++++++++++++++++++++++++++++++++++++++++++++++++++++++++++++
-- Conformance-related definitions  (.15.2.1.4) --
flexwaveurhMIBConformance  	OBJECT IDENTIFIER ::=  { flexwaveURHMibModule 4}
-- +++++++++++++++++++++++++++++++++++++++++++++++++++++++++++++++++++++++++++++

flexwaveurhMIBCompliances	OBJECT IDENTIFIER ::= {flexwaveurhMIBConformance 	1}
flexwaveurhMIBGroups		OBJECT IDENTIFIER ::= {flexwaveurhMIBConformance 	2}	

-- compliance statements
flexwaveurhBasicCompliance MODULE-COMPLIANCE
        STATUS      current
        DESCRIPTION	"The compliance statement for Flexwave entities which implement the ADC-FLEXWAVE-URH-MIB."
        MODULE -- This Module
        MANDATORY-GROUPS {	fwuSerfGroup,
				fwuOpticsGroup,
				fwuDartGroup,
				fwuLnaGroup,
				fwuLpaGroup,
				fwuDuplexerGroup,
				fwuAlarmConfigGroup, 							
				fwuNotificationGroup,
				fwuLinkingGroup,
				fwuMateInfoGroup,
				fwuSprintModeGroup,
				fwuSNMPSettingGroup	}
        ::= { flexwaveurhMIBCompliances 1 }


	fwuSerfGroup  OBJECT-GROUP
		OBJECTS {				-- Host SERF Objects --
					fwuHstNumber, 				fwuHstName, 
					fwuHstUnitReset, 			fwuHstBackPlaneRev, 
					fwuHstAlarmStatusSummary, 	fwuHstTempMeas, 
					fwuSystemAlarmStatusSummary,	--fwuHstLinkingMode,
					fwuHstSystemDateAndTime,	
					fwuAlarmAck,			fwuAlarmLevel,
					fwuUserCommLinkTest,		fwuUserLinkTestStatus,
					fwuUserCommLinkTestDartBandType, 
					fwuUserCommLinkTestDartId,	fwuHstpThreadSWVer,
					fwuClearSysConfig,			--fwuPwrUpLinkTest,
					fwuLinkTestLastRuntime,
					fwuHstSubagentSWVer,		fwuHstWebServerSWVer,
					fwuHstMajorContactAlarmOutput,	fwuHstMinorContactAlarmOutput, 
					fwuRmtMajorContactAlarmOutput, 	fwuRmtMinorContactAlarmOutput,
					fwuHstSERFFPGAStatus,		fwuHstSysCardRIADCPartNumber,
					fwuHstSysCardRISerialNumber,	fwuHstSysCardRIDateCode,
					fwuHstSysCardRIHWVer,		fwuHstSERFLinuxKernelVer,
					fwuHstSERFLinuxBootLoaderVer,	fwuHstSERFCompactFlashSWVer,
					fwuHstSERFFPGAVer,		fwuHstSERFPPCSNMPAgentSWVer,
					fwuHstSERFPPCHWMonSWVer,	fwuHstSERFPPCAPPMonSWVer,
					fwuHstSERFPPCMATEMonSWVer,	fwuHstSERFPPCENETMonSWVer,
					fwuHstSERFPPCFPGAMonSWVer,	fwuHstSERFRIDateCode,
					fwuHstSERFRIHWVer,		fwuHstSERFRISerialNumber,
					fwuHstSERFRIADCPartNumber,	fwuHstSysCard10MhzRefClock,			
					fwuHstSysCardCPLevel,		fwuHstSysCardOutputRefClock,
					fwuHstSERFRIHWGen,		fwuHstSysCardRIHWGen,
					fwuHstSERFLinuxBootLoaderFirstVer,fwuNTPServerIP,
				        fwuSyncNTPServer,
								-- Remote SERF Objects --
					fwuRmtNumber,				fwuRmtCatalogState,
					fwuRmtName,					fwuRmtAlarmStatusSummary,
					fwuRmtTempMeasurement,		fwuRmtGeneralTableRowStatus,
					fwuRmtType,					fwuDruIfCombinerReboot,
					fwuUsrCommLinkTestIFBr, 	fwuUsrCommLinkTestIFBrDType,
					fwuUsrCommLinkTestDartId,	fwuDruBackPlaneRev,					
					fwuRmtSERFFPGAStatus,
					fwuRmtRSIRIADCPartNumber,	fwuRmtRSIRISerialNumber,
					fwuRmtRSIRIDateCode,		fwuRmtRSIRIHWVer,
					fwuRmtCapacity,				fwuRmtSERFLinuxKernelVer,
					fwuRmtSERFRIHWGen,		fwuRmtWebServerSWVer,
					fwuRmtpThreadSWVer,
					fwuRmtSERFLinuxBootLoaderVer,	fwuRmtSERFCompactFlashSWVer,
					fwuRmtSERFFPGAVer,			fwuRmtSERFPPCHWMonSWVer,
					fwuRmtSERFPPCAPPMonSWVer,	--fwuRmtSERFPPCGPSMonSWVer,	
					--fwuRmtSERFPPCSNMPAgentSWVer,
					fwuRmtSERFPPCMATEMonSWVer,
					fwuRmtSERFPPCENETMonSWVer,	fwuRmtSERFPPCFPGAMonSWVer,
					fwuRmtSERFRIDateCode,		fwuRmtSERFRIHWVer,
					fwuRmtSERFRISerialNumber,	fwuRmtSERFRIADCPartNumber,	
					fwuPrismUnitReset	}
		STATUS		current
		DESCRIPTION	"A collection of Host and Remote SERF objects."
		::= { flexwaveurhMIBGroups 1 }
	
	fwuOpticsGroup  OBJECT-GROUP
		OBJECTS {  				-- Host Optics & Ethernet --
					fwuHstSERFOptSFPNumber,		fwuHstSERFOptSFPName,		
					fwuHstSERFOptSFPType, 		fwuHstSERFOptSFPTxColor,	
					fwuHstSERFOptRevLaunchPowerMeas,	fwuHstSERFOptFwdLaunchPowerMeas,	
					fwuHstSERFOptMateName,		fwuHstSERFIPEnable,
					fwuHstSERFOptMateId,		fwuHstSERFOptMateSfpId,					
					fwuHstSERFEthPortNumber, 	fwuHstSERFEthPortType, 
					fwuHstSERFEthPortRxBytes, 	fwuHstSERFEthPortRxPkts, 
					fwuHstSERFEthPortRxFcsErrors, 		fwuHstSERFEthPortRxBroadcastPkts,
					fwuHstSERFEthPortRxMulticastPkts, 	fwuHstSERFEthPortRxFragmtdFrames, 
					fwuHstSERFEthPortRxJabbersFrames, 	fwuHstSERFEthPortTxByteCounter, 
					fwuHstSERFEthPortTxPkts, 	fwuHstSERFEthPortTxBroadcastPkts, 
					fwuHstSERFEthPortTxMulticastPkts, 	fwuHstSERFEthPortSFPId,							
								-- Remote Optics & Ethernet --
					fwuRmtSERFOptSFPNumber,		fwuRmtSERFOptSFPName,
					fwuRmtSERFOptSFPType,		fwuRmtSERFOptSFPColor,
					fwuRmtSERFOptRevLaunchPowerMeas,	fwuRmtSERFOptFwdLaunchPowerMeas,
					fwuRmtSERFOptMateName,		fwuRmtSERFIPEnable,
					fwuRmtSERFOptMateId,		fwuRmtSERFOptMateSfpId,
					fwuRmtSERFOptMateSfpDir,
					fwuRmtSERFEthPortNumber,	fwuRmtSERFEthPortType,
					fwuRmtSERFEthPortRxBytes,	fwuRmtSERFEthPortRxPkts,
					fwuRmtSERFEthPortRxFcsErrors,		fwuRmtSERFEthPortRxBroadcastPkts,
					fwuRmtSERFEthPortRxMulticastPkts,	fwuRmtSERFEthPortRxFragmtdFrames,
					fwuRmtSERFEthPortRxJabbersFrames,	fwuRmtSERFEthPortTxByteCounter,
					fwuRmtSERFEthPortTxPkts,	fwuRmtSERFEthPortTxBroadcastPkts,
					fwuRmtSERFEthPortTxMulticastPkts,	fwuRmtSERFEthPortSFPId,
                                        fwuRmtSERFOptHostIP     }
		STATUS		current
	    DESCRIPTION	"A collection of Host and Remote Optical and Ethernet port objects."
		::= { flexwaveurhMIBGroups 2 }


	fwuDartGroup  OBJECT-GROUP
		OBJECTS {  				-- Host Dart --
					fwuHstDARTNumber, 			fwuHstDARTName, 
					fwuHstDARTBandType, 		fwuHstDARTPassBand, 
					fwuHstDARTOperatingMode,	fwuHstDARTDiversityStatus, 
					fwuHstDARTForwardGain,		fwuHstDARTReverseGain, 
					fwuHstDARTFPGAStatus, 		fwuHstDARTFPGAProgramVer, 
					fwuHstDARTRIADCPartNumber, 	fwuHstDARTRISerialNumber, 
					fwuHstDARTRIDateCode,		fwuHstDARTRIHWVer, 
					fwuHstDARTRowStatus,		fwuHstDARTPeakInputPwrLvl1,
					fwuHstDARTPeakInputPwrLvl2,	fwuHstDARTPeakAvgInputPwrLvl1,
					fwuHstDARTPeakAvgInputPwrLvl2,	fwuHstDARTMinAvgInputPwrLvl1,
					fwuHstDARTMinAvgInputPwrLvl2,	fwuHstDARTInputPowerMode,
					fwuHstDARTPwrLevelMaxHoldReset,	fwuHstDARTLastMaxHoldResetTime,
					fwuHstDARTInputSrc,
					
								-- Remote Dart --
					fwuRmtDARTNumber,			fwuRmtDARTName,
					fwuRmtDARTBandType,			fwuRmtDARTPassBand,
					fwuRmtDARTOperatingMode,	fwuRmtDARTDiversityStatus,
					fwuRmtDARTForwardGain,		fwuRmtDARTReverseGain,
					fwuRmtDARTForwardDelay,		fwuRmtDARTReverseDelay,
					fwuRmtDARTTempMeas,			fwuRmtDARTFPGAStatus,
					fwuRmtDARTFPGAProgramVer,	fwuRmtDARTRIADCPartNumber,
					fwuRmtDARTRISerialNumber,	fwuRmtDARTRIDateCode,
					fwuRmtDARTRIHWVer,			fwuRmtDARTGeneralTableRowStatus,
					fwuRmtDARTActualForwardDelay,		fwuRmtDARTForwardLowerboundDelay,
					fwuRmtDARTForwardUpperboundDelay,	fwuRmtDARTActualReverseDelay,
					fwuRmtDARTReverseLowerboundDelay,	fwuRmtDARTReverseUpperboundDelay,
					fwuRmtDARTPeakInputPwrLvl1,		fwuRmtDARTPeakInputPwrLvl2,
					fwuRmtDARTPeakAvgInputPwrLvl1,		fwuRmtDARTPeakAvgInputPwrLvl2,
					fwuRmtDARTMinAvgInputPwrLvl1,		fwuRmtDARTMinAvgInputPwrLvl2,
					fwuRmtDARTInputPowerMode,		fwuRmtDARTPwrLevelMaxHoldReset,
					fwuRmtDARTLastMaxHoldResetTime, fwuRmtDARTReverseGainMode, 
					fwuRmtDARTTxRIADCPartNumber, fwuRmtDARTTxRISerialNumber,
					fwuRmtDARTTxRIDateCode, fwuRmtDARTTxRIHWVer,
                                        fwuRmtDARTLinkedStatus, fwuRmtDARTAvailable,
                                        fwuRmtDARTUsedSFP       }
		STATUS		current
		DESCRIPTION	"A collection of Host and Remote DART objects."
		::= { flexwaveurhMIBGroups 3 }

	fwuLnaGroup		OBJECT-GROUP
		OBJECTS {	fwuRmtLNANumber,
					fwuRmtLNAType,
					fwuRmtLNARIADCPartNumber,
					fwuRmtLNARISerialNumber,
					fwuRmtLNARIDateCode,
					fwuRmtLNARIHWVer,
					fwuRmtDuplexerType }
		STATUS		current
		DESCRIPTION	"A collection of Host and Remote LNA objects."
		::= { flexwaveurhMIBGroups 4 }

	fwuLpaGroup		OBJECT-GROUP
		OBJECTS {	fwuRmtLPANumber,
					fwuRmtLPAReset,
					fwuRmtLPAOpState,
					fwuRmtLPAPartNum,
					fwuRmtLPASerialNum,
					fwuRmtLPAHWVer,
					fwuRmtLPASWVer, 
					fwuRmtLPADescr,
					fwuRmtLPAControl,
					fwuRmtLPAMaxOpPwr,
					fwuRmtLPABandType }
		STATUS		current
		DESCRIPTION	"A collection of Host and Remote LPA objects."
		::= { flexwaveurhMIBGroups 5 }
	
	fwuDuplexerGroup  OBJECT-GROUP
		OBJECTS {  	fwuRmtPowerDetectorNumber,
					fwuRmtSystemVswrMeas,
					fwuRmtRFPowerOutputMeas,
					fwuRmtPwrDetectorBoardRIADCPartNum,
					fwuRmtPwrDetectorBoardRISerialNum,
					fwuRmtPwrDetectorBoardRIDateCode,
					fwuRmtPwrDetectorBoardRIHWVer,
					fwuRmtRDINumber,
					fwuRmtRDIRIADCPartNumber,
					fwuRmtRDIRISerialNumber,
					fwuRmtRDIRIDateCode,
					fwuRmtRDIRIHWVer,
					fwuRmtRDIRIHWType,
					fwuRmtPwrDetectorNoRfPowerThershold,
					fwuRmtSystemVSWRThreshold}
	    STATUS		current
		DESCRIPTION	"A collection of Host and Remote Duplexer objects."
		::= { flexwaveurhMIBGroups 6 }
	
	fwuAlarmConfigGroup  OBJECT-GROUP
		OBJECTS {  	fwuSystemAlarmTrapNodeAddress,
					fwuSystemlabel,
					fwuSystemAlarmRmtName,
					fwuSystemAlarmRmtType,
					fwuSystemAlarmModuleType,
					fwuSystemAlarmModuleNumber,
					fwuSystemAlarmModuleName,
					fwuSystemAlarmSeverity,
					fwuSystemAlarmRFBand,
					fwuSystemAlarmTimeStamp,
					fwuSystemAlarmCode,
					fwuSystemAlarmHstNbr,
					fwuSystemAlarmAnalogAddress,
					fwuRmtMajorContactAlarmOutput, 
					fwuRmtMinorContactAlarmOutput,
					fwuTrapSequenceNumber,
					fwuTrapTimeStamp,
					fwuNotificationStatus,
					fwuModuleType,
					fwuModuleNumber,
					fwuTrapCode,
					fwuTrapNodeAddress,
					fwuAlarmedModuleName,
					fwuUnitIndex,
					fwuSYstemAlarmCode,
					fwuContactAlarm,
					fwuContactAlarmMode,
					fwuContactAlarmName,
					fwuContactAlarmEnable,
					fwuContactAlarmSeverity,
					fwuSystemAlarmManageable,
					fwuSystemAlarmThreshold,
					fwuSystemAlarmModType,
					fwuSystemAlarmcode,
					fwuSystemTrapNodeAddress,
					fwuSystemAlarmModuleNo,
					fwuSystemModuleAlarmcode,
					fwuSystemAlarmEnabled	}
		STATUS		current
		DESCRIPTION	"A collection of Host and Remote Alarm configuration objects."
		::= { flexwaveurhMIBGroups 7 }

	fwuNotificationGroup   NOTIFICATION-GROUP
		NOTIFICATIONS {  
					fwuHstModuleMissingFault, 
					fwuHstOverTempFault, 
					fwuHstUnderTempFault, 
					fwuHstSysCardFanFault, 
					fwuHstSysCardClockMismatchFault,
					fwuHstSERFSynthAlarmFault, 
					fwuHstSERFFault,
					fwuHstSERFRmtLostFault, 
					fwuHstSERFOptRxBERFault, 
					fwuHstSERFOptRxNoLightFault, 
					fwuHstSERFOptLaserFault,
					fwuHstSERFOptOverDriveFault,
					fwuHstSERFOptUnderDriveFault,	
					fwuHstSERFOptIpEnableFault,
                                        fwuMastClockPriorityLvlConflict,
					fwuHstI2CBus1Fault,
					fwuHstI2CBus2Fault,
					fwuHstDARTFault,
					fwuHstDARTDCSupplyFault,
					fwuHstDARTHardwareMismatchFault,
					fwuHstDARTDwnCon1SynLockFault,
					fwuHstDARTDwnCon2SynLockFault,
					fwuHstDARTUpConSynLockFault,
					fwuHstDARTOverDriveFault,
					fwuHstDARTUnderDriveFault,
					fwuHstDARTALCLimitingFault,
				        fwuHstDARTLinkingConflictFault, 
                                        fwuHstIamAliveFault,
					fwuRmtModuleMissingFault,
					fwuRmtOverTempFault,
					fwuRmtUnderTempFault,
					fwuRmtOpenDoorFault,
					fwuRmtFanOverSpeedFault,
					fwuRmtFanUnderSpeedFault,
					fwuSWVersionMismatchFault,
					fwuDruSysCardFanFault,
					fwuDruOverTempFault,
					fwuDruUnderTempFault,
					fwuRmtAcPowerSupplyFault,
					fwuRmtMajorExtAlarmInputFault,
					fwuRmtMinorExtAlarmInputFault,
					fwuRmtSERFHstLostFault,
					fwuRmtSERFOptRxBERFault,
					fwuRmtSERFOptRxNoLightFault,
					fwuRmtSERFOptLaserFault,
					fwuRmtSERFOptOverDriveFault,
					fwuRmtSERFOptUnderDriveFault,
					fwuRmtSERFSynthAlarmFault,
					fwuRmtSERFFault,
					fwuRmtI2CBus1Fault,
					fwuRmtI2CBus2Fault,
					fwuRmtDARTDwnCon1SynLockFault,
					fwuRmtDARTDwnCon2SynLockFault,
					fwuRmtDARTUpConSynLockFault,
					fwuRmtDARTDCSupplyFault,
					fwuRmtDARTFault,
					fwuRmtDARTHardwareMismatchFault,
					fwuRmtRangingFault,
					fwuRmtDARTOverTempFault,
					fwuRmtDARTLowTempFault,
					fwuRmtDARTUplinkInactivityFault,
					fwuRmtDARTCommsFault,					
					fwuRmtLPADisableFault,
					fwuRmtLPAOverPowerFault,
					fwuRmtLPAHighTempFault,
					fwuRmtLPAVswrFault,
					fwuRmtLPADcFault,
					fwuRmtLPALoopFault,
					fwuRmtLPALowPowerFault,
					fwuRmtLPADetectFault,
					fwuRmtPaOverCurrentFault,
					fwuRmtSystemVswrFault,
					fwuRmtRFPowerFault,
					fwuRmtLNAPowerFault,
					fwuRmtDuplexerFreqMismatchFault,					
					fwuRmtACPowerSupplyMon4Fault,
					fwuRmtACPowerSupplyMon1Fault,
					fwuRmtACPowerSupplyMon2Fault,
					fwuRmtACPowerSupplyMon3Fault,
					fwuHstBTSUnderPowerFault,
					fwuHstFLMDownconvertFailureFault,
					fwuHstRLMUpconvertFailureFault,
					fwuHstRLMUpConIndetFault,
					fwuRmtDownLinkCalToneFailureFault,
					fwuRmtUplinkFailureDetectLowFault,
					fwuRmtUpConvertFailureFault,
					fwuRmtUnderPowerFault,
					fwuRmtDownConvertFailureFault,
					fwuRmtUpconIndetFault,
					fwuRmtFiberConnMismatchFault,
					fwuRmtExcessConnFault,
					fwuRmtInvalidDevConnFault,
					fwuDruSysCardClockMismatchFault,
					fwuDruNoCommsFault,
					fwuHstContactAlarmOutput1,
					fwuHstContactAlarmOutput2,
					fwuHstContactAlarmInput1,
					fwuHstContactAlarmInput2,
					fwuRmtContactAlarmInput1,
					fwuRmtContactAlarmInput2,
					fwuRmtContactAlarmOutput1,
					fwuRmtContactAlarmOutput2	}
	    STATUS		current
		DESCRIPTION	"A collection of Host and Remote Notification objects."
		::= { flexwaveurhMIBGroups 8 }


	fwuLinkingGroup	OBJECT-GROUP
		OBJECTS {
				fwuMappingStatus,
				fwuUnitID,
				fwuUnitDARTID,
				fwuUnitSFPID,
				fwuUnitDartPassBand,
				fwuMateID,
				fwuMateDARTID,
				fwuMateSFPID,
				fwuMateDartPassband,
				fwuSFPStartTimeSlot,
				fwuSFPEndTimeSlot,
				fwuDARTMappingIndex }
		STATUS	current
		DESCRIPTION	"A collection of RF linking configuration objects."
		::= { flexwaveurhMIBGroups 9 }

	fwuMateInfoGroup	OBJECT-GROUP
		OBJECTS {
				fwuHMmonRmtID,
				fwuHMmonRmtIPAddress
				--fwuRMmonIndex,				
				--fwuRMmonHstIPAddress,
				--fwuRMmonHstID,
				--fwuRMmonRmtID	
				}
		STATUS		current
		DESCRIPTION	"A collection of mate information objects."
		::= { flexwaveurhMIBGroups 10 }
	
	fwuSprintModeGroup	OBJECT-GROUP
		OBJECTS {
				--fwuGeoHeartbeatTimer,
				fwuGeoIndex, 
				fwuGeoLatitude, 
				fwuGeoLongitude,
				fwuGeoRmtName,		
				fwuGeoStatus	}
		STATUS		current
		DESCRIPTION	"A collection of objects supported in Sprint mode Objects."
	    ::= { flexwaveurhMIBGroups 11 }

	fwuSNMPSettingGroup	OBJECT-GROUP
		OBJECTS {				
				fwuV1TrapAgentAddrOverrideMode, 
				fwuV1TrapAgentAddrOverrideIPAddr, 
				fwuSnmpTrapResendInterval,
				fwuSnmpTrapResendMaximum,
				fwuEnableNotifHysteresis,
				fwuEventNotifHysteresis,
				fwuEnableNotifInterval,
				fwuEventNotifInterval,
				--fwuImAliveTrapInterval,
				--fwuEthernetModemWakeUp,
				fwuTrapMgrIpAddress,
				fwuTrapMgrListeningPort,
				fwuTrapMgrCommunity,
				fwuTrapVersion,
				fwuTrapMgrRowStatus,
				fwuTaskType,
				fwuScheduleStatus,
				fwuTaskStartTime,
				fwuOccurrences,
				fwuRecurrence,
				fwuFunctionArgs,
				fwuRowStatus }				
		STATUS		current
		DESCRIPTION	"A collection of objects supported in System Link test."
		::= { flexwaveurhMIBGroups 12 }
    
    fwuSystemStaticAlarmsGroup	OBJECT-GROUP
		OBJECTS {	fwuSystemUnitID, 
    				fwuSystemUnitType, 
    				fwuUnitMajorAlarms,
    				fwuUnitMinorAlarms	}
    	STATUS		current
        DESCRIPTION	"A collection of objects supported in Static Alarms Table."
	    ::= { flexwaveurhMIBGroups 13 }
    	
END
