-- ====================================================================
-- Copyright (C) 2003 by  HUAWEI TECHNOLOGIES. All rights reserved.
-- 
-- Description: Huawei LOOPDETECT MIB
-- Reference:   Huawei Enterprise MIB
-- Version:     V1.0
-- History:
--              2010-11  modified by xuxuguang for atn loopback-detect
-- 
-- =====================================================================

    HUAWEI-LOOPDETECT-MIB DEFINITIONS ::= BEGIN
 
        IMPORTS
            huawei            
                FROM HUAWEI-MIB 
                     
            MODULE-COMPLIANCE, OBJECT-GROUP, NOTIFICATION-GROUP
                FROM SNMPv2-CONF 
                                     
            OBJECT-TYPE, NOTIFICATION-TYPE, MODULE-IDENTITY, Integer32            
                FROM SNMPv2-SMI
            
            TruthValue,TEXTUAL-CONVENTION,
            RowStatus,MacAddress,DisplayString
                FROM SNMPv2-TC;
 

--
-- Node definitions
--
    
--  Node definitions
-- 
-- 1.3.6.1.4.1.2011.25
        -- 1.3.6.1.4.1.2011.25
        hwDatacomm OBJECT IDENTIFIER ::= { huawei 25 }
        
        -- 1.3.6.1.4.1.2011.25.180    
        hwLoopDetectMIB MODULE-IDENTITY
        LAST-UPDATED "201011130000Z"        -- October 30, 2010 at 00:00 GMT
        ORGANIZATION 
        "Huawei Technologies co., Ltd."
        CONTACT-INFO 
        "L2-Adp Team Huawei Technologies co., Ltd.
        Huawei Bld., NO.3 Xinxi Rd., 
        Shang-Di Information Industry Base,
        Hai-Dian District Beijing P.R. China
        http://www.huawei.com
            Zip:100085
        "
        DESCRIPTION
            "The LoopDetect MIB module is defined to indicate loop-detect function of Huawei Technologies co., Ltd."
            ::= { hwDatacomm 180 }

        -- hwLoopDetectMIB OBJECT IDENTIFIER ::= { hwDatacomm 180 }
        
        
        -- Textual Convention               
		EnabledStatus ::= TEXTUAL-CONVENTION
		    STATUS      current
		    DESCRIPTION
		        "A simple status value for the object."
		    SYNTAX      INTEGER 
		    { 
		      enabled(1),
		      disabled(2)
		    }
        
        -- 1.3.6.1.4.1.2011.25.180.1
        hwLoopDetectCfgTable OBJECT-TYPE
            SYNTAX SEQUENCE OF HwLoopDetectCfgEntry
            MAX-ACCESS not-accessible
            STATUS current
            DESCRIPTION
                "Indicates the table that shows the loop detect configuration and blocking state."
            ::= {hwLoopDetectMIB 1}    
        
        hwLoopDetectCfgEntry OBJECT-TYPE
            SYNTAX     HwLoopDetectCfgEntry
            MAX-ACCESS not-accessible
            STATUS current
            DESCRIPTION
                "Indicates the entries about the loop detect configuration and blocking state."
            INDEX {hwLoopDetectCfgPortIndex}
            ::= {hwLoopDetectCfgTable 1}
         
          HwLoopDetectCfgEntry ::=  
              SEQUENCE { 
              hwLoopDetectCfgPortIndex Integer32,
              hwLoopDetectCfgPortName OCTET STRING,
              hwLoopDetectCfg    Integer32,
              hwLoopDetectCfgBlock Integer32,        
            hwLoopDetectCfgBlockTime Integer32,
            hwLoopDetectCfgPriority Integer32,
            hwLoopDetectCfgTrigger Integer32,
            hwLoopDetectCfgSta    Integer32 
          }   
          
          hwLoopDetectCfgPortIndex OBJECT-TYPE
              SYNTAX  Integer32 (0..2147483647)
              MAX-ACCESS not-accessible
              STATUS current
              DESCRIPTION
                  "Indicates the interface index."
              ::= {hwLoopDetectCfgEntry 1}  
              
          hwLoopDetectCfgPortName OBJECT-TYPE
               SYNTAX  OCTET STRING(SIZE (0..80)) 
                   MAX-ACCESS read-only
              STATUS current
              DESCRIPTION
                  "Indicates the interface name."
              ::= {hwLoopDetectCfgEntry 2}
              
          hwLoopDetectCfg OBJECT-TYPE
              SYNTAX Integer32
              MAX-ACCESS read-only
              STATUS current
              DESCRIPTION
                  "Indicates whether the loop detect function is enabled." 
              ::= {hwLoopDetectCfgEntry 3}
              
          hwLoopDetectCfgBlock OBJECT-TYPE
              SYNTAX Integer32
              MAX-ACCESS read-only
              STATUS current
              DESCRIPTION 
                  "Indicates whether the interface can enter the blocking state after a loop is detected."
              ::= {hwLoopDetectCfgEntry 4}
              
          hwLoopDetectCfgBlockTime OBJECT-TYPE
              SYNTAX Integer32
              MAX-ACCESS read-only
              STATUS current
              DESCRIPTION
                  "Indicates the interval that is used to judge whether the loop disappears and the blocking state ends."
              ::= {hwLoopDetectCfgEntry 5}        

          hwLoopDetectCfgPriority OBJECT-TYPE
              SYNTAX Integer32
              MAX-ACCESS read-only
              STATUS current
              DESCRIPTION
                  "Indicates the priority in loop detect."
              ::= {hwLoopDetectCfgEntry 6}
              
          hwLoopDetectCfgTrigger OBJECT-TYPE
              SYNTAX Integer32
              MAX-ACCESS read-only
              STATUS current
              DESCRIPTION
                  "Indicates whether the function of immediate interface Down/Up is triggered after a loop is detected."
              ::= {hwLoopDetectCfgEntry 7}
              
          hwLoopDetectCfgSta OBJECT-TYPE
              SYNTAX Integer32
              MAX-ACCESS read-only
              STATUS current
              DESCRIPTION
                  "Identify the interface that is blocked after a loop is detected."
              ::= {hwLoopDetectCfgEntry 8}     
        
        
              
        -- 1.3.6.1.4.1.2011.25.180.2
        hwLoopDetectTraps OBJECT IDENTIFIER ::= { hwLoopDetectMIB 2 }
        
        -- 1.3.6.1.4.1.2011.25.180.2.1
        hwLoopDetectEnabled NOTIFICATION-TYPE
            OBJECTS { hwLoopDetectCfgPortName }
            STATUS current
            DESCRIPTION 
                "The loop detect function is enabled."
            ::= { hwLoopDetectTraps 1 }
        
        -- 1.3.6.1.4.1.2011.25.180.2.2
        hwLoopDetectDisabled NOTIFICATION-TYPE
            OBJECTS { hwLoopDetectCfgPortName }
            STATUS current
            DESCRIPTION 
                "The loop detect function is disabled."
            ::= { hwLoopDetectTraps 2 }
        
        -- 1.3.6.1.4.1.2011.25.180.2.3
        hwLoopDetectBlocked NOTIFICATION-TYPE
            OBJECTS { hwLoopDetectCfgPortName }
            STATUS current
            DESCRIPTION 
                "The interface is blocked."
            ::= { hwLoopDetectTraps 3 }
        
        -- 1.3.6.1.4.1.2011.25.180.2.4
        hwLoopDetectUnBlocked NOTIFICATION-TYPE
            OBJECTS { hwLoopDetectCfgPortName }
            STATUS current
            DESCRIPTION 
                "The interface is unblocked."
            ::= { hwLoopDetectTraps 4 }   
            
        -- 1.3.6.1.4.1.2011.25.180.2.5
        hwLoopDetectAlarm NOTIFICATION-TYPE
            OBJECTS { hwLoopDetectCfgPortName }
            STATUS current
            DESCRIPTION 
                "The interface is in loopback state."
            ::= { hwLoopDetectTraps 5 }  
            
        -- 1.3.6.1.4.1.2011.25.180.2.6
        hwLoopDetectRecover NOTIFICATION-TYPE
            OBJECTS { hwLoopDetectCfgPortName }
            STATUS current
            DESCRIPTION 
                "The loopback state of the interface is recovered."
            ::= { hwLoopDetectTraps 6 }  

        -- for compile builder     
        -- 1.3.6.1.4.1.2011.25.180.3
        hwLoopDetectGroups OBJECT IDENTIFIER ::= { hwLoopDetectMIB 3 }

        hwLoopDetectCfgEntryGroup OBJECT-GROUP
            OBJECTS{ 
            hwLoopDetectCfgPortName,
              hwLoopDetectCfg,
              hwLoopDetectCfgBlock,        
            hwLoopDetectCfgBlockTime,
            hwLoopDetectCfgPriority,
            hwLoopDetectCfgTrigger,
            hwLoopDetectCfgSta 
            }
           STATUS      current
           DESCRIPTION
               "Entries about the loop detect configuration and blocking state group."
           ::= { hwLoopDetectGroups 1 }    
           
        hwLoopDetectTrapsGroup NOTIFICATION-GROUP
            NOTIFICATIONS 
                    {
                        hwLoopDetectEnabled,  
                        hwLoopDetectDisabled,
                        hwLoopDetectBlocked,
                        hwLoopDetectUnBlocked,
                        hwLoopDetectAlarm,
                        hwLoopDetectRecover
                    }
            STATUS current
            DESCRIPTION 
                "Loop-detect traps group."
            ::= { hwLoopDetectGroups 2 } 
       
        
        -- 1.3.6.1.4.1.2011.25.180.1.4
        hwLoopbackDetectCfgTable OBJECT-TYPE
            SYNTAX SEQUENCE OF HwLoopbackDetectCfgEntry
            MAX-ACCESS not-accessible
            STATUS current
            DESCRIPTION
                "Indicates the table that shows the loop detect configuration and blocking state."
            ::= {hwLoopDetectMIB 4}    
            
        hwLoopbackDetectCfgEntry OBJECT-TYPE
            SYNTAX     HwLoopbackDetectCfgEntry
            MAX-ACCESS not-accessible
            STATUS current
            DESCRIPTION
                "The configuration of loopback detect table."
            INDEX {hwLoopbackDetectCfgPortIndex}
            ::= {hwLoopbackDetectCfgTable 1}
         
          HwLoopbackDetectCfgEntry ::=  
              SEQUENCE { 
              hwLoopbackDetectCfgPortIndex Integer32,
              hwLoopbackDetectCfgPortName OCTET STRING,
              hwLoopbackDetectCfg    EnabledStatus,
              hwLoopbackDetectRowStatus     RowStatus 
          }   
          
          hwLoopbackDetectCfgPortIndex OBJECT-TYPE
              SYNTAX  Integer32 (0..2147483647)
              MAX-ACCESS not-accessible
              STATUS current
              DESCRIPTION
                  "Indicates the interface index."
              ::= {hwLoopbackDetectCfgEntry 1}  
              
          hwLoopbackDetectCfgPortName OBJECT-TYPE
               SYNTAX  OCTET STRING(SIZE (0..80)) 
                   MAX-ACCESS read-only
              STATUS current
              DESCRIPTION
                  "Indicates the interface name."
              ::= {hwLoopbackDetectCfgEntry 12}
              
          hwLoopbackDetectCfg OBJECT-TYPE
              SYNTAX EnabledStatus
              MAX-ACCESS read-only
              STATUS current
              DESCRIPTION
                  "Indicates whether the loop detect function is enabled." 
              ::= {hwLoopbackDetectCfgEntry 13}
              
         hwLoopbackDetectRowStatus  OBJECT-TYPE
              SYNTAX          RowStatus
              MAX-ACCESS      read-create
              STATUS          current
              DESCRIPTION
                  "This object is used to create or delete a row
              and represent the current status of this row.
              Now support state:CreateAndGo,Destroy."
              ::= { hwLoopbackDetectCfgEntry 100}      
            
    END

--
-- HUAWEI-LOOPDETECT-MIB.mib
--
