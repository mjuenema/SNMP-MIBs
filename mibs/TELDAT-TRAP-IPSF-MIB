-- file automatically created


TELDAT-TRAP-IPSF-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


ipsfTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IPSF event subsystem."
    REVISION "201401200930Z"
    DESCRIPTION "Initial implementation"
        ::= { telEventTraps 230 }


ipsfEventsGroup	OBJECT IDENTIFIER	::= { ipsfTrapsMIB 1 }

ipsfNotifications	OBJECT IDENTIFIER	::= { ipsfTrapsMIB 2 }
ipsfNotificationsPrefix	OBJECT IDENTIFIER	::= { ipsfNotifications 0 }

ipsfEventObjects1 OBJECT-IDENTITY
    STATUS current
    DESCRIPTION
        "Event IPSF.1
        Generic abnormal internal error message."
    ::= { ipsfEventsGroup 1 }

ipsf1_message OBJECT-TYPE
    SYNTAX DisplayString
    MAX-ACCESS accessible-for-notify
    STATUS current
    DESCRIPTION
        "Parameter 'message' in event IPSF.1"
    ::= { ipsfEventObjects1 1 }

ipsfEventObjects2 OBJECT-IDENTITY
    STATUS current
    DESCRIPTION
        "Event IPSF.2
        Generic usual internal error message."
    ::= { ipsfEventsGroup 2 }

ipsf2_message OBJECT-TYPE
    SYNTAX DisplayString
    MAX-ACCESS accessible-for-notify
    STATUS current
    DESCRIPTION
        "Parameter 'message' in event IPSF.2"
    ::= { ipsfEventObjects2 1 }

ipsfEventObjects3 OBJECT-IDENTITY
    STATUS current
    DESCRIPTION
        "Event IPSF.3
        Generic abnormal external error message."
    ::= { ipsfEventsGroup 3 }

ipsf3_message OBJECT-TYPE
    SYNTAX DisplayString
    MAX-ACCESS accessible-for-notify
    STATUS current
    DESCRIPTION
        "Parameter 'message' in event IPSF.3"
    ::= { ipsfEventObjects3 1 }

ipsfEventObjects4 OBJECT-IDENTITY
    STATUS current
    DESCRIPTION
        "Event IPSF.4
        Generic usual external error message."
    ::= { ipsfEventsGroup 4 }

ipsf4_message OBJECT-TYPE
    SYNTAX DisplayString
    MAX-ACCESS accessible-for-notify
    STATUS current
    DESCRIPTION
        "Parameter 'message' in event IPSF.4"
    ::= { ipsfEventObjects4 1 }

ipsfEventObjects5 OBJECT-IDENTITY
    STATUS current
    DESCRIPTION
        "Event IPSF.5
        Generic comment on abnormal information message."
    ::= { ipsfEventsGroup 5 }

ipsf5_message OBJECT-TYPE
    SYNTAX DisplayString
    MAX-ACCESS accessible-for-notify
    STATUS current
    DESCRIPTION
        "Parameter 'message' in event IPSF.5"
    ::= { ipsfEventObjects5 1 }

ipsfEventObjects6 OBJECT-IDENTITY
    STATUS current
    DESCRIPTION
        "Event IPSF.6
        Generic comment on usual information message."
    ::= { ipsfEventsGroup 6 }

ipsf6_message OBJECT-TYPE
    SYNTAX DisplayString
    MAX-ACCESS accessible-for-notify
    STATUS current
    DESCRIPTION
        "Parameter 'message' in event IPSF.6"
    ::= { ipsfEventObjects6 1 }

ipsfEventObjects7 OBJECT-IDENTITY
    STATUS current
    DESCRIPTION
        "Event IPSF.7
        Generic packet trace message."
    ::= { ipsfEventsGroup 7 }

ipsf7_message OBJECT-TYPE
    SYNTAX DisplayString
    MAX-ACCESS accessible-for-notify
    STATUS current
    DESCRIPTION
        "Parameter 'message' in event IPSF.7"
    ::= { ipsfEventObjects7 1 }

ipsfEventObjects8 OBJECT-IDENTITY
    STATUS current
    DESCRIPTION
        "Event IPSF.8
        Generic abnormal operation trace message."
    ::= { ipsfEventsGroup 8 }

ipsf8_message OBJECT-TYPE
    SYNTAX DisplayString
    MAX-ACCESS accessible-for-notify
    STATUS current
    DESCRIPTION
        "Parameter 'message' in event IPSF.8"
    ::= { ipsfEventObjects8 1 }

ipsfEventObjects9 OBJECT-IDENTITY
    STATUS current
    DESCRIPTION
        "Event IPSF.9
        Generic usual operation trace message."
    ::= { ipsfEventsGroup 9 }

ipsf9_message OBJECT-TYPE
    SYNTAX DisplayString
    MAX-ACCESS accessible-for-notify
    STATUS current
    DESCRIPTION
        "Parameter 'message' in event IPSF.9"
    ::= { ipsfEventObjects9 1 }

ipsfEventObjects10 OBJECT-IDENTITY
    STATUS current
    DESCRIPTION
        "Event IPSF.10
        The generic event level is wrong."
    ::= { ipsfEventsGroup 10 }

ipsf10_event_level OBJECT-TYPE
    SYNTAX Integer32
    MAX-ACCESS accessible-for-notify
    STATUS current
    DESCRIPTION
        "Parameter 'event_level' in event IPSF.10"
    ::= { ipsfEventObjects10 1 }

ipsf10_message OBJECT-TYPE
    SYNTAX DisplayString
    MAX-ACCESS accessible-for-notify
    STATUS current
    DESCRIPTION
        "Parameter 'message' in event IPSF.10"
    ::= { ipsfEventObjects10 2 }

ipsfEventObjects11 OBJECT-IDENTITY
    STATUS current
    DESCRIPTION
        "Event IPSF.11
        A new peer has been added to the session list."
    ::= { ipsfEventsGroup 11 }

ipsf11_peerID OBJECT-TYPE
    SYNTAX Integer32
    MAX-ACCESS accessible-for-notify
    STATUS current
    DESCRIPTION
        "Parameter 'peerID' in event IPSF.11"
    ::= { ipsfEventObjects11 1 }

ipsf11_SID OBJECT-TYPE
    SYNTAX DisplayString
    MAX-ACCESS accessible-for-notify
    STATUS current
    DESCRIPTION
        "Parameter 'SID' in event IPSF.11"
    ::= { ipsfEventObjects11 2 }

ipsf11_SID_value OBJECT-TYPE
    SYNTAX Integer32
    MAX-ACCESS accessible-for-notify
    STATUS current
    DESCRIPTION
        "Parameter 'SID_value' in event IPSF.11"
    ::= { ipsfEventObjects11 3 }

ipsfEventObjects12 OBJECT-IDENTITY
    STATUS current
    DESCRIPTION
        "Event IPSF.12
        A peer has been deleted from the session list."
    ::= { ipsfEventsGroup 12 }

ipsf12_peerID OBJECT-TYPE
    SYNTAX Integer32
    MAX-ACCESS accessible-for-notify
    STATUS current
    DESCRIPTION
        "Parameter 'peerID' in event IPSF.12"
    ::= { ipsfEventObjects12 1 }

ipsf12_SID OBJECT-TYPE
    SYNTAX DisplayString
    MAX-ACCESS accessible-for-notify
    STATUS current
    DESCRIPTION
        "Parameter 'SID' in event IPSF.12"
    ::= { ipsfEventObjects12 2 }

ipsf12_SID_value OBJECT-TYPE
    SYNTAX Integer32
    MAX-ACCESS accessible-for-notify
    STATUS current
    DESCRIPTION
        "Parameter 'SID_value' in event IPSF.12"
    ::= { ipsfEventObjects12 3 }

ipsfEventObjects13 OBJECT-IDENTITY
    STATUS current
    DESCRIPTION
        "Event IPSF.13
        The specified message could not be sent to IPSecFT queue."
    ::= { ipsfEventsGroup 13 }

ipsf13_type OBJECT-TYPE
    SYNTAX DisplayString
    MAX-ACCESS accessible-for-notify
    STATUS current
    DESCRIPTION
        "Parameter 'type' in event IPSF.13"
    ::= { ipsfEventObjects13 1 }

ipsf13_reason OBJECT-TYPE
    SYNTAX DisplayString
    MAX-ACCESS accessible-for-notify
    STATUS current
    DESCRIPTION
        "Parameter 'reason' in event IPSF.13"
    ::= { ipsfEventObjects13 2 }

ipsfEventObjects14 OBJECT-IDENTITY
    STATUS current
    DESCRIPTION
        "Event IPSF.14
        The specified message has been sent to IPSecFT queue."
    ::= { ipsfEventsGroup 14 }

ipsf14_type OBJECT-TYPE
    SYNTAX DisplayString
    MAX-ACCESS accessible-for-notify
    STATUS current
    DESCRIPTION
        "Parameter 'type' in event IPSF.14"
    ::= { ipsfEventObjects14 1 }

ipsfEventObjects15 OBJECT-IDENTITY
    STATUS current
    DESCRIPTION
        "Event IPSF.15
        The specified task has been created."
    ::= { ipsfEventsGroup 15 }

ipsf15_task_name OBJECT-TYPE
    SYNTAX DisplayString
    MAX-ACCESS accessible-for-notify
    STATUS current
    DESCRIPTION
        "Parameter 'task_name' in event IPSF.15"
    ::= { ipsfEventObjects15 1 }

ipsfEventObjects16 OBJECT-IDENTITY
    STATUS current
    DESCRIPTION
        "Event IPSF.16
        The specified session has change its state."
    ::= { ipsfEventsGroup 16 }

ipsf16_current_state OBJECT-TYPE
    SYNTAX DisplayString
    MAX-ACCESS accessible-for-notify
    STATUS current
    DESCRIPTION
        "Parameter 'current_state' in event IPSF.16"
    ::= { ipsfEventObjects16 1 }

ipsf16_new_state OBJECT-TYPE
    SYNTAX DisplayString
    MAX-ACCESS accessible-for-notify
    STATUS current
    DESCRIPTION
        "Parameter 'new_state' in event IPSF.16"
    ::= { ipsfEventObjects16 2 }

ipsf16_SID OBJECT-TYPE
    SYNTAX DisplayString
    MAX-ACCESS accessible-for-notify
    STATUS current
    DESCRIPTION
        "Parameter 'SID' in event IPSF.16"
    ::= { ipsfEventObjects16 3 }

ipsf16_SID_value OBJECT-TYPE
    SYNTAX Integer32
    MAX-ACCESS accessible-for-notify
    STATUS current
    DESCRIPTION
        "Parameter 'SID_value' in event IPSF.16"
    ::= { ipsfEventObjects16 4 }

ipsfEventObjects17 OBJECT-IDENTITY
    STATUS current
    DESCRIPTION
        "Event IPSF.17
        The specified session will change its state."
    ::= { ipsfEventsGroup 17 }

ipsf17_timeout OBJECT-TYPE
    SYNTAX Integer32
    MAX-ACCESS accessible-for-notify
    STATUS current
    DESCRIPTION
        "Parameter 'timeout' in event IPSF.17"
    ::= { ipsfEventObjects17 1 }

ipsf17_current_state OBJECT-TYPE
    SYNTAX DisplayString
    MAX-ACCESS accessible-for-notify
    STATUS current
    DESCRIPTION
        "Parameter 'current_state' in event IPSF.17"
    ::= { ipsfEventObjects17 2 }

ipsf17_new_state OBJECT-TYPE
    SYNTAX DisplayString
    MAX-ACCESS accessible-for-notify
    STATUS current
    DESCRIPTION
        "Parameter 'new_state' in event IPSF.17"
    ::= { ipsfEventObjects17 3 }

ipsf17_SID OBJECT-TYPE
    SYNTAX DisplayString
    MAX-ACCESS accessible-for-notify
    STATUS current
    DESCRIPTION
        "Parameter 'SID' in event IPSF.17"
    ::= { ipsfEventObjects17 4 }

ipsf17_SID_value OBJECT-TYPE
    SYNTAX Integer32
    MAX-ACCESS accessible-for-notify
    STATUS current
    DESCRIPTION
        "Parameter 'SID_value' in event IPSF.17"
    ::= { ipsfEventObjects17 5 }

ipsfEventObjects18 OBJECT-IDENTITY
    STATUS current
    DESCRIPTION
        "Event IPSF.18
        The specified session is connecting."
    ::= { ipsfEventsGroup 18 }

ipsf18_src_addr OBJECT-TYPE
    SYNTAX IpAddress
    MAX-ACCESS accessible-for-notify
    STATUS current
    DESCRIPTION
        "Parameter 'src_addr' in event IPSF.18"
    ::= { ipsfEventObjects18 1 }

ipsf18_src_port OBJECT-TYPE
    SYNTAX Integer32
    MAX-ACCESS accessible-for-notify
    STATUS current
    DESCRIPTION
        "Parameter 'src_port' in event IPSF.18"
    ::= { ipsfEventObjects18 2 }

ipsf18_dst_addr OBJECT-TYPE
    SYNTAX IpAddress
    MAX-ACCESS accessible-for-notify
    STATUS current
    DESCRIPTION
        "Parameter 'dst_addr' in event IPSF.18"
    ::= { ipsfEventObjects18 3 }

ipsf18_dst_port OBJECT-TYPE
    SYNTAX Integer32
    MAX-ACCESS accessible-for-notify
    STATUS current
    DESCRIPTION
        "Parameter 'dst_port' in event IPSF.18"
    ::= { ipsfEventObjects18 4 }

ipsf18_timeout OBJECT-TYPE
    SYNTAX Integer32
    MAX-ACCESS accessible-for-notify
    STATUS current
    DESCRIPTION
        "Parameter 'timeout' in event IPSF.18"
    ::= { ipsfEventObjects18 5 }

ipsf18_SID OBJECT-TYPE
    SYNTAX DisplayString
    MAX-ACCESS accessible-for-notify
    STATUS current
    DESCRIPTION
        "Parameter 'SID' in event IPSF.18"
    ::= { ipsfEventObjects18 6 }

ipsf18_SID_value OBJECT-TYPE
    SYNTAX Integer32
    MAX-ACCESS accessible-for-notify
    STATUS current
    DESCRIPTION
        "Parameter 'SID_value' in event IPSF.18"
    ::= { ipsfEventObjects18 7 }

ipsfEventObjects19 OBJECT-IDENTITY
    STATUS current
    DESCRIPTION
        "Event IPSF.19
        IPSecFT has been started as specified type."
    ::= { ipsfEventsGroup 19 }

ipsf19_type OBJECT-TYPE
    SYNTAX DisplayString
    MAX-ACCESS accessible-for-notify
    STATUS current
    DESCRIPTION
        "Parameter 'type' in event IPSF.19"
    ::= { ipsfEventObjects19 1 }

ipsfEventObjects20 OBJECT-IDENTITY
    STATUS current
    DESCRIPTION
        "Event IPSF.20
        The specified process is being restarted."
    ::= { ipsfEventsGroup 20 }

ipsf20_process OBJECT-TYPE
    SYNTAX DisplayString
    MAX-ACCESS accessible-for-notify
    STATUS current
    DESCRIPTION
        "Parameter 'process' in event IPSF.20"
    ::= { ipsfEventObjects20 1 }

ipsfEventObjects21 OBJECT-IDENTITY
    STATUS current
    DESCRIPTION
        "Event IPSF.21
        The TCP connection has been established."
    ::= { ipsfEventsGroup 21 }

ipsf21_SID_value OBJECT-TYPE
    SYNTAX Integer32
    MAX-ACCESS accessible-for-notify
    STATUS current
    DESCRIPTION
        "Parameter 'SID_value' in event IPSF.21"
    ::= { ipsfEventObjects21 1 }

ipsfEventObjects22 OBJECT-IDENTITY
    STATUS current
    DESCRIPTION
        "Event IPSF.22
        The specified event has been received."
    ::= { ipsfEventsGroup 22 }

ipsf22_event OBJECT-TYPE
    SYNTAX DisplayString
    MAX-ACCESS accessible-for-notify
    STATUS current
    DESCRIPTION
        "Parameter 'event' in event IPSF.22"
    ::= { ipsfEventObjects22 1 }

ipsf22_current_state OBJECT-TYPE
    SYNTAX DisplayString
    MAX-ACCESS accessible-for-notify
    STATUS current
    DESCRIPTION
        "Parameter 'current_state' in event IPSF.22"
    ::= { ipsfEventObjects22 2 }

ipsf22_SID OBJECT-TYPE
    SYNTAX DisplayString
    MAX-ACCESS accessible-for-notify
    STATUS current
    DESCRIPTION
        "Parameter 'SID' in event IPSF.22"
    ::= { ipsfEventObjects22 3 }

ipsf22_SID_value OBJECT-TYPE
    SYNTAX Integer32
    MAX-ACCESS accessible-for-notify
    STATUS current
    DESCRIPTION
        "Parameter 'SID_value' in event IPSF.22"
    ::= { ipsfEventObjects22 4 }

ipsfEventObjects23 OBJECT-IDENTITY
    STATUS current
    DESCRIPTION
        "Event IPSF.23
        The specified packet has been sent."
    ::= { ipsfEventsGroup 23 }

ipsf23_packet_type OBJECT-TYPE
    SYNTAX DisplayString
    MAX-ACCESS accessible-for-notify
    STATUS current
    DESCRIPTION
        "Parameter 'packet_type' in event IPSF.23"
    ::= { ipsfEventObjects23 1 }

ipsf23_len OBJECT-TYPE
    SYNTAX Integer32
    MAX-ACCESS accessible-for-notify
    STATUS current
    DESCRIPTION
        "Parameter 'len' in event IPSF.23"
    ::= { ipsfEventObjects23 2 }

ipsf23_SID OBJECT-TYPE
    SYNTAX DisplayString
    MAX-ACCESS accessible-for-notify
    STATUS current
    DESCRIPTION
        "Parameter 'SID' in event IPSF.23"
    ::= { ipsfEventObjects23 3 }

ipsf23_SID_value OBJECT-TYPE
    SYNTAX Integer32
    MAX-ACCESS accessible-for-notify
    STATUS current
    DESCRIPTION
        "Parameter 'SID_value' in event IPSF.23"
    ::= { ipsfEventObjects23 4 }

ipsfEventObjects24 OBJECT-IDENTITY
    STATUS current
    DESCRIPTION
        "Event IPSF.24
        IPSecFT is listening for incoming data."
    ::= { ipsfEventsGroup 24 }

ipsf24_timeout OBJECT-TYPE
    SYNTAX Integer32
    MAX-ACCESS accessible-for-notify
    STATUS current
    DESCRIPTION
        "Parameter 'timeout' in event IPSF.24"
    ::= { ipsfEventObjects24 1 }

ipsf24_interval OBJECT-TYPE
    SYNTAX DisplayString
    MAX-ACCESS accessible-for-notify
    STATUS current
    DESCRIPTION
        "Parameter 'interval' in event IPSF.24"
    ::= { ipsfEventObjects24 2 }

ipsf24_SID OBJECT-TYPE
    SYNTAX DisplayString
    MAX-ACCESS accessible-for-notify
    STATUS current
    DESCRIPTION
        "Parameter 'SID' in event IPSF.24"
    ::= { ipsfEventObjects24 3 }

ipsf24_SID_value OBJECT-TYPE
    SYNTAX Integer32
    MAX-ACCESS accessible-for-notify
    STATUS current
    DESCRIPTION
        "Parameter 'SID_value' in event IPSF.24"
    ::= { ipsfEventObjects24 4 }

ipsfEventObjects25 OBJECT-IDENTITY
    STATUS current
    DESCRIPTION
        "Event IPSF.25
        The ACK is wrong."
    ::= { ipsfEventsGroup 25 }

ipsf25_reason OBJECT-TYPE
    SYNTAX DisplayString
    MAX-ACCESS accessible-for-notify
    STATUS current
    DESCRIPTION
        "Parameter 'reason' in event IPSF.25"
    ::= { ipsfEventObjects25 1 }

ipsf25_SID OBJECT-TYPE
    SYNTAX DisplayString
    MAX-ACCESS accessible-for-notify
    STATUS current
    DESCRIPTION
        "Parameter 'SID' in event IPSF.25"
    ::= { ipsfEventObjects25 2 }

ipsf25_SID_value OBJECT-TYPE
    SYNTAX Integer32
    MAX-ACCESS accessible-for-notify
    STATUS current
    DESCRIPTION
        "Parameter 'SID_value' in event IPSF.25"
    ::= { ipsfEventObjects25 3 }

ipsfEventObjects26 OBJECT-IDENTITY
    STATUS current
    DESCRIPTION
        "Event IPSF.26
        The specified IP has been inherited."
    ::= { ipsfEventsGroup 26 }

ipsf26_IP OBJECT-TYPE
    SYNTAX IpAddress
    MAX-ACCESS accessible-for-notify
    STATUS current
    DESCRIPTION
        "Parameter 'IP' in event IPSF.26"
    ::= { ipsfEventObjects26 1 }

ipsf26_SID OBJECT-TYPE
    SYNTAX DisplayString
    MAX-ACCESS accessible-for-notify
    STATUS current
    DESCRIPTION
        "Parameter 'SID' in event IPSF.26"
    ::= { ipsfEventObjects26 2 }

ipsf26_SID_value OBJECT-TYPE
    SYNTAX Integer32
    MAX-ACCESS accessible-for-notify
    STATUS current
    DESCRIPTION
        "Parameter 'SID_value' in event IPSF.26"
    ::= { ipsfEventObjects26 3 }

ipsfEventObjects27 OBJECT-IDENTITY
    STATUS current
    DESCRIPTION
        "Event IPSF.27
        Keepalive packet will be sent at the specified time."
    ::= { ipsfEventsGroup 27 }

ipsf27_timer OBJECT-TYPE
    SYNTAX Integer32
    MAX-ACCESS accessible-for-notify
    STATUS current
    DESCRIPTION
        "Parameter 'timer' in event IPSF.27"
    ::= { ipsfEventObjects27 1 }

ipsf27_SID OBJECT-TYPE
    SYNTAX DisplayString
    MAX-ACCESS accessible-for-notify
    STATUS current
    DESCRIPTION
        "Parameter 'SID' in event IPSF.27"
    ::= { ipsfEventObjects27 2 }

ipsf27_SID_value OBJECT-TYPE
    SYNTAX Integer32
    MAX-ACCESS accessible-for-notify
    STATUS current
    DESCRIPTION
        "Parameter 'SID_value' in event IPSF.27"
    ::= { ipsfEventObjects27 3 }

ipsfEventObjects28 OBJECT-IDENTITY
    STATUS current
    DESCRIPTION
        "Event IPSF.28
        IPSecFT is retrieving queued elements."
    ::= { ipsfEventsGroup 28 }

ipsf28_SID OBJECT-TYPE
    SYNTAX DisplayString
    MAX-ACCESS accessible-for-notify
    STATUS current
    DESCRIPTION
        "Parameter 'SID' in event IPSF.28"
    ::= { ipsfEventObjects28 1 }

ipsf28_SID_value OBJECT-TYPE
    SYNTAX Integer32
    MAX-ACCESS accessible-for-notify
    STATUS current
    DESCRIPTION
        "Parameter 'SID_value' in event IPSF.28"
    ::= { ipsfEventObjects28 2 }

ipsfEventObjects29 OBJECT-IDENTITY
    STATUS current
    DESCRIPTION
        "Event IPSF.29
        The specified session has been established."
    ::= { ipsfEventsGroup 29 }

ipsf29_SID OBJECT-TYPE
    SYNTAX DisplayString
    MAX-ACCESS accessible-for-notify
    STATUS current
    DESCRIPTION
        "Parameter 'SID' in event IPSF.29"
    ::= { ipsfEventObjects29 1 }

ipsf29_SID_value OBJECT-TYPE
    SYNTAX Integer32
    MAX-ACCESS accessible-for-notify
    STATUS current
    DESCRIPTION
        "Parameter 'SID_value' in event IPSF.29"
    ::= { ipsfEventObjects29 2 }

ipsfEventObjects30 OBJECT-IDENTITY
    STATUS current
    DESCRIPTION
        "Event IPSF.30
        IPSecFT is waiting for incoming connections."
    ::= { ipsfEventsGroup 30 }

ipsf30_local_addr OBJECT-TYPE
    SYNTAX IpAddress
    MAX-ACCESS accessible-for-notify
    STATUS current
    DESCRIPTION
        "Parameter 'local_addr' in event IPSF.30"
    ::= { ipsfEventObjects30 1 }

ipsf30_local_port OBJECT-TYPE
    SYNTAX Integer32
    MAX-ACCESS accessible-for-notify
    STATUS current
    DESCRIPTION
        "Parameter 'local_port' in event IPSF.30"
    ::= { ipsfEventObjects30 2 }

ipsfEventObjects31 OBJECT-IDENTITY
    STATUS current
    DESCRIPTION
        "Event IPSF.31
        A TCP connection has been accepted."
    ::= { ipsfEventsGroup 31 }

ipsf31_remote_addr OBJECT-TYPE
    SYNTAX IpAddress
    MAX-ACCESS accessible-for-notify
    STATUS current
    DESCRIPTION
        "Parameter 'remote_addr' in event IPSF.31"
    ::= { ipsfEventObjects31 1 }

ipsf31_remote_port OBJECT-TYPE
    SYNTAX Integer32
    MAX-ACCESS accessible-for-notify
    STATUS current
    DESCRIPTION
        "Parameter 'remote_port' in event IPSF.31"
    ::= { ipsfEventObjects31 2 }

ipsf31_local_addr OBJECT-TYPE
    SYNTAX IpAddress
    MAX-ACCESS accessible-for-notify
    STATUS current
    DESCRIPTION
        "Parameter 'local_addr' in event IPSF.31"
    ::= { ipsfEventObjects31 3 }

ipsf31_local_port OBJECT-TYPE
    SYNTAX Integer32
    MAX-ACCESS accessible-for-notify
    STATUS current
    DESCRIPTION
        "Parameter 'local_port' in event IPSF.31"
    ::= { ipsfEventObjects31 4 }

ipsf31_internalID OBJECT-TYPE
    SYNTAX DisplayString
    MAX-ACCESS accessible-for-notify
    STATUS current
    DESCRIPTION
        "Parameter 'internalID' in event IPSF.31"
    ::= { ipsfEventObjects31 5 }

ipsf31_internalID_value OBJECT-TYPE
    SYNTAX Integer32
    MAX-ACCESS accessible-for-notify
    STATUS current
    DESCRIPTION
        "Parameter 'internalID_value' in event IPSF.31"
    ::= { ipsfEventObjects31 6 }

ipsfEventObjects32 OBJECT-IDENTITY
    STATUS current
    DESCRIPTION
        "Event IPSF.32
        A TCP connection has been closed."
    ::= { ipsfEventsGroup 32 }

ipsf32_source_addr OBJECT-TYPE
    SYNTAX IpAddress
    MAX-ACCESS accessible-for-notify
    STATUS current
    DESCRIPTION
        "Parameter 'source_addr' in event IPSF.32"
    ::= { ipsfEventObjects32 1 }

ipsf32_source_port OBJECT-TYPE
    SYNTAX Integer32
    MAX-ACCESS accessible-for-notify
    STATUS current
    DESCRIPTION
        "Parameter 'source_port' in event IPSF.32"
    ::= { ipsfEventObjects32 2 }

ipsf32_destination_addr OBJECT-TYPE
    SYNTAX IpAddress
    MAX-ACCESS accessible-for-notify
    STATUS current
    DESCRIPTION
        "Parameter 'destination_addr' in event IPSF.32"
    ::= { ipsfEventObjects32 3 }

ipsf32_destination_port OBJECT-TYPE
    SYNTAX Integer32
    MAX-ACCESS accessible-for-notify
    STATUS current
    DESCRIPTION
        "Parameter 'destination_port' in event IPSF.32"
    ::= { ipsfEventObjects32 4 }

ipsf32_SID OBJECT-TYPE
    SYNTAX DisplayString
    MAX-ACCESS accessible-for-notify
    STATUS current
    DESCRIPTION
        "Parameter 'SID' in event IPSF.32"
    ::= { ipsfEventObjects32 5 }

ipsf32_SID_value OBJECT-TYPE
    SYNTAX Integer32
    MAX-ACCESS accessible-for-notify
    STATUS current
    DESCRIPTION
        "Parameter 'SID_value' in event IPSF.32"
    ::= { ipsfEventObjects32 6 }

ipsfEventObjects33 OBJECT-IDENTITY
    STATUS current
    DESCRIPTION
        "Event IPSF.33
        The specified data length has been received."
    ::= { ipsfEventsGroup 33 }

ipsf33_length OBJECT-TYPE
    SYNTAX Integer32
    MAX-ACCESS accessible-for-notify
    STATUS current
    DESCRIPTION
        "Parameter 'length' in event IPSF.33"
    ::= { ipsfEventObjects33 1 }

ipsf33_SID OBJECT-TYPE
    SYNTAX DisplayString
    MAX-ACCESS accessible-for-notify
    STATUS current
    DESCRIPTION
        "Parameter 'SID' in event IPSF.33"
    ::= { ipsfEventObjects33 2 }

ipsf33_SID_value OBJECT-TYPE
    SYNTAX Integer32
    MAX-ACCESS accessible-for-notify
    STATUS current
    DESCRIPTION
        "Parameter 'SID_value' in event IPSF.33"
    ::= { ipsfEventObjects33 3 }

ipsfEventObjects34 OBJECT-IDENTITY
    STATUS current
    DESCRIPTION
        "Event IPSF.34
        The specified packet has been received."
    ::= { ipsfEventsGroup 34 }

ipsf34_packet_type OBJECT-TYPE
    SYNTAX DisplayString
    MAX-ACCESS accessible-for-notify
    STATUS current
    DESCRIPTION
        "Parameter 'packet_type' in event IPSF.34"
    ::= { ipsfEventObjects34 1 }

ipsf34_SID OBJECT-TYPE
    SYNTAX DisplayString
    MAX-ACCESS accessible-for-notify
    STATUS current
    DESCRIPTION
        "Parameter 'SID' in event IPSF.34"
    ::= { ipsfEventObjects34 2 }

ipsf34_SID_value OBJECT-TYPE
    SYNTAX Integer32
    MAX-ACCESS accessible-for-notify
    STATUS current
    DESCRIPTION
        "Parameter 'SID_value' in event IPSF.34"
    ::= { ipsfEventObjects34 3 }

ipsfEventObjects35 OBJECT-IDENTITY
    STATUS current
    DESCRIPTION
        "Event IPSF.35
        The callback for writing was successful."
    ::= { ipsfEventsGroup 35 }

ipsf35_length OBJECT-TYPE
    SYNTAX Integer32
    MAX-ACCESS accessible-for-notify
    STATUS current
    DESCRIPTION
        "Parameter 'length' in event IPSF.35"
    ::= { ipsfEventObjects35 1 }

ipsf35_SID OBJECT-TYPE
    SYNTAX DisplayString
    MAX-ACCESS accessible-for-notify
    STATUS current
    DESCRIPTION
        "Parameter 'SID' in event IPSF.35"
    ::= { ipsfEventObjects35 2 }

ipsf35_SID_value OBJECT-TYPE
    SYNTAX Integer32
    MAX-ACCESS accessible-for-notify
    STATUS current
    DESCRIPTION
        "Parameter 'SID_value' in event IPSF.35"
    ::= { ipsfEventObjects35 3 }

ipsfEventObjects36 OBJECT-IDENTITY
    STATUS current
    DESCRIPTION
        "Event IPSF.36
        IPSecFT as backup server has inherited the tunnels."
    ::= { ipsfEventsGroup 36 }

ipsf36_tunnels OBJECT-TYPE
    SYNTAX Integer32
    MAX-ACCESS accessible-for-notify
    STATUS current
    DESCRIPTION
        "Parameter 'tunnels' in event IPSF.36"
    ::= { ipsfEventObjects36 1 }

ipsf36_SID OBJECT-TYPE
    SYNTAX DisplayString
    MAX-ACCESS accessible-for-notify
    STATUS current
    DESCRIPTION
        "Parameter 'SID' in event IPSF.36"
    ::= { ipsfEventObjects36 2 }

ipsf36_SID_value OBJECT-TYPE
    SYNTAX Integer32
    MAX-ACCESS accessible-for-notify
    STATUS current
    DESCRIPTION
        "Parameter 'SID_value' in event IPSF.36"
    ::= { ipsfEventObjects36 3 }

ipsfEventObjects37 OBJECT-IDENTITY
    STATUS current
    DESCRIPTION
        "Event IPSF.37
        The specified session will be finished."
    ::= { ipsfEventsGroup 37 }

ipsf37_internalID OBJECT-TYPE
    SYNTAX DisplayString
    MAX-ACCESS accessible-for-notify
    STATUS current
    DESCRIPTION
        "Parameter 'internalID' in event IPSF.37"
    ::= { ipsfEventObjects37 1 }

ipsf37_internalID_value OBJECT-TYPE
    SYNTAX Integer32
    MAX-ACCESS accessible-for-notify
    STATUS current
    DESCRIPTION
        "Parameter 'internalID_value' in event IPSF.37"
    ::= { ipsfEventObjects37 2 }

ipsf37_SID OBJECT-TYPE
    SYNTAX DisplayString
    MAX-ACCESS accessible-for-notify
    STATUS current
    DESCRIPTION
        "Parameter 'SID' in event IPSF.37"
    ::= { ipsfEventObjects37 3 }

ipsf37_SID_value OBJECT-TYPE
    SYNTAX Integer32
    MAX-ACCESS accessible-for-notify
    STATUS current
    DESCRIPTION
        "Parameter 'SID_value' in event IPSF.37"
    ::= { ipsfEventObjects37 4 }

ipsfEventObjects38 OBJECT-IDENTITY
    STATUS current
    DESCRIPTION
        "Event IPSF.38
        Timeout in keepalive timer."
    ::= { ipsfEventsGroup 38 }

ipsf38_SID OBJECT-TYPE
    SYNTAX DisplayString
    MAX-ACCESS accessible-for-notify
    STATUS current
    DESCRIPTION
        "Parameter 'SID' in event IPSF.38"
    ::= { ipsfEventObjects38 1 }

ipsf38_SID_value OBJECT-TYPE
    SYNTAX Integer32
    MAX-ACCESS accessible-for-notify
    STATUS current
    DESCRIPTION
        "Parameter 'SID_value' in event IPSF.38"
    ::= { ipsfEventObjects38 2 }

ipsfEventObjects39 OBJECT-IDENTITY
    STATUS current
    DESCRIPTION
        "Event IPSF.39
        The timer for keepalive transmission has been deleted."
    ::= { ipsfEventsGroup 39 }

ipsf39_SID OBJECT-TYPE
    SYNTAX DisplayString
    MAX-ACCESS accessible-for-notify
    STATUS current
    DESCRIPTION
        "Parameter 'SID' in event IPSF.39"
    ::= { ipsfEventObjects39 1 }

ipsf39_SID_value OBJECT-TYPE
    SYNTAX Integer32
    MAX-ACCESS accessible-for-notify
    STATUS current
    DESCRIPTION
        "Parameter 'SID_value' in event IPSF.39"
    ::= { ipsfEventObjects39 2 }

ipsfEventObjects40 OBJECT-IDENTITY
    STATUS current
    DESCRIPTION
        "Event IPSF.40
        The configuration has changed."
    ::= { ipsfEventsGroup 40 }

ipsf40_current_state OBJECT-TYPE
    SYNTAX DisplayString
    MAX-ACCESS accessible-for-notify
    STATUS current
    DESCRIPTION
        "Parameter 'current_state' in event IPSF.40"
    ::= { ipsfEventObjects40 1 }

ipsf40_event OBJECT-TYPE
    SYNTAX DisplayString
    MAX-ACCESS accessible-for-notify
    STATUS current
    DESCRIPTION
        "Parameter 'event' in event IPSF.40"
    ::= { ipsfEventObjects40 2 }

ipsf40_SID OBJECT-TYPE
    SYNTAX DisplayString
    MAX-ACCESS accessible-for-notify
    STATUS current
    DESCRIPTION
        "Parameter 'SID' in event IPSF.40"
    ::= { ipsfEventObjects40 3 }

ipsf40_SID_value OBJECT-TYPE
    SYNTAX Integer32
    MAX-ACCESS accessible-for-notify
    STATUS current
    DESCRIPTION
        "Parameter 'SID_value' in event IPSF.40"
    ::= { ipsfEventObjects40 4 }

ipsfEventObjects41 OBJECT-IDENTITY
    STATUS current
    DESCRIPTION
        "Event IPSF.41
        An innocuous event has been received."
    ::= { ipsfEventsGroup 41 }

ipsf41_current_state OBJECT-TYPE
    SYNTAX DisplayString
    MAX-ACCESS accessible-for-notify
    STATUS current
    DESCRIPTION
        "Parameter 'current_state' in event IPSF.41"
    ::= { ipsfEventObjects41 1 }

ipsf41_event OBJECT-TYPE
    SYNTAX DisplayString
    MAX-ACCESS accessible-for-notify
    STATUS current
    DESCRIPTION
        "Parameter 'event' in event IPSF.41"
    ::= { ipsfEventObjects41 2 }

ipsf41_SID OBJECT-TYPE
    SYNTAX DisplayString
    MAX-ACCESS accessible-for-notify
    STATUS current
    DESCRIPTION
        "Parameter 'SID' in event IPSF.41"
    ::= { ipsfEventObjects41 3 }

ipsf41_SID_value OBJECT-TYPE
    SYNTAX Integer32
    MAX-ACCESS accessible-for-notify
    STATUS current
    DESCRIPTION
        "Parameter 'SID_value' in event IPSF.41"
    ::= { ipsfEventObjects41 4 }

ipsfEventObjects42 OBJECT-IDENTITY
    STATUS current
    DESCRIPTION
        "Event IPSF.42
        The specified task has been suspended."
    ::= { ipsfEventsGroup 42 }

ipsf42_task_name OBJECT-TYPE
    SYNTAX DisplayString
    MAX-ACCESS accessible-for-notify
    STATUS current
    DESCRIPTION
        "Parameter 'task_name' in event IPSF.42"
    ::= { ipsfEventObjects42 1 }

ipsfEventObjects43 OBJECT-IDENTITY
    STATUS current
    DESCRIPTION
        "Event IPSF.43
        The specified task has been resumed."
    ::= { ipsfEventsGroup 43 }

ipsf43_task_name OBJECT-TYPE
    SYNTAX DisplayString
    MAX-ACCESS accessible-for-notify
    STATUS current
    DESCRIPTION
        "Parameter 'task_name' in event IPSF.43"
    ::= { ipsfEventObjects43 1 }

ipsfEventObjects44 OBJECT-IDENTITY
    STATUS current
    DESCRIPTION
        "Event IPSF.44
        Sending signal to IPSec to inherit the specified tunnel."
    ::= { ipsfEventsGroup 44 }

ipsf44_peerID OBJECT-TYPE
    SYNTAX Integer32
    MAX-ACCESS accessible-for-notify
    STATUS current
    DESCRIPTION
        "Parameter 'peerID' in event IPSF.44"
    ::= { ipsfEventObjects44 1 }

ipsf44_ep_dest OBJECT-TYPE
    SYNTAX IpAddress
    MAX-ACCESS accessible-for-notify
    STATUS current
    DESCRIPTION
        "Parameter 'ep_dest' in event IPSF.44"
    ::= { ipsfEventObjects44 2 }

ipsf44_client_dest OBJECT-TYPE
    SYNTAX IpAddress
    MAX-ACCESS accessible-for-notify
    STATUS current
    DESCRIPTION
        "Parameter 'client_dest' in event IPSF.44"
    ::= { ipsfEventObjects44 3 }

ipsf44_SID OBJECT-TYPE
    SYNTAX DisplayString
    MAX-ACCESS accessible-for-notify
    STATUS current
    DESCRIPTION
        "Parameter 'SID' in event IPSF.44"
    ::= { ipsfEventObjects44 4 }

ipsf44_SID_value OBJECT-TYPE
    SYNTAX Integer32
    MAX-ACCESS accessible-for-notify
    STATUS current
    DESCRIPTION
        "Parameter 'SID_value' in event IPSF.44"
    ::= { ipsfEventObjects44 5 }

ipsfEventObjects45 OBJECT-IDENTITY
    STATUS current
    DESCRIPTION
        "Event IPSF.45
        Event delete list has been received."
    ::= { ipsfEventsGroup 45 }

ipsf45_current_state OBJECT-TYPE
    SYNTAX DisplayString
    MAX-ACCESS accessible-for-notify
    STATUS current
    DESCRIPTION
        "Parameter 'current_state' in event IPSF.45"
    ::= { ipsfEventObjects45 1 }

ipsf45_event OBJECT-TYPE
    SYNTAX DisplayString
    MAX-ACCESS accessible-for-notify
    STATUS current
    DESCRIPTION
        "Parameter 'event' in event IPSF.45"
    ::= { ipsfEventObjects45 2 }

ipsf45_SID OBJECT-TYPE
    SYNTAX DisplayString
    MAX-ACCESS accessible-for-notify
    STATUS current
    DESCRIPTION
        "Parameter 'SID' in event IPSF.45"
    ::= { ipsfEventObjects45 3 }

ipsf45_SID_value OBJECT-TYPE
    SYNTAX Integer32
    MAX-ACCESS accessible-for-notify
    STATUS current
    DESCRIPTION
        "Parameter 'SID_value' in event IPSF.45"
    ::= { ipsfEventObjects45 4 }

ipsfEventObjects46 OBJECT-IDENTITY
    STATUS current
    DESCRIPTION
        "Event IPSF.46
        Deleting IPSec sessions with the specified source IP address."
    ::= { ipsfEventsGroup 46 }

ipsf46_IP OBJECT-TYPE
    SYNTAX IpAddress
    MAX-ACCESS accessible-for-notify
    STATUS current
    DESCRIPTION
        "Parameter 'IP' in event IPSF.46"
    ::= { ipsfEventObjects46 1 }

ipsf46_SID OBJECT-TYPE
    SYNTAX DisplayString
    MAX-ACCESS accessible-for-notify
    STATUS current
    DESCRIPTION
        "Parameter 'SID' in event IPSF.46"
    ::= { ipsfEventObjects46 2 }

ipsf46_SID_value OBJECT-TYPE
    SYNTAX Integer32
    MAX-ACCESS accessible-for-notify
    STATUS current
    DESCRIPTION
        "Parameter 'SID_value' in event IPSF.46"
    ::= { ipsfEventObjects46 3 }

ipsfEventObjects47 OBJECT-IDENTITY
    STATUS current
    DESCRIPTION
        "Event IPSF.47
        The specified list has been initilized."
    ::= { ipsfEventsGroup 47 }

ipsf47_list OBJECT-TYPE
    SYNTAX DisplayString
    MAX-ACCESS accessible-for-notify
    STATUS current
    DESCRIPTION
        "Parameter 'list' in event IPSF.47"
    ::= { ipsfEventObjects47 1 }

ipsf47_n_of_peers OBJECT-TYPE
    SYNTAX Integer32
    MAX-ACCESS accessible-for-notify
    STATUS current
    DESCRIPTION
        "Parameter 'n_of_peers' in event IPSF.47"
    ::= { ipsfEventObjects47 2 }

ipsfEventObjects48 OBJECT-IDENTITY
    STATUS current
    DESCRIPTION
        "Event IPSF.48
        The specified session has been removed."
    ::= { ipsfEventsGroup 48 }

ipsf48_internalID_value OBJECT-TYPE
    SYNTAX Integer32
    MAX-ACCESS accessible-for-notify
    STATUS current
    DESCRIPTION
        "Parameter 'internalID_value' in event IPSF.48"
    ::= { ipsfEventObjects48 1 }

ipsfEventObjects49 OBJECT-IDENTITY
    STATUS current
    DESCRIPTION
        "Event IPSF.49
        There are no peers to inherit."
    ::= { ipsfEventsGroup 49 }

ipsf49_SID OBJECT-TYPE
    SYNTAX DisplayString
    MAX-ACCESS accessible-for-notify
    STATUS current
    DESCRIPTION
        "Parameter 'SID' in event IPSF.49"
    ::= { ipsfEventObjects49 1 }

ipsf49_SID_value OBJECT-TYPE
    SYNTAX Integer32
    MAX-ACCESS accessible-for-notify
    STATUS current
    DESCRIPTION
        "Parameter 'SID_value' in event IPSF.49"
    ::= { ipsfEventObjects49 2 }

ipsfEventObjects50 OBJECT-IDENTITY
    STATUS current
    DESCRIPTION
        "Event IPSF.50
        The inherit task has finished."
    ::= { ipsfEventsGroup 50 }

ipsf50_peers_inherited OBJECT-TYPE
    SYNTAX Integer32
    MAX-ACCESS accessible-for-notify
    STATUS current
    DESCRIPTION
        "Parameter 'peers_inherited' in event IPSF.50"
    ::= { ipsfEventObjects50 1 }

ipsf50_SID OBJECT-TYPE
    SYNTAX DisplayString
    MAX-ACCESS accessible-for-notify
    STATUS current
    DESCRIPTION
        "Parameter 'SID' in event IPSF.50"
    ::= { ipsfEventObjects50 2 }

ipsf50_SID_value OBJECT-TYPE
    SYNTAX Integer32
    MAX-ACCESS accessible-for-notify
    STATUS current
    DESCRIPTION
        "Parameter 'SID_value' in event IPSF.50"
    ::= { ipsfEventObjects50 3 }

ipsfEventObjects51 OBJECT-IDENTITY
    STATUS current
    DESCRIPTION
        "Event IPSF.51
        The specified peer has been found."
    ::= { ipsfEventsGroup 51 }

ipsf51_place OBJECT-TYPE
    SYNTAX DisplayString
    MAX-ACCESS accessible-for-notify
    STATUS current
    DESCRIPTION
        "Parameter 'place' in event IPSF.51"
    ::= { ipsfEventObjects51 1 }

ipsf51_peerID OBJECT-TYPE
    SYNTAX Integer32
    MAX-ACCESS accessible-for-notify
    STATUS current
    DESCRIPTION
        "Parameter 'peerID' in event IPSF.51"
    ::= { ipsfEventObjects51 2 }

ipsf51_ep_dest OBJECT-TYPE
    SYNTAX IpAddress
    MAX-ACCESS accessible-for-notify
    STATUS current
    DESCRIPTION
        "Parameter 'ep_dest' in event IPSF.51"
    ::= { ipsfEventObjects51 3 }

ipsf51_client_dest OBJECT-TYPE
    SYNTAX IpAddress
    MAX-ACCESS accessible-for-notify
    STATUS current
    DESCRIPTION
        "Parameter 'client_dest' in event IPSF.51"
    ::= { ipsfEventObjects51 4 }

ipsf51_SID OBJECT-TYPE
    SYNTAX DisplayString
    MAX-ACCESS accessible-for-notify
    STATUS current
    DESCRIPTION
        "Parameter 'SID' in event IPSF.51"
    ::= { ipsfEventObjects51 5 }

ipsf51_SID_value OBJECT-TYPE
    SYNTAX Integer32
    MAX-ACCESS accessible-for-notify
    STATUS current
    DESCRIPTION
        "Parameter 'SID_value' in event IPSF.51"
    ::= { ipsfEventObjects51 6 }


ipsfNotification1 NOTIFICATION-TYPE
    OBJECTS { 
              ipsf1_message 
            }
    STATUS current
    DESCRIPTION
        "Notification of Event IPSF.1

        Message: '$1'

        Parameters list:
              $1: ipsf1_message

        Generic abnormal internal error message."
    ::= { ipsfNotificationsPrefix 1 }

ipsfNotification2 NOTIFICATION-TYPE
    OBJECTS { 
              ipsf2_message 
            }
    STATUS current
    DESCRIPTION
        "Notification of Event IPSF.2

        Message: '$1'

        Parameters list:
              $1: ipsf2_message

        Generic usual internal error message."
    ::= { ipsfNotificationsPrefix 2 }

ipsfNotification3 NOTIFICATION-TYPE
    OBJECTS { 
              ipsf3_message 
            }
    STATUS current
    DESCRIPTION
        "Notification of Event IPSF.3

        Message: '$1'

        Parameters list:
              $1: ipsf3_message

        Generic abnormal external error message."
    ::= { ipsfNotificationsPrefix 3 }

ipsfNotification4 NOTIFICATION-TYPE
    OBJECTS { 
              ipsf4_message 
            }
    STATUS current
    DESCRIPTION
        "Notification of Event IPSF.4

        Message: '$1'

        Parameters list:
              $1: ipsf4_message

        Generic usual external error message."
    ::= { ipsfNotificationsPrefix 4 }

ipsfNotification5 NOTIFICATION-TYPE
    OBJECTS { 
              ipsf5_message 
            }
    STATUS current
    DESCRIPTION
        "Notification of Event IPSF.5

        Message: '$1'

        Parameters list:
              $1: ipsf5_message

        Generic comment on abnormal information message."
    ::= { ipsfNotificationsPrefix 5 }

ipsfNotification6 NOTIFICATION-TYPE
    OBJECTS { 
              ipsf6_message 
            }
    STATUS current
    DESCRIPTION
        "Notification of Event IPSF.6

        Message: '$1'

        Parameters list:
              $1: ipsf6_message

        Generic comment on usual information message."
    ::= { ipsfNotificationsPrefix 6 }

ipsfNotification7 NOTIFICATION-TYPE
    OBJECTS { 
              ipsf7_message 
            }
    STATUS current
    DESCRIPTION
        "Notification of Event IPSF.7

        Message: '$1'

        Parameters list:
              $1: ipsf7_message

        Generic packet trace message."
    ::= { ipsfNotificationsPrefix 7 }

ipsfNotification8 NOTIFICATION-TYPE
    OBJECTS { 
              ipsf8_message 
            }
    STATUS current
    DESCRIPTION
        "Notification of Event IPSF.8

        Message: '$1'

        Parameters list:
              $1: ipsf8_message

        Generic abnormal operation trace message."
    ::= { ipsfNotificationsPrefix 8 }

ipsfNotification9 NOTIFICATION-TYPE
    OBJECTS { 
              ipsf9_message 
            }
    STATUS current
    DESCRIPTION
        "Notification of Event IPSF.9

        Message: '$1'

        Parameters list:
              $1: ipsf9_message

        Generic usual operation trace message."
    ::= { ipsfNotificationsPrefix 9 }

ipsfNotification10 NOTIFICATION-TYPE
    OBJECTS { 
              ipsf10_event_level, 
              ipsf10_message 
            }
    STATUS current
    DESCRIPTION
        "Notification of Event IPSF.10

        Message: 'Bad generic event level ($1) ($2)'

        Parameters list:
              $1: ipsf10_event_level
              $2: ipsf10_message

        The generic event level is wrong."
    ::= { ipsfNotificationsPrefix 10 }

ipsfNotification11 NOTIFICATION-TYPE
    OBJECTS { 
              ipsf11_peerID, 
              ipsf11_SID,
              ipsf11_SID_value 
            }
    STATUS current
    DESCRIPTION
        "Notification of Event IPSF.11

        Message: 'Peer 0x$1 added to session list [$2 0x$3]'

        Parameters list:
              $1: ipsf11_peerID
              $2: ipsf11_SID
              $3: ipsf11_SID_value

        A new peer has been added to the session list."
    ::= { ipsfNotificationsPrefix 11 }

ipsfNotification12 NOTIFICATION-TYPE
    OBJECTS { 
              ipsf12_peerID, 
              ipsf12_SID,
              ipsf12_SID_value 
            }
    STATUS current
    DESCRIPTION
        "Notification of Event IPSF.12

        Message: 'Peer 0x$1 deleted from session list [$2 0x$3]'

        Parameters list:
              $1: ipsf12_peerID
              $2: ipsf12_SID
              $3: ipsf12_SID_value

        A peer has been deleted from the session list."
    ::= { ipsfNotificationsPrefix 12 }

ipsfNotification13 NOTIFICATION-TYPE
    OBJECTS { 
              ipsf13_type, 
              ipsf13_reason 
            }
    STATUS current
    DESCRIPTION
        "Notification of Event IPSF.13

        Message: 'Message $1 could not be sent to queue: $2'

        Parameters list:
              $1: ipsf13_type
              $2: ipsf13_reason

        The specified message could not be sent to IPSecFT queue."
    ::= { ipsfNotificationsPrefix 13 }

ipsfNotification14 NOTIFICATION-TYPE
    OBJECTS { 
              ipsf14_type 
            }
    STATUS current
    DESCRIPTION
        "Notification of Event IPSF.14

        Message: 'Message $1 has been sent to queue'

        Parameters list:
              $1: ipsf14_type

        The specified message has been sent to IPSecFT queue."
    ::= { ipsfNotificationsPrefix 14 }

ipsfNotification15 NOTIFICATION-TYPE
    OBJECTS { 
              ipsf15_task_name 
            }
    STATUS current
    DESCRIPTION
        "Notification of Event IPSF.15

        Message: '$1 task created'

        Parameters list:
              $1: ipsf15_task_name

        The specified task has been created."
    ::= { ipsfNotificationsPrefix 15 }

ipsfNotification16 NOTIFICATION-TYPE
    OBJECTS { 
              ipsf16_current_state, 
              ipsf16_new_state,
              ipsf16_SID,
              ipsf16_SID_value 
            }
    STATUS current
    DESCRIPTION
        "Notification of Event IPSF.16

        Message: 'Changing state ($1->$2) [$3 0x$4]'

        Parameters list:
              $1: ipsf16_current_state
              $2: ipsf16_new_state
              $3: ipsf16_SID
              $4: ipsf16_SID_value

        The specified session has change its state."
    ::= { ipsfNotificationsPrefix 16 }

ipsfNotification17 NOTIFICATION-TYPE
    OBJECTS { 
              ipsf17_timeout, 
              ipsf17_current_state,
              ipsf17_new_state,
              ipsf17_SID,
              ipsf17_SID_value 
            }
    STATUS current
    DESCRIPTION
        "Notification of Event IPSF.17

        Message: 'Changing state in $1 second[s] ($2->$3) [$4 0x$5]'

        Parameters list:
              $1: ipsf17_timeout
              $2: ipsf17_current_state
              $3: ipsf17_new_state
              $4: ipsf17_SID
              $5: ipsf17_SID_value

        The specified session will change its state."
    ::= { ipsfNotificationsPrefix 17 }

ipsfNotification18 NOTIFICATION-TYPE
    OBJECTS { 
              ipsf18_src_addr, 
              ipsf18_src_port,
              ipsf18_dst_addr,
              ipsf18_dst_port,
              ipsf18_timeout,
              ipsf18_SID,
              ipsf18_SID_value 
            }
    STATUS current
    DESCRIPTION
        "Notification of Event IPSF.18

        Message: 'Connecting ($1:$2->$3:$4). Timeout in $5 second[s] [$6 0x$7]'

        Parameters list:
              $1: ipsf18_src_addr
              $2: ipsf18_src_port
              $3: ipsf18_dst_addr
              $4: ipsf18_dst_port
              $5: ipsf18_timeout
              $6: ipsf18_SID
              $7: ipsf18_SID_value

        The specified session is connecting."
    ::= { ipsfNotificationsPrefix 18 }

ipsfNotification19 NOTIFICATION-TYPE
    OBJECTS { 
              ipsf19_type 
            }
    STATUS current
    DESCRIPTION
        "Notification of Event IPSF.19

        Message: 'IPSecFT has been started as $1 server'

        Parameters list:
              $1: ipsf19_type

        IPSecFT has been started as specified type."
    ::= { ipsfNotificationsPrefix 19 }

ipsfNotification20 NOTIFICATION-TYPE
    OBJECTS { 
              ipsf20_process 
            }
    STATUS current
    DESCRIPTION
        "Notification of Event IPSF.20

        Message: '$1 is being restarted'

        Parameters list:
              $1: ipsf20_process

        The specified process is being restarted."
    ::= { ipsfNotificationsPrefix 20 }

ipsfNotification21 NOTIFICATION-TYPE
    OBJECTS { 
              ipsf21_SID_value 
            }
    STATUS current
    DESCRIPTION
        "Notification of Event IPSF.21

        Message: 'TCP connect OK [MSID 0x$1]'

        Parameters list:
              $1: ipsf21_SID_value

        The TCP connection has been established."
    ::= { ipsfNotificationsPrefix 21 }

ipsfNotification22 NOTIFICATION-TYPE
    OBJECTS { 
              ipsf22_event, 
              ipsf22_current_state,
              ipsf22_SID,
              ipsf22_SID_value 
            }
    STATUS current
    DESCRIPTION
        "Notification of Event IPSF.22

        Message: 'Event $1 received (state $2) [$3 0x$4]'

        Parameters list:
              $1: ipsf22_event
              $2: ipsf22_current_state
              $3: ipsf22_SID
              $4: ipsf22_SID_value

        The specified event has been received."
    ::= { ipsfNotificationsPrefix 22 }

ipsfNotification23 NOTIFICATION-TYPE
    OBJECTS { 
              ipsf23_packet_type, 
              ipsf23_len,
              ipsf23_SID,
              ipsf23_SID_value 
            }
    STATUS current
    DESCRIPTION
        "Notification of Event IPSF.23

        Message: '$1 packet has been sent ($2 bytes) [$3 0x$4]'

        Parameters list:
              $1: ipsf23_packet_type
              $2: ipsf23_len
              $3: ipsf23_SID
              $4: ipsf23_SID_value

        The specified packet has been sent."
    ::= { ipsfNotificationsPrefix 23 }

ipsfNotification24 NOTIFICATION-TYPE
    OBJECTS { 
              ipsf24_timeout, 
              ipsf24_interval,
              ipsf24_SID,
              ipsf24_SID_value 
            }
    STATUS current
    DESCRIPTION
        "Notification of Event IPSF.24

        Message: 'Listen for incoming data. Timeout in $1 $2 [$3 0x$4]'

        Parameters list:
              $1: ipsf24_timeout
              $2: ipsf24_interval
              $3: ipsf24_SID
              $4: ipsf24_SID_value

        IPSecFT is listening for incoming data."
    ::= { ipsfNotificationsPrefix 24 }

ipsfNotification25 NOTIFICATION-TYPE
    OBJECTS { 
              ipsf25_reason, 
              ipsf25_SID,
              ipsf25_SID_value 
            }
    STATUS current
    DESCRIPTION
        "Notification of Event IPSF.25

        Message: 'Wrong ACK: $1 [$2 0x$3]'

        Parameters list:
              $1: ipsf25_reason
              $2: ipsf25_SID
              $3: ipsf25_SID_value

        The ACK is wrong."
    ::= { ipsfNotificationsPrefix 25 }

ipsfNotification26 NOTIFICATION-TYPE
    OBJECTS { 
              ipsf26_IP, 
              ipsf26_SID,
              ipsf26_SID_value 
            }
    STATUS current
    DESCRIPTION
        "Notification of Event IPSF.26

        Message: 'IP address $1 has been inherited [$2 0x$3]'

        Parameters list:
              $1: ipsf26_IP
              $2: ipsf26_SID
              $3: ipsf26_SID_value

        The specified IP has been inherited."
    ::= { ipsfNotificationsPrefix 26 }

ipsfNotification27 NOTIFICATION-TYPE
    OBJECTS { 
              ipsf27_timer, 
              ipsf27_SID,
              ipsf27_SID_value 
            }
    STATUS current
    DESCRIPTION
        "Notification of Event IPSF.27

        Message: 'Added timer for keepalive transmission. Timeout in $1 millisecond[s] [$2 0x$3]'

        Parameters list:
              $1: ipsf27_timer
              $2: ipsf27_SID
              $3: ipsf27_SID_value

        Keepalive packet will be sent at the specified time."
    ::= { ipsfNotificationsPrefix 27 }

ipsfNotification28 NOTIFICATION-TYPE
    OBJECTS { 
              ipsf28_SID, 
              ipsf28_SID_value 
            }
    STATUS current
    DESCRIPTION
        "Notification of Event IPSF.28

        Message: 'Retrieving queued elements [$1 0x$2]'

        Parameters list:
              $1: ipsf28_SID
              $2: ipsf28_SID_value

        IPSecFT is retrieving queued elements."
    ::= { ipsfNotificationsPrefix 28 }

ipsfNotification29 NOTIFICATION-TYPE
    OBJECTS { 
              ipsf29_SID, 
              ipsf29_SID_value 
            }
    STATUS current
    DESCRIPTION
        "Notification of Event IPSF.29

        Message: 'Session established [$1 0x$2]'

        Parameters list:
              $1: ipsf29_SID
              $2: ipsf29_SID_value

        The specified session has been established."
    ::= { ipsfNotificationsPrefix 29 }

ipsfNotification30 NOTIFICATION-TYPE
    OBJECTS { 
              ipsf30_local_addr, 
              ipsf30_local_port 
            }
    STATUS current
    DESCRIPTION
        "Notification of Event IPSF.30

        Message: 'Waiting for incoming connections ($1:$2)'

        Parameters list:
              $1: ipsf30_local_addr
              $2: ipsf30_local_port

        IPSecFT is waiting for incoming connections."
    ::= { ipsfNotificationsPrefix 30 }

ipsfNotification31 NOTIFICATION-TYPE
    OBJECTS { 
              ipsf31_remote_addr, 
              ipsf31_remote_port,
              ipsf31_local_addr,
              ipsf31_local_port,
              ipsf31_internalID,
              ipsf31_internalID_value 
            }
    STATUS current
    DESCRIPTION
        "Notification of Event IPSF.31

        Message: 'TCP connection accepted ($1:$2->$3:$4) [$5 0x$6]'

        Parameters list:
              $1: ipsf31_remote_addr
              $2: ipsf31_remote_port
              $3: ipsf31_local_addr
              $4: ipsf31_local_port
              $5: ipsf31_internalID
              $6: ipsf31_internalID_value

        A TCP connection has been accepted."
    ::= { ipsfNotificationsPrefix 31 }

ipsfNotification32 NOTIFICATION-TYPE
    OBJECTS { 
              ipsf32_source_addr, 
              ipsf32_source_port,
              ipsf32_destination_addr,
              ipsf32_destination_port,
              ipsf32_SID,
              ipsf32_SID_value 
            }
    STATUS current
    DESCRIPTION
        "Notification of Event IPSF.32

        Message: 'Closing connection ($1:$2->$3:$4) [$5 0x$6]'

        Parameters list:
              $1: ipsf32_source_addr
              $2: ipsf32_source_port
              $3: ipsf32_destination_addr
              $4: ipsf32_destination_port
              $5: ipsf32_SID
              $6: ipsf32_SID_value

        A TCP connection has been closed."
    ::= { ipsfNotificationsPrefix 32 }

ipsfNotification33 NOTIFICATION-TYPE
    OBJECTS { 
              ipsf33_length, 
              ipsf33_SID,
              ipsf33_SID_value 
            }
    STATUS current
    DESCRIPTION
        "Notification of Event IPSF.33

        Message: 'Read complete ($1 bytes) [$2 0x$3]'

        Parameters list:
              $1: ipsf33_length
              $2: ipsf33_SID
              $3: ipsf33_SID_value

        The specified data length has been received."
    ::= { ipsfNotificationsPrefix 33 }

ipsfNotification34 NOTIFICATION-TYPE
    OBJECTS { 
              ipsf34_packet_type, 
              ipsf34_SID,
              ipsf34_SID_value 
            }
    STATUS current
    DESCRIPTION
        "Notification of Event IPSF.34

        Message: '$1 packet received [$2 0x$3]'

        Parameters list:
              $1: ipsf34_packet_type
              $2: ipsf34_SID
              $3: ipsf34_SID_value

        The specified packet has been received."
    ::= { ipsfNotificationsPrefix 34 }

ipsfNotification35 NOTIFICATION-TYPE
    OBJECTS { 
              ipsf35_length, 
              ipsf35_SID,
              ipsf35_SID_value 
            }
    STATUS current
    DESCRIPTION
        "Notification of Event IPSF.35

        Message: 'Write callback OK ($1 bytes) [$2 0x$3]'

        Parameters list:
              $1: ipsf35_length
              $2: ipsf35_SID
              $3: ipsf35_SID_value

        The callback for writing was successful."
    ::= { ipsfNotificationsPrefix 35 }

ipsfNotification36 NOTIFICATION-TYPE
    OBJECTS { 
              ipsf36_tunnels, 
              ipsf36_SID,
              ipsf36_SID_value 
            }
    STATUS current
    DESCRIPTION
        "Notification of Event IPSF.36

        Message: '$1 tunnels have been inherited [$2 0x$3]'

        Parameters list:
              $1: ipsf36_tunnels
              $2: ipsf36_SID
              $3: ipsf36_SID_value

        IPSecFT as backup server has inherited the tunnels."
    ::= { ipsfNotificationsPrefix 36 }

ipsfNotification37 NOTIFICATION-TYPE
    OBJECTS { 
              ipsf37_internalID, 
              ipsf37_internalID_value,
              ipsf37_SID,
              ipsf37_SID_value 
            }
    STATUS current
    DESCRIPTION
        "Notification of Event IPSF.37

        Message: 'Finishing session [$1 0x$2, $3 0x$4]'

        Parameters list:
              $1: ipsf37_internalID
              $2: ipsf37_internalID_value
              $3: ipsf37_SID
              $4: ipsf37_SID_value

        The specified session will be finished."
    ::= { ipsfNotificationsPrefix 37 }

ipsfNotification38 NOTIFICATION-TYPE
    OBJECTS { 
              ipsf38_SID, 
              ipsf38_SID_value 
            }
    STATUS current
    DESCRIPTION
        "Notification of Event IPSF.38

        Message: 'Timeout in keepalive timer [$1 0x$2]'

        Parameters list:
              $1: ipsf38_SID
              $2: ipsf38_SID_value

        Timeout in keepalive timer."
    ::= { ipsfNotificationsPrefix 38 }

ipsfNotification39 NOTIFICATION-TYPE
    OBJECTS { 
              ipsf39_SID, 
              ipsf39_SID_value 
            }
    STATUS current
    DESCRIPTION
        "Notification of Event IPSF.39

        Message: 'Deleting timer for keepalive transmission [$1 0x$2]'

        Parameters list:
              $1: ipsf39_SID
              $2: ipsf39_SID_value

        The timer for keepalive transmission has been deleted."
    ::= { ipsfNotificationsPrefix 39 }

ipsfNotification40 NOTIFICATION-TYPE
    OBJECTS { 
              ipsf40_current_state, 
              ipsf40_event,
              ipsf40_SID,
              ipsf40_SID_value 
            }
    STATUS current
    DESCRIPTION
        "Notification of Event IPSF.40

        Message: 'Configuration has changed (state $1, event $2) [$3 0x$4]'

        Parameters list:
              $1: ipsf40_current_state
              $2: ipsf40_event
              $3: ipsf40_SID
              $4: ipsf40_SID_value

        The configuration has changed."
    ::= { ipsfNotificationsPrefix 40 }

ipsfNotification41 NOTIFICATION-TYPE
    OBJECTS { 
              ipsf41_current_state, 
              ipsf41_event,
              ipsf41_SID,
              ipsf41_SID_value 
            }
    STATUS current
    DESCRIPTION
        "Notification of Event IPSF.41

        Message: 'Innocuous event (state $1, event $2) [$3 0x$4]'

        Parameters list:
              $1: ipsf41_current_state
              $2: ipsf41_event
              $3: ipsf41_SID
              $4: ipsf41_SID_value

        An innocuous event has been received."
    ::= { ipsfNotificationsPrefix 41 }

ipsfNotification42 NOTIFICATION-TYPE
    OBJECTS { 
              ipsf42_task_name 
            }
    STATUS current
    DESCRIPTION
        "Notification of Event IPSF.42

        Message: 'Task $1 has been suspended'

        Parameters list:
              $1: ipsf42_task_name

        The specified task has been suspended."
    ::= { ipsfNotificationsPrefix 42 }

ipsfNotification43 NOTIFICATION-TYPE
    OBJECTS { 
              ipsf43_task_name 
            }
    STATUS current
    DESCRIPTION
        "Notification of Event IPSF.43

        Message: 'Task $1 has been resumed'

        Parameters list:
              $1: ipsf43_task_name

        The specified task has been resumed."
    ::= { ipsfNotificationsPrefix 43 }

ipsfNotification44 NOTIFICATION-TYPE
    OBJECTS { 
              ipsf44_peerID, 
              ipsf44_ep_dest,
              ipsf44_client_dest,
              ipsf44_SID,
              ipsf44_SID_value 
            }
    STATUS current
    DESCRIPTION
        "Notification of Event IPSF.44

        Message: 'Sending signal to IPSec to inherit tunnel 0x$1: ep_dest $2, client_dest $3 [$4 0x$5]'

        Parameters list:
              $1: ipsf44_peerID
              $2: ipsf44_ep_dest
              $3: ipsf44_client_dest
              $4: ipsf44_SID
              $5: ipsf44_SID_value

        Sending signal to IPSec to inherit the specified tunnel."
    ::= { ipsfNotificationsPrefix 44 }

ipsfNotification45 NOTIFICATION-TYPE
    OBJECTS { 
              ipsf45_current_state, 
              ipsf45_event,
              ipsf45_SID,
              ipsf45_SID_value 
            }
    STATUS current
    DESCRIPTION
        "Notification of Event IPSF.45

        Message: 'Delete list received (state $1, event $2) [$3 0x$4]'

        Parameters list:
              $1: ipsf45_current_state
              $2: ipsf45_event
              $3: ipsf45_SID
              $4: ipsf45_SID_value

        Event delete list has been received."
    ::= { ipsfNotificationsPrefix 45 }

ipsfNotification46 NOTIFICATION-TYPE
    OBJECTS { 
              ipsf46_IP, 
              ipsf46_SID,
              ipsf46_SID_value 
            }
    STATUS current
    DESCRIPTION
        "Notification of Event IPSF.46

        Message: 'Deleting IPSec sessions with source IP address $1 [$2 0x$3]'

        Parameters list:
              $1: ipsf46_IP
              $2: ipsf46_SID
              $3: ipsf46_SID_value

        Deleting IPSec sessions with the specified source IP address."
    ::= { ipsfNotificationsPrefix 46 }

ipsfNotification47 NOTIFICATION-TYPE
    OBJECTS { 
              ipsf47_list, 
              ipsf47_n_of_peers 
            }
    STATUS current
    DESCRIPTION
        "Notification of Event IPSF.47

        Message: '$1 list has been initialized with $2 peers'

        Parameters list:
              $1: ipsf47_list
              $2: ipsf47_n_of_peers

        The specified list has been initilized."
    ::= { ipsfNotificationsPrefix 47 }

ipsfNotification48 NOTIFICATION-TYPE
    OBJECTS { 
              ipsf48_internalID_value 
            }
    STATUS current
    DESCRIPTION
        "Notification of Event IPSF.48

        Message: 'Backup session has already been removed [IBSID 0x$1]'

        Parameters list:
              $1: ipsf48_internalID_value

        The specified session has been removed."
    ::= { ipsfNotificationsPrefix 48 }

ipsfNotification49 NOTIFICATION-TYPE
    OBJECTS { 
              ipsf49_SID, 
              ipsf49_SID_value 
            }
    STATUS current
    DESCRIPTION
        "Notification of Event IPSF.49

        Message: 'No peers to inherit [$1 0x$2]'

        Parameters list:
              $1: ipsf49_SID
              $2: ipsf49_SID_value

        There are no peers to inherit."
    ::= { ipsfNotificationsPrefix 49 }

ipsfNotification50 NOTIFICATION-TYPE
    OBJECTS { 
              ipsf50_peers_inherited, 
              ipsf50_SID,
              ipsf50_SID_value 
            }
    STATUS current
    DESCRIPTION
        "Notification of Event IPSF.50

        Message: 'Inherit task finished with $1 peers [$2 0x$3]'

        Parameters list:
              $1: ipsf50_peers_inherited
              $2: ipsf50_SID
              $3: ipsf50_SID_value

        The inherit task has finished."
    ::= { ipsfNotificationsPrefix 50 }

ipsfNotification51 NOTIFICATION-TYPE
    OBJECTS { 
              ipsf51_place, 
              ipsf51_peerID,
              ipsf51_ep_dest,
              ipsf51_client_dest,
              ipsf51_SID,
              ipsf51_SID_value 
            }
    STATUS current
    DESCRIPTION
        "Notification of Event IPSF.51

        Message: 'Peer found in $1 for fast inheriting, 0x$2: ep_dest $3, client_dest $4 [$5 0x$6]'

        Parameters list:
              $1: ipsf51_place
              $2: ipsf51_peerID
              $3: ipsf51_ep_dest
              $4: ipsf51_client_dest
              $5: ipsf51_SID
              $6: ipsf51_SID_value

        The specified peer has been found."
    ::= { ipsfNotificationsPrefix 51 }


END
