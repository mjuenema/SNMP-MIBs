-- file automatically created


TELDAT-TRAP-SDEV-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


sdevTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SDEV event subsystem."
    REVISION "201401200930Z"
    DESCRIPTION "Initial implementation"
        ::= { telEventTraps 227 }


sdevEventsGroup	OBJECT IDENTIFIER	::= { sdevTrapsMIB 1 }

sdevNotifications	OBJECT IDENTIFIER	::= { sdevTrapsMIB 2 }
sdevNotificationsPrefix	OBJECT IDENTIFIER	::= { sdevNotifications 0 }

sdevEventObjects1 OBJECT-IDENTITY
    STATUS current
    DESCRIPTION
        "Event SDEV.1
        RBOOT misc event"
    ::= { sdevEventsGroup 1 }

sdev1_mnemonic OBJECT-TYPE
    SYNTAX DisplayString
    MAX-ACCESS accessible-for-notify
    STATUS current
    DESCRIPTION
        "Parameter 'mnemonic' in event SDEV.1"
    ::= { sdevEventObjects1 1 }

sdev1_event_descr OBJECT-TYPE
    SYNTAX DisplayString
    MAX-ACCESS accessible-for-notify
    STATUS current
    DESCRIPTION
        "Parameter 'event_descr' in event SDEV.1"
    ::= { sdevEventObjects1 2 }

sdevEventObjects2 OBJECT-IDENTITY
    STATUS current
    DESCRIPTION
        "Event SDEV.2
        RBOOT unusual event"
    ::= { sdevEventsGroup 2 }

sdev2_mnemonic OBJECT-TYPE
    SYNTAX DisplayString
    MAX-ACCESS accessible-for-notify
    STATUS current
    DESCRIPTION
        "Parameter 'mnemonic' in event SDEV.2"
    ::= { sdevEventObjects2 1 }

sdev2_event_descr OBJECT-TYPE
    SYNTAX DisplayString
    MAX-ACCESS accessible-for-notify
    STATUS current
    DESCRIPTION
        "Parameter 'event_descr' in event SDEV.2"
    ::= { sdevEventObjects2 2 }

sdevEventObjects3 OBJECT-IDENTITY
    STATUS current
    DESCRIPTION
        "Event SDEV.3
        RBOOT HSM event"
    ::= { sdevEventsGroup 3 }

sdev3_mnemonic OBJECT-TYPE
    SYNTAX DisplayString
    MAX-ACCESS accessible-for-notify
    STATUS current
    DESCRIPTION
        "Parameter 'mnemonic' in event SDEV.3"
    ::= { sdevEventObjects3 1 }

sdev3_event_descr OBJECT-TYPE
    SYNTAX DisplayString
    MAX-ACCESS accessible-for-notify
    STATUS current
    DESCRIPTION
        "Parameter 'event_descr' in event SDEV.3"
    ::= { sdevEventObjects3 2 }

sdevEventObjects4 OBJECT-IDENTITY
    STATUS current
    DESCRIPTION
        "Event SDEV.4
        RCONSOLE misc event"
    ::= { sdevEventsGroup 4 }

sdev4_mnemonic OBJECT-TYPE
    SYNTAX DisplayString
    MAX-ACCESS accessible-for-notify
    STATUS current
    DESCRIPTION
        "Parameter 'mnemonic' in event SDEV.4"
    ::= { sdevEventObjects4 1 }

sdev4_event_descr OBJECT-TYPE
    SYNTAX DisplayString
    MAX-ACCESS accessible-for-notify
    STATUS current
    DESCRIPTION
        "Parameter 'event_descr' in event SDEV.4"
    ::= { sdevEventObjects4 2 }

sdevEventObjects5 OBJECT-IDENTITY
    STATUS current
    DESCRIPTION
        "Event SDEV.5
        RCONSOLE unusual event"
    ::= { sdevEventsGroup 5 }

sdev5_mnemonic OBJECT-TYPE
    SYNTAX DisplayString
    MAX-ACCESS accessible-for-notify
    STATUS current
    DESCRIPTION
        "Parameter 'mnemonic' in event SDEV.5"
    ::= { sdevEventObjects5 1 }

sdev5_event_descr OBJECT-TYPE
    SYNTAX DisplayString
    MAX-ACCESS accessible-for-notify
    STATUS current
    DESCRIPTION
        "Parameter 'event_descr' in event SDEV.5"
    ::= { sdevEventObjects5 2 }

sdevEventObjects6 OBJECT-IDENTITY
    STATUS current
    DESCRIPTION
        "Event SDEV.6
        RCONSOLE message event"
    ::= { sdevEventsGroup 6 }

sdev6_mnemonic OBJECT-TYPE
    SYNTAX DisplayString
    MAX-ACCESS accessible-for-notify
    STATUS current
    DESCRIPTION
        "Parameter 'mnemonic' in event SDEV.6"
    ::= { sdevEventObjects6 1 }

sdev6_event_descr OBJECT-TYPE
    SYNTAX DisplayString
    MAX-ACCESS accessible-for-notify
    STATUS current
    DESCRIPTION
        "Parameter 'event_descr' in event SDEV.6"
    ::= { sdevEventObjects6 2 }

sdevEventObjects7 OBJECT-IDENTITY
    STATUS current
    DESCRIPTION
        "Event SDEV.7
        HTE DEV misc event"
    ::= { sdevEventsGroup 7 }

sdev7_mnemonic OBJECT-TYPE
    SYNTAX DisplayString
    MAX-ACCESS accessible-for-notify
    STATUS current
    DESCRIPTION
        "Parameter 'mnemonic' in event SDEV.7"
    ::= { sdevEventObjects7 1 }

sdev7_event_descr OBJECT-TYPE
    SYNTAX DisplayString
    MAX-ACCESS accessible-for-notify
    STATUS current
    DESCRIPTION
        "Parameter 'event_descr' in event SDEV.7"
    ::= { sdevEventObjects7 2 }

sdevEventObjects8 OBJECT-IDENTITY
    STATUS current
    DESCRIPTION
        "Event SDEV.8
        HTE DEV error misc event"
    ::= { sdevEventsGroup 8 }

sdev8_mnemonic OBJECT-TYPE
    SYNTAX DisplayString
    MAX-ACCESS accessible-for-notify
    STATUS current
    DESCRIPTION
        "Parameter 'mnemonic' in event SDEV.8"
    ::= { sdevEventObjects8 1 }

sdev8_event_descr OBJECT-TYPE
    SYNTAX DisplayString
    MAX-ACCESS accessible-for-notify
    STATUS current
    DESCRIPTION
        "Parameter 'event_descr' in event SDEV.8"
    ::= { sdevEventObjects8 2 }

sdevEventObjects9 OBJECT-IDENTITY
    STATUS current
    DESCRIPTION
        "Event SDEV.9
        HTE DEV Tx ack event"
    ::= { sdevEventsGroup 9 }

sdev9_mnemonic OBJECT-TYPE
    SYNTAX DisplayString
    MAX-ACCESS accessible-for-notify
    STATUS current
    DESCRIPTION
        "Parameter 'mnemonic' in event SDEV.9"
    ::= { sdevEventObjects9 1 }

sdev9_event_descr OBJECT-TYPE
    SYNTAX DisplayString
    MAX-ACCESS accessible-for-notify
    STATUS current
    DESCRIPTION
        "Parameter 'event_descr' in event SDEV.9"
    ::= { sdevEventObjects9 2 }

sdevEventObjects10 OBJECT-IDENTITY
    STATUS current
    DESCRIPTION
        "Event SDEV.10
        HTE DEV Tx ack unusual event"
    ::= { sdevEventsGroup 10 }

sdev10_mnemonic OBJECT-TYPE
    SYNTAX DisplayString
    MAX-ACCESS accessible-for-notify
    STATUS current
    DESCRIPTION
        "Parameter 'mnemonic' in event SDEV.10"
    ::= { sdevEventObjects10 1 }

sdev10_event_descr OBJECT-TYPE
    SYNTAX DisplayString
    MAX-ACCESS accessible-for-notify
    STATUS current
    DESCRIPTION
        "Parameter 'event_descr' in event SDEV.10"
    ::= { sdevEventObjects10 2 }

sdevEventObjects11 OBJECT-IDENTITY
    STATUS current
    DESCRIPTION
        "Event SDEV.11
        HTE DEV Tx request error event"
    ::= { sdevEventsGroup 11 }

sdev11_mnemonic OBJECT-TYPE
    SYNTAX DisplayString
    MAX-ACCESS accessible-for-notify
    STATUS current
    DESCRIPTION
        "Parameter 'mnemonic' in event SDEV.11"
    ::= { sdevEventObjects11 1 }

sdev11_event_descr OBJECT-TYPE
    SYNTAX DisplayString
    MAX-ACCESS accessible-for-notify
    STATUS current
    DESCRIPTION
        "Parameter 'event_descr' in event SDEV.11"
    ::= { sdevEventObjects11 2 }

sdevEventObjects12 OBJECT-IDENTITY
    STATUS current
    DESCRIPTION
        "Event SDEV.12
        HTE DEV Tx request CTRL event"
    ::= { sdevEventsGroup 12 }

sdev12_mnemonic OBJECT-TYPE
    SYNTAX DisplayString
    MAX-ACCESS accessible-for-notify
    STATUS current
    DESCRIPTION
        "Parameter 'mnemonic' in event SDEV.12"
    ::= { sdevEventObjects12 1 }

sdev12_event_descr OBJECT-TYPE
    SYNTAX DisplayString
    MAX-ACCESS accessible-for-notify
    STATUS current
    DESCRIPTION
        "Parameter 'event_descr' in event SDEV.12"
    ::= { sdevEventObjects12 2 }

sdevEventObjects13 OBJECT-IDENTITY
    STATUS current
    DESCRIPTION
        "Event SDEV.13
        HTE DEV Tx request PTM event"
    ::= { sdevEventsGroup 13 }

sdev13_mnemonic OBJECT-TYPE
    SYNTAX DisplayString
    MAX-ACCESS accessible-for-notify
    STATUS current
    DESCRIPTION
        "Parameter 'mnemonic' in event SDEV.13"
    ::= { sdevEventObjects13 1 }

sdev13_event_descr OBJECT-TYPE
    SYNTAX DisplayString
    MAX-ACCESS accessible-for-notify
    STATUS current
    DESCRIPTION
        "Parameter 'event_descr' in event SDEV.13"
    ::= { sdevEventObjects13 2 }

sdevEventObjects14 OBJECT-IDENTITY
    STATUS current
    DESCRIPTION
        "Event SDEV.14
        HTE DEV Tx request ATM event"
    ::= { sdevEventsGroup 14 }

sdev14_mnemonic OBJECT-TYPE
    SYNTAX DisplayString
    MAX-ACCESS accessible-for-notify
    STATUS current
    DESCRIPTION
        "Parameter 'mnemonic' in event SDEV.14"
    ::= { sdevEventObjects14 1 }

sdev14_event_descr OBJECT-TYPE
    SYNTAX DisplayString
    MAX-ACCESS accessible-for-notify
    STATUS current
    DESCRIPTION
        "Parameter 'event_descr' in event SDEV.14"
    ::= { sdevEventObjects14 2 }

sdevEventObjects15 OBJECT-IDENTITY
    STATUS current
    DESCRIPTION
        "Event SDEV.15
        HTE DEV Tx request RAW event"
    ::= { sdevEventsGroup 15 }

sdev15_mnemonic OBJECT-TYPE
    SYNTAX DisplayString
    MAX-ACCESS accessible-for-notify
    STATUS current
    DESCRIPTION
        "Parameter 'mnemonic' in event SDEV.15"
    ::= { sdevEventObjects15 1 }

sdev15_event_descr OBJECT-TYPE
    SYNTAX DisplayString
    MAX-ACCESS accessible-for-notify
    STATUS current
    DESCRIPTION
        "Parameter 'event_descr' in event SDEV.15"
    ::= { sdevEventObjects15 2 }

sdevEventObjects16 OBJECT-IDENTITY
    STATUS current
    DESCRIPTION
        "Event SDEV.16
        HTE DEV Tx check error event"
    ::= { sdevEventsGroup 16 }

sdev16_mnemonic OBJECT-TYPE
    SYNTAX DisplayString
    MAX-ACCESS accessible-for-notify
    STATUS current
    DESCRIPTION
        "Parameter 'mnemonic' in event SDEV.16"
    ::= { sdevEventObjects16 1 }

sdev16_event_descr OBJECT-TYPE
    SYNTAX DisplayString
    MAX-ACCESS accessible-for-notify
    STATUS current
    DESCRIPTION
        "Parameter 'event_descr' in event SDEV.16"
    ::= { sdevEventObjects16 2 }

sdevEventObjects17 OBJECT-IDENTITY
    STATUS current
    DESCRIPTION
        "Event SDEV.17
        HTE DEV Tx check CTRL event"
    ::= { sdevEventsGroup 17 }

sdev17_mnemonic OBJECT-TYPE
    SYNTAX DisplayString
    MAX-ACCESS accessible-for-notify
    STATUS current
    DESCRIPTION
        "Parameter 'mnemonic' in event SDEV.17"
    ::= { sdevEventObjects17 1 }

sdev17_event_descr OBJECT-TYPE
    SYNTAX DisplayString
    MAX-ACCESS accessible-for-notify
    STATUS current
    DESCRIPTION
        "Parameter 'event_descr' in event SDEV.17"
    ::= { sdevEventObjects17 2 }

sdevEventObjects18 OBJECT-IDENTITY
    STATUS current
    DESCRIPTION
        "Event SDEV.18
        HTE DEV Tx check PTM event"
    ::= { sdevEventsGroup 18 }

sdev18_mnemonic OBJECT-TYPE
    SYNTAX DisplayString
    MAX-ACCESS accessible-for-notify
    STATUS current
    DESCRIPTION
        "Parameter 'mnemonic' in event SDEV.18"
    ::= { sdevEventObjects18 1 }

sdev18_event_descr OBJECT-TYPE
    SYNTAX DisplayString
    MAX-ACCESS accessible-for-notify
    STATUS current
    DESCRIPTION
        "Parameter 'event_descr' in event SDEV.18"
    ::= { sdevEventObjects18 2 }

sdevEventObjects19 OBJECT-IDENTITY
    STATUS current
    DESCRIPTION
        "Event SDEV.19
        HTE DEV Tx check ATM event"
    ::= { sdevEventsGroup 19 }

sdev19_mnemonic OBJECT-TYPE
    SYNTAX DisplayString
    MAX-ACCESS accessible-for-notify
    STATUS current
    DESCRIPTION
        "Parameter 'mnemonic' in event SDEV.19"
    ::= { sdevEventObjects19 1 }

sdev19_event_descr OBJECT-TYPE
    SYNTAX DisplayString
    MAX-ACCESS accessible-for-notify
    STATUS current
    DESCRIPTION
        "Parameter 'event_descr' in event SDEV.19"
    ::= { sdevEventObjects19 2 }

sdevEventObjects20 OBJECT-IDENTITY
    STATUS current
    DESCRIPTION
        "Event SDEV.20
        HTE DEV Tx check RAW event"
    ::= { sdevEventsGroup 20 }

sdev20_mnemonic OBJECT-TYPE
    SYNTAX DisplayString
    MAX-ACCESS accessible-for-notify
    STATUS current
    DESCRIPTION
        "Parameter 'mnemonic' in event SDEV.20"
    ::= { sdevEventObjects20 1 }

sdev20_event_descr OBJECT-TYPE
    SYNTAX DisplayString
    MAX-ACCESS accessible-for-notify
    STATUS current
    DESCRIPTION
        "Parameter 'event_descr' in event SDEV.20"
    ::= { sdevEventObjects20 2 }

sdevEventObjects21 OBJECT-IDENTITY
    STATUS current
    DESCRIPTION
        "Event SDEV.21
        HTE DEV Rx check error event"
    ::= { sdevEventsGroup 21 }

sdev21_mnemonic OBJECT-TYPE
    SYNTAX DisplayString
    MAX-ACCESS accessible-for-notify
    STATUS current
    DESCRIPTION
        "Parameter 'mnemonic' in event SDEV.21"
    ::= { sdevEventObjects21 1 }

sdev21_event_descr OBJECT-TYPE
    SYNTAX DisplayString
    MAX-ACCESS accessible-for-notify
    STATUS current
    DESCRIPTION
        "Parameter 'event_descr' in event SDEV.21"
    ::= { sdevEventObjects21 2 }

sdevEventObjects22 OBJECT-IDENTITY
    STATUS current
    DESCRIPTION
        "Event SDEV.22
        HTE DEV Rx check CTRL event"
    ::= { sdevEventsGroup 22 }

sdev22_mnemonic OBJECT-TYPE
    SYNTAX DisplayString
    MAX-ACCESS accessible-for-notify
    STATUS current
    DESCRIPTION
        "Parameter 'mnemonic' in event SDEV.22"
    ::= { sdevEventObjects22 1 }

sdev22_event_descr OBJECT-TYPE
    SYNTAX DisplayString
    MAX-ACCESS accessible-for-notify
    STATUS current
    DESCRIPTION
        "Parameter 'event_descr' in event SDEV.22"
    ::= { sdevEventObjects22 2 }

sdevEventObjects23 OBJECT-IDENTITY
    STATUS current
    DESCRIPTION
        "Event SDEV.23
        HTE DEV Rx check PTM event"
    ::= { sdevEventsGroup 23 }

sdev23_mnemonic OBJECT-TYPE
    SYNTAX DisplayString
    MAX-ACCESS accessible-for-notify
    STATUS current
    DESCRIPTION
        "Parameter 'mnemonic' in event SDEV.23"
    ::= { sdevEventObjects23 1 }

sdev23_event_descr OBJECT-TYPE
    SYNTAX DisplayString
    MAX-ACCESS accessible-for-notify
    STATUS current
    DESCRIPTION
        "Parameter 'event_descr' in event SDEV.23"
    ::= { sdevEventObjects23 2 }

sdevEventObjects24 OBJECT-IDENTITY
    STATUS current
    DESCRIPTION
        "Event SDEV.24
        HTE DEV Rx check ATM event"
    ::= { sdevEventsGroup 24 }

sdev24_mnemonic OBJECT-TYPE
    SYNTAX DisplayString
    MAX-ACCESS accessible-for-notify
    STATUS current
    DESCRIPTION
        "Parameter 'mnemonic' in event SDEV.24"
    ::= { sdevEventObjects24 1 }

sdev24_event_descr OBJECT-TYPE
    SYNTAX DisplayString
    MAX-ACCESS accessible-for-notify
    STATUS current
    DESCRIPTION
        "Parameter 'event_descr' in event SDEV.24"
    ::= { sdevEventObjects24 2 }

sdevEventObjects25 OBJECT-IDENTITY
    STATUS current
    DESCRIPTION
        "Event SDEV.25
        HTE DEV Rx check RAW event"
    ::= { sdevEventsGroup 25 }

sdev25_mnemonic OBJECT-TYPE
    SYNTAX DisplayString
    MAX-ACCESS accessible-for-notify
    STATUS current
    DESCRIPTION
        "Parameter 'mnemonic' in event SDEV.25"
    ::= { sdevEventObjects25 1 }

sdev25_event_descr OBJECT-TYPE
    SYNTAX DisplayString
    MAX-ACCESS accessible-for-notify
    STATUS current
    DESCRIPTION
        "Parameter 'event_descr' in event SDEV.25"
    ::= { sdevEventObjects25 2 }

sdevEventObjects26 OBJECT-IDENTITY
    STATUS current
    DESCRIPTION
        "Event SDEV.26
        HTE DEV Tx done error event"
    ::= { sdevEventsGroup 26 }

sdev26_mnemonic OBJECT-TYPE
    SYNTAX DisplayString
    MAX-ACCESS accessible-for-notify
    STATUS current
    DESCRIPTION
        "Parameter 'mnemonic' in event SDEV.26"
    ::= { sdevEventObjects26 1 }

sdev26_event_descr OBJECT-TYPE
    SYNTAX DisplayString
    MAX-ACCESS accessible-for-notify
    STATUS current
    DESCRIPTION
        "Parameter 'event_descr' in event SDEV.26"
    ::= { sdevEventObjects26 2 }

sdevEventObjects27 OBJECT-IDENTITY
    STATUS current
    DESCRIPTION
        "Event SDEV.27
        HTE DEV Tx done CTRL event"
    ::= { sdevEventsGroup 27 }

sdev27_mnemonic OBJECT-TYPE
    SYNTAX DisplayString
    MAX-ACCESS accessible-for-notify
    STATUS current
    DESCRIPTION
        "Parameter 'mnemonic' in event SDEV.27"
    ::= { sdevEventObjects27 1 }

sdev27_event_descr OBJECT-TYPE
    SYNTAX DisplayString
    MAX-ACCESS accessible-for-notify
    STATUS current
    DESCRIPTION
        "Parameter 'event_descr' in event SDEV.27"
    ::= { sdevEventObjects27 2 }

sdevEventObjects28 OBJECT-IDENTITY
    STATUS current
    DESCRIPTION
        "Event SDEV.28
        HTE DEV Tx done PTM event"
    ::= { sdevEventsGroup 28 }

sdev28_mnemonic OBJECT-TYPE
    SYNTAX DisplayString
    MAX-ACCESS accessible-for-notify
    STATUS current
    DESCRIPTION
        "Parameter 'mnemonic' in event SDEV.28"
    ::= { sdevEventObjects28 1 }

sdev28_event_descr OBJECT-TYPE
    SYNTAX DisplayString
    MAX-ACCESS accessible-for-notify
    STATUS current
    DESCRIPTION
        "Parameter 'event_descr' in event SDEV.28"
    ::= { sdevEventObjects28 2 }

sdevEventObjects29 OBJECT-IDENTITY
    STATUS current
    DESCRIPTION
        "Event SDEV.29
        HTE DEV Tx done ATM event"
    ::= { sdevEventsGroup 29 }

sdev29_mnemonic OBJECT-TYPE
    SYNTAX DisplayString
    MAX-ACCESS accessible-for-notify
    STATUS current
    DESCRIPTION
        "Parameter 'mnemonic' in event SDEV.29"
    ::= { sdevEventObjects29 1 }

sdev29_event_descr OBJECT-TYPE
    SYNTAX DisplayString
    MAX-ACCESS accessible-for-notify
    STATUS current
    DESCRIPTION
        "Parameter 'event_descr' in event SDEV.29"
    ::= { sdevEventObjects29 2 }

sdevEventObjects30 OBJECT-IDENTITY
    STATUS current
    DESCRIPTION
        "Event SDEV.30
        HTE DEV Tx done RAW event"
    ::= { sdevEventsGroup 30 }

sdev30_mnemonic OBJECT-TYPE
    SYNTAX DisplayString
    MAX-ACCESS accessible-for-notify
    STATUS current
    DESCRIPTION
        "Parameter 'mnemonic' in event SDEV.30"
    ::= { sdevEventObjects30 1 }

sdev30_event_descr OBJECT-TYPE
    SYNTAX DisplayString
    MAX-ACCESS accessible-for-notify
    STATUS current
    DESCRIPTION
        "Parameter 'event_descr' in event SDEV.30"
    ::= { sdevEventObjects30 2 }

sdevEventObjects31 OBJECT-IDENTITY
    STATUS current
    DESCRIPTION
        "Event SDEV.31
        HTE DEV Rx done error event"
    ::= { sdevEventsGroup 31 }

sdev31_mnemonic OBJECT-TYPE
    SYNTAX DisplayString
    MAX-ACCESS accessible-for-notify
    STATUS current
    DESCRIPTION
        "Parameter 'mnemonic' in event SDEV.31"
    ::= { sdevEventObjects31 1 }

sdev31_event_descr OBJECT-TYPE
    SYNTAX DisplayString
    MAX-ACCESS accessible-for-notify
    STATUS current
    DESCRIPTION
        "Parameter 'event_descr' in event SDEV.31"
    ::= { sdevEventObjects31 2 }

sdevEventObjects32 OBJECT-IDENTITY
    STATUS current
    DESCRIPTION
        "Event SDEV.32
        HTE DEV Rx done CTRL event"
    ::= { sdevEventsGroup 32 }

sdev32_mnemonic OBJECT-TYPE
    SYNTAX DisplayString
    MAX-ACCESS accessible-for-notify
    STATUS current
    DESCRIPTION
        "Parameter 'mnemonic' in event SDEV.32"
    ::= { sdevEventObjects32 1 }

sdev32_event_descr OBJECT-TYPE
    SYNTAX DisplayString
    MAX-ACCESS accessible-for-notify
    STATUS current
    DESCRIPTION
        "Parameter 'event_descr' in event SDEV.32"
    ::= { sdevEventObjects32 2 }

sdevEventObjects33 OBJECT-IDENTITY
    STATUS current
    DESCRIPTION
        "Event SDEV.33
        HTE DEV Rx done PTM event"
    ::= { sdevEventsGroup 33 }

sdev33_mnemonic OBJECT-TYPE
    SYNTAX DisplayString
    MAX-ACCESS accessible-for-notify
    STATUS current
    DESCRIPTION
        "Parameter 'mnemonic' in event SDEV.33"
    ::= { sdevEventObjects33 1 }

sdev33_event_descr OBJECT-TYPE
    SYNTAX DisplayString
    MAX-ACCESS accessible-for-notify
    STATUS current
    DESCRIPTION
        "Parameter 'event_descr' in event SDEV.33"
    ::= { sdevEventObjects33 2 }

sdevEventObjects34 OBJECT-IDENTITY
    STATUS current
    DESCRIPTION
        "Event SDEV.34
        HTE DEV Rx done ATM event"
    ::= { sdevEventsGroup 34 }

sdev34_mnemonic OBJECT-TYPE
    SYNTAX DisplayString
    MAX-ACCESS accessible-for-notify
    STATUS current
    DESCRIPTION
        "Parameter 'mnemonic' in event SDEV.34"
    ::= { sdevEventObjects34 1 }

sdev34_event_descr OBJECT-TYPE
    SYNTAX DisplayString
    MAX-ACCESS accessible-for-notify
    STATUS current
    DESCRIPTION
        "Parameter 'event_descr' in event SDEV.34"
    ::= { sdevEventObjects34 2 }

sdevEventObjects35 OBJECT-IDENTITY
    STATUS current
    DESCRIPTION
        "Event SDEV.35
        HTE DEV Rx done RAW event"
    ::= { sdevEventsGroup 35 }

sdev35_mnemonic OBJECT-TYPE
    SYNTAX DisplayString
    MAX-ACCESS accessible-for-notify
    STATUS current
    DESCRIPTION
        "Parameter 'mnemonic' in event SDEV.35"
    ::= { sdevEventObjects35 1 }

sdev35_event_descr OBJECT-TYPE
    SYNTAX DisplayString
    MAX-ACCESS accessible-for-notify
    STATUS current
    DESCRIPTION
        "Parameter 'event_descr' in event SDEV.35"
    ::= { sdevEventObjects35 2 }

sdevEventObjects36 OBJECT-IDENTITY
    STATUS current
    DESCRIPTION
        "Event SDEV.36
        HTE PROVIDER misc event"
    ::= { sdevEventsGroup 36 }

sdev36_mnemonic OBJECT-TYPE
    SYNTAX DisplayString
    MAX-ACCESS accessible-for-notify
    STATUS current
    DESCRIPTION
        "Parameter 'mnemonic' in event SDEV.36"
    ::= { sdevEventObjects36 1 }

sdev36_event_descr OBJECT-TYPE
    SYNTAX DisplayString
    MAX-ACCESS accessible-for-notify
    STATUS current
    DESCRIPTION
        "Parameter 'event_descr' in event SDEV.36"
    ::= { sdevEventObjects36 2 }

sdevEventObjects37 OBJECT-IDENTITY
    STATUS current
    DESCRIPTION
        "Event SDEV.37
        HTE PROVIDER misc err event"
    ::= { sdevEventsGroup 37 }

sdev37_mnemonic OBJECT-TYPE
    SYNTAX DisplayString
    MAX-ACCESS accessible-for-notify
    STATUS current
    DESCRIPTION
        "Parameter 'mnemonic' in event SDEV.37"
    ::= { sdevEventObjects37 1 }

sdev37_event_descr OBJECT-TYPE
    SYNTAX DisplayString
    MAX-ACCESS accessible-for-notify
    STATUS current
    DESCRIPTION
        "Parameter 'event_descr' in event SDEV.37"
    ::= { sdevEventObjects37 2 }

sdevEventObjects38 OBJECT-IDENTITY
    STATUS current
    DESCRIPTION
        "Event SDEV.38
        HTE PROVIDER Tx feed error event"
    ::= { sdevEventsGroup 38 }

sdev38_mnemonic OBJECT-TYPE
    SYNTAX DisplayString
    MAX-ACCESS accessible-for-notify
    STATUS current
    DESCRIPTION
        "Parameter 'mnemonic' in event SDEV.38"
    ::= { sdevEventObjects38 1 }

sdev38_event_descr OBJECT-TYPE
    SYNTAX DisplayString
    MAX-ACCESS accessible-for-notify
    STATUS current
    DESCRIPTION
        "Parameter 'event_descr' in event SDEV.38"
    ::= { sdevEventObjects38 2 }

sdevEventObjects39 OBJECT-IDENTITY
    STATUS current
    DESCRIPTION
        "Event SDEV.39
        HTE PROVIDER Tx feed event"
    ::= { sdevEventsGroup 39 }

sdev39_mnemonic OBJECT-TYPE
    SYNTAX DisplayString
    MAX-ACCESS accessible-for-notify
    STATUS current
    DESCRIPTION
        "Parameter 'mnemonic' in event SDEV.39"
    ::= { sdevEventObjects39 1 }

sdev39_event_descr OBJECT-TYPE
    SYNTAX DisplayString
    MAX-ACCESS accessible-for-notify
    STATUS current
    DESCRIPTION
        "Parameter 'event_descr' in event SDEV.39"
    ::= { sdevEventObjects39 2 }

sdevEventObjects40 OBJECT-IDENTITY
    STATUS current
    DESCRIPTION
        "Event SDEV.40
        HTE PROVIDER Tx request error event"
    ::= { sdevEventsGroup 40 }

sdev40_mnemonic OBJECT-TYPE
    SYNTAX DisplayString
    MAX-ACCESS accessible-for-notify
    STATUS current
    DESCRIPTION
        "Parameter 'mnemonic' in event SDEV.40"
    ::= { sdevEventObjects40 1 }

sdev40_event_descr OBJECT-TYPE
    SYNTAX DisplayString
    MAX-ACCESS accessible-for-notify
    STATUS current
    DESCRIPTION
        "Parameter 'event_descr' in event SDEV.40"
    ::= { sdevEventObjects40 2 }

sdevEventObjects41 OBJECT-IDENTITY
    STATUS current
    DESCRIPTION
        "Event SDEV.41
        HTE PROVIDER Tx done error event"
    ::= { sdevEventsGroup 41 }

sdev41_mnemonic OBJECT-TYPE
    SYNTAX DisplayString
    MAX-ACCESS accessible-for-notify
    STATUS current
    DESCRIPTION
        "Parameter 'mnemonic' in event SDEV.41"
    ::= { sdevEventObjects41 1 }

sdev41_event_descr OBJECT-TYPE
    SYNTAX DisplayString
    MAX-ACCESS accessible-for-notify
    STATUS current
    DESCRIPTION
        "Parameter 'event_descr' in event SDEV.41"
    ::= { sdevEventObjects41 2 }

sdevEventObjects42 OBJECT-IDENTITY
    STATUS current
    DESCRIPTION
        "Event SDEV.42
        HTE PROVIDER Tx done event"
    ::= { sdevEventsGroup 42 }

sdev42_mnemonic OBJECT-TYPE
    SYNTAX DisplayString
    MAX-ACCESS accessible-for-notify
    STATUS current
    DESCRIPTION
        "Parameter 'mnemonic' in event SDEV.42"
    ::= { sdevEventObjects42 1 }

sdev42_event_descr OBJECT-TYPE
    SYNTAX DisplayString
    MAX-ACCESS accessible-for-notify
    STATUS current
    DESCRIPTION
        "Parameter 'event_descr' in event SDEV.42"
    ::= { sdevEventObjects42 2 }

sdevEventObjects43 OBJECT-IDENTITY
    STATUS current
    DESCRIPTION
        "Event SDEV.43
        HTE PROVIDER Rx done error event"
    ::= { sdevEventsGroup 43 }

sdev43_mnemonic OBJECT-TYPE
    SYNTAX DisplayString
    MAX-ACCESS accessible-for-notify
    STATUS current
    DESCRIPTION
        "Parameter 'mnemonic' in event SDEV.43"
    ::= { sdevEventObjects43 1 }

sdev43_event_descr OBJECT-TYPE
    SYNTAX DisplayString
    MAX-ACCESS accessible-for-notify
    STATUS current
    DESCRIPTION
        "Parameter 'event_descr' in event SDEV.43"
    ::= { sdevEventObjects43 2 }

sdevEventObjects44 OBJECT-IDENTITY
    STATUS current
    DESCRIPTION
        "Event SDEV.44
        HTE PROVIDER Rx done event"
    ::= { sdevEventsGroup 44 }

sdev44_mnemonic OBJECT-TYPE
    SYNTAX DisplayString
    MAX-ACCESS accessible-for-notify
    STATUS current
    DESCRIPTION
        "Parameter 'mnemonic' in event SDEV.44"
    ::= { sdevEventObjects44 1 }

sdev44_event_descr OBJECT-TYPE
    SYNTAX DisplayString
    MAX-ACCESS accessible-for-notify
    STATUS current
    DESCRIPTION
        "Parameter 'event_descr' in event SDEV.44"
    ::= { sdevEventObjects44 2 }

sdevEventObjects45 OBJECT-IDENTITY
    STATUS current
    DESCRIPTION
        "Event SDEV.45
        HTE PROVIDER Rx ack done event"
    ::= { sdevEventsGroup 45 }

sdev45_mnemonic OBJECT-TYPE
    SYNTAX DisplayString
    MAX-ACCESS accessible-for-notify
    STATUS current
    DESCRIPTION
        "Parameter 'mnemonic' in event SDEV.45"
    ::= { sdevEventObjects45 1 }

sdev45_event_descr OBJECT-TYPE
    SYNTAX DisplayString
    MAX-ACCESS accessible-for-notify
    STATUS current
    DESCRIPTION
        "Parameter 'event_descr' in event SDEV.45"
    ::= { sdevEventObjects45 2 }


sdevNotification1 NOTIFICATION-TYPE
    OBJECTS { 
              sdev1_mnemonic, 
              sdev1_event_descr 
            }
    STATUS current
    DESCRIPTION
        "Notification of Event SDEV.1

        Message: 'RBOOT($1) $2'

        Parameters list:
              $1: sdev1_mnemonic
              $2: sdev1_event_descr

        RBOOT misc event"
    ::= { sdevNotificationsPrefix 1 }

sdevNotification2 NOTIFICATION-TYPE
    OBJECTS { 
              sdev2_mnemonic, 
              sdev2_event_descr 
            }
    STATUS current
    DESCRIPTION
        "Notification of Event SDEV.2

        Message: 'RBOOT($1) $2'

        Parameters list:
              $1: sdev2_mnemonic
              $2: sdev2_event_descr

        RBOOT unusual event"
    ::= { sdevNotificationsPrefix 2 }

sdevNotification3 NOTIFICATION-TYPE
    OBJECTS { 
              sdev3_mnemonic, 
              sdev3_event_descr 
            }
    STATUS current
    DESCRIPTION
        "Notification of Event SDEV.3

        Message: 'RBOOT-HSM($1) $2'

        Parameters list:
              $1: sdev3_mnemonic
              $2: sdev3_event_descr

        RBOOT HSM event"
    ::= { sdevNotificationsPrefix 3 }

sdevNotification4 NOTIFICATION-TYPE
    OBJECTS { 
              sdev4_mnemonic, 
              sdev4_event_descr 
            }
    STATUS current
    DESCRIPTION
        "Notification of Event SDEV.4

        Message: 'RCONSOLE($1) $2'

        Parameters list:
              $1: sdev4_mnemonic
              $2: sdev4_event_descr

        RCONSOLE misc event"
    ::= { sdevNotificationsPrefix 4 }

sdevNotification5 NOTIFICATION-TYPE
    OBJECTS { 
              sdev5_mnemonic, 
              sdev5_event_descr 
            }
    STATUS current
    DESCRIPTION
        "Notification of Event SDEV.5

        Message: 'RCONSOLE($1) $2'

        Parameters list:
              $1: sdev5_mnemonic
              $2: sdev5_event_descr

        RCONSOLE unusual event"
    ::= { sdevNotificationsPrefix 5 }

sdevNotification6 NOTIFICATION-TYPE
    OBJECTS { 
              sdev6_mnemonic, 
              sdev6_event_descr 
            }
    STATUS current
    DESCRIPTION
        "Notification of Event SDEV.6

        Message: 'RCONSOLE($1) $2'

        Parameters list:
              $1: sdev6_mnemonic
              $2: sdev6_event_descr

        RCONSOLE message event"
    ::= { sdevNotificationsPrefix 6 }

sdevNotification7 NOTIFICATION-TYPE
    OBJECTS { 
              sdev7_mnemonic, 
              sdev7_event_descr 
            }
    STATUS current
    DESCRIPTION
        "Notification of Event SDEV.7

        Message: 'HTE-DEV($1) $2'

        Parameters list:
              $1: sdev7_mnemonic
              $2: sdev7_event_descr

        HTE DEV misc event"
    ::= { sdevNotificationsPrefix 7 }

sdevNotification8 NOTIFICATION-TYPE
    OBJECTS { 
              sdev8_mnemonic, 
              sdev8_event_descr 
            }
    STATUS current
    DESCRIPTION
        "Notification of Event SDEV.8

        Message: 'HTE-DEV($1) Error $2'

        Parameters list:
              $1: sdev8_mnemonic
              $2: sdev8_event_descr

        HTE DEV error misc event"
    ::= { sdevNotificationsPrefix 8 }

sdevNotification9 NOTIFICATION-TYPE
    OBJECTS { 
              sdev9_mnemonic, 
              sdev9_event_descr 
            }
    STATUS current
    DESCRIPTION
        "Notification of Event SDEV.9

        Message: 'HTE-DEV($1) Tx ack $2'

        Parameters list:
              $1: sdev9_mnemonic
              $2: sdev9_event_descr

        HTE DEV Tx ack event"
    ::= { sdevNotificationsPrefix 9 }

sdevNotification10 NOTIFICATION-TYPE
    OBJECTS { 
              sdev10_mnemonic, 
              sdev10_event_descr 
            }
    STATUS current
    DESCRIPTION
        "Notification of Event SDEV.10

        Message: 'HTE-DEV($1) Tx ack $2'

        Parameters list:
              $1: sdev10_mnemonic
              $2: sdev10_event_descr

        HTE DEV Tx ack unusual event"
    ::= { sdevNotificationsPrefix 10 }

sdevNotification11 NOTIFICATION-TYPE
    OBJECTS { 
              sdev11_mnemonic, 
              sdev11_event_descr 
            }
    STATUS current
    DESCRIPTION
        "Notification of Event SDEV.11

        Message: 'HTE-DEV($1) Tx request error $2'

        Parameters list:
              $1: sdev11_mnemonic
              $2: sdev11_event_descr

        HTE DEV Tx request error event"
    ::= { sdevNotificationsPrefix 11 }

sdevNotification12 NOTIFICATION-TYPE
    OBJECTS { 
              sdev12_mnemonic, 
              sdev12_event_descr 
            }
    STATUS current
    DESCRIPTION
        "Notification of Event SDEV.12

        Message: 'HTE-DEV($1) Tx request CTRL $2'

        Parameters list:
              $1: sdev12_mnemonic
              $2: sdev12_event_descr

        HTE DEV Tx request CTRL event"
    ::= { sdevNotificationsPrefix 12 }

sdevNotification13 NOTIFICATION-TYPE
    OBJECTS { 
              sdev13_mnemonic, 
              sdev13_event_descr 
            }
    STATUS current
    DESCRIPTION
        "Notification of Event SDEV.13

        Message: 'HTE-DEV($1) Tx request PTM $2'

        Parameters list:
              $1: sdev13_mnemonic
              $2: sdev13_event_descr

        HTE DEV Tx request PTM event"
    ::= { sdevNotificationsPrefix 13 }

sdevNotification14 NOTIFICATION-TYPE
    OBJECTS { 
              sdev14_mnemonic, 
              sdev14_event_descr 
            }
    STATUS current
    DESCRIPTION
        "Notification of Event SDEV.14

        Message: 'HTE-DEV($1) Tx request ATM $2'

        Parameters list:
              $1: sdev14_mnemonic
              $2: sdev14_event_descr

        HTE DEV Tx request ATM event"
    ::= { sdevNotificationsPrefix 14 }

sdevNotification15 NOTIFICATION-TYPE
    OBJECTS { 
              sdev15_mnemonic, 
              sdev15_event_descr 
            }
    STATUS current
    DESCRIPTION
        "Notification of Event SDEV.15

        Message: 'HTE-DEV($1) Tx request RAW $2'

        Parameters list:
              $1: sdev15_mnemonic
              $2: sdev15_event_descr

        HTE DEV Tx request RAW event"
    ::= { sdevNotificationsPrefix 15 }

sdevNotification16 NOTIFICATION-TYPE
    OBJECTS { 
              sdev16_mnemonic, 
              sdev16_event_descr 
            }
    STATUS current
    DESCRIPTION
        "Notification of Event SDEV.16

        Message: 'HTE-DEV($1) Tx check error $2'

        Parameters list:
              $1: sdev16_mnemonic
              $2: sdev16_event_descr

        HTE DEV Tx check error event"
    ::= { sdevNotificationsPrefix 16 }

sdevNotification17 NOTIFICATION-TYPE
    OBJECTS { 
              sdev17_mnemonic, 
              sdev17_event_descr 
            }
    STATUS current
    DESCRIPTION
        "Notification of Event SDEV.17

        Message: 'HTE-DEV($1) Tx check CTRL $2'

        Parameters list:
              $1: sdev17_mnemonic
              $2: sdev17_event_descr

        HTE DEV Tx check CTRL event"
    ::= { sdevNotificationsPrefix 17 }

sdevNotification18 NOTIFICATION-TYPE
    OBJECTS { 
              sdev18_mnemonic, 
              sdev18_event_descr 
            }
    STATUS current
    DESCRIPTION
        "Notification of Event SDEV.18

        Message: 'HTE-DEV($1) Tx check PTM $2'

        Parameters list:
              $1: sdev18_mnemonic
              $2: sdev18_event_descr

        HTE DEV Tx check PTM event"
    ::= { sdevNotificationsPrefix 18 }

sdevNotification19 NOTIFICATION-TYPE
    OBJECTS { 
              sdev19_mnemonic, 
              sdev19_event_descr 
            }
    STATUS current
    DESCRIPTION
        "Notification of Event SDEV.19

        Message: 'HTE-DEV($1) Tx check ATM $2'

        Parameters list:
              $1: sdev19_mnemonic
              $2: sdev19_event_descr

        HTE DEV Tx check ATM event"
    ::= { sdevNotificationsPrefix 19 }

sdevNotification20 NOTIFICATION-TYPE
    OBJECTS { 
              sdev20_mnemonic, 
              sdev20_event_descr 
            }
    STATUS current
    DESCRIPTION
        "Notification of Event SDEV.20

        Message: 'HTE-DEV($1) Tx check RAW $2'

        Parameters list:
              $1: sdev20_mnemonic
              $2: sdev20_event_descr

        HTE DEV Tx check RAW event"
    ::= { sdevNotificationsPrefix 20 }

sdevNotification21 NOTIFICATION-TYPE
    OBJECTS { 
              sdev21_mnemonic, 
              sdev21_event_descr 
            }
    STATUS current
    DESCRIPTION
        "Notification of Event SDEV.21

        Message: 'HTE-DEV($1) Rx check error $2'

        Parameters list:
              $1: sdev21_mnemonic
              $2: sdev21_event_descr

        HTE DEV Rx check error event"
    ::= { sdevNotificationsPrefix 21 }

sdevNotification22 NOTIFICATION-TYPE
    OBJECTS { 
              sdev22_mnemonic, 
              sdev22_event_descr 
            }
    STATUS current
    DESCRIPTION
        "Notification of Event SDEV.22

        Message: 'HTE-DEV($1) Rx check CTRL $2'

        Parameters list:
              $1: sdev22_mnemonic
              $2: sdev22_event_descr

        HTE DEV Rx check CTRL event"
    ::= { sdevNotificationsPrefix 22 }

sdevNotification23 NOTIFICATION-TYPE
    OBJECTS { 
              sdev23_mnemonic, 
              sdev23_event_descr 
            }
    STATUS current
    DESCRIPTION
        "Notification of Event SDEV.23

        Message: 'HTE-DEV($1) Rx check PTM $2'

        Parameters list:
              $1: sdev23_mnemonic
              $2: sdev23_event_descr

        HTE DEV Rx check PTM event"
    ::= { sdevNotificationsPrefix 23 }

sdevNotification24 NOTIFICATION-TYPE
    OBJECTS { 
              sdev24_mnemonic, 
              sdev24_event_descr 
            }
    STATUS current
    DESCRIPTION
        "Notification of Event SDEV.24

        Message: 'HTE-DEV($1) Rx check ATM $2'

        Parameters list:
              $1: sdev24_mnemonic
              $2: sdev24_event_descr

        HTE DEV Rx check ATM event"
    ::= { sdevNotificationsPrefix 24 }

sdevNotification25 NOTIFICATION-TYPE
    OBJECTS { 
              sdev25_mnemonic, 
              sdev25_event_descr 
            }
    STATUS current
    DESCRIPTION
        "Notification of Event SDEV.25

        Message: 'HTE-DEV($1) Rx check RAW $2'

        Parameters list:
              $1: sdev25_mnemonic
              $2: sdev25_event_descr

        HTE DEV Rx check RAW event"
    ::= { sdevNotificationsPrefix 25 }

sdevNotification26 NOTIFICATION-TYPE
    OBJECTS { 
              sdev26_mnemonic, 
              sdev26_event_descr 
            }
    STATUS current
    DESCRIPTION
        "Notification of Event SDEV.26

        Message: 'HTE-DEV($1) Tx done error $2'

        Parameters list:
              $1: sdev26_mnemonic
              $2: sdev26_event_descr

        HTE DEV Tx done error event"
    ::= { sdevNotificationsPrefix 26 }

sdevNotification27 NOTIFICATION-TYPE
    OBJECTS { 
              sdev27_mnemonic, 
              sdev27_event_descr 
            }
    STATUS current
    DESCRIPTION
        "Notification of Event SDEV.27

        Message: 'HTE-DEV($1) Tx done CTRL $2'

        Parameters list:
              $1: sdev27_mnemonic
              $2: sdev27_event_descr

        HTE DEV Tx done CTRL event"
    ::= { sdevNotificationsPrefix 27 }

sdevNotification28 NOTIFICATION-TYPE
    OBJECTS { 
              sdev28_mnemonic, 
              sdev28_event_descr 
            }
    STATUS current
    DESCRIPTION
        "Notification of Event SDEV.28

        Message: 'HTE-DEV($1) Tx done PTM $2'

        Parameters list:
              $1: sdev28_mnemonic
              $2: sdev28_event_descr

        HTE DEV Tx done PTM event"
    ::= { sdevNotificationsPrefix 28 }

sdevNotification29 NOTIFICATION-TYPE
    OBJECTS { 
              sdev29_mnemonic, 
              sdev29_event_descr 
            }
    STATUS current
    DESCRIPTION
        "Notification of Event SDEV.29

        Message: 'HTE-DEV($1) Tx done ATM $2'

        Parameters list:
              $1: sdev29_mnemonic
              $2: sdev29_event_descr

        HTE DEV Tx done ATM event"
    ::= { sdevNotificationsPrefix 29 }

sdevNotification30 NOTIFICATION-TYPE
    OBJECTS { 
              sdev30_mnemonic, 
              sdev30_event_descr 
            }
    STATUS current
    DESCRIPTION
        "Notification of Event SDEV.30

        Message: 'HTE-DEV($1) Tx done RAW $2'

        Parameters list:
              $1: sdev30_mnemonic
              $2: sdev30_event_descr

        HTE DEV Tx done RAW event"
    ::= { sdevNotificationsPrefix 30 }

sdevNotification31 NOTIFICATION-TYPE
    OBJECTS { 
              sdev31_mnemonic, 
              sdev31_event_descr 
            }
    STATUS current
    DESCRIPTION
        "Notification of Event SDEV.31

        Message: 'HTE-DEV($1) Rx done error $2'

        Parameters list:
              $1: sdev31_mnemonic
              $2: sdev31_event_descr

        HTE DEV Rx done error event"
    ::= { sdevNotificationsPrefix 31 }

sdevNotification32 NOTIFICATION-TYPE
    OBJECTS { 
              sdev32_mnemonic, 
              sdev32_event_descr 
            }
    STATUS current
    DESCRIPTION
        "Notification of Event SDEV.32

        Message: 'HTE-DEV($1) Rx done CTRL $2'

        Parameters list:
              $1: sdev32_mnemonic
              $2: sdev32_event_descr

        HTE DEV Rx done CTRL event"
    ::= { sdevNotificationsPrefix 32 }

sdevNotification33 NOTIFICATION-TYPE
    OBJECTS { 
              sdev33_mnemonic, 
              sdev33_event_descr 
            }
    STATUS current
    DESCRIPTION
        "Notification of Event SDEV.33

        Message: 'HTE-DEV($1) Rx done PTM $2'

        Parameters list:
              $1: sdev33_mnemonic
              $2: sdev33_event_descr

        HTE DEV Rx done PTM event"
    ::= { sdevNotificationsPrefix 33 }

sdevNotification34 NOTIFICATION-TYPE
    OBJECTS { 
              sdev34_mnemonic, 
              sdev34_event_descr 
            }
    STATUS current
    DESCRIPTION
        "Notification of Event SDEV.34

        Message: 'HTE-DEV($1) Rx done ATM $2'

        Parameters list:
              $1: sdev34_mnemonic
              $2: sdev34_event_descr

        HTE DEV Rx done ATM event"
    ::= { sdevNotificationsPrefix 34 }

sdevNotification35 NOTIFICATION-TYPE
    OBJECTS { 
              sdev35_mnemonic, 
              sdev35_event_descr 
            }
    STATUS current
    DESCRIPTION
        "Notification of Event SDEV.35

        Message: 'HTE-DEV($1) Rx done RAW $2'

        Parameters list:
              $1: sdev35_mnemonic
              $2: sdev35_event_descr

        HTE DEV Rx done RAW event"
    ::= { sdevNotificationsPrefix 35 }

sdevNotification36 NOTIFICATION-TYPE
    OBJECTS { 
              sdev36_mnemonic, 
              sdev36_event_descr 
            }
    STATUS current
    DESCRIPTION
        "Notification of Event SDEV.36

        Message: 'HTE-PROV($1) $2'

        Parameters list:
              $1: sdev36_mnemonic
              $2: sdev36_event_descr

        HTE PROVIDER misc event"
    ::= { sdevNotificationsPrefix 36 }

sdevNotification37 NOTIFICATION-TYPE
    OBJECTS { 
              sdev37_mnemonic, 
              sdev37_event_descr 
            }
    STATUS current
    DESCRIPTION
        "Notification of Event SDEV.37

        Message: 'HTE-PROV($1) Error $2'

        Parameters list:
              $1: sdev37_mnemonic
              $2: sdev37_event_descr

        HTE PROVIDER misc err event"
    ::= { sdevNotificationsPrefix 37 }

sdevNotification38 NOTIFICATION-TYPE
    OBJECTS { 
              sdev38_mnemonic, 
              sdev38_event_descr 
            }
    STATUS current
    DESCRIPTION
        "Notification of Event SDEV.38

        Message: 'HTE-PROV($1) Tx feed error $2'

        Parameters list:
              $1: sdev38_mnemonic
              $2: sdev38_event_descr

        HTE PROVIDER Tx feed error event"
    ::= { sdevNotificationsPrefix 38 }

sdevNotification39 NOTIFICATION-TYPE
    OBJECTS { 
              sdev39_mnemonic, 
              sdev39_event_descr 
            }
    STATUS current
    DESCRIPTION
        "Notification of Event SDEV.39

        Message: 'HTE-PROV($1) Tx feed $2'

        Parameters list:
              $1: sdev39_mnemonic
              $2: sdev39_event_descr

        HTE PROVIDER Tx feed event"
    ::= { sdevNotificationsPrefix 39 }

sdevNotification40 NOTIFICATION-TYPE
    OBJECTS { 
              sdev40_mnemonic, 
              sdev40_event_descr 
            }
    STATUS current
    DESCRIPTION
        "Notification of Event SDEV.40

        Message: 'HTE-PROV($1) Tx request error $2'

        Parameters list:
              $1: sdev40_mnemonic
              $2: sdev40_event_descr

        HTE PROVIDER Tx request error event"
    ::= { sdevNotificationsPrefix 40 }

sdevNotification41 NOTIFICATION-TYPE
    OBJECTS { 
              sdev41_mnemonic, 
              sdev41_event_descr 
            }
    STATUS current
    DESCRIPTION
        "Notification of Event SDEV.41

        Message: 'HTE-PROV($1) Tx done error $2'

        Parameters list:
              $1: sdev41_mnemonic
              $2: sdev41_event_descr

        HTE PROVIDER Tx done error event"
    ::= { sdevNotificationsPrefix 41 }

sdevNotification42 NOTIFICATION-TYPE
    OBJECTS { 
              sdev42_mnemonic, 
              sdev42_event_descr 
            }
    STATUS current
    DESCRIPTION
        "Notification of Event SDEV.42

        Message: 'HTE-PROV($1) Tx done $2'

        Parameters list:
              $1: sdev42_mnemonic
              $2: sdev42_event_descr

        HTE PROVIDER Tx done event"
    ::= { sdevNotificationsPrefix 42 }

sdevNotification43 NOTIFICATION-TYPE
    OBJECTS { 
              sdev43_mnemonic, 
              sdev43_event_descr 
            }
    STATUS current
    DESCRIPTION
        "Notification of Event SDEV.43

        Message: 'HTE-PROV($1) Rx done error $2'

        Parameters list:
              $1: sdev43_mnemonic
              $2: sdev43_event_descr

        HTE PROVIDER Rx done error event"
    ::= { sdevNotificationsPrefix 43 }

sdevNotification44 NOTIFICATION-TYPE
    OBJECTS { 
              sdev44_mnemonic, 
              sdev44_event_descr 
            }
    STATUS current
    DESCRIPTION
        "Notification of Event SDEV.44

        Message: 'HTE-PROV($1) Rx done $2'

        Parameters list:
              $1: sdev44_mnemonic
              $2: sdev44_event_descr

        HTE PROVIDER Rx done event"
    ::= { sdevNotificationsPrefix 44 }

sdevNotification45 NOTIFICATION-TYPE
    OBJECTS { 
              sdev45_mnemonic, 
              sdev45_event_descr 
            }
    STATUS current
    DESCRIPTION
        "Notification of Event SDEV.45

        Message: 'HTE-PROV($1) Rx ack done $2'

        Parameters list:
              $1: sdev45_mnemonic
              $2: sdev45_event_descr

        HTE PROVIDER Rx ack done event"
    ::= { sdevNotificationsPrefix 45 }


END
