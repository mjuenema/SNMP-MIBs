--  =================================================================
-- Copyright (C) 2007 by HUAWEI TECHNOLOGIES. All rights reserved.
-- 
-- Description: HUAWEI Inner Link MIB File for inner links between 
--                frames
-- Reference:   
-- Version:     V1.00
-- History: 
-- 
--           V1.00   2007-10-24, Create 
-- =================================================================

    HUAWEI-INNER-LINK-MIB DEFINITIONS ::= BEGIN
 
        IMPORTS          
            hwDatacomm            
                FROM HUAWEI-MIB
            PhysicalIndex
                FROM ENTITY-MIB    
            SnmpAdminString            
                FROM SNMP-FRAMEWORK-MIB            
            OBJECT-GROUP, MODULE-COMPLIANCE, NOTIFICATION-GROUP                          
                FROM SNMPv2-CONF            
            Unsigned32, BITS, OBJECT-TYPE, MODULE-IDENTITY, NOTIFICATION-TYPE            
                FROM SNMPv2-SMI            
            TEXTUAL-CONVENTION, DisplayString           
                FROM SNMPv2-TC;
    
    
        hwInnerLinkMIB MODULE-IDENTITY 
            LAST-UPDATED "200710241430Z"        -- Oct. 24, 2007 at 14:30 GMT
            ORGANIZATION 
                "Huawei Technologies co.,Ltd."
            CONTACT-INFO 
                " R&D BeiJing, Huawei Technologies co.,Ltd.
                Huawei Bld.,NO.3 Xinxi Rd., 
                Shang-Di Information Industry Base,
                Hai-Dian District Beijing P.R. China
                Zip:100085 
                Http://www.huawei.com                                       
                E-mail:support@huawei.com "
            DESCRIPTION 
                "The private mib file includes the general  
                information of inner links between frames
                in cluster system."
            ::= { hwDatacomm 158 }
             
--
-- Node definitions 
--      
        hwInnerLinkMIBObjects OBJECT IDENTIFIER ::= { hwInnerLinkMIB 1 }
        
        hwInnerLinkMIBObjPrefix OBJECT IDENTIFIER ::= { hwInnerLinkMIBObjects 1 }
        hwInnerLinkLeftPortPhysicalIndex OBJECT-TYPE
            SYNTAX PhysicalIndex
            MAX-ACCESS accessible-for-notify
            STATUS current
            DESCRIPTION
                "To describe physical entity index of left port of 
                 the physical link which is part of the corresponding
                 inner logical link."
            ::= { hwInnerLinkMIBObjPrefix 1 }
            
        hwInnerLinkLeftPortPhysicalName OBJECT-TYPE
            SYNTAX SnmpAdminString
            MAX-ACCESS accessible-for-notify
            STATUS current
            DESCRIPTION
                "To describe physical entity name of left port of 
                 the physical link which is part of the corresponding
                 inner logical link."
            ::= { hwInnerLinkMIBObjPrefix 2 }
            
        hwInnerLinkRightPortPhysicalIndex OBJECT-TYPE
            SYNTAX PhysicalIndex
            MAX-ACCESS accessible-for-notify
            STATUS current
            DESCRIPTION
                "To describe physical entity index of right port of 
                 the physical link which is part of the corresponding
                 inner logical link."
            ::= { hwInnerLinkMIBObjPrefix 3 }
            
        hwInnerLinkRightPortPhysicalName OBJECT-TYPE
            SYNTAX SnmpAdminString
            MAX-ACCESS accessible-for-notify
            STATUS current
            DESCRIPTION
                "To describe physical entity name of right port of 
                 the physical link which is part of the corresponding
                 inner logical link."
            ::= { hwInnerLinkMIBObjPrefix 4 }
            
        hwInnerLinkTable OBJECT-TYPE
            SYNTAX SEQUENCE OF HwInnerLinkEntry
            MAX-ACCESS not-accessible
            STATUS current
            DESCRIPTION
                "This table contains one row per inner link entity.
                Each inner link is composed of all physical links
                of the same kind between two frames. 
                 It describes the status of the inner link between
                 frames in NE5000E Cluster system."
            ::= { hwInnerLinkMIBObjects 2 }
        
        hwInnerLinkEntry OBJECT-TYPE
            SYNTAX HwInnerLinkEntry
            MAX-ACCESS not-accessible
            STATUS current
            DESCRIPTION
                "Information about a particular inner link entity.
                Each entry provides left and right vitural port and status
                of the link to NMS to manage the links."
            INDEX { hwInnerLinkIndex }
            ::= { hwInnerLinkTable 1 }
    
        HwInnerLinkEntry ::=
            SEQUENCE { 
                hwInnerLinkIndex
                    Unsigned32,
                hwInnerLinkLeftFrameType
                    INTEGER,
                hwInnerLinkLeftFrameId
                    Unsigned32,             
                hwInnerLinkLeftPortId
                    Unsigned32,
                hwInnerLinkRightFrameType
                    INTEGER,
                hwInnerLinkRightFrameId
                    Unsigned32,
                hwInnerLinkRightPortId
                    Unsigned32,            
                hwInnerLinkType
                    INTEGER,
                hwInnerLinkAdminState
                    INTEGER,
                hwInnerLinkOperState
                    INTEGER,
                hwInnerLinkAlarmLight
                    BITS
                 }
             
        hwInnerLinkIndex OBJECT-TYPE
            SYNTAX      Unsigned32
            MAX-ACCESS  not-accessible
            STATUS      current
            DESCRIPTION
                "The index for this entry.It comprises of left frame
                ID, right frame ID and type of the logical link."
            ::= { hwInnerLinkEntry 1 }
        
        hwInnerLinkLeftFrameType OBJECT-TYPE
            SYNTAX INTEGER{
                unknown(1),
                centralChassis (2),
                lineChassis (3)
                }
            MAX-ACCESS  read-only
            STATUS      current
            DESCRIPTION
                "Frame type of the link's left point. A value of centralChassis 
                means the central frame in the system which can manage the system.
                A value of lineChassis means a frame managed by the central frame."
            ::= { hwInnerLinkEntry 2 }
            
        hwInnerLinkLeftFrameId OBJECT-TYPE
            SYNTAX      Unsigned32
            MAX-ACCESS  read-only
            STATUS      current
            DESCRIPTION
                "Frame ID of the link's left point."
            ::= { hwInnerLinkEntry 3 }
            
        hwInnerLinkLeftPortId OBJECT-TYPE
            SYNTAX      Unsigned32
            MAX-ACCESS  read-only
            STATUS      current
            DESCRIPTION
                "Port ID of the link's left virtual port."
            ::= { hwInnerLinkEntry 4 }
            
        hwInnerLinkRightFrameType OBJECT-TYPE
            SYNTAX INTEGER{
                unknown(1),
                centralChassis (2),
                lineChassis (3)
                }
            MAX-ACCESS  read-only
            STATUS      current
            DESCRIPTION
                "Frame type of the link's right point."
            ::= { hwInnerLinkEntry 5 }
            
        hwInnerLinkRightFrameId OBJECT-TYPE
            SYNTAX      Unsigned32
            MAX-ACCESS  read-only
            STATUS      current
            DESCRIPTION
                "Frame ID of the link's right point."
            ::= { hwInnerLinkEntry 6 }
            
        hwInnerLinkRightPortId OBJECT-TYPE
            SYNTAX      Unsigned32
            MAX-ACCESS  read-only
            STATUS      current
            DESCRIPTION
                "Port ID of the link's right virtual port."
            ::= { hwInnerLinkEntry 7 }
            
        hwInnerLinkType OBJECT-TYPE
            SYNTAX INTEGER{
                unknown(1),
                controlChannel(2),
                monitorChannel(3),
                forwardChannel(4)
                }
            MAX-ACCESS  read-only
            STATUS      current
            DESCRIPTION
                "Inner link type between the frames. A value of controlChannel
                means a kind of logical link through which control messages're
                transferred. A value of monitorChannel  means a kind of logical 
                control link which only exists between the central chassises. 
                A value of forwardChannel mean a kind of logical link which is 
                used for data forwarding."
            ::= { hwInnerLinkEntry 8 }
            
        hwInnerLinkAdminState OBJECT-TYPE
            SYNTAX INTEGER{
                notSupported(1),
                locked(2),
                shuttingDown(3),
                unlocked(4)
                }
            MAX-ACCESS read-write
            STATUS     current
            DESCRIPTION
                "The administrative state for this object, and it is possible 
                to set the state when needed. A value of locked means the resource 
                is administratively prohibited from use. A value of shuttingDown 
                means that usage is administratively limited to current instances 
                of use. A value of unlocked means the resource is not administratively 
                prohibited from use."
            ::= { hwInnerLinkEntry 9 }
        
        hwInnerLinkOperState OBJECT-TYPE
            SYNTAX INTEGER{
                unknown(1),
                mostPhyChannelUp(2),
                partPhyChannelUp(3),
                mostPhyChannelDown(4)
                }
            MAX-ACCESS read-only
            STATUS     current
            DESCRIPTION
                "The operational state for this object. A value of mostPhyChannelUp means
                most of the physical links consisting of the logical link are working well.
                It's possible that none of the physical links is wrong. A value of 
                partPhyChannelUp means several physical links of the logical link are broken
                down. A value of mostPhyChannelDown means most of the physical links of the
                logical link are down. It's possible that none of the physical links is ok. "
            ::= { hwInnerLinkEntry 10 }        
        
        hwInnerLinkAlarmLight OBJECT-TYPE
            SYNTAX BITS{
                notSupported(0),
                underRepair(1),
                critical(2),
                major(3),
                minor(4),
                alarmOutstanding(5),
                warning(6),
                indeterminate(7)
                }
            MAX-ACCESS read-only
            STATUS     current
            DESCRIPTION
                "The alarm status for this entity. It is decided by
                the alarm status of the physical links which compose
                the logical link.
                
                When no bits of this attribute are set, then none of the
                status conditions described below are present. When the
                value of under repair is set, the resource is currently
                being repaired.
                
                When the value of critical is set, one or more critical
                alarms are active against the resource. When the value of
                major is set, one or more major alarms are active against
                the resource. When the value of minor is set, one or more
                minor alarms are active against the resource. When the
                value of warning is set, one or more warning alarms are
                active against the resource. When the value of
                indeterminate is set, one or more  alarms of indeterminate
                severity are active against the resource.
                
                When the value of alarm outstanding is set, one or more
                alarms is active against the resource. The fault may or may
                not be disabling."
            ::= { hwInnerLinkEntry 11 } 

       hwInnerLinkTraps OBJECT IDENTIFIER ::= { hwInnerLinkMIB 2 }
       hwInnerLinkTrapsPrefix OBJECT IDENTIFIER ::= { hwInnerLinkTraps 1 }
       
       hwInnerLinkOnePhysicalLinkUp NOTIFICATION-TYPE
            OBJECTS { hwInnerLinkLeftPortPhysicalIndex, hwInnerLinkLeftPortPhysicalName, 
                       hwInnerLinkRightPortPhysicalIndex, hwInnerLinkRightPortPhysicalName }
            STATUS current
            DESCRIPTION 
                "One physical link of the corrresponding inner logical link is available."
            ::= { hwInnerLinkTrapsPrefix 1 }
            
       hwInnerLinkOnePhysicalLinkDown NOTIFICATION-TYPE
            OBJECTS { hwInnerLinkLeftPortPhysicalIndex, hwInnerLinkLeftPortPhysicalName, 
                       hwInnerLinkRightPortPhysicalIndex, hwInnerLinkRightPortPhysicalName }
            STATUS current
            DESCRIPTION 
                "One physical link of the corrresponding inner logical link is unavailable."
            ::= { hwInnerLinkTrapsPrefix 2 }
             
            
--     Conformance and Compliance
-- 
        hwInnerLinkConformance OBJECT IDENTIFIER ::= { hwInnerLinkMIB 3 }
        
        hwInnerLinkCompliances OBJECT IDENTIFIER ::= { hwInnerLinkConformance 1 }   
       
--  this module
        hwInnerLinkCompliance MODULE-COMPLIANCE
            STATUS              current
            DESCRIPTION 
                "The compliance statement for systems supporting
                the HUAWEI Inner Link MIB."
            MODULE -- this module
            MANDATORY-GROUPS { hwInnerLinkGroup }
            OBJECT hwInnerLinkAdminState
                MIN-ACCESS read-only
                DESCRIPTION 
                    "Write access is not required."
            ::= { hwInnerLinkCompliances 1 }   
            
        hwInnerLinkGroups OBJECT IDENTIFIER ::= { hwInnerLinkConformance 2 }
        
        hwInnerLinkGroup OBJECT-GROUP
            OBJECTS { hwInnerLinkLeftPortPhysicalIndex, hwInnerLinkLeftPortPhysicalName,
            hwInnerLinkRightPortPhysicalIndex, hwInnerLinkRightPortPhysicalName,
            hwInnerLinkLeftFrameType, hwInnerLinkLeftFrameId,
            hwInnerLinkLeftPortId, hwInnerLinkRightFrameType, hwInnerLinkRightFrameId,
            hwInnerLinkRightPortId, hwInnerLinkType, hwInnerLinkAdminState,
            hwInnerLinkOperState, hwInnerLinkAlarmLight
          }
            STATUS current
            DESCRIPTION 
                "HUAWEI Inner Link group."
            ::= { hwInnerLinkGroups 1 }
            
        hwInnerLinkNotificationGroup NOTIFICATION-GROUP
            NOTIFICATIONS { hwInnerLinkOnePhysicalLinkUp, hwInnerLinkOnePhysicalLinkDown }
            STATUS current
            DESCRIPTION 
                "Inner Link Notification group."
            ::= { hwInnerLinkGroups 2 }
    END

--
-- HUAWEI-INNER-LINK-MIB.mib
--
