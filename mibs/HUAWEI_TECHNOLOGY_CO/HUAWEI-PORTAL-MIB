-- =================================================================
-- Copyright (C) 2003 by  HUAWEI TECHNOLOGIES. All rights reserved.
--
-- Description:The HUAWEI-PORTAL-MIB  provides information about portal server
-- Reference:
-- Version: V1.0
-- History:
--     
-- =================================================================

    HUAWEI-PORTAL-MIB DEFINITIONS ::= BEGIN
 
        IMPORTS
            huaweiMgmt            
                FROM HUAWEI-MIB
            InterfaceIndex                  
                                FROM IF-MIB
            IpAddress,Unsigned32, Integer32, Counter64, OBJECT-TYPE, MODULE-IDENTITY, NOTIFICATION-TYPE
                FROM SNMPv2-SMI            
            MODULE-COMPLIANCE,OBJECT-GROUP,NOTIFICATION-GROUP
                 FROM SNMPv2-CONF	
            DisplayString, DateAndTime, RowStatus, MacAddress, TruthValue
                FROM SNMPv2-TC
            mplsVpnVrfName
                                FROM MPLS-VPN-MIB
            EnabledStatus
                                FROM P-BRIDGE-MIB;
    
    
        hwPortal MODULE-IDENTITY 
            LAST-UPDATED "201304011650Z"
            ORGANIZATION 
                "Huawei Technologies Co.,Ltd."
            CONTACT-INFO 
                    "Huawei Industrial Base
                    Bantian, Longgang
                    Shenzhen 518129
                    People's Republic of China
                    Website: http://www.huawei.com
                    Email: support@huawei.com
                    "
            DESCRIPTION 
                "The MIB contains objects of module PORTAL." 

           REVISION "201304011650Z"              -- April 01, 2013 at 16:50 GMT
            DESCRIPTION
                "Modify  hwPortalUserSlot ."    
           
            REVISION "201303271350Z"              -- March 27, 2013 at 13:50 GMT
            DESCRIPTION
                "The MIB contains objects of module PORTAL."    

            REVISION "201303191621Z"              -- March 19, 2013 at 16:21 GMT
            DESCRIPTION
                "The MIB contains objects of module PORTAL."
           
            REVISION "201301101150Z"              -- January 11, 2013 at 11:50 GMT
            DESCRIPTION
                "The MIB contains objects of module PORTAL."       
            REVISION "201306291150Z"              -- JUNE 26, 2013 at 11:50 GMT
            DESCRIPTION
                "The MIB contains objects of module PORTAL." 
            REVISION "201311281725Z"              -- NOV 28, 2013 at 17:25 GMT
            DESCRIPTION
                "The MIB contains objects of module PORTAL."     
            ::= { huaweiMgmt 4 }

        hwPortalMibObjects OBJECT IDENTIFIER ::= { hwPortal 1 }

--
-- Node definitions
--
    
--  ==================================================================
-- 
-- ======================= definition begin =========================
-- 
-- ================================================================== 


    --  ============== hwPortalConfigPara  define beginning ==============
    
        hwPortalConfigPara OBJECT IDENTIFIER ::= { hwPortalMibObjects 1 }
        
        hwPortalConfigVersionSupport OBJECT-TYPE
            SYNTAX INTEGER
                {
                v2(2),
                both(3)
                }
            MAX-ACCESS read-write
            STATUS current
            DESCRIPTION
                " 
                The version of supported protocol."
            DEFVAL { both }
            ::= { hwPortalConfigPara 1 }
        
        hwPortalConfigTextInfoSwitch OBJECT-TYPE
            SYNTAX TruthValue
            MAX-ACCESS read-write
            STATUS current
            DESCRIPTION
                "Changed to transparent transmission information.
                The source of transparent transmission information, 'true' means transparent transmission the information of PORTAL server,
                        'false' means no transparent transmission the information of PORTAL server, the default is no transparent transmission.
                "
            DEFVAL { false }
            ::= { hwPortalConfigPara 2 }

        hwPortalConfigServerUdpReceivePort OBJECT-TYPE
            SYNTAX Integer32 (1024..65535)
            MAX-ACCESS read-write
            STATUS current
            DESCRIPTION
                "The receiving UDP port of server. "
            DEFVAL { 2000 }
            ::= { hwPortalConfigPara 3 }

        hwPortalConfigServerUdpSendPort OBJECT-TYPE
            SYNTAX Integer32 (1024..65535)
            MAX-ACCESS read-write
            STATUS current
            DESCRIPTION
                "The sending UDP port of server.   "
            DEFVAL { 2000 }
            ::= { hwPortalConfigPara 4 }

        hwPortalConfigTrapUdpPort OBJECT-TYPE
            SYNTAX Integer32 (1024..65535)
            MAX-ACCESS read-write
            STATUS current
            DESCRIPTION
                "The trap sending UDP port of server, used to send the message that user has been forced to leave.  
                "
            DEFVAL { 50100 }
            ::= { hwPortalConfigPara 5 }
            
        hwPortalConfigSourecIfIndex OBJECT-TYPE
            SYNTAX InterfaceIndex
            MAX-ACCESS read-write
            STATUS current
            DESCRIPTION
                "The source interface of sending PORTAL packet.
                "
            ::= { hwPortalConfigPara 6 }  
            
        hwPortalConfigUserAgentEnableSwitch OBJECT-TYPE
           SYNTAX EnabledStatus
            MAX-ACCESS read-write
            STATUS current
            DESCRIPTION
                "The Global user agent configuration. Enable this before you want to enable
                parse http message to obtain user agent information.
                "
           ::= { hwPortalConfigPara 7 }  
            
    --  ============== hwPortalConfigPara  define end ==============         
                
    --  ============== hwPortalPacketStatisticsPara  define beginning ==============
        
        hwPortalPacketStatisticsPara OBJECT IDENTIFIER ::= { hwPortalMibObjects 2 }
        
        hwPortalStatisticsBeginTime OBJECT-TYPE
            SYNTAX DateAndTime
            MAX-ACCESS read-only
            STATUS current
            DESCRIPTION
                "The time of system startup time, statistics of start time.
                 When clear the statistics data, it will be reset.
                 If power off, the data would not be saved.
                "
            ::= { hwPortalPacketStatisticsPara 1 }
        
        hwPortalPacketStatisticsAuthenticatorError OBJECT-TYPE
            SYNTAX Counter64
            MAX-ACCESS read-only
            STATUS current
            DESCRIPTION
                "The total packet number of validate failure.
                 "
            ::= { hwPortalPacketStatisticsPara 2 }
        
        hwPortalPacketStatisticsAccessReqError OBJECT-TYPE
            SYNTAX Counter64
            MAX-ACCESS read-only
            STATUS current
            DESCRIPTION
                " The total number of access request error packet."
            ::= { hwPortalPacketStatisticsPara 3 }
        
        hwPortalPacketStatisticsLogoutReqError OBJECT-TYPE
            SYNTAX Counter64
            MAX-ACCESS read-only
            STATUS current
            DESCRIPTION
                " The total number of logout request error packet."
            ::= { hwPortalPacketStatisticsPara 4 }
        
        hwPortalPacketStatisticsInquiryReqError OBJECT-TYPE
            SYNTAX Counter64
            MAX-ACCESS read-only
            STATUS current
            DESCRIPTION
                "The total number of inquiry request error packet.
                "
            ::= { hwPortalPacketStatisticsPara 5 }
        
        hwPortalPacketStatisticsLoginConfirmError OBJECT-TYPE
            SYNTAX Counter64
            MAX-ACCESS read-only
            STATUS current
            DESCRIPTION
                "The total number of login confirm error packet.
                "
            ::= { hwPortalPacketStatisticsPara 6 }
        
        hwPortalPacketStatisticsAccessReqReceived OBJECT-TYPE
            SYNTAX Counter64
            MAX-ACCESS read-only
            STATUS current
            DESCRIPTION
                "The total number of received access request packet.
                "
            ::= { hwPortalPacketStatisticsPara 7 }
        
        hwPortalPacketStatisticsLoginReqReceived OBJECT-TYPE
            SYNTAX Counter64
            MAX-ACCESS read-only
            STATUS current
            DESCRIPTION
                "The total number of received login request packet.
                "
            ::= { hwPortalPacketStatisticsPara 8 }
        
        hwPortalPacketStatisticsLogoutReqReceived OBJECT-TYPE
            SYNTAX Counter64
            MAX-ACCESS read-only
            STATUS current
            DESCRIPTION
                "The total number of received logout request packet.
                "
            ::= { hwPortalPacketStatisticsPara 9 }
        
        hwPortalPacketStatisticsInquiryReqReceived OBJECT-TYPE
            SYNTAX Counter64
            MAX-ACCESS read-only
            STATUS current
            DESCRIPTION
                "The total number of received inquiry request packet. "
            ::= { hwPortalPacketStatisticsPara 10 }
        
        hwPortalPacketStatisticsLoginConfirmReceived OBJECT-TYPE
            SYNTAX Counter64
            MAX-ACCESS read-only
            STATUS current
            DESCRIPTION
                "The total number of received login confirm packet. "
            ::= { hwPortalPacketStatisticsPara 11 }
        
        hwPortalPacketStatisticsAccessACKFailed OBJECT-TYPE
            SYNTAX Counter64
            MAX-ACCESS read-only
            STATUS current
            DESCRIPTION
                "The total number of access ack failure packet.  "
            ::= { hwPortalPacketStatisticsPara 12 }
        
        hwPortalPacketStatisticsLoginACKFailed OBJECT-TYPE
            SYNTAX Counter64
            MAX-ACCESS read-only
            STATUS current
            DESCRIPTION
                "The total number of login ack failure packet. "
            ::= { hwPortalPacketStatisticsPara 13 }
        
        hwPortalPacketStatisticsLogoutACKFailed OBJECT-TYPE
            SYNTAX Counter64
            MAX-ACCESS read-only
            STATUS current
            DESCRIPTION
                "The total number of logout ack failure packet.  "
            ::= { hwPortalPacketStatisticsPara 14 }
        
        hwPortalPacketStatisticsInquiryACKFailed OBJECT-TYPE
            SYNTAX Counter64
            MAX-ACCESS read-only
            STATUS current
            DESCRIPTION
                "The total number of inquiry ack failure packet.  "
            ::= { hwPortalPacketStatisticsPara 15 }
        
        hwPortalPacketStatisticsAccessAckSent OBJECT-TYPE
            SYNTAX Counter64
            MAX-ACCESS read-only
            STATUS current
            DESCRIPTION
                "The total number of sending access ack packet. "
            ::= { hwPortalPacketStatisticsPara 16 }
        
        hwPortalPacketStatisticsLoginAckSent OBJECT-TYPE
            SYNTAX Counter64
            MAX-ACCESS read-only
            STATUS current
            DESCRIPTION
                "The total number of sending login ack packet. "
            ::= { hwPortalPacketStatisticsPara 17 }
        
        hwPortalPacketStatisticsLogoutAckSent OBJECT-TYPE
            SYNTAX Counter64
            MAX-ACCESS read-only
            STATUS current
            DESCRIPTION
                "The total number of sending logout ack packet.  "
            ::= { hwPortalPacketStatisticsPara 18 }
        
        hwPortalPacketStatisticsInquiryAckSent OBJECT-TYPE
            SYNTAX Counter64
            MAX-ACCESS read-only
            STATUS current
            DESCRIPTION
                "The total number of sending inquiry ack packet.  "
            ::= { hwPortalPacketStatisticsPara 19 }
        
    --  ============== hwPortalPacketStatisticsPara  define end ==============         
                
    --  ============== hwPortalConfigSecretKeyTable  define beginning ==============
        
        hwPortalConfigSecretKeyTable OBJECT-TYPE
            SYNTAX SEQUENCE OF HwPortalConfigSecretKeyEntry
            MAX-ACCESS not-accessible
            STATUS current
            DESCRIPTION
                "The shared secret key table, realizing the config of shared secret key.
                "
            ::= { hwPortalMibObjects 3 }
        
        hwPortalConfigSecretKeyEntry OBJECT-TYPE
            SYNTAX HwPortalConfigSecretKeyEntry
            MAX-ACCESS not-accessible
            STATUS current
            DESCRIPTION
                "The entry of shared secret key table. "
            INDEX { mplsVpnVrfName, hwPortalConfigPortalServerIpAddress }
            ::= { hwPortalConfigSecretKeyTable 1 }
        
        HwPortalConfigSecretKeyEntry ::=
            SEQUENCE { 
                hwPortalConfigPortalServerIpAddress
                    IpAddress,
                hwPortalConfigPortalServerIpMask
                    IpAddress,
                hwPortalConfigSecretKey
                    DisplayString,
                hwPortalConfigPortalServerPort
                        Integer32,
                hwPortalConfigPortalServerNasip   
                        TruthValue,                
                hwPortalConfigStatus
                    RowStatus,
                hwPortalConfigDetectTime  
                	Integer32
             }

        hwPortalConfigPortalServerIpAddress OBJECT-TYPE
            SYNTAX IpAddress
            MAX-ACCESS read-only
            STATUS current
            DESCRIPTION
                "The IP address of PORTAL server. "
            ::= { hwPortalConfigSecretKeyEntry 1 }
        
        hwPortalConfigPortalServerIpMask OBJECT-TYPE
            SYNTAX IpAddress
            MAX-ACCESS read-write
            STATUS current
            DESCRIPTION
                "The IP mask of PORTAL server. "
            ::= { hwPortalConfigSecretKeyEntry 2 }

        hwPortalConfigSecretKey OBJECT-TYPE
            SYNTAX DisplayString (SIZE (0..16))
            MAX-ACCESS read-write
            STATUS current
            DESCRIPTION
                "The secret key of PORTAL server.
                "
            ::= { hwPortalConfigSecretKeyEntry 3 }
        
        hwPortalConfigPortalServerPort OBJECT-TYPE
            SYNTAX Integer32
            MAX-ACCESS read-write
            STATUS current
            DESCRIPTION
                "The port of PORTAL server."
            ::= { hwPortalConfigSecretKeyEntry 4 }

        hwPortalConfigPortalServerNasip OBJECT-TYPE
            SYNTAX TruthValue
            MAX-ACCESS read-write
            STATUS current
            DESCRIPTION
                "Whether transport the NAS IP address.
                "
            DEFVAL { false }
            ::= { hwPortalConfigSecretKeyEntry 5 }    
            
        hwPortalConfigStatus OBJECT-TYPE
            SYNTAX RowStatus
            MAX-ACCESS read-write
            STATUS current
            DESCRIPTION
                "The row status."
            ::= { hwPortalConfigSecretKeyEntry 6 } 
            
        hwPortalConfigDetectTime OBJECT-TYPE
            SYNTAX Integer32 (1..65535)
            MAX-ACCESS read-create
            STATUS current
            DESCRIPTION
                "WEB authentication server detect time."
            ::= { hwPortalConfigSecretKeyEntry 7 }

        
    --  ============== hwPortalConfigSecretKeyTable  define end ==============         
                
    --  ============== hwPortalServerTable  define beginning ==============
        
        hwPortalServerTable OBJECT-TYPE
            SYNTAX SEQUENCE OF HwPortalServerEntry
            MAX-ACCESS not-accessible
            STATUS current
            DESCRIPTION
                "The statistics table of PORTAL server, used to inquire total number of every access user on PORTAL server.
                "
            ::= { hwPortalMibObjects 4 }
        
        hwPortalServerEntry OBJECT-TYPE
            SYNTAX HwPortalServerEntry
            MAX-ACCESS not-accessible
            STATUS current
            DESCRIPTION
                "The entry of statistics table of PORTAL server."
            INDEX { mplsVpnVrfName, hwPortalServerIpAddress }
            ::= { hwPortalServerTable 1 }
        
        HwPortalServerEntry ::=
            SEQUENCE { 
                hwPortalServerIpAddress
                    IpAddress,
                hwPortalServerUserNum    
                    Integer32
             }

        hwPortalServerIpAddress OBJECT-TYPE
            SYNTAX IpAddress
            MAX-ACCESS read-only
            STATUS current
            DESCRIPTION
                "The IP address of PORTAL server."
            ::= { hwPortalServerEntry 1 }
        
        hwPortalServerUserNum     OBJECT-TYPE
            SYNTAX Integer32
            MAX-ACCESS read-only
            STATUS current
            DESCRIPTION
                "
                The total number of access users on PORTAL server.
                "
            ::= { hwPortalServerEntry 2 }

    --  ============== hwPortalServerTable  define end ==============         
                
    --  ============== hwPortalUserTable  define beginning ==============
        
        hwPortalUserTable OBJECT-TYPE
            SYNTAX SEQUENCE OF HwPortalUserEntry
            MAX-ACCESS not-accessible
            STATUS current
            DESCRIPTION
                "
                The PORTAL user table, used to inquire the attribute of PORTAL users.
                "
            ::= { hwPortalMibObjects 5 }
        
        hwPortalUserEntry OBJECT-TYPE
            SYNTAX HwPortalUserEntry
            MAX-ACCESS not-accessible
            STATUS current
            DESCRIPTION
                "The entry of PORTAL user table."
            INDEX { hwPortalUserMACAddress }
            ::= { hwPortalUserTable 1 }
        
        HwPortalUserEntry ::=
            SEQUENCE { 
                hwPortalUserMACAddress
                    MacAddress,
                hwPortalUserIpAddress
                    IpAddress,
                hwPortalUserPort
                    OCTET STRING,
                hwPortalUserUpFlow
                    Integer32,
                hwPortalUserDownFlow
                    Counter64,
                hwPortalUserName
                    OCTET STRING,
                hwPortalUserLoginTime
                    Integer32,
                hwPortalUserServerIpAddress
                    IpAddress                    
             }

        hwPortalUserMACAddress OBJECT-TYPE
            SYNTAX MacAddress
            MAX-ACCESS read-only
            STATUS current
            DESCRIPTION
                "
                The MAC address of users.
                "
            ::= { hwPortalUserEntry 1 }
        
        hwPortalUserIpAddress OBJECT-TYPE
            SYNTAX IpAddress
            MAX-ACCESS read-only
            STATUS current
            DESCRIPTION
                "
                The IP address of users.
                "
            ::= { hwPortalUserEntry 2 }

        hwPortalUserPort OBJECT-TYPE
            SYNTAX OCTET STRING
            MAX-ACCESS read-only
            STATUS current
            DESCRIPTION
                "
                The port number of users.
                "
            ::= { hwPortalUserEntry 3 }

        hwPortalUserUpFlow OBJECT-TYPE
            SYNTAX Integer32
            MAX-ACCESS read-only
            STATUS current
            DESCRIPTION
                "
                The upstream flow, unit is bytes.
                "
            ::= { hwPortalUserEntry 4 }

        hwPortalUserDownFlow OBJECT-TYPE
            SYNTAX Counter64
            MAX-ACCESS read-only
            STATUS current
            DESCRIPTION
                "
                The downstream flow, unit is bytes.
                "
            ::= { hwPortalUserEntry 5 }

        hwPortalUserName OBJECT-TYPE
            SYNTAX OCTET STRING (SIZE(1..253))
            MAX-ACCESS read-only
            STATUS current
            DESCRIPTION
                "
                The username.
                "
            ::= { hwPortalUserEntry 6 }

        hwPortalUserLoginTime OBJECT-TYPE
            SYNTAX Integer32
            MAX-ACCESS read-only
            STATUS current
            DESCRIPTION
                "
                The login time of user.
                "
            ::= { hwPortalUserEntry 7 }

        hwPortalUserServerIpAddress OBJECT-TYPE
            SYNTAX IpAddress
            MAX-ACCESS read-only
            STATUS current
            DESCRIPTION
                "The IP address of PORTAL server."
            ::= { hwPortalUserEntry 8 }

    --  ============== hwPortalUserTable  define end ==============         
    --  ============== hwPortalConfigSecretKeyV2Table  define beginning ==============
        
        hwPortalConfigSecretKeyV2Table OBJECT-TYPE
            SYNTAX SEQUENCE OF HwPortalConfigSecretKeyV2Entry
            MAX-ACCESS not-accessible
            STATUS current
            DESCRIPTION
                "The shared secret key table, realizing the config of shared secret key.
                "
            ::= { hwPortalMibObjects 6 }
        
        hwPortalConfigSecretKeyV2Entry OBJECT-TYPE
            SYNTAX HwPortalConfigSecretKeyV2Entry
            MAX-ACCESS not-accessible
            STATUS current
            DESCRIPTION
                "The entry of shared secret key table.(V2)"
            INDEX { hwPortalVrfNameV2, hwPortalConfigPortalServerIpAddressV2 }
            ::= { hwPortalConfigSecretKeyV2Table 1 }
        
        HwPortalConfigSecretKeyV2Entry ::=
            SEQUENCE { 
                hwPortalConfigPortalServerIpAddressV2
                    IpAddress,
                hwPortalConfigPortalServerIpMaskV2
                    IpAddress,
                hwPortalConfigSecretKeyV2
                    DisplayString,
                hwPortalConfigPortalServerPortV2
                    Integer32,
                hwPortalConfigPortalServerNasipV2   
                    TruthValue,
                hwPortalConfigStatusV2
                    RowStatus,
                hwPortalVrfNameV2
                    DisplayString            
             }

        hwPortalConfigPortalServerIpAddressV2 OBJECT-TYPE
            SYNTAX IpAddress
            MAX-ACCESS read-only
            STATUS current
            DESCRIPTION
                "The IP address of PORTAL server.(V2) "
            ::= { hwPortalConfigSecretKeyV2Entry 1 }
        
        hwPortalConfigPortalServerIpMaskV2 OBJECT-TYPE
            SYNTAX IpAddress
            MAX-ACCESS read-write
            STATUS current
            DESCRIPTION
                "The IP mask of PORTAL server.(V2) "
            ::= { hwPortalConfigSecretKeyV2Entry 2 }

        hwPortalConfigSecretKeyV2 OBJECT-TYPE
            SYNTAX DisplayString (SIZE (0..16))
            MAX-ACCESS read-write
            STATUS current
            DESCRIPTION
                "The secret key of PORTAL server.(V2)"
            ::= { hwPortalConfigSecretKeyV2Entry 3 }
        
        hwPortalConfigPortalServerPortV2 OBJECT-TYPE
            SYNTAX Integer32
            MAX-ACCESS read-write
            STATUS current
            DESCRIPTION
                "The port of PORTAL server.(V2)"
            ::= { hwPortalConfigSecretKeyV2Entry 4 }

        hwPortalConfigPortalServerNasipV2 OBJECT-TYPE
            SYNTAX TruthValue
            MAX-ACCESS read-write
            STATUS current
            DESCRIPTION
                "Whether transport the NAS IP address.(V2)"
            DEFVAL { false }
            ::= { hwPortalConfigSecretKeyV2Entry 5 }
            
        hwPortalConfigStatusV2 OBJECT-TYPE
            SYNTAX RowStatus
            MAX-ACCESS read-write
            STATUS current
            DESCRIPTION
                "The row status.(V2)"
            ::= { hwPortalConfigSecretKeyV2Entry 6 }          
            
      hwPortalVrfNameV2 OBJECT-TYPE
            SYNTAX DisplayString (SIZE (1..31))
            MAX-ACCESS read-only
            STATUS current
            DESCRIPTION
                "VPN instance name of portal server (V2)"
            ::= { hwPortalConfigSecretKeyV2Entry 7 }   
                     
  
            

    --  ============== hwPortalConfigSecretKeyV2Table  define end ==============         
                
    --  ============== hwPortalServerV2Table  define beginning ==============
        
        hwPortalServerV2Table OBJECT-TYPE
            SYNTAX SEQUENCE OF HwPortalServerV2Entry
            MAX-ACCESS not-accessible
            STATUS current
            DESCRIPTION
                "The statistics table of PORTAL server, used to inquire total number of every access user on PORTAL server.(V2)"
            ::= { hwPortalMibObjects 7 }
        
        hwPortalServerV2Entry OBJECT-TYPE
            SYNTAX HwPortalServerV2Entry
            MAX-ACCESS not-accessible
            STATUS current
            DESCRIPTION
                "The entry of statistics table of PORTAL server.(V2)"
            INDEX { hwPortalVrfNameV2, hwPortalServerIpAddressV2 }
            ::= { hwPortalServerV2Table 1 }
        
        HwPortalServerV2Entry ::=
            SEQUENCE { 
                hwPortalServerIpAddressV2
                    IpAddress,
                hwPortalServerUserNumV2    
                    Integer32
             }

        hwPortalServerIpAddressV2 OBJECT-TYPE
            SYNTAX IpAddress
            MAX-ACCESS read-only
            STATUS current
            DESCRIPTION
                "The IP address of PORTAL server.(V2)"
            ::= { hwPortalServerV2Entry 1 }
        
        hwPortalServerUserNumV2     OBJECT-TYPE
            SYNTAX Integer32
            MAX-ACCESS read-only
            STATUS current
            DESCRIPTION
                "The total number of access users on PORTAL server.(V2)"
            ::= { hwPortalServerV2Entry 2 }

    --  ============== hwPortalFreeRuleTable  define beginning ==============
        hwPortalFreeRuleTable OBJECT-TYPE
	SYNTAX SEQUENCE OF HwPortalFreeRuleEntry
	MAX-ACCESS not-accessible
	STATUS current
	DESCRIPTION
		"Description."
	::= { hwPortalMibObjects 8 }

	
        hwPortalFreeRuleEntry OBJECT-TYPE
	SYNTAX HwPortalFreeRuleEntry
	MAX-ACCESS not-accessible
	STATUS current
	DESCRIPTION
		"Description."
	INDEX { hwPortalFreeRuleNumber }
	::= { hwPortalFreeRuleTable 1 }

	
        HwPortalFreeRuleEntry ::=
	SEQUENCE { 
		hwPortalFreeRuleNumber
			Integer32,
		hwPortalFreeRuleSourceMode
			Integer32,
		hwPortalFreeRuleSourceVlan
			Integer32,
		hwPortalFreeRuleSourceInterface
			OCTET STRING,
		hwPortalFreeRuleSourceIP
			IpAddress,
		hwPortalFreeRuleSourceIPMask
			IpAddress,
		hwPortalFreeRuleSourceMac
			MacAddress,
		hwPortalFreeRuleDestinationMode
			Integer32,
		hwPortalFreeRuleDestinationIP
			IpAddress,
		hwPortalFreeRuleDestinationIPMask
			IpAddress,
		hwPortalFreeRuleDestinationProtocol
			INTEGER,
		hwPortalFreeRuleDestinationPort
			Integer32,
		hwPortalFreeRuleDestinationUserGroup
			OCTET STRING
	 }

        hwPortalFreeRuleNumber OBJECT-TYPE
	SYNTAX Integer32 (0..1023)
	MAX-ACCESS not-accessible
	STATUS current
	DESCRIPTION
		"Description."
	::= { hwPortalFreeRuleEntry 1 }

	
        hwPortalFreeRuleSourceMode OBJECT-TYPE
	SYNTAX Integer32 (0..3)
	MAX-ACCESS read-only
	STATUS current
	DESCRIPTION
		"Description."
	::= { hwPortalFreeRuleEntry 2 }

	
        hwPortalFreeRuleSourceVlan OBJECT-TYPE
	SYNTAX Integer32
	MAX-ACCESS read-only
	STATUS current
	DESCRIPTION
		"Description."
	::= { hwPortalFreeRuleEntry 3 }

	
        hwPortalFreeRuleSourceInterface OBJECT-TYPE
	SYNTAX OCTET STRING
	MAX-ACCESS read-only
	STATUS current
	DESCRIPTION
		"Description."
	::= { hwPortalFreeRuleEntry 4 }

	
        hwPortalFreeRuleSourceIP OBJECT-TYPE
	SYNTAX IpAddress
	MAX-ACCESS read-only
	STATUS current
	DESCRIPTION
		"Description."
	::= { hwPortalFreeRuleEntry 5 }

	
        hwPortalFreeRuleSourceIPMask OBJECT-TYPE
	SYNTAX IpAddress
	MAX-ACCESS read-only
	STATUS current
	DESCRIPTION
		"Description."
	::= { hwPortalFreeRuleEntry 6 }

	
        hwPortalFreeRuleSourceMac OBJECT-TYPE
	SYNTAX MacAddress
	MAX-ACCESS read-only
	STATUS current
	DESCRIPTION
		"Description."
	::= { hwPortalFreeRuleEntry 7 }

	
        hwPortalFreeRuleDestinationMode OBJECT-TYPE
	SYNTAX Integer32 (0..3)
	MAX-ACCESS read-only
	STATUS current
	DESCRIPTION
		"Description."
	::= { hwPortalFreeRuleEntry 8 }

	
        hwPortalFreeRuleDestinationIP OBJECT-TYPE
	SYNTAX IpAddress
	MAX-ACCESS read-only
	STATUS current
	DESCRIPTION
		"Description."
	::= { hwPortalFreeRuleEntry 9 }

	
        hwPortalFreeRuleDestinationIPMask OBJECT-TYPE
	SYNTAX IpAddress
	MAX-ACCESS read-only
	STATUS current
	DESCRIPTION
		"Description."
	::= { hwPortalFreeRuleEntry 10 }

	
        hwPortalFreeRuleDestinationProtocol OBJECT-TYPE
	SYNTAX INTEGER
		{
		tcp(1),
		udp(2),
                                           none(3)
		}
	MAX-ACCESS read-only
	STATUS current
	DESCRIPTION
		"Description."
	::= { hwPortalFreeRuleEntry 11 }

	
        hwPortalFreeRuleDestinationPort OBJECT-TYPE
	SYNTAX Integer32
	MAX-ACCESS read-only
	STATUS current
	DESCRIPTION
		"Description."
	::= { hwPortalFreeRuleEntry 12 }

	
        hwPortalFreeRuleDestinationUserGroup OBJECT-TYPE
	SYNTAX OCTET STRING
	MAX-ACCESS read-only
	STATUS current
	DESCRIPTION
		"Description."
	::= { hwPortalFreeRuleEntry 13 }
		

        
	hwWebAuthServerListeningPort OBJECT-TYPE
	SYNTAX Integer32 (1024..55535)
	MAX-ACCESS read-write
	STATUS current
	DESCRIPTION
		"Description."
	DEFVAL { 2000 }
	::= { hwPortalMibObjects 9 }
		
	hwWebAuthServerReplyMessage OBJECT-TYPE
	SYNTAX INTEGER
		{
		enable(1),
		disable(2)
		}
	MAX-ACCESS read-write
	STATUS current
	DESCRIPTION
		"Description."
	DEFVAL { enable }
	::= { hwPortalMibObjects 10 }

	hwWebAuthServerVersion OBJECT-TYPE
	SYNTAX INTEGER
		{
		v2(1),
		v2v1(2)
		}
	MAX-ACCESS read-write
	STATUS current
	DESCRIPTION
		"Description."
	DEFVAL { v2v1 }
	::= { hwPortalMibObjects 11 }

	hwPortalOfflineDetect OBJECT-TYPE
	SYNTAX Integer32 (30..7200)
	UNITS "s"
	MAX-ACCESS read-write
	STATUS current
	DESCRIPTION
		"Description."
	DEFVAL { 300 }
	::= { hwPortalMibObjects 12 }

	hwPortalLocalServerIp OBJECT-TYPE
	SYNTAX IpAddress
	MAX-ACCESS read-write
	STATUS current
	DESCRIPTION
		"Description."
	::= { hwPortalMibObjects 13 }

	hwPortalLocalServerSSLPolicyName OBJECT-TYPE
	SYNTAX OCTET STRING (SIZE (0..31))
	MAX-ACCESS read-write
	STATUS current
	DESCRIPTION
		"Description."
	::= { hwPortalMibObjects 14 }

	hwPortalLocalServerSSLPolicyPortNum OBJECT-TYPE
	SYNTAX Integer32 (1..65535)
	MAX-ACCESS read-write
	STATUS current
	DESCRIPTION
		"Description."
	::= { hwPortalMibObjects 15 }
		
	hwPortalMaxUser OBJECT-TYPE
	SYNTAX Unsigned32 (0..4294967295)
	MAX-ACCESS read-write
	STATUS current
	DESCRIPTION
		"Description."
	::= { hwPortalMibObjects 16 }
		
	hwPortalLocalServerMaxUser OBJECT-TYPE
	SYNTAX Unsigned32 (0..4294967295)
	MAX-ACCESS read-write
	STATUS current
	DESCRIPTION
		"Description."
	::= { hwPortalMibObjects 17 }

	hwPortalLocalServerAuthMethod OBJECT-TYPE
	SYNTAX INTEGER
		{
		chap(1),
		pap(2)
		}
	MAX-ACCESS read-write
	STATUS current
	DESCRIPTION
		"Description."
	::= { hwPortalMibObjects 18 }

	hwWebAuthServerCfgTable OBJECT-TYPE
	SYNTAX SEQUENCE OF HwWebAuthServerCfgEntry
	MAX-ACCESS not-accessible
	STATUS current
	DESCRIPTION
		"Description."
	::= { hwPortalMibObjects 19 }

	hwWebAuthServerCfgEntry OBJECT-TYPE
	SYNTAX HwWebAuthServerCfgEntry
	MAX-ACCESS not-accessible
	STATUS current
	DESCRIPTION
		"Description."
	INDEX { hwWebAuthServerName }
	::= { hwWebAuthServerCfgTable 1 }

	
	HwWebAuthServerCfgEntry ::=
	SEQUENCE { 
		hwWebAuthServerName
			OCTET STRING,
		hwWebAuthServerUrl
			OCTET STRING,
		hwWebAuthServerUrlTemplate
			OCTET STRING,
		hwWebAuthServerSourceIp
			IpAddress,
		hwWebAuthServerShareKeyFormat
			INTEGER,
		hwWebAuthServerShareKey
			OCTET STRING,
		hwWebAuthServerPort
			Integer32,
		hwWebAuthServerServerDetectInterval
			Integer32,
		hwWebAuthServerServerDetectMaxTimes
			Integer32,
		hwWebAuthServerCriticalNum
			Integer32,
		hwWebAuthServerServerDetectAction
			INTEGER,
		hwWebAuthServerWebRedirection
			INTEGER,
		hwWebAuthServerUserSyncInterval
			Integer32,
		hwWebAuthServerUserSyncMaxTimes
			Integer32,
		hwWebAuthServerVpnInstance
			OCTET STRING,
		hwWebAuthServerRowStatus
			RowStatus,
		hwWebAuthServerPortAll
			INTEGER
		 }

	hwWebAuthServerName OBJECT-TYPE
	SYNTAX OCTET STRING (SIZE (1..31))
	MAX-ACCESS read-create
	STATUS current
	DESCRIPTION
		"Description."
	::= { hwWebAuthServerCfgEntry 1 }

	hwWebAuthServerUrl OBJECT-TYPE
	SYNTAX OCTET STRING (SIZE (0..200))
	MAX-ACCESS read-create
	STATUS current
	DESCRIPTION
		"Description."
	::= { hwWebAuthServerCfgEntry 2 }

	hwWebAuthServerUrlTemplate OBJECT-TYPE
	SYNTAX OCTET STRING (SIZE (0..31))
	MAX-ACCESS read-create
	STATUS current
	DESCRIPTION
		"Description."
	::= { hwWebAuthServerCfgEntry 3 }

	hwWebAuthServerSourceIp OBJECT-TYPE
	SYNTAX IpAddress
	MAX-ACCESS read-create
	STATUS current
	DESCRIPTION
		"Description."
	::= { hwWebAuthServerCfgEntry 4 }

	hwWebAuthServerShareKeyFormat OBJECT-TYPE
	SYNTAX INTEGER
		{
		simple(1),
		cipher(2)
		}
	MAX-ACCESS read-create
	STATUS current
	DESCRIPTION
		"Description."
	::= { hwWebAuthServerCfgEntry 5 }

	hwWebAuthServerShareKey OBJECT-TYPE
	SYNTAX OCTET STRING (SIZE (0..16 | 32))
	MAX-ACCESS read-create
	STATUS current
	DESCRIPTION
		"Description."
	::= { hwWebAuthServerCfgEntry 6 }

	hwWebAuthServerPort OBJECT-TYPE
	SYNTAX Integer32 (1..65535)
	MAX-ACCESS read-create
	STATUS current
	DESCRIPTION
		"Description."
	DEFVAL { 50100 }
	::= { hwWebAuthServerCfgEntry 7 }

	hwWebAuthServerServerDetectInterval OBJECT-TYPE
	SYNTAX Integer32 (30..65535)
	UNITS "s"
	MAX-ACCESS read-create
	STATUS current
	DESCRIPTION
		"Description."
	DEFVAL { 60 }
	::= { hwWebAuthServerCfgEntry 8 }

	hwWebAuthServerServerDetectMaxTimes OBJECT-TYPE
	SYNTAX Integer32 (1..255)
	MAX-ACCESS read-create
	STATUS current
	DESCRIPTION
		"Description."
	DEFVAL { 3 }
	::= { hwWebAuthServerCfgEntry 9 }

	hwWebAuthServerCriticalNum OBJECT-TYPE
	SYNTAX Integer32 (0..65535)
	MAX-ACCESS read-create
	STATUS current
	DESCRIPTION
		"Description."
	::= { hwWebAuthServerCfgEntry 10 }

	hwWebAuthServerServerDetectAction OBJECT-TYPE
	SYNTAX INTEGER
		{
		invalid(0),
		log(1),
		trap(2),
		logtrap(3),
		permitall(4),
		logpermitall(5),
		trappermitall(6),
		logtrappermitall(7)
		}
	MAX-ACCESS read-create
	STATUS current
	DESCRIPTION
		"Description."
	::= { hwWebAuthServerCfgEntry 11 }

	hwWebAuthServerWebRedirection OBJECT-TYPE
	SYNTAX INTEGER
		{
		disable(1),
		enable(2)
		}
	MAX-ACCESS read-create
	STATUS current
	DESCRIPTION
		"Description."
	::= { hwWebAuthServerCfgEntry 12 }

	hwWebAuthServerUserSyncInterval OBJECT-TYPE
	SYNTAX Integer32 (30..65535)
	UNITS "s"
	MAX-ACCESS read-create
	STATUS current
	DESCRIPTION
		"Description."
	DEFVAL { 300 }
	::= { hwWebAuthServerCfgEntry 13 }

	hwWebAuthServerUserSyncMaxTimes OBJECT-TYPE
	SYNTAX Integer32 (2..255)
	MAX-ACCESS read-create
	STATUS current
	DESCRIPTION
		"Description."
        DEFVAL { 3 }
	::= { hwWebAuthServerCfgEntry 14 }

	hwWebAuthServerVpnInstance OBJECT-TYPE
	SYNTAX OCTET STRING (SIZE (0..31))
	MAX-ACCESS read-create
	STATUS current
	DESCRIPTION
		"Description."
	::= { hwWebAuthServerCfgEntry 15 }

	hwWebAuthServerRowStatus OBJECT-TYPE
	SYNTAX RowStatus
	MAX-ACCESS read-create
	STATUS current
	DESCRIPTION
		"Description."
	::= { hwWebAuthServerCfgEntry 16 }

	hwWebAuthServerPortAll OBJECT-TYPE
	SYNTAX INTEGER
		{
		enable(1),
		disable(2)
		}
	MAX-ACCESS read-create
	STATUS current
	DESCRIPTION
		"Description."
	::= { hwWebAuthServerCfgEntry 17 }

	hwWebAuthServerIpCfgTable OBJECT-TYPE
	SYNTAX SEQUENCE OF HwWebAuthServerIpCfgEntry
	MAX-ACCESS not-accessible
	STATUS current
	DESCRIPTION
		"Description."
	::= { hwPortalMibObjects 20 }

	hwWebAuthServerIpCfgEntry OBJECT-TYPE
	SYNTAX HwWebAuthServerIpCfgEntry
	MAX-ACCESS not-accessible
	STATUS current
	DESCRIPTION
		"Description."
	INDEX { hwWebAuthServerName,hwWebAuthServerServerIp }
	::= { hwWebAuthServerIpCfgTable 1 }

	
	HwWebAuthServerIpCfgEntry ::=
	SEQUENCE { 
		hwWebAuthServerServerIp
			IpAddress,
		hwWebAuthServerIpRowStatus
			RowStatus
	 }

	hwWebAuthServerServerIp OBJECT-TYPE
	SYNTAX IpAddress
	MAX-ACCESS read-create
	STATUS current
	DESCRIPTION
	"Description."
	::= { hwWebAuthServerIpCfgEntry 1 }

	hwWebAuthServerIpRowStatus OBJECT-TYPE
	SYNTAX RowStatus
	MAX-ACCESS read-create
	STATUS current
	DESCRIPTION
		"Description."
	::= { hwWebAuthServerIpCfgEntry 2 }

	hwWebAuthenCfgTable OBJECT-TYPE
	SYNTAX SEQUENCE OF HwWebAuthenCfgEntry
	MAX-ACCESS not-accessible
	STATUS current
	DESCRIPTION
	"Description."
	::= { hwPortalMibObjects 21 }

	hwWebAuthenCfgEntry OBJECT-TYPE
	SYNTAX HwWebAuthenCfgEntry
	MAX-ACCESS not-accessible
	STATUS current
	DESCRIPTION
		"Description."
	INDEX { hwWebAuthenIfIndex }
	::= { hwWebAuthenCfgTable 1 }

	
	HwWebAuthenCfgEntry ::=
	SEQUENCE { 
		hwWebAuthenIfIndex
			Unsigned32,
		hwWebAuthenWebAuthServer
			OCTET STRING,
		hwWebAuthenWebAuthServerFlag
			INTEGER,
		hwWebAuthenPortalDomain
			OCTET STRING,
                                           hwWebAuthenWebAuthBakServer
			OCTET STRING

	 }

	hwWebAuthenIfIndex OBJECT-TYPE
	SYNTAX Unsigned32 (0..4294967295)
	MAX-ACCESS read-only
	STATUS current
	DESCRIPTION
		"Description."
	::= { hwWebAuthenCfgEntry 1 }

	hwWebAuthenWebAuthServer OBJECT-TYPE
	SYNTAX OCTET STRING (SIZE (0..31))
	MAX-ACCESS read-write
	STATUS current
	DESCRIPTION
		"Description."
	::= { hwWebAuthenCfgEntry 2 }

	hwWebAuthenWebAuthServerFlag OBJECT-TYPE
	SYNTAX INTEGER
		{
		invalid(0),
		direct(2),
		layer3(3)
		}
	MAX-ACCESS read-write
	STATUS current
	DESCRIPTION
		"Description."
	::= { hwWebAuthenCfgEntry 3 }

	hwWebAuthenPortalDomain OBJECT-TYPE
	SYNTAX OCTET STRING (SIZE (0..64))
	MAX-ACCESS read-write
	STATUS current
	DESCRIPTION
		"Description."
	::= { hwWebAuthenCfgEntry 4 }

	hwWebAuthenWebAuthBakServer OBJECT-TYPE
	SYNTAX OCTET STRING (SIZE (0..31))
	MAX-ACCESS read-write
	STATUS current
	DESCRIPTION
		"Description."
	::= { hwWebAuthenCfgEntry 5 }

	hwWebAuthenAuthNetWorkCfgTable OBJECT-TYPE
	SYNTAX SEQUENCE OF HwWebAuthenAuthNetWorkCfgEntry
	MAX-ACCESS not-accessible
	STATUS current
	DESCRIPTION
		"Description."
	::= { hwPortalMibObjects 22 }

	hwWebAuthenAuthNetWorkCfgEntry OBJECT-TYPE
	SYNTAX HwWebAuthenAuthNetWorkCfgEntry
	MAX-ACCESS not-accessible
	STATUS current
	DESCRIPTION
		"Description."
	INDEX { hwWebAuthenIfIndex, hwWebAuthenAuthNetWorkIpIndex }
	::= { hwWebAuthenAuthNetWorkCfgTable 1 }

	
	HwWebAuthenAuthNetWorkCfgEntry ::=
	SEQUENCE { 
	        hwWebAuthenAuthNetWorkIpIndex
			Integer32,
		hwWebAuthenPortalAuthNetWorkIp
			IpAddress,
		hwWebAuthenPortalAuthNetWorkIpMask
			Integer32,
		hwWebAuthenAuthNetWorkRowStatus
			RowStatus
	 }

	hwWebAuthenAuthNetWorkIpIndex OBJECT-TYPE
	SYNTAX Integer32 (1..32)
	MAX-ACCESS read-only
	STATUS current
	DESCRIPTION
		"Description."
	::= { hwWebAuthenAuthNetWorkCfgEntry 1 }
		
	hwWebAuthenPortalAuthNetWorkIp OBJECT-TYPE
	SYNTAX IpAddress
	MAX-ACCESS read-create
	STATUS current
	DESCRIPTION
		"Description."
	::= { hwWebAuthenAuthNetWorkCfgEntry 2 }

	hwWebAuthenPortalAuthNetWorkIpMask OBJECT-TYPE
	SYNTAX Integer32 (1..32)
	MAX-ACCESS read-create
	STATUS current
	DESCRIPTION
		"Description."
	::= { hwWebAuthenAuthNetWorkCfgEntry 3 }

	
	hwWebAuthenAuthNetWorkRowStatus OBJECT-TYPE
	SYNTAX RowStatus
	MAX-ACCESS read-create
	STATUS current
	DESCRIPTION
		"Description."
	::= { hwWebAuthenAuthNetWorkCfgEntry 4 }
	
	hwWebAuthenLocalServerCfgTable OBJECT-TYPE
	SYNTAX SEQUENCE OF HwWebAuthenLocalServerCfgEntry
	MAX-ACCESS not-accessible
	STATUS current
	DESCRIPTION
		"Description."
	::= { hwPortalMibObjects 23 }
	hwWebAuthenLocalServerCfgEntry OBJECT-TYPE
	SYNTAX HwWebAuthenLocalServerCfgEntry
	MAX-ACCESS not-accessible
	STATUS current
	DESCRIPTION
		"Description."
	INDEX { hwWebAuthenLocalServerIfIndex }
	::= { hwWebAuthenLocalServerCfgTable 1 }

	
	HwWebAuthenLocalServerCfgEntry ::=
	SEQUENCE { 
		hwWebAuthenLocalServerIfIndex
			Unsigned32,
		hwWebAuthenLocalServerEnable
			INTEGER
	 }
	hwWebAuthenLocalServerIfIndex OBJECT-TYPE
	SYNTAX Unsigned32 (0..4294967295)
	MAX-ACCESS read-only
	STATUS current
	DESCRIPTION
		"Description."
	::= { hwWebAuthenLocalServerCfgEntry 1 }
		
	hwWebAuthenLocalServerEnable OBJECT-TYPE
	SYNTAX INTEGER
		{
		enable(1),
		disable(2)
		}
	MAX-ACCESS read-write
	STATUS current
	DESCRIPTION
		"Description."
	::= { hwWebAuthenLocalServerCfgEntry 2 }
    --  ============== hwPortalFreeRuleTable  define ending ==============
    --  ============== hwPortalServerV2Table  define end ==============     			
			
        hwPortalMIBTrap OBJECT IDENTIFIER ::= { hwPortal 2 }

        hwPortalTrapObject OBJECT IDENTIFIER ::= { hwPortalMIBTrap 1 }
            
        hwStateChangePortalServerIp OBJECT-TYPE
            SYNTAX IpAddress
            MAX-ACCESS accessible-for-notify
            STATUS current
            DESCRIPTION
                "IP address of portal server which state is changed.

                "
            ::= { hwPortalTrapObject 1 } 
            
        hwStateChangePortalServerVrf OBJECT-TYPE
            SYNTAX OCTET STRING(SIZE (1..31))
            MAX-ACCESS accessible-for-notify
            STATUS current
            DESCRIPTION
                " VPN-instance of portal server which state is changed.

                "   
            ::= { hwPortalTrapObject 2 }    
            
       hwPortalUserSlot OBJECT-TYPE
            SYNTAX DisplayString (SIZE(1..32))
            MAX-ACCESS read-only
            STATUS current
            DESCRIPTION
            "Slot"    
            ::= { hwPortalTrapObject 3 }
            
       hwPortalUserNum OBJECT-TYPE
            SYNTAX Integer32
            MAX-ACCESS accessible-for-notify
            STATUS current
            DESCRIPTION
                "The number of portal users."   
            ::= { hwPortalTrapObject 4 }    
            
       hwPortalPercentage OBJECT-TYPE
            SYNTAX Integer32
            MAX-ACCESS accessible-for-notify
            STATUS current
            DESCRIPTION
                "The number of portal alarm percentage."   
            ::= { hwPortalTrapObject 5 }
        hwPortalTrapsDefine OBJECT IDENTIFIER ::= { hwPortalMIBTrap 2 }
                
        hwPortalServerTraps OBJECT IDENTIFIER ::= { hwPortalTrapsDefine 1 }
       
        hwPortalServerUp NOTIFICATION-TYPE
            OBJECTS { hwStateChangePortalServerIp, hwStateChangePortalServerVrf }
            STATUS current
            DESCRIPTION
                "
                1 Notice/Trap name:  Portal server up
                2 Notice/Trap generation cause:  Portal server up 
                3 Repair suggestions:
                    Check portal server status .                
                "
            ::= { hwPortalServerTraps 1 }
            
        hwPortalServerDown NOTIFICATION-TYPE
            OBJECTS { hwStateChangePortalServerIp, hwStateChangePortalServerVrf }
            STATUS current
            DESCRIPTION
                "
                1 Notice/Trap name:  Portal server down
                2 Notice/Trap generation cause:  Portal server down 
                3 Repair suggestions:
                    Check portal server status .
                "
            ::= { hwPortalServerTraps 2 }
            
        hwPortalMaxUserAlarm NOTIFICATION-TYPE
            OBJECTS { hwPortalUserSlot, hwPortalUserNum, hwPortalPercentage }
            STATUS current
            DESCRIPTION 
               "
                1 Notice/Trap name:  Portal Max User Alarm 
                2 Notice/Trap generation cause:  The number of portal users reached the maximum  
                3 Repair suggestions:
               "
           ::= { hwPortalServerTraps 3 }
            
        hwPortalUserClearAlarm NOTIFICATION-TYPE
            OBJECTS { hwPortalUserSlot, hwPortalUserNum, hwPortalPercentage }
            STATUS current
            DESCRIPTION  
              "
                1 Notice/Trap name:  Portal User Clear Alarm  
                2 Notice/Trap generation cause:  The Portal Max User Alarm is cleared 
               3 Repair suggestions:
               "
           ::= { hwPortalServerTraps 4 }
            
    --  ============== conformance information ==============
        hwPortalConformance OBJECT IDENTIFIER ::= { hwPortal 3 }
        
        hwPortalCompliances OBJECT IDENTIFIER ::= { hwPortalConformance 1 }
        hwPortalCompliance MODULE-COMPLIANCE
               STATUS      current
               DESCRIPTION
                   "The compliance statement for systems supporting 
                the this module."

               MODULE      -- this module
               MANDATORY-GROUPS    {hwPortalConfigParaObjectGroup, 
                                    hwPortalPacketStatisticsParaObjectGroup,
                                    hwPortalConfigSecretKeyObjectGroup, 
                                    hwPortalServerObjectGroup, 
                                    hwPortalUserObjectGroup,
                                    hwPortalConfigSecretKeyV2ObjectGroup,
                                    hwPortalServerV2ObjectGroup,
                                    hwPortalServerUpDownGroup,
                                    hwPortalServerTrapGroup,                                    
				    hwWebAuthServerGlobalCfgGroup, 
				    hwWebAuthServerCfgGroup, 
				    hwWebAuthServerIpCfgGroup, 
				    hwWebAuthenCfgGroup, 
				    hwWebAuthenAuthNetWorkCfgGroup, 
			            hwWebAuthenLocalServerCfgGroup }                                               
              ::= { hwPortalCompliances 1 }  
              
          
        --  ============== groups ==============  
        hwPortalObjectGroups OBJECT IDENTIFIER ::= { hwPortalConformance 2 } 
            
        hwPortalConfigParaObjectGroup OBJECT-GROUP
            OBJECTS { hwPortalConfigVersionSupport, 
                      hwPortalConfigTextInfoSwitch,
                      hwPortalConfigServerUdpReceivePort,
                      hwPortalConfigServerUdpSendPort, 
                      hwPortalConfigTrapUdpPort, 
                      hwPortalConfigSourecIfIndex ,
                      hwPortalConfigUserAgentEnableSwitch}
            STATUS current
            DESCRIPTION 
                "The config parameter group."
            ::= { hwPortalObjectGroups 1 }

        hwPortalPacketStatisticsParaObjectGroup OBJECT-GROUP
            OBJECTS { hwPortalStatisticsBeginTime, 
                      hwPortalPacketStatisticsAuthenticatorError, 
                      hwPortalPacketStatisticsAccessReqError, 
                      hwPortalPacketStatisticsLogoutReqError,
                      hwPortalPacketStatisticsInquiryReqError, 
                      hwPortalPacketStatisticsLoginConfirmError,
                      hwPortalPacketStatisticsAccessReqReceived, 
                      hwPortalPacketStatisticsLoginReqReceived,
                      hwPortalPacketStatisticsLogoutReqReceived, 
                      hwPortalPacketStatisticsInquiryReqReceived,
                      hwPortalPacketStatisticsLoginConfirmReceived,
                      hwPortalPacketStatisticsAccessACKFailed,
                      hwPortalPacketStatisticsLoginACKFailed, 
                      hwPortalPacketStatisticsLogoutACKFailed,
                      hwPortalPacketStatisticsInquiryACKFailed, 
                      hwPortalPacketStatisticsAccessAckSent,
                      hwPortalPacketStatisticsLoginAckSent, 
                      hwPortalPacketStatisticsLogoutAckSent,
                      hwPortalPacketStatisticsInquiryAckSent }
            STATUS current
            DESCRIPTION 
                "The pachet statistics parameter group."
            ::= { hwPortalObjectGroups 2 }
        
        hwPortalConfigSecretKeyObjectGroup OBJECT-GROUP
            OBJECTS { hwPortalConfigPortalServerIpAddress, 
                      hwPortalConfigPortalServerIpMask, 
                      hwPortalConfigSecretKey,
                      hwPortalConfigPortalServerPort, 
                      hwPortalConfigPortalServerNasip, 
                      hwPortalConfigStatus }
            STATUS current
            DESCRIPTION 
                "The config secret key group."
            ::= { hwPortalObjectGroups 3 }
        
        hwPortalServerObjectGroup OBJECT-GROUP
            OBJECTS { hwPortalServerIpAddress, 
                      hwPortalServerUserNum}
            STATUS current
            DESCRIPTION 
                "The PORTAL server group."
            ::= { hwPortalObjectGroups 4 }
        
        hwPortalUserObjectGroup OBJECT-GROUP
            OBJECTS { hwPortalUserMACAddress, 
                      hwPortalUserIpAddress, 
                      hwPortalUserPort,
                      hwPortalUserUpFlow, 
                      hwPortalUserDownFlow, 
                      hwPortalUserName,
                      hwPortalUserLoginTime, 
                      hwPortalUserServerIpAddress}
            STATUS current
            DESCRIPTION 
                "The PORTAL user group."
            ::= { hwPortalObjectGroups 5 }
            
        hwPortalConfigSecretKeyV2ObjectGroup OBJECT-GROUP
            OBJECTS { hwPortalConfigPortalServerIpAddressV2, 
                      hwPortalConfigPortalServerIpMaskV2, 
                      hwPortalConfigSecretKeyV2,
                      hwPortalConfigPortalServerPortV2, 
                      hwPortalConfigPortalServerNasipV2,
                      hwPortalConfigStatusV2, 
                      hwPortalVrfNameV2}
            STATUS current
            DESCRIPTION 
                "The config secret key group.(V2)"
            ::= { hwPortalObjectGroups 6 }        
                
        hwPortalServerV2ObjectGroup OBJECT-GROUP
            OBJECTS { hwPortalServerIpAddressV2, 
                      hwPortalServerUserNumV2}
            STATUS current
            DESCRIPTION 
                "The PORTAL server group.(V2)"
            ::= { hwPortalObjectGroups 7 } 
            
        hwPortalServerUpDownGroup NOTIFICATION-GROUP
            NOTIFICATIONS { hwPortalServerUp, hwPortalServerDown, hwPortalMaxUserAlarm, hwPortalUserClearAlarm}
            STATUS current
            DESCRIPTION 
                "The PORTAL server status."
            ::= { hwPortalObjectGroups 8 } 

        hwPortalServerTrapGroup OBJECT-GROUP
            OBJECTS { hwStateChangePortalServerIp, hwStateChangePortalServerVrf, hwPortalUserSlot, hwPortalUserNum, hwPortalPercentage}
            STATUS current
            DESCRIPTION 
            "The PORTAL trap  group configuration."
            ::= { hwPortalObjectGroups 9 }
       
        hwWebAuthServerCfgGroup OBJECT-GROUP
            OBJECTS { hwWebAuthServerName, hwWebAuthServerUrl, hwWebAuthServerSourceIp, hwWebAuthServerShareKeyFormat, 
				hwWebAuthServerShareKey, hwWebAuthServerPort, hwWebAuthServerServerDetectInterval, hwWebAuthServerServerDetectMaxTimes, hwWebAuthServerCriticalNum, 
				hwWebAuthServerServerDetectAction, hwWebAuthServerWebRedirection, hwWebAuthServerUserSyncInterval, hwWebAuthServerUserSyncMaxTimes, hwWebAuthServerVpnInstance, 
				hwWebAuthServerRowStatus, hwWebAuthServerPortAll}
            STATUS current
            DESCRIPTION 
            "The WEB auth server configuration."
            ::= { hwPortalObjectGroups 10 }

        hwWebAuthServerIpCfgGroup OBJECT-GROUP
            OBJECTS { hwWebAuthServerServerIp, hwWebAuthServerIpRowStatus }
            STATUS current
            DESCRIPTION 
            "The WEB auth server ip configuration."
            ::= { hwPortalObjectGroups 11 }

        hwWebAuthenCfgGroup OBJECT-GROUP
            OBJECTS { hwWebAuthenIfIndex, hwWebAuthenWebAuthServer, hwWebAuthenWebAuthServerFlag,hwWebAuthenPortalDomain,hwWebAuthenWebAuthBakServer }
            STATUS current
            DESCRIPTION 
            "The WEB authen configuration."
            ::= { hwPortalObjectGroups 12 }

        hwWebAuthenAuthNetWorkCfgGroup OBJECT-GROUP
            OBJECTS { hwWebAuthenAuthNetWorkIpIndex,hwWebAuthenPortalAuthNetWorkIp, hwWebAuthenPortalAuthNetWorkIpMask, hwWebAuthenAuthNetWorkRowStatus }
            STATUS current
            DESCRIPTION 
            "The WEB authen configuration."
            ::= { hwPortalObjectGroups 13 }

        hwWebAuthenLocalServerCfgGroup OBJECT-GROUP
            OBJECTS { hwWebAuthenLocalServerIfIndex, hwWebAuthenLocalServerEnable }
            STATUS current
            DESCRIPTION 
            "The WEB authen local server configuration."
            ::= { hwPortalObjectGroups 14 }
        hwWebAuthServerGlobalCfgGroup OBJECT-GROUP
            OBJECTS { hwWebAuthServerListeningPort, hwWebAuthServerReplyMessage, hwWebAuthServerVersion, hwPortalOfflineDetect, hwPortalLocalServerIp, 
				hwPortalLocalServerSSLPolicyName, hwPortalLocalServerSSLPolicyPortNum, hwPortalMaxUser,hwPortalLocalServerMaxUser, hwPortalLocalServerAuthMethod }
            STATUS current
            DESCRIPTION 
            "The global configuration."
            ::= { hwPortalObjectGroups 15 }
        --  ============== conformance information define end ==============            
                
    
    END
