-- Description: HUAWEI Private Extended Interface MIB
-- Reference:
-- Version: V1.0
-- History:
--      V1.0 
-- ==================================================================
-- ==================================================================
-- 
-- Varibles and types be imported
--
-- ==================================================================
HUAWEI-RANAPS-MIB DEFINITIONS ::= BEGIN

    IMPORTS         
    	InterfaceIndex, ifName			
			FROM IF-MIB                
    	OBJECT-GROUP, MODULE-COMPLIANCE, NOTIFICATION-GROUP            
			FROM SNMPv2-CONF  	          
    	IpAddress, Integer32, Unsigned32, OBJECT-TYPE,MODULE-IDENTITY, NOTIFICATION-TYPE            
        	FROM SNMPv2-SMI                           
    	PhysAddress,RowStatus            
        	FROM SNMPv2-TC 
    	hwDatacomm
        	FROM HUAWEI-MIB;
  
    hwRanApsMIB MODULE-IDENTITY
        LAST-UPDATED "200906020000Z"          -- June 2, 2009 at 00:00 GMT

        ORGANIZATION 
            "Huawei Technologies co.,Ltd."
        CONTACT-INFO 
            "8090 Team Huawei Technologies co.,Ltd.
            Huawei Bld.,NO.3 Xinxi Rd., 
            Shang-Di Information Industry Base,
            Hai-Dian District Beijing P.R. China
            http://www.huawei.com
        Zip:100085
            "
        DESCRIPTION
            "This file is an Automatic Protection Switching MIB. It provides some 
            APS configurations MIB and some APS alarms."
            ::= { hwDatacomm 200 }  
         
      -- Textual Convention

-- ============================================================================
-- Node definitions
-- ============================================================================ 

-- 1.3.6.1.4.1.2011.5.25.200
 
    hwRanApsObjects OBJECT IDENTIFIER ::= { hwRanApsMIB 1 }   
    hwRanApsTraps OBJECT IDENTIFIER ::= { hwRanApsMIB 2 }  
    hwRanApsConformance OBJECT IDENTIFIER ::= { hwRanApsMIB 3 }

-- ============================================================================
--
-- ======================= Objects definitions=================================
--
-- ============================================================================  
  
  		hwRanApsProtectionTable OBJECT-TYPE
			SYNTAX SEQUENCE OF HwRanApsProtectionEntry
			MAX-ACCESS not-accessible
			STATUS current
			DESCRIPTION
				"APS protection configuration."
			::= { hwRanApsObjects 1 }	

		hwRanApsProtectionEntry OBJECT-TYPE
			SYNTAX HwRanApsProtectionEntry
			MAX-ACCESS not-accessible
			STATUS current
			DESCRIPTION
				"APS protection configuration entry."
			INDEX { hwRanApsProGroupIdIndex,hwRanApsIfIndexIndex }
			::= { hwRanApsProtectionTable 1 }
		
		HwRanApsProtectionEntry ::=
			SEQUENCE {
				hwRanApsProGroupIdIndex 
					Unsigned32,
				hwRanApsIfIndexIndex 
					InterfaceIndex,				 
				hwRanApsProtectionGroupNum 
					Unsigned32,
				hwRanApsIfIndex 
					InterfaceIndex,
				hwRanApsIfType
					INTEGER, 
				hwRanApsRestoreWaitTime  
					Integer32,
				hwRanApsProtectSwitch 
					INTEGER,
				hwRanApsProtectMode
					INTEGER,
				hwRanApsWorkingIfStatus 
					INTEGER,
				hwRanApsIfPeerIp
					IpAddress,
				hwRanApsIfLocalIp
					IpAddress,
				hwRanApsKeepaliveTimer
					Integer32,
				hwRanApsHoldTimer 
					Integer32, 
				hwRanApsIfName
				    OCTET STRING,
				hwRanApsSystemId
					PhysAddress,
				hwRanApsRowStatus
					RowStatus  
			 }
-- ==============================================================================			 
		hwRanApsProGroupIdIndex OBJECT-TYPE
			SYNTAX Unsigned32  (1..192)
			MAX-ACCESS read-create
			STATUS current
			DESCRIPTION
				"The table's index that is APS protection group number from 1 to 192."
			::= { hwRanApsProtectionEntry 1 }
		hwRanApsIfIndexIndex OBJECT-TYPE
			SYNTAX InterfaceIndex
			MAX-ACCESS read-only
			STATUS current
			DESCRIPTION
				"The APS interface index."
			::= { hwRanApsProtectionEntry 2 }

		hwRanApsProtectionGroupNum OBJECT-TYPE
			SYNTAX Unsigned32  (1..192)
			MAX-ACCESS read-create
			STATUS current
			DESCRIPTION
				"The table's index that is APS protection group number from 1 to 192."
			::= { hwRanApsProtectionEntry 3 }
		hwRanApsIfIndex OBJECT-TYPE
			SYNTAX InterfaceIndex
			MAX-ACCESS read-only
			STATUS current
			DESCRIPTION
				"The APS interface index."
			::= { hwRanApsProtectionEntry 4 }
		
		hwRanApsIfType OBJECT-TYPE
			SYNTAX INTEGER  
			{
			invalid(0),
			work(1),
			protect(2)
			}
			MAX-ACCESS read-create
			STATUS current
			DESCRIPTION
				"The APS interface type."
			::= { hwRanApsProtectionEntry 5 }
 		
		hwRanApsRestoreWaitTime  OBJECT-TYPE
			SYNTAX Integer32 (0..12)
			MAX-ACCESS read-create
			STATUS current
			DESCRIPTION
				"The APS restrore wait time.zero is no revert mode"
			::= { hwRanApsProtectionEntry 6 }	   
		hwRanApsProtectSwitch  OBJECT-TYPE
			SYNTAX INTEGER 
			{
			invalid(0),
			lock(1),
			force(2),
			manual(3)
			}
			MAX-ACCESS read-create
			STATUS current
			DESCRIPTION
				"The switch of APS protection."
			::= { hwRanApsProtectionEntry 7 }
		hwRanApsProtectMode  OBJECT-TYPE
			SYNTAX INTEGER
			{
			invalid(0),
			oneplusoneunidirection(1),
			oneplusonebidirection(2),
			onetooneunidirection(3),
			onetoonebidirection(4)
			}
			MAX-ACCESS read-create
			STATUS current
			DESCRIPTION
				"The protect mode of APS."
			::= { hwRanApsProtectionEntry 8 }
		hwRanApsWorkingIfStatus  OBJECT-TYPE
			SYNTAX INTEGER
			{
			active(1),
			inactive(2)
			}
			MAX-ACCESS read-only
			STATUS current
			DESCRIPTION
				"Status of the APS interface."
			::= { hwRanApsProtectionEntry 9 }
		hwRanApsIfPeerIp  OBJECT-TYPE
			SYNTAX IpAddress
			MAX-ACCESS read-create
			STATUS current
			DESCRIPTION
				"MC-APS peer ip."
			::= { hwRanApsProtectionEntry 10 }
		hwRanApsIfLocalIp  OBJECT-TYPE
			SYNTAX IpAddress
			MAX-ACCESS read-create
			STATUS current
			DESCRIPTION
				"MC-APS local ip."
			::= { hwRanApsProtectionEntry 11 }
		hwRanApsKeepaliveTimer  OBJECT-TYPE
			SYNTAX Integer32 (1..60)
			MAX-ACCESS read-create
			STATUS current
			DESCRIPTION
				"MC-APS keep a live timer."
			::= { hwRanApsProtectionEntry 12 }			
		hwRanApsHoldTimer  OBJECT-TYPE
			SYNTAX Integer32 (3..180)
			MAX-ACCESS read-create
			STATUS current
			DESCRIPTION
				"MC-APS hold timer."
			::= { hwRanApsProtectionEntry 13 }								
		hwRanApsIfName  OBJECT-TYPE
	    	SYNTAX      OCTET STRING (SIZE (1..64))
			MAX-ACCESS read-only
			STATUS current
			DESCRIPTION
				"Interface name."
			::= { hwRanApsProtectionEntry 14 }
		hwRanApsSystemId  OBJECT-TYPE
	    	SYNTAX PhysAddress
			MAX-ACCESS read-only
			STATUS current
			DESCRIPTION
				"The system ID of the APS. It is a physical address.."
			::= { hwRanApsProtectionEntry 15 }
		hwRanApsRowStatus  OBJECT-TYPE
			SYNTAX RowStatus
			MAX-ACCESS read-create
			STATUS current
			DESCRIPTION
				"Current operation status of the row."
			::= { hwRanApsProtectionEntry 16}

  -- ======================= APS group table =================================
		hwRanApsGroupTable OBJECT-TYPE
			SYNTAX SEQUENCE OF HwRanApsGroupEntry
			MAX-ACCESS not-accessible
			STATUS current
			DESCRIPTION
				"APS group table."
			::= { hwRanApsObjects 2 }	

		hwRanApsGroupEntry OBJECT-TYPE
			SYNTAX HwRanApsGroupEntry
			MAX-ACCESS not-accessible
			STATUS current
			DESCRIPTION
				"APS group table entry."
			INDEX { hwRanApsGroupId }
			::= { hwRanApsGroupTable 1 }
		
		HwRanApsGroupEntry ::=
			SEQUENCE { 
				hwRanApsGroupId
					Unsigned32,
				hwRanApsTableRowStatus
					RowStatus  
			 }
-- ==============================================================================			 
		hwRanApsGroupId OBJECT-TYPE
			SYNTAX Unsigned32  (1..192)
			MAX-ACCESS read-only
			STATUS current
			DESCRIPTION
				"The table's index that is APS protection group number from 1 to 192."
			::= { hwRanApsGroupEntry 1 }
 
 		hwRanApsTableRowStatus  OBJECT-TYPE
			SYNTAX RowStatus
			MAX-ACCESS read-create
			STATUS current
			DESCRIPTION
				"Current operation status of the row."
			::= { hwRanApsGroupEntry 2 }
 
-- ==================================================================================

 -- ======================= APS info table =================================
		hwRanApsInfoTable OBJECT-TYPE
			SYNTAX SEQUENCE OF HwRanApsInfoEntry
			MAX-ACCESS not-accessible
			STATUS current
			DESCRIPTION
				"APS group table."
			::= { hwRanApsObjects 3 }	

		hwRanApsInfoEntry OBJECT-TYPE
			SYNTAX HwRanApsInfoEntry
			MAX-ACCESS not-accessible
			STATUS current
			DESCRIPTION
				"APS group table entry."
			INDEX { hwRanApsInfoGroupId }
			::= { hwRanApsInfoTable 1 }
		
		HwRanApsInfoEntry ::=
			SEQUENCE { 
				hwRanApsInfoGroupId
					Unsigned32,
			    hwRanApsRemoteProtectMode
					INTEGER,   
				hwRanApsPgpInfo
					INTEGER,
				hwRanApsInfoRowStatus
					RowStatus  
			 }
-- ==============================================================================			 
		hwRanApsInfoGroupId OBJECT-TYPE
			SYNTAX Unsigned32  (1..192)
			MAX-ACCESS read-only
			STATUS current
			DESCRIPTION
				"The table's index that is APS protection group number from 1 to 192."
			::= { hwRanApsInfoEntry 1 }
 		hwRanApsRemoteProtectMode  OBJECT-TYPE
			SYNTAX INTEGER 			
			{
			invalid(0),
			oneplusoneunidirection(1),
			oneplusonebidirection(2),
			onetooneunidirection(3),
			onetoonebidirection(4)
			}  
			MAX-ACCESS read-only
			STATUS current
			DESCRIPTION
				"Remote APS mode."
			::= { hwRanApsInfoEntry 2 }						 
		hwRanApsPgpInfo  OBJECT-TYPE
			SYNTAX INTEGER 			
			{
			valid(0),
			apsgroupidmismatch(1),
			apsgroupversionmismatch(2)
			}  
			MAX-ACCESS read-only
			STATUS current
			DESCRIPTION
				"PGP information."
			::= { hwRanApsInfoEntry 3 } 
 		hwRanApsInfoRowStatus  OBJECT-TYPE
			SYNTAX RowStatus
			MAX-ACCESS read-only
			STATUS current
			DESCRIPTION
				"Current operation status of the row."
			::= { hwRanApsInfoEntry 4 }
 
-- ==================================================================================
									
-- ==================================================================================
-- alarm
  
		hwRanApsFsmFail  NOTIFICATION-TYPE
			OBJECTS {hwRanApsIfIndex, hwRanApsIfName,hwRanApsProtectionGroupNum}
			STATUS current
			DESCRIPTION 
			"APS FSM fail."
			::= { hwRanApsTraps 1}
	

		hwRanPgpPktError  NOTIFICATION-TYPE
			OBJECTS {hwRanApsIfIndex ,hwRanApsIfName,hwRanApsProtectionGroupNum,hwRanApsIfPeerIp,hwRanApsPgpInfo}
			STATUS current	
			DESCRIPTION 
			"PGP receive error packets."
			::= { hwRanApsTraps 2}  
	
		hwRanPgpKeepalivePktOvertime  NOTIFICATION-TYPE
			OBJECTS {hwRanApsIfIndex,hwRanApsIfName,hwRanApsProtectionGroupNum,hwRanApsIfPeerIp}
			STATUS current	
			DESCRIPTION 
			"Keep alive packet of PGP is overtime."
			::= { hwRanApsTraps 3}  
   	
		hwRanApsUniBidMismatch  NOTIFICATION-TYPE
			OBJECTS {hwRanApsIfIndex, hwRanApsIfName,hwRanApsProtectionGroupNum,hwRanApsProtectMode,hwRanApsRemoteProtectMode}
			STATUS current
			DESCRIPTION 
			"The type of APS proctection doesn't match."
			::= { hwRanApsTraps 4}                      
                         
		hwRanApsK1K2Mismatch  NOTIFICATION-TYPE
			OBJECTS {hwRanApsIfIndex ,hwRanApsIfName, hwRanApsProtectionGroupNum}
			STATUS current	
			DESCRIPTION 
			"The byte K1 and K2 are not matched."
			::= { hwRanApsTraps 5}  
		
		hwRanApsK2Mismatch  NOTIFICATION-TYPE
			OBJECTS {hwRanApsIfIndex,hwRanApsIfName, hwRanApsProtectionGroupNum}
			STATUS current	
			DESCRIPTION 
			"The byte K2 is not matched."
			::= { hwRanApsTraps 6} 
			
		hwRanApsProtectSwitchOver NOTIFICATION-TYPE
			OBJECTS {hwRanApsIfIndex,hwRanApsIfName ,hwRanApsIfType,hwRanApsProtectionGroupNum }
			STATUS current
			DESCRIPTION 
				"APS protection switch successful."
			::= { hwRanApsTraps 7 }
			
		hwRanApsProtectSwitchBackOver NOTIFICATION-TYPE
			OBJECTS {hwRanApsIfIndex,hwRanApsIfName,hwRanApsIfType,hwRanApsProtectionGroupNum}
			STATUS current
			DESCRIPTION 
				"APS protection restore successful."
			::= { hwRanApsTraps 8 }	
			
		hwRanApsInterfaceReady NOTIFICATION-TYPE
			OBJECTS {hwRanApsIfIndex,hwRanApsIfName,hwRanApsProtectionGroupNum}
			STATUS current
			DESCRIPTION 
				"The interface is up, and it becomes the APS back interface."
			::= { hwRanApsTraps 9 }			
	
--  compliance statements	 

		
		hwRanApsCompliances OBJECT IDENTIFIER ::= { hwRanApsConformance 1 }
		

-- this module

		hwRanApsCompliance MODULE-COMPLIANCE
			STATUS current
			DESCRIPTION 
				"The compliance statement for entities that implement 
				extend APS on a router."
			MODULE -- this module
				MANDATORY-GROUPS {hwRanApsProtectionGroup,hwRanApsGroupGroup,hwRanApsInfoGroup,hwRanApsNotificationsGroup }
			::= { hwRanApsCompliances 1 }


		hwRanApsGroups OBJECT IDENTIFIER ::= { hwRanApsConformance 2 }
		
--   units of conformance 
		hwRanApsProtectionGroup OBJECT-GROUP
			OBJECTS {hwRanApsProGroupIdIndex,hwRanApsIfIndexIndex,hwRanApsProtectionGroupNum,hwRanApsIfIndex,hwRanApsIfType,hwRanApsRestoreWaitTime,hwRanApsProtectSwitch, hwRanApsProtectMode,
					hwRanApsWorkingIfStatus,hwRanApsIfPeerIp,hwRanApsIfLocalIp,hwRanApsKeepaliveTimer,hwRanApsHoldTimer,hwRanApsIfName,hwRanApsSystemId,hwRanApsRowStatus }
			STATUS current
			DESCRIPTION 
				"This is a optional group of APS configuration information."
			::= { hwRanApsGroups 1 }
			
		hwRanApsGroupGroup OBJECT-GROUP
			OBJECTS {hwRanApsGroupId,hwRanApsTableRowStatus }
			STATUS current
			DESCRIPTION 
				"This is a optional group of APS group information."
			::= { hwRanApsGroups 2 }
		hwRanApsInfoGroup OBJECT-GROUP
			OBJECTS {hwRanApsInfoGroupId,hwRanApsRemoteProtectMode,hwRanApsPgpInfo,hwRanApsInfoRowStatus}
			STATUS current
			DESCRIPTION 
				"This is a optional group of APS information."
			::= { hwRanApsGroups 3 }
		hwRanApsNotificationsGroup NOTIFICATION-GROUP
			NOTIFICATIONS {hwRanApsFsmFail,hwRanPgpPktError,hwRanPgpKeepalivePktOvertime,
					hwRanApsUniBidMismatch,hwRanApsK1K2Mismatch,hwRanApsK2Mismatch,hwRanApsProtectSwitchOver, hwRanApsProtectSwitchBackOver,hwRanApsInterfaceReady}
			STATUS current
			DESCRIPTION 
				"This is a optional group of information."
			::= { hwRanApsGroups 4 }

		
END     
    
--
-- HUAWEI-RANAPS-MIB.mib
--
