HDREG-MIB2 DEFINITIONS ::= BEGIN

IMPORTS
    enterprises, MODULE-IDENTITY
        FROM SNMPv2-SMI;

hdreg MODULE-IDENTITY
    LAST-UPDATED "0609201255Z"
    ORGANIZATION "Sun Microsystems Inc."
    CONTACT-INFO
        "        Sun Microsystems Inc.
       Customer Support
            Postal: 901 San Antonio Road 
       Palo Alto, CA-94303-4900
    USA
                         Tel: 650-960-1300
                E-mail: service@sun.com"
    DESCRIPTION
        ""
    ::= { modules 17 }
modules	OBJECT IDENTIFIER ::= { agent 2 }

agent	OBJECT IDENTIFIER ::= { sunsymon 2 }

sunsymon	OBJECT IDENTIFIER ::= { prod 12 }

prod	OBJECT IDENTIFIER ::= { sun 2 }

sun	OBJECT IDENTIFIER ::= { enterprises 42 }

DisplayString ::= TEXTUAL-CONVENTION
    DISPLAY-HINT "255a"
    STATUS       current
    DESCRIPTION
            "Represents textual information taken from the NVT ASCII
            character set, as defined in pages 4, 10-11 of RFC 854.

            To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

            Any object defined using this syntax may not exceed 255
            characters in length."
    SYNTAX       OCTET STRING (SIZE (0..255))

hdregtable OBJECT-TYPE
    SYNTAX      SEQUENCE OF Hdregentry
    MAX-ACCESS  not-accessible
    STATUS      current
    DESCRIPTION
                "MIB tree branch"
    ::= { hdreg 1 }

hdregentry OBJECT-TYPE
    SYNTAX      Hdregentry
    MAX-ACCESS  not-accessible
    STATUS      current
    DESCRIPTION
                "MIB tree branch"
    INDEX  { modname }
    ::= { hdregtable 1 }

Hdregentry ::=
    SEQUENCE {
        modname
            DisplayString,
        label
            DisplayString,
        svflag
            DisplayString,
        rootoid
            DisplayString
    }

modname OBJECT-TYPE
    SYNTAX      DisplayString
    MAX-ACCESS  read-only
    STATUS      current
    DESCRIPTION
                "Character string value"
    ::= { hdregentry 1 }

label OBJECT-TYPE
    SYNTAX      DisplayString
    MAX-ACCESS  read-only
    STATUS      current
    DESCRIPTION
                "Character string value"
    ::= { hdregentry 2 }

svflag OBJECT-TYPE
    SYNTAX      DisplayString
    MAX-ACCESS  read-only
    STATUS      current
    DESCRIPTION
                "Character string value"
    ::= { hdregentry 3 }

rootoid OBJECT-TYPE
    SYNTAX      DisplayString
    MAX-ACCESS  read-only
    STATUS      current
    DESCRIPTION
                "Character string value"
    ::= { hdregentry 4 }
END
