FORTIMAIL-TRAP-MIB-220 DEFINITIONS ::= BEGIN
	IMPORTS
		DisplayString
			FROM SNMPv2-TC
		MODULE-IDENTITY, OBJECT-TYPE, NOTIFICATION-TYPE,
		Integer32, Gauge32, enterprises, IpAddress
			FROM SNMPv2-SMI
		ifIndex
			FROM IF-MIB
		fmlTraps, fmlSysSerial
			FROM FORTIMAIL-MIB-220;

--


	fmlTrapCpuHighThreshold  NOTIFICATION-TYPE
		OBJECTS       { fmlSysSerial }
		STATUS        current
		DESCRIPTION   "Trap being sent if CPU usage becomes too high"
		::=  {  fmlTraps  101  }

	fmlTrapMemLowThreshold  NOTIFICATION-TYPE
		OBJECTS       { fmlSysSerial }
		STATUS        current
		DESCRIPTION   "Trap being sent if memory usage becomes too high"
		::=  {  fmlTraps  102  }

	fmlTrapLogDiskHighThreshold  NOTIFICATION-TYPE
		OBJECTS       { fmlSysSerial }
		STATUS        current
		DESCRIPTION   "Trap being sent if Log disk usage becomes too high"
		::=  {  fmlTraps  103  }
		
	fmlTrapMailDiskHighThreshold  NOTIFICATION-TYPE
		OBJECTS       { fmlSysSerial }
		STATUS        current
		DESCRIPTION   "Trap being sent if Mailbox disk usage becomes too high"
		::=  {  fmlTraps  104  }		
		
	fmlTrapMailDeferredQueueHighThreshold  NOTIFICATION-TYPE
		OBJECTS       { fmlSysSerial }
		STATUS        current
		DESCRIPTION   "Trap being sent if Mail server deferred emails becomes too high"
		::=  {  fmlTraps  105  }		
		
	fmlTrapAvThresholdEvent	NOTIFICATION-TYPE
		OBJECTS      { fmlSysSerial }
		STATUS       current
		DESCRIPTION   "Trap being sent when detected virus number reaches the threshold"
		::=  {  fmlTraps  106  }	

	fmlTrapSpamThresholdEvent	NOTIFICATION-TYPE
		OBJECTS      { fmlSysSerial }
		STATUS       current
		DESCRIPTION   "Trap being sent when detected spam email number reaches the threshold"
		::=  {  fmlTraps  107  }	


	fmlTrapSystemEvent	NOTIFICATION-TYPE
		OBJECTS      { fmlSysSerial, fmlSysEventCode }
		STATUS       current
		DESCRIPTION   "Trap being sent when system component halt, reboot, upgrade etc.,"
		::=  {  fmlTraps  201  }
		
	fmlTrapRAIDEvent	NOTIFICATION-TYPE
		OBJECTS      { fmlSysSerial, fmlRAIDCode, fmlRAIDDevName }
		STATUS       current
		DESCRIPTION   "Trap being sent for RAID operation"
		::=  {  fmlTraps  202  }

	fmlTrapHAEvent	NOTIFICATION-TYPE
		OBJECTS      { fmlSysSerial, fmlHAEventId, fmlHAUnitIp, fmlHAEventReason }
		STATUS       current
		DESCRIPTION   "Trap being sent when HA event occurs"
		::=  {  fmlTraps  203  }

	fmlTrapArchiveEvent	NOTIFICATION-TYPE
		OBJECTS      { fmlSysSerial, fmlArchiveServerIp, fmlArchiveFilename}
		STATUS       current
		DESCRIPTION   "Trap being sent when remote archive event occurs"
		::=  {  fmlTraps  204  }


	fmlTrapIpChange	NOTIFICATION-TYPE
		OBJECTS       { fmlSysSerial, ifIndex }
		STATUS        current
		DESCRIPTION   "Trap being sent when IP address of
		               the specified interface has been
		               changed"
		::=  {  fmlTraps  301  }

		
		
		
END
