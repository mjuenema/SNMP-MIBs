-- File Name : LRCS-PROXY-CONFIG-MIB
-- Date      : Thursday, November 21, 2002
-- Author    : Watsh Rajneesh. 



LRCS-PROXY-CONFIG-MIB	DEFINITIONS ::= BEGIN
	IMPORTS
		DisplayString, RowStatus
			FROM SNMPv2-TC
		DisplayString
			FROM RFC1213-MIB
		enterprises, OBJECT-TYPE, Integer32 , IpAddress, TimeTicks, 
		Counter32,Unsigned32, Counter64, NOTIFICATION-TYPE, 
		MODULE-IDENTITY, TEXTUAL-CONVENTION
                	FROM SNMPv2-SMI;
        
        adc	MODULE-IDENTITY
			LAST-UPDATED	"9912180051Z"
			ORGANIZATION	"ADC Telecommunications, Inc."
			CONTACT-INFO	"ADC Telecommunications, Inc.
					13625 Technology Drive
				 	Eden Prairie, MN 55344 USA 
	
					Telephone:
						1-800-366-3891
						Extension 73000
						North America: 952-917-3000
						Brussels: 32 2712 6504 (Sales Administration)
							  32 2712 6542 (Technical Assistance Center)

						Germany: 0180-2232923
						United Kingdom: 0800-960236
						Spain: 900-983291
						France: 0800-914032		
					 
					 
					Fax:
						952-917-3237 (US)
						952-917-3080 (International)
	
					Email: cs@adc.com"
			DESCRIPTION	
					"This MIB contains management information of LRCS
					SNMP Proxy runtime agent. This MIB is
					used to monitor and manage the C run time agent which
					supports SNMP protocol."
	
			REVISION		"200209141141Z"
			DESCRIPTION		""
		::=  {  enterprises  2014  }
                
        org	OBJECT IDENTIFIER
			::=  {  iso  3  }
	
	dod	OBJECT IDENTIFIER
		::=  {  org  6  }

	internet	OBJECT IDENTIFIER
		::=  {  dod  1  }

	private	OBJECT IDENTIFIER
		::=  {  internet  4  }

	enterprises	OBJECT IDENTIFIER
	::=  {  private  1  }
	
	digivance	OBJECT IDENTIFIER
		::=  {  adc  9  }

	lrcs	OBJECT IDENTIFIER
		::=  {  digivance  1  }

	lrcsConfigMibModule	OBJECT IDENTIFIER
		::=  {  lrcs  2  }


	agentConfiguration	OBJECT IDENTIFIER
		::=  {  lrcsConfigMibModule  1  }

	

	trapTables	OBJECT IDENTIFIER
		::=  {  agentConfiguration  1  }




	v1v2TrapForwardingTable	OBJECT-TYPE
		SYNTAX		SEQUENCE  OF  V1v2TrapForwardingEntry
		MAX-ACCESS	not-accessible
		STATUS		current
		DESCRIPTION	"This table maintains the SNMP v1 and v2c managers
			information like manager IP address, port number,
			community, time out, retires, etc which are used 
			in trap generation.  Timeout and retires are used 
			in the case of SNMPv2c INFORM."
		::=  { trapTables  1 }

	v1v2TrapForwardingEntry	OBJECT-TYPE
		SYNTAX		V1v2TrapForwardingEntry
		MAX-ACCESS	not-accessible
		STATUS		current
		DESCRIPTION	"Each entry in this table refers one manager
			information who is registered to receive traps
			fromt the agent."
		INDEX		{  v1v2ManagerHost, v1v2ManagerPort  }
		::=  { v1v2TrapForwardingTable 1 }

	V1v2TrapForwardingEntry  ::=  SEQUENCE {
		v1v2ManagerHost  IpAddress,
		v1v2ManagerPort  Unsigned32,
		v1v2ManagerVersion  Integer32,
		v1v2ManagerCommunity  DisplayString,
		v1v2ManagerTimeOut  Unsigned32,
		v1v2ManagerRetries  Unsigned32,
		v1v2ManagerStatus  RowStatus
		}


	v1v2ManagerHost	OBJECT-TYPE	
		SYNTAX			IpAddress
		MAX-ACCESS		read-only
		STATUS			current
		DESCRIPTION		"IP address where the manager is listening to
				receive traps from the agent."
		DEFVAL			{ "127.0.0.1" }
		::=  {  v1v2TrapForwardingEntry  1  }


	v1v2ManagerPort	OBJECT-TYPE	
		SYNTAX			Unsigned32
		MAX-ACCESS		read-only
		STATUS			current
		DESCRIPTION		"The port at which manager is listening for
				the traps from the agent."
		DEFVAL			{ 162 }
		::=  {  v1v2TrapForwardingEntry  2  }


	v1v2ManagerVersion	OBJECT-TYPE	
		SYNTAX			Integer32
		MAX-ACCESS		read-write
		STATUS			current
		DESCRIPTION		"Description"
		::=  {  v1v2TrapForwardingEntry  3  }


	v1v2ManagerCommunity	OBJECT-TYPE	
		SYNTAX			DisplayString
		MAX-ACCESS		read-write
		STATUS			current
		DESCRIPTION		"The community used by the agent to send trap
				or inform to this manager."
		DEFVAL			{ "public" }
		::=  {  v1v2TrapForwardingEntry  4  }


	v1v2ManagerTimeOut	OBJECT-TYPE	
		SYNTAX			Unsigned32
		MAX-ACCESS		read-write
		STATUS			current
		DESCRIPTION		"The  time out value in seconds for SNMPv2c INFORM."
		DEFVAL			{ 5 }
		::=  {  v1v2TrapForwardingEntry  5  }


	v1v2ManagerRetries	OBJECT-TYPE	
		SYNTAX			Unsigned32
		MAX-ACCESS		read-write
		STATUS			current
		DESCRIPTION		"The number of retries in the case of SNMPV2c INFORM."
		DEFVAL			{ 0 }
		::=  {  v1v2TrapForwardingEntry  6  }


	v1v2ManagerStatus	OBJECT-TYPE	
		SYNTAX			RowStatus
		MAX-ACCESS		read-write
		STATUS			current
		DESCRIPTION		"The status of this conceptual row.

                 Until instances of all corresponding columns are
                 appropriately configured, the value of the
                 corresponding instance of the usmUserStatus column
                 is 'notReady'"
		::=  {  v1v2TrapForwardingEntry  7  }

	

END
