-- file automatically created


TELDAT-TRAP-HTTP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


httpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the HTTP event subsystem."
    REVISION "201401200930Z"
    DESCRIPTION "Initial implementation"
        ::= { telEventTraps 142 }


httpEventsGroup	OBJECT IDENTIFIER	::= { httpTrapsMIB 1 }

httpNotifications	OBJECT IDENTIFIER	::= { httpTrapsMIB 2 }
httpNotificationsPrefix	OBJECT IDENTIFIER	::= { httpNotifications 0 }

httpEventObjects1 OBJECT-IDENTITY
    STATUS current
    DESCRIPTION
        "Event HTTP.1
        The Web probe could not be started because of memory limitations."
    ::= { httpEventsGroup 1 }

http1_probe_identifier OBJECT-TYPE
    SYNTAX Integer32
    MAX-ACCESS accessible-for-notify
    STATUS current
    DESCRIPTION
        "Parameter 'probe_identifier' in event HTTP.1"
    ::= { httpEventObjects1 1 }

httpEventObjects2 OBJECT-IDENTITY
    STATUS current
    DESCRIPTION
        "Event HTTP.2
        The router was unable to read the data configured for a Web probe."
    ::= { httpEventsGroup 2 }

http2_probe_identifier OBJECT-TYPE
    SYNTAX Integer32
    MAX-ACCESS accessible-for-notify
    STATUS current
    DESCRIPTION
        "Parameter 'probe_identifier' in event HTTP.2"
    ::= { httpEventObjects2 1 }

httpEventObjects3 OBJECT-IDENTITY
    STATUS current
    DESCRIPTION
        "Event HTTP.3
        The router was unable to open a TCP session for a Web probe."
    ::= { httpEventsGroup 3 }

http3_host OBJECT-TYPE
    SYNTAX IpAddress
    MAX-ACCESS accessible-for-notify
    STATUS current
    DESCRIPTION
        "Parameter 'host' in event HTTP.3"
    ::= { httpEventObjects3 1 }

http3_url OBJECT-TYPE
    SYNTAX DisplayString
    MAX-ACCESS accessible-for-notify
    STATUS current
    DESCRIPTION
        "Parameter 'url' in event HTTP.3"
    ::= { httpEventObjects3 2 }

httpEventObjects4 OBJECT-IDENTITY
    STATUS current
    DESCRIPTION
        "Event HTTP.4
        The probe, for a generic page, finished before being successfully
        completed."
    ::= { httpEventsGroup 4 }

http4_bytes OBJECT-TYPE
    SYNTAX Integer32
    MAX-ACCESS accessible-for-notify
    STATUS current
    DESCRIPTION
        "Parameter 'bytes' in event HTTP.4"
    ::= { httpEventObjects4 1 }

http4_time OBJECT-TYPE
    SYNTAX Integer32
    MAX-ACCESS accessible-for-notify
    STATUS current
    DESCRIPTION
        "Parameter 'time' in event HTTP.4"
    ::= { httpEventObjects4 2 }

http4_bps OBJECT-TYPE
    SYNTAX Integer32
    MAX-ACCESS accessible-for-notify
    STATUS current
    DESCRIPTION
        "Parameter 'bps' in event HTTP.4"
    ::= { httpEventObjects4 3 }

http4_host OBJECT-TYPE
    SYNTAX IpAddress
    MAX-ACCESS accessible-for-notify
    STATUS current
    DESCRIPTION
        "Parameter 'host' in event HTTP.4"
    ::= { httpEventObjects4 4 }

http4_url OBJECT-TYPE
    SYNTAX DisplayString
    MAX-ACCESS accessible-for-notify
    STATUS current
    DESCRIPTION
        "Parameter 'url' in event HTTP.4"
    ::= { httpEventObjects4 5 }

http4_time_dns OBJECT-TYPE
    SYNTAX Integer32
    MAX-ACCESS accessible-for-notify
    STATUS current
    DESCRIPTION
        "Parameter 'time_dns' in event HTTP.4"
    ::= { httpEventObjects4 6 }

http4_time_tcp OBJECT-TYPE
    SYNTAX Integer32
    MAX-ACCESS accessible-for-notify
    STATUS current
    DESCRIPTION
        "Parameter 'time_tcp' in event HTTP.4"
    ::= { httpEventObjects4 7 }

http4_device_status OBJECT-TYPE
    SYNTAX Integer32
    MAX-ACCESS accessible-for-notify
    STATUS current
    DESCRIPTION
        "Parameter 'device_status' in event HTTP.4"
    ::= { httpEventObjects4 8 }

http4_time_server_response OBJECT-TYPE
    SYNTAX Integer32
    MAX-ACCESS accessible-for-notify
    STATUS current
    DESCRIPTION
        "Parameter 'time_server_response' in event HTTP.4"
    ::= { httpEventObjects4 9 }

http4_transmit_speed OBJECT-TYPE
    SYNTAX Integer32
    MAX-ACCESS accessible-for-notify
    STATUS current
    DESCRIPTION
        "Parameter 'transmit_speed' in event HTTP.4"
    ::= { httpEventObjects4 10 }

http4_receive_speed OBJECT-TYPE
    SYNTAX Integer32
    MAX-ACCESS accessible-for-notify
    STATUS current
    DESCRIPTION
        "Parameter 'receive_speed' in event HTTP.4"
    ::= { httpEventObjects4 11 }

httpEventObjects5 OBJECT-IDENTITY
    STATUS current
    DESCRIPTION
        "Event HTTP.5
        The HTTP header received is not the expected."
    ::= { httpEventsGroup 5 }

http5_level OBJECT-TYPE
    SYNTAX Integer32
    MAX-ACCESS accessible-for-notify
    STATUS current
    DESCRIPTION
        "Parameter 'level' in event HTTP.5"
    ::= { httpEventObjects5 1 }

http5_sublevel OBJECT-TYPE
    SYNTAX Integer32
    MAX-ACCESS accessible-for-notify
    STATUS current
    DESCRIPTION
        "Parameter 'sublevel' in event HTTP.5"
    ::= { httpEventObjects5 2 }

http5_status_code OBJECT-TYPE
    SYNTAX Integer32
    MAX-ACCESS accessible-for-notify
    STATUS current
    DESCRIPTION
        "Parameter 'status_code' in event HTTP.5"
    ::= { httpEventObjects5 3 }

http5_reason OBJECT-TYPE
    SYNTAX DisplayString
    MAX-ACCESS accessible-for-notify
    STATUS current
    DESCRIPTION
        "Parameter 'reason' in event HTTP.5"
    ::= { httpEventObjects5 4 }

httpEventObjects6 OBJECT-IDENTITY
    STATUS current
    DESCRIPTION
        "Event HTTP.6
        The probe, for a generic page, was successfully completed."
    ::= { httpEventsGroup 6 }

http6_bytes OBJECT-TYPE
    SYNTAX Integer32
    MAX-ACCESS accessible-for-notify
    STATUS current
    DESCRIPTION
        "Parameter 'bytes' in event HTTP.6"
    ::= { httpEventObjects6 1 }

http6_time OBJECT-TYPE
    SYNTAX Integer32
    MAX-ACCESS accessible-for-notify
    STATUS current
    DESCRIPTION
        "Parameter 'time' in event HTTP.6"
    ::= { httpEventObjects6 2 }

http6_bps OBJECT-TYPE
    SYNTAX Integer32
    MAX-ACCESS accessible-for-notify
    STATUS current
    DESCRIPTION
        "Parameter 'bps' in event HTTP.6"
    ::= { httpEventObjects6 3 }

http6_host OBJECT-TYPE
    SYNTAX IpAddress
    MAX-ACCESS accessible-for-notify
    STATUS current
    DESCRIPTION
        "Parameter 'host' in event HTTP.6"
    ::= { httpEventObjects6 4 }

http6_url OBJECT-TYPE
    SYNTAX DisplayString
    MAX-ACCESS accessible-for-notify
    STATUS current
    DESCRIPTION
        "Parameter 'url' in event HTTP.6"
    ::= { httpEventObjects6 5 }

http6_time_dns OBJECT-TYPE
    SYNTAX Integer32
    MAX-ACCESS accessible-for-notify
    STATUS current
    DESCRIPTION
        "Parameter 'time_dns' in event HTTP.6"
    ::= { httpEventObjects6 6 }

http6_time_tcp OBJECT-TYPE
    SYNTAX Integer32
    MAX-ACCESS accessible-for-notify
    STATUS current
    DESCRIPTION
        "Parameter 'time_tcp' in event HTTP.6"
    ::= { httpEventObjects6 7 }

http6_device_status OBJECT-TYPE
    SYNTAX Integer32
    MAX-ACCESS accessible-for-notify
    STATUS current
    DESCRIPTION
        "Parameter 'device_status' in event HTTP.6"
    ::= { httpEventObjects6 8 }

http6_time_server_response OBJECT-TYPE
    SYNTAX Integer32
    MAX-ACCESS accessible-for-notify
    STATUS current
    DESCRIPTION
        "Parameter 'time_server_response' in event HTTP.6"
    ::= { httpEventObjects6 9 }

http6_transmit_speed OBJECT-TYPE
    SYNTAX Integer32
    MAX-ACCESS accessible-for-notify
    STATUS current
    DESCRIPTION
        "Parameter 'transmit_speed' in event HTTP.6"
    ::= { httpEventObjects6 10 }

http6_receive_speed OBJECT-TYPE
    SYNTAX Integer32
    MAX-ACCESS accessible-for-notify
    STATUS current
    DESCRIPTION
        "Parameter 'receive_speed' in event HTTP.6"
    ::= { httpEventObjects6 11 }

httpEventObjects7 OBJECT-IDENTITY
    STATUS current
    DESCRIPTION
        "Event HTTP.7
        The probe has been started."
    ::= { httpEventsGroup 7 }

http7_url OBJECT-TYPE
    SYNTAX DisplayString
    MAX-ACCESS accessible-for-notify
    STATUS current
    DESCRIPTION
        "Parameter 'url' in event HTTP.7"
    ::= { httpEventObjects7 1 }

httpEventObjects8 OBJECT-IDENTITY
    STATUS current
    DESCRIPTION
        "Event HTTP.8
        An error occurred while reading a chunk."
    ::= { httpEventsGroup 8 }

http8_host OBJECT-TYPE
    SYNTAX IpAddress
    MAX-ACCESS accessible-for-notify
    STATUS current
    DESCRIPTION
        "Parameter 'host' in event HTTP.8"
    ::= { httpEventObjects8 1 }

http8_url OBJECT-TYPE
    SYNTAX DisplayString
    MAX-ACCESS accessible-for-notify
    STATUS current
    DESCRIPTION
        "Parameter 'url' in event HTTP.8"
    ::= { httpEventObjects8 2 }

httpEventObjects9 OBJECT-IDENTITY
    STATUS current
    DESCRIPTION
        "Event HTTP.9
        An error occurred while reading a JavaScript."
    ::= { httpEventsGroup 9 }

http9_host OBJECT-TYPE
    SYNTAX IpAddress
    MAX-ACCESS accessible-for-notify
    STATUS current
    DESCRIPTION
        "Parameter 'host' in event HTTP.9"
    ::= { httpEventObjects9 1 }

http9_url OBJECT-TYPE
    SYNTAX DisplayString
    MAX-ACCESS accessible-for-notify
    STATUS current
    DESCRIPTION
        "Parameter 'url' in event HTTP.9"
    ::= { httpEventObjects9 2 }

http9_JavaScript_number OBJECT-TYPE
    SYNTAX Integer32
    MAX-ACCESS accessible-for-notify
    STATUS current
    DESCRIPTION
        "Parameter 'JavaScript_number' in event HTTP.9"
    ::= { httpEventObjects9 3 }

httpEventObjects10 OBJECT-IDENTITY
    STATUS current
    DESCRIPTION
        "Event HTTP.10
        The speed calculated probing the url specified was below the threshold
        configured in n consecutive probes."
    ::= { httpEventsGroup 10 }

http10_host OBJECT-TYPE
    SYNTAX IpAddress
    MAX-ACCESS accessible-for-notify
    STATUS current
    DESCRIPTION
        "Parameter 'host' in event HTTP.10"
    ::= { httpEventObjects10 1 }

http10_url OBJECT-TYPE
    SYNTAX DisplayString
    MAX-ACCESS accessible-for-notify
    STATUS current
    DESCRIPTION
        "Parameter 'url' in event HTTP.10"
    ::= { httpEventObjects10 2 }

http10_threshold OBJECT-TYPE
    SYNTAX Integer32
    MAX-ACCESS accessible-for-notify
    STATUS current
    DESCRIPTION
        "Parameter 'threshold' in event HTTP.10"
    ::= { httpEventObjects10 3 }

http10_n_failures OBJECT-TYPE
    SYNTAX Integer32
    MAX-ACCESS accessible-for-notify
    STATUS current
    DESCRIPTION
        "Parameter 'n_failures' in event HTTP.10"
    ::= { httpEventObjects10 4 }

httpEventObjects11 OBJECT-IDENTITY
    STATUS current
    DESCRIPTION
        "Event HTTP.11
        An http 'get' has been made for the url shown."
    ::= { httpEventsGroup 11 }

http11_url OBJECT-TYPE
    SYNTAX DisplayString
    MAX-ACCESS accessible-for-notify
    STATUS current
    DESCRIPTION
        "Parameter 'url' in event HTTP.11"
    ::= { httpEventObjects11 1 }

httpEventObjects12 OBJECT-IDENTITY
    STATUS current
    DESCRIPTION
        "Event HTTP.12
        A HTTP packet has been received."
    ::= { httpEventsGroup 12 }

http12_host OBJECT-TYPE
    SYNTAX IpAddress
    MAX-ACCESS accessible-for-notify
    STATUS current
    DESCRIPTION
        "Parameter 'host' in event HTTP.12"
    ::= { httpEventObjects12 1 }

http12_url OBJECT-TYPE
    SYNTAX DisplayString
    MAX-ACCESS accessible-for-notify
    STATUS current
    DESCRIPTION
        "Parameter 'url' in event HTTP.12"
    ::= { httpEventObjects12 2 }

http12_size OBJECT-TYPE
    SYNTAX Integer32
    MAX-ACCESS accessible-for-notify
    STATUS current
    DESCRIPTION
        "Parameter 'size' in event HTTP.12"
    ::= { httpEventObjects12 3 }

httpEventObjects14 OBJECT-IDENTITY
    STATUS current
    DESCRIPTION
        "Event HTTP.14
        The Web probe could not be started because of memory limitations."
    ::= { httpEventsGroup 14 }

http14_host OBJECT-TYPE
    SYNTAX IpAddress
    MAX-ACCESS accessible-for-notify
    STATUS current
    DESCRIPTION
        "Parameter 'host' in event HTTP.14"
    ::= { httpEventObjects14 1 }

http14_url OBJECT-TYPE
    SYNTAX DisplayString
    MAX-ACCESS accessible-for-notify
    STATUS current
    DESCRIPTION
        "Parameter 'url' in event HTTP.14"
    ::= { httpEventObjects14 2 }

httpEventObjects15 OBJECT-IDENTITY
    STATUS current
    DESCRIPTION
        "Event HTTP.15
        The probe timed out before being successfully completed."
    ::= { httpEventsGroup 15 }

http15_host OBJECT-TYPE
    SYNTAX IpAddress
    MAX-ACCESS accessible-for-notify
    STATUS current
    DESCRIPTION
        "Parameter 'host' in event HTTP.15"
    ::= { httpEventObjects15 1 }

http15_url OBJECT-TYPE
    SYNTAX DisplayString
    MAX-ACCESS accessible-for-notify
    STATUS current
    DESCRIPTION
        "Parameter 'url' in event HTTP.15"
    ::= { httpEventObjects15 2 }

httpEventObjects16 OBJECT-IDENTITY
    STATUS current
    DESCRIPTION
        "Event HTTP.16
        An HTTP response was received with the status-code shown."
    ::= { httpEventsGroup 16 }

http16_status_code OBJECT-TYPE
    SYNTAX Integer32
    MAX-ACCESS accessible-for-notify
    STATUS current
    DESCRIPTION
        "Parameter 'status_code' in event HTTP.16"
    ::= { httpEventObjects16 1 }

http16_reason OBJECT-TYPE
    SYNTAX DisplayString
    MAX-ACCESS accessible-for-notify
    STATUS current
    DESCRIPTION
        "Parameter 'reason' in event HTTP.16"
    ::= { httpEventObjects16 2 }

httpEventObjects17 OBJECT-IDENTITY
    STATUS current
    DESCRIPTION
        "Event HTTP.17
        An HTTP response was received with status-code 3xx (redirection). The
        location requested is shown for informational purposes."
    ::= { httpEventsGroup 17 }

http17_location OBJECT-TYPE
    SYNTAX DisplayString
    MAX-ACCESS accessible-for-notify
    STATUS current
    DESCRIPTION
        "Parameter 'location' in event HTTP.17"
    ::= { httpEventObjects17 1 }

httpEventObjects18 OBJECT-IDENTITY
    STATUS current
    DESCRIPTION
        "Event HTTP.18
        When parsing a HTTP response, the temporal buffer was not big enough
        to store the bytes needed. The response parsed could be inexact."
    ::= { httpEventsGroup 18 }

http18_bytes_stored OBJECT-TYPE
    SYNTAX Integer32
    MAX-ACCESS accessible-for-notify
    STATUS current
    DESCRIPTION
        "Parameter 'bytes_stored' in event HTTP.18"
    ::= { httpEventObjects18 1 }

http18_bytes_to_store OBJECT-TYPE
    SYNTAX Integer32
    MAX-ACCESS accessible-for-notify
    STATUS current
    DESCRIPTION
        "Parameter 'bytes_to_store' in event HTTP.18"
    ::= { httpEventObjects18 2 }

httpEventObjects19 OBJECT-IDENTITY
    STATUS current
    DESCRIPTION
        "Event HTTP.19
        The probe, for an specific page, was successfully completed."
    ::= { httpEventsGroup 19 }

http19_bytes OBJECT-TYPE
    SYNTAX Integer32
    MAX-ACCESS accessible-for-notify
    STATUS current
    DESCRIPTION
        "Parameter 'bytes' in event HTTP.19"
    ::= { httpEventObjects19 1 }

http19_time OBJECT-TYPE
    SYNTAX Integer32
    MAX-ACCESS accessible-for-notify
    STATUS current
    DESCRIPTION
        "Parameter 'time' in event HTTP.19"
    ::= { httpEventObjects19 2 }

http19_bps OBJECT-TYPE
    SYNTAX Integer32
    MAX-ACCESS accessible-for-notify
    STATUS current
    DESCRIPTION
        "Parameter 'bps' in event HTTP.19"
    ::= { httpEventObjects19 3 }

http19_host OBJECT-TYPE
    SYNTAX IpAddress
    MAX-ACCESS accessible-for-notify
    STATUS current
    DESCRIPTION
        "Parameter 'host' in event HTTP.19"
    ::= { httpEventObjects19 4 }

http19_url OBJECT-TYPE
    SYNTAX DisplayString
    MAX-ACCESS accessible-for-notify
    STATUS current
    DESCRIPTION
        "Parameter 'url' in event HTTP.19"
    ::= { httpEventObjects19 5 }

http19_time_dns OBJECT-TYPE
    SYNTAX Integer32
    MAX-ACCESS accessible-for-notify
    STATUS current
    DESCRIPTION
        "Parameter 'time_dns' in event HTTP.19"
    ::= { httpEventObjects19 6 }

http19_time_tcp OBJECT-TYPE
    SYNTAX Integer32
    MAX-ACCESS accessible-for-notify
    STATUS current
    DESCRIPTION
        "Parameter 'time_tcp' in event HTTP.19"
    ::= { httpEventObjects19 7 }

http19_device_status OBJECT-TYPE
    SYNTAX Integer32
    MAX-ACCESS accessible-for-notify
    STATUS current
    DESCRIPTION
        "Parameter 'device_status' in event HTTP.19"
    ::= { httpEventObjects19 8 }

http19_time_server_response OBJECT-TYPE
    SYNTAX Integer32
    MAX-ACCESS accessible-for-notify
    STATUS current
    DESCRIPTION
        "Parameter 'time_server_response' in event HTTP.19"
    ::= { httpEventObjects19 9 }

http19_transmit_speed OBJECT-TYPE
    SYNTAX Integer32
    MAX-ACCESS accessible-for-notify
    STATUS current
    DESCRIPTION
        "Parameter 'transmit_speed' in event HTTP.19"
    ::= { httpEventObjects19 10 }

http19_receive_speed OBJECT-TYPE
    SYNTAX Integer32
    MAX-ACCESS accessible-for-notify
    STATUS current
    DESCRIPTION
        "Parameter 'receive_speed' in event HTTP.19"
    ::= { httpEventObjects19 11 }

httpEventObjects20 OBJECT-IDENTITY
    STATUS current
    DESCRIPTION
        "Event HTTP.20
        The probe, for an specific page, finished before being successfully
        completed."
    ::= { httpEventsGroup 20 }

http20_bytes OBJECT-TYPE
    SYNTAX Integer32
    MAX-ACCESS accessible-for-notify
    STATUS current
    DESCRIPTION
        "Parameter 'bytes' in event HTTP.20"
    ::= { httpEventObjects20 1 }

http20_time OBJECT-TYPE
    SYNTAX Integer32
    MAX-ACCESS accessible-for-notify
    STATUS current
    DESCRIPTION
        "Parameter 'time' in event HTTP.20"
    ::= { httpEventObjects20 2 }

http20_bps OBJECT-TYPE
    SYNTAX Integer32
    MAX-ACCESS accessible-for-notify
    STATUS current
    DESCRIPTION
        "Parameter 'bps' in event HTTP.20"
    ::= { httpEventObjects20 3 }

http20_host OBJECT-TYPE
    SYNTAX IpAddress
    MAX-ACCESS accessible-for-notify
    STATUS current
    DESCRIPTION
        "Parameter 'host' in event HTTP.20"
    ::= { httpEventObjects20 4 }

http20_url OBJECT-TYPE
    SYNTAX DisplayString
    MAX-ACCESS accessible-for-notify
    STATUS current
    DESCRIPTION
        "Parameter 'url' in event HTTP.20"
    ::= { httpEventObjects20 5 }

http20_time_dns OBJECT-TYPE
    SYNTAX Integer32
    MAX-ACCESS accessible-for-notify
    STATUS current
    DESCRIPTION
        "Parameter 'time_dns' in event HTTP.20"
    ::= { httpEventObjects20 6 }

http20_time_tcp OBJECT-TYPE
    SYNTAX Integer32
    MAX-ACCESS accessible-for-notify
    STATUS current
    DESCRIPTION
        "Parameter 'time_tcp' in event HTTP.20"
    ::= { httpEventObjects20 7 }

http20_device_status OBJECT-TYPE
    SYNTAX Integer32
    MAX-ACCESS accessible-for-notify
    STATUS current
    DESCRIPTION
        "Parameter 'device_status' in event HTTP.20"
    ::= { httpEventObjects20 8 }

http20_time_server_response OBJECT-TYPE
    SYNTAX Integer32
    MAX-ACCESS accessible-for-notify
    STATUS current
    DESCRIPTION
        "Parameter 'time_server_response' in event HTTP.20"
    ::= { httpEventObjects20 9 }

http20_transmit_speed OBJECT-TYPE
    SYNTAX Integer32
    MAX-ACCESS accessible-for-notify
    STATUS current
    DESCRIPTION
        "Parameter 'transmit_speed' in event HTTP.20"
    ::= { httpEventObjects20 10 }

http20_receive_speed OBJECT-TYPE
    SYNTAX Integer32
    MAX-ACCESS accessible-for-notify
    STATUS current
    DESCRIPTION
        "Parameter 'receive_speed' in event HTTP.20"
    ::= { httpEventObjects20 11 }

httpEventObjects21 OBJECT-IDENTITY
    STATUS current
    DESCRIPTION
        "Event HTTP.21
        There was some error when querying for the IP address associated with
        the host."
    ::= { httpEventsGroup 21 }

http21_url OBJECT-TYPE
    SYNTAX DisplayString
    MAX-ACCESS accessible-for-notify
    STATUS current
    DESCRIPTION
        "Parameter 'url' in event HTTP.21"
    ::= { httpEventObjects21 1 }

httpEventObjects22 OBJECT-IDENTITY
    STATUS current
    DESCRIPTION
        "Event HTTP.22
        Generic informational event from HTTP server."
    ::= { httpEventsGroup 22 }

http22_string OBJECT-TYPE
    SYNTAX DisplayString
    MAX-ACCESS accessible-for-notify
    STATUS current
    DESCRIPTION
        "Parameter 'string' in event HTTP.22"
    ::= { httpEventObjects22 1 }

httpEventObjects23 OBJECT-IDENTITY
    STATUS current
    DESCRIPTION
        "Event HTTP.23
        The configured maximum number of redirections allowed has been reached.
        The next redirection required is not followed."
    ::= { httpEventsGroup 23 }

http23_url OBJECT-TYPE
    SYNTAX DisplayString
    MAX-ACCESS accessible-for-notify
    STATUS current
    DESCRIPTION
        "Parameter 'url' in event HTTP.23"
    ::= { httpEventObjects23 1 }

httpEventObjects24 OBJECT-IDENTITY
    STATUS current
    DESCRIPTION
        "Event HTTP.24
        A HTTP chunk has been received."
    ::= { httpEventsGroup 24 }

http24_host OBJECT-TYPE
    SYNTAX IpAddress
    MAX-ACCESS accessible-for-notify
    STATUS current
    DESCRIPTION
        "Parameter 'host' in event HTTP.24"
    ::= { httpEventObjects24 1 }

http24_url OBJECT-TYPE
    SYNTAX DisplayString
    MAX-ACCESS accessible-for-notify
    STATUS current
    DESCRIPTION
        "Parameter 'url' in event HTTP.24"
    ::= { httpEventObjects24 2 }

http24_size OBJECT-TYPE
    SYNTAX Integer32
    MAX-ACCESS accessible-for-notify
    STATUS current
    DESCRIPTION
        "Parameter 'size' in event HTTP.24"
    ::= { httpEventObjects24 3 }

httpEventObjects25 OBJECT-IDENTITY
    STATUS current
    DESCRIPTION
        "Event HTTP.25
        A HTTP packet has been passed to the web probe."
    ::= { httpEventsGroup 25 }

http25_host OBJECT-TYPE
    SYNTAX IpAddress
    MAX-ACCESS accessible-for-notify
    STATUS current
    DESCRIPTION
        "Parameter 'host' in event HTTP.25"
    ::= { httpEventObjects25 1 }

http25_url OBJECT-TYPE
    SYNTAX DisplayString
    MAX-ACCESS accessible-for-notify
    STATUS current
    DESCRIPTION
        "Parameter 'url' in event HTTP.25"
    ::= { httpEventObjects25 2 }

http25_size OBJECT-TYPE
    SYNTAX Integer32
    MAX-ACCESS accessible-for-notify
    STATUS current
    DESCRIPTION
        "Parameter 'size' in event HTTP.25"
    ::= { httpEventObjects25 3 }

http25_total_size OBJECT-TYPE
    SYNTAX Integer32
    MAX-ACCESS accessible-for-notify
    STATUS current
    DESCRIPTION
        "Parameter 'total_size' in event HTTP.25"
    ::= { httpEventObjects25 4 }


httpNotification1 NOTIFICATION-TYPE
    OBJECTS { 
              http1_probe_identifier 
            }
    STATUS current
    DESCRIPTION
        "Notification of Event HTTP.1

        Message: 'no memory to start probe, identifier=$1'

        Parameters list:
              $1: http1_probe_identifier

        The Web probe could not be started because of memory limitations."
    ::= { httpNotificationsPrefix 1 }

httpNotification2 NOTIFICATION-TYPE
    OBJECTS { 
              http2_probe_identifier 
            }
    STATUS current
    DESCRIPTION
        "Notification of Event HTTP.2

        Message: 'no data for probe identifier=$1'

        Parameters list:
              $1: http2_probe_identifier

        The router was unable to read the data configured for a Web probe."
    ::= { httpNotificationsPrefix 2 }

httpNotification3 NOTIFICATION-TYPE
    OBJECTS { 
              http3_host, 
              http3_url 
            }
    STATUS current
    DESCRIPTION
        "Notification of Event HTTP.3

        Message: 'cannot open TCP session with destination IP addr=$1 url=$2'

        Parameters list:
              $1: http3_host
              $2: http3_url

        The router was unable to open a TCP session for a Web probe."
    ::= { httpNotificationsPrefix 3 }

httpNotification4 NOTIFICATION-TYPE
    OBJECTS { 
              http4_bytes, 
              http4_time,
              http4_bps,
              http4_host,
              http4_url,
              http4_time_dns,
              http4_time_tcp,
              http4_device_status,
              http4_time_server_response,
              http4_transmit_speed,
              http4_receive_speed 
            }
    STATUS current
    DESCRIPTION
        "Notification of Event HTTP.4

        Message: 'probe failed, bytes=$1 time=$2 bps=$3 IP addr=$4 url=$5 time_dns=$6 time_tcp=$7 device_status=$8 time_server_response=$9 transmit_speed=$10 receive_speed=$11'

        Parameters list:
              $1: http4_bytes
              $2: http4_time
              $3: http4_bps
              $4: http4_host
              $5: http4_url
              $6: http4_time_dns
              $7: http4_time_tcp
              $8: http4_device_status
              $9: http4_time_server_response
              $10: http4_transmit_speed
              $11: http4_receive_speed

        The probe, for a generic page, finished before being successfully
        completed."
    ::= { httpNotificationsPrefix 4 }

httpNotification5 NOTIFICATION-TYPE
    OBJECTS { 
              http5_level, 
              http5_sublevel,
              http5_status_code,
              http5_reason 
            }
    STATUS current
    DESCRIPTION
        "Notification of Event HTTP.5

        Message: 'header error, HTTP version: $1.$2 status_code=$3 (cause: $4)'

        Parameters list:
              $1: http5_level
              $2: http5_sublevel
              $3: http5_status_code
              $4: http5_reason

        The HTTP header received is not the expected."
    ::= { httpNotificationsPrefix 5 }

httpNotification6 NOTIFICATION-TYPE
    OBJECTS { 
              http6_bytes, 
              http6_time,
              http6_bps,
              http6_host,
              http6_url,
              http6_time_dns,
              http6_time_tcp,
              http6_device_status,
              http6_time_server_response,
              http6_transmit_speed,
              http6_receive_speed 
            }
    STATUS current
    DESCRIPTION
        "Notification of Event HTTP.6

        Message: 'probe completed, bytes=$1 time=$2 bps=$3 IP addr=$4 url=$5 time_dns=$6 time_tcp=$7 device_status=$8 time_server_response=$9 transmit_speed=$10 receive_speed=$11'

        Parameters list:
              $1: http6_bytes
              $2: http6_time
              $3: http6_bps
              $4: http6_host
              $5: http6_url
              $6: http6_time_dns
              $7: http6_time_tcp
              $8: http6_device_status
              $9: http6_time_server_response
              $10: http6_transmit_speed
              $11: http6_receive_speed

        The probe, for a generic page, was successfully completed."
    ::= { httpNotificationsPrefix 6 }

httpNotification7 NOTIFICATION-TYPE
    OBJECTS { 
              http7_url 
            }
    STATUS current
    DESCRIPTION
        "Notification of Event HTTP.7

        Message: 'probe started, url=$1'

        Parameters list:
              $1: http7_url

        The probe has been started."
    ::= { httpNotificationsPrefix 7 }

httpNotification8 NOTIFICATION-TYPE
    OBJECTS { 
              http8_host, 
              http8_url 
            }
    STATUS current
    DESCRIPTION
        "Notification of Event HTTP.8

        Message: 'chunk error, IP addr=$1 url=$2'

        Parameters list:
              $1: http8_host
              $2: http8_url

        An error occurred while reading a chunk."
    ::= { httpNotificationsPrefix 8 }

httpNotification9 NOTIFICATION-TYPE
    OBJECTS { 
              http9_host, 
              http9_url,
              http9_JavaScript_number 
            }
    STATUS current
    DESCRIPTION
        "Notification of Event HTTP.9

        Message: 'JavaScript error, IP addr=$1 url=$2, JavaScript number=$3'

        Parameters list:
              $1: http9_host
              $2: http9_url
              $3: http9_JavaScript_number

        An error occurred while reading a JavaScript."
    ::= { httpNotificationsPrefix 9 }

httpNotification10 NOTIFICATION-TYPE
    OBJECTS { 
              http10_host, 
              http10_url,
              http10_threshold,
              http10_n_failures 
            }
    STATUS current
    DESCRIPTION
        "Notification of Event HTTP.10

        Message: 'Probe error, IP addr=$1 url=$2, threshold=$3, number of failures=$4'

        Parameters list:
              $1: http10_host
              $2: http10_url
              $3: http10_threshold
              $4: http10_n_failures

        The speed calculated probing the url specified was below the threshold
        configured in n consecutive probes."
    ::= { httpNotificationsPrefix 10 }

httpNotification11 NOTIFICATION-TYPE
    OBJECTS { 
              http11_url 
            }
    STATUS current
    DESCRIPTION
        "Notification of Event HTTP.11

        Message: 'get url=/$1'

        Parameters list:
              $1: http11_url

        An http 'get' has been made for the url shown."
    ::= { httpNotificationsPrefix 11 }

httpNotification12 NOTIFICATION-TYPE
    OBJECTS { 
              http12_host, 
              http12_url,
              http12_size 
            }
    STATUS current
    DESCRIPTION
        "Notification of Event HTTP.12

        Message: 'received packet IP addr=$1 url=$2 size=$3'

        Parameters list:
              $1: http12_host
              $2: http12_url
              $3: http12_size

        A HTTP packet has been received."
    ::= { httpNotificationsPrefix 12 }

httpNotification13 NOTIFICATION-TYPE
    STATUS current
    DESCRIPTION
        "Notification of Event HTTP.13

        Message: 'no memory to start probe process'

        The Web probe process could not be started because of memory limitations."
    ::= { httpNotificationsPrefix 13 }

httpNotification14 NOTIFICATION-TYPE
    OBJECTS { 
              http14_host, 
              http14_url 
            }
    STATUS current
    DESCRIPTION
        "Notification of Event HTTP.14

        Message: 'no memory to start probe, IP addr=$1 url=$2'

        Parameters list:
              $1: http14_host
              $2: http14_url

        The Web probe could not be started because of memory limitations."
    ::= { httpNotificationsPrefix 14 }

httpNotification15 NOTIFICATION-TYPE
    OBJECTS { 
              http15_host, 
              http15_url 
            }
    STATUS current
    DESCRIPTION
        "Notification of Event HTTP.15

        Message: 'probe time out, closing TCP session, IP addr=$1 url=$2'

        Parameters list:
              $1: http15_host
              $2: http15_url

        The probe timed out before being successfully completed."
    ::= { httpNotificationsPrefix 15 }

httpNotification16 NOTIFICATION-TYPE
    OBJECTS { 
              http16_status_code, 
              http16_reason 
            }
    STATUS current
    DESCRIPTION
        "Notification of Event HTTP.16

        Message: 'received response with status_code=$1 (cause: $2)'

        Parameters list:
              $1: http16_status_code
              $2: http16_reason

        An HTTP response was received with the status-code shown."
    ::= { httpNotificationsPrefix 16 }

httpNotification17 NOTIFICATION-TYPE
    OBJECTS { 
              http17_location 
            }
    STATUS current
    DESCRIPTION
        "Notification of Event HTTP.17

        Message: 'Redirection requested, location:$1'

        Parameters list:
              $1: http17_location

        An HTTP response was received with status-code 3xx (redirection). The
        location requested is shown for informational purposes."
    ::= { httpNotificationsPrefix 17 }

httpNotification18 NOTIFICATION-TYPE
    OBJECTS { 
              http18_bytes_stored, 
              http18_bytes_to_store 
            }
    STATUS current
    DESCRIPTION
        "Notification of Event HTTP.18

        Message: 'no memory to store in temporal buffer, bytes stored=$1, bytes to store=$2'

        Parameters list:
              $1: http18_bytes_stored
              $2: http18_bytes_to_store

        When parsing a HTTP response, the temporal buffer was not big enough
        to store the bytes needed. The response parsed could be inexact."
    ::= { httpNotificationsPrefix 18 }

httpNotification19 NOTIFICATION-TYPE
    OBJECTS { 
              http19_bytes, 
              http19_time,
              http19_bps,
              http19_host,
              http19_url,
              http19_time_dns,
              http19_time_tcp,
              http19_device_status,
              http19_time_server_response,
              http19_transmit_speed,
              http19_receive_speed 
            }
    STATUS current
    DESCRIPTION
        "Notification of Event HTTP.19

        Message: 'probe completed, bytes=$1 time=$2 bps=$3 IP addr=$4 url=$5 time_dns=$6 time_tcp=$7 device_status=$8 time_server_response=$9 transmit_speed=$10 receive_speed=$11'

        Parameters list:
              $1: http19_bytes
              $2: http19_time
              $3: http19_bps
              $4: http19_host
              $5: http19_url
              $6: http19_time_dns
              $7: http19_time_tcp
              $8: http19_device_status
              $9: http19_time_server_response
              $10: http19_transmit_speed
              $11: http19_receive_speed

        The probe, for an specific page, was successfully completed."
    ::= { httpNotificationsPrefix 19 }

httpNotification20 NOTIFICATION-TYPE
    OBJECTS { 
              http20_bytes, 
              http20_time,
              http20_bps,
              http20_host,
              http20_url,
              http20_time_dns,
              http20_time_tcp,
              http20_device_status,
              http20_time_server_response,
              http20_transmit_speed,
              http20_receive_speed 
            }
    STATUS current
    DESCRIPTION
        "Notification of Event HTTP.20

        Message: 'probe failed, bytes=$1 time=$2 bps=$3 IP addr=$4 url=$5 time_dns=$6 time_tcp=$7 device_status=$8 time_server_response=$9 transmit_speed=$10 receive_speed=$11'

        Parameters list:
              $1: http20_bytes
              $2: http20_time
              $3: http20_bps
              $4: http20_host
              $5: http20_url
              $6: http20_time_dns
              $7: http20_time_tcp
              $8: http20_device_status
              $9: http20_time_server_response
              $10: http20_transmit_speed
              $11: http20_receive_speed

        The probe, for an specific page, finished before being successfully
        completed."
    ::= { httpNotificationsPrefix 20 }

httpNotification21 NOTIFICATION-TYPE
    OBJECTS { 
              http21_url 
            }
    STATUS current
    DESCRIPTION
        "Notification of Event HTTP.21

        Message: 'cannot resolve DNS url=$1'

        Parameters list:
              $1: http21_url

        There was some error when querying for the IP address associated with
        the host."
    ::= { httpNotificationsPrefix 21 }

httpNotification22 NOTIFICATION-TYPE
    OBJECTS { 
              http22_string 
            }
    STATUS current
    DESCRIPTION
        "Notification of Event HTTP.22

        Message: '$1'

        Parameters list:
              $1: http22_string

        Generic informational event from HTTP server."
    ::= { httpNotificationsPrefix 22 }

httpNotification23 NOTIFICATION-TYPE
    OBJECTS { 
              http23_url 
            }
    STATUS current
    DESCRIPTION
        "Notification of Event HTTP.23

        Message: 'max redirections reached url=$1'

        Parameters list:
              $1: http23_url

        The configured maximum number of redirections allowed has been reached.
        The next redirection required is not followed."
    ::= { httpNotificationsPrefix 23 }

httpNotification24 NOTIFICATION-TYPE
    OBJECTS { 
              http24_host, 
              http24_url,
              http24_size 
            }
    STATUS current
    DESCRIPTION
        "Notification of Event HTTP.24

        Message: 'received chunk IP addr=$1 url=$2 size=$3'

        Parameters list:
              $1: http24_host
              $2: http24_url
              $3: http24_size

        A HTTP chunk has been received."
    ::= { httpNotificationsPrefix 24 }

httpNotification25 NOTIFICATION-TYPE
    OBJECTS { 
              http25_host, 
              http25_url,
              http25_size,
              http25_total_size 
            }
    STATUS current
    DESCRIPTION
        "Notification of Event HTTP.25

        Message: 'received data IP addr=$1 url=$2 size=$3, total_size=$4'

        Parameters list:
              $1: http25_host
              $2: http25_url
              $3: http25_size
              $4: http25_total_size

        A HTTP packet has been passed to the web probe."
    ::= { httpNotificationsPrefix 25 }


END
