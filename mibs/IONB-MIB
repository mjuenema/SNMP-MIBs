--
-- IONB-MIB.mib
-- MIB generated by MG-SOFT Visual MIB Builder Version 3.0 Build 253
-- Thursday, June 26, 2014 at 11:45:21
--

	IONB-MIB DEFINITIONS ::= BEGIN
 
		IMPORTS
			OBJECT-GROUP			
				FROM SNMPv2-CONF			
			OBJECT-TYPE, MODULE-IDENTITY, OBJECT-IDENTITY			
				FROM SNMPv2-SMI			
			TruthValue			
				FROM SNMPv2-TC			
			ionB, CTA, PositiveIntegerButNotZero			
				FROM WIRELESS-INNOVATIONS-PRODUCTS-MIB;
	
	
		ionbConfiguration MODULE-IDENTITY 
			LAST-UPDATED "201406121035Z"		-- June 12, 2014 at 10:35 GMT
			ORGANIZATION 
				"Wireless Innovations"
			CONTACT-INFO 
				"Industriering 10
				86675 Buchdorf
				Germany"
			DESCRIPTION 
				"MIB for ION-B device configuration."
			REVISION "201406121035Z"		-- June 12, 2014 at 10:35 GMT
			DESCRIPTION
				"1.0.0.0
				Created."
			::= { ionB 1 }
		
	
	
--
-- Node definitions
--
	
		-- 1.3.6.1.4.1.331.1.2.1.6.2.1.1
		ionbDeviceControl OBJECT-IDENTITY
			STATUS current
			DESCRIPTION 
				"Description."
			::= { ionbConfiguration 1 }
		
		-- 1.3.6.1.4.1.331.1.2.1.6.2.1.1.1
		deviceControlTable OBJECT-TYPE
			SYNTAX SEQUENCE OF DeviceControlEntry
			MAX-ACCESS not-accessible
			STATUS current
			DESCRIPTION
				"Description."
			::= { ionbDeviceControl 1 }
		
		-- 1.3.6.1.4.1.331.1.2.1.6.2.1.1.1.1
		deviceControlEntry OBJECT-TYPE
			SYNTAX DeviceControlEntry
			MAX-ACCESS not-accessible
			STATUS current
			DESCRIPTION
				"Description."
			INDEX { deviceCTA }
			::= { deviceControlTable 1 }
		
		DeviceControlEntry ::=
			SEQUENCE { 
				deviceCTA
					CTA,
				deviceReboot
					TruthValue
			 }

		-- 1.3.6.1.4.1.331.1.2.1.6.2.1.1.1.1.1
		deviceCTA OBJECT-TYPE
			SYNTAX CTA
			MAX-ACCESS read-only
			STATUS current
			DESCRIPTION
				"Common Topology Address of the device.
				Table index."
			::= { deviceControlEntry 1 }
		
		-- 1.3.6.1.4.1.331.1.2.1.6.2.1.1.1.1.2
		deviceReboot OBJECT-TYPE
			SYNTAX TruthValue
			MAX-ACCESS read-write
			STATUS current
			DESCRIPTION
				"Object to trigger a reboot of a individual device.
				
				Get returns always false(2).
				Set true(1) triggers a device reboot."
			::= { deviceControlEntry 2 }
		
		-- 1.3.6.1.4.1.331.1.2.1.6.2.1.2
		ionbDeviceAlarmMask OBJECT-IDENTITY
			STATUS current
			DESCRIPTION 
				"Description."
			::= { ionbConfiguration 2 }
		
		-- 1.3.6.1.4.1.331.1.2.1.6.2.1.2.1
		alarmMaskTable OBJECT-TYPE
			SYNTAX SEQUENCE OF AlarmMaskEntry
			MAX-ACCESS not-accessible
			STATUS current
			DESCRIPTION
				"Description."
			::= { ionbDeviceAlarmMask 1 }
		
		-- 1.3.6.1.4.1.331.1.2.1.6.2.1.2.1.1
		alarmMaskEntry OBJECT-TYPE
			SYNTAX AlarmMaskEntry
			MAX-ACCESS not-accessible
			STATUS current
			DESCRIPTION
				"Description."
			INDEX { deviceCTA, alarmID }
			::= { alarmMaskTable 1 }
		
		AlarmMaskEntry ::=
			SEQUENCE { 
				alarmID
					PositiveIntegerButNotZero,
				alarmText
					OCTET STRING,
				alarmMasked
					TruthValue
			 }

		-- 1.3.6.1.4.1.331.1.2.1.6.2.1.2.1.1.1
		alarmID OBJECT-TYPE
			SYNTAX PositiveIntegerButNotZero
			MAX-ACCESS read-only
			STATUS current
			DESCRIPTION
				"Alarm ID.
				Second table index (first index is deviceCTA)."
			::= { alarmMaskEntry 1 }
		
		-- 1.3.6.1.4.1.331.1.2.1.6.2.1.2.1.1.2
		alarmText OBJECT-TYPE
			SYNTAX OCTET STRING
			MAX-ACCESS read-only
			STATUS current
			DESCRIPTION
				"Alarm text."
			::= { alarmMaskEntry 2 }
		
		-- 1.3.6.1.4.1.331.1.2.1.6.2.1.2.1.1.3
		alarmMasked OBJECT-TYPE
			SYNTAX TruthValue
			MAX-ACCESS read-write
			STATUS current
			DESCRIPTION
				"Alarm is masked (true) or not (false)."
			::= { alarmMaskEntry 3 }
		
		-- 1.3.6.1.4.1.331.1.2.1.6.2.1.2.2
		alarmMaskApplyToCTA OBJECT-TYPE
			SYNTAX CTA
			MAX-ACCESS read-write
			STATUS current
			DESCRIPTION
				"Object to set the alarm mask of a individual device.
				
				Get returns always an empty string.
				Set to the device CTA string to trigger the alarm mask configuration of that device."
			::= { ionbDeviceAlarmMask 2 }
		
		-- 1.3.6.1.4.1.331.1.2.1.6.2.1.3
		ionbDeviceStatusValues OBJECT-IDENTITY
			STATUS current
			DESCRIPTION 
				"Description."
			::= { ionbConfiguration 3 }
		
		-- 1.3.6.1.4.1.331.1.2.1.6.2.1.3.1
		statusTable OBJECT-TYPE
			SYNTAX SEQUENCE OF StatusEntry
			MAX-ACCESS not-accessible
			STATUS current
			DESCRIPTION
				"Description."
			::= { ionbDeviceStatusValues 1 }
		
		-- 1.3.6.1.4.1.331.1.2.1.6.2.1.3.1.1
		statusEntry OBJECT-TYPE
			SYNTAX StatusEntry
			MAX-ACCESS not-accessible
			STATUS current
			DESCRIPTION
				"Description."
			INDEX { deviceCTA, statusIdx }
			::= { statusTable 1 }
		
		StatusEntry ::=
			SEQUENCE { 
				statusIdx
					PositiveIntegerButNotZero,
				statusName
					OCTET STRING,
				statusDescriptionOff
					OCTET STRING,
				statusDescriptionOn
					OCTET STRING,
				statusValueWritable
					TruthValue,
				statusValue
					TruthValue
			 }

		-- 1.3.6.1.4.1.331.1.2.1.6.2.1.3.1.1.1
		statusIdx OBJECT-TYPE
			SYNTAX PositiveIntegerButNotZero
			MAX-ACCESS read-only
			STATUS current
			DESCRIPTION
				"Second table index (first index is deviceCTA)."
			::= { statusEntry 1 }
		
		-- 1.3.6.1.4.1.331.1.2.1.6.2.1.3.1.1.2
		statusName OBJECT-TYPE
			SYNTAX OCTET STRING
			MAX-ACCESS read-only
			STATUS current
			DESCRIPTION
				"Status value name."
			::= { statusEntry 2 }
		
		-- 1.3.6.1.4.1.331.1.2.1.6.2.1.3.1.1.3
		statusDescriptionOff OBJECT-TYPE
			SYNTAX OCTET STRING
			MAX-ACCESS read-only
			STATUS current
			DESCRIPTION
				"String representation for value false(2)."
			::= { statusEntry 3 }
		
		-- 1.3.6.1.4.1.331.1.2.1.6.2.1.3.1.1.4
		statusDescriptionOn OBJECT-TYPE
			SYNTAX OCTET STRING
			MAX-ACCESS read-only
			STATUS current
			DESCRIPTION
				"String representation for value true(1)."
			::= { statusEntry 4 }
		
		-- 1.3.6.1.4.1.331.1.2.1.6.2.1.3.1.1.5
		statusValueWritable OBJECT-TYPE
			SYNTAX TruthValue
			MAX-ACCESS read-only
			STATUS current
			DESCRIPTION
				"Status value is writable (true) or just read only (false)."
			::= { statusEntry 5 }
		
		-- 1.3.6.1.4.1.331.1.2.1.6.2.1.3.1.1.6
		statusValue OBJECT-TYPE
			SYNTAX TruthValue
			MAX-ACCESS read-write
			STATUS current
			DESCRIPTION
				"Boolean status value."
			::= { statusEntry 6 }
		
		-- 1.3.6.1.4.1.331.1.2.1.6.2.1.4
		ionbDeviceAnalogValues OBJECT-IDENTITY
			STATUS current
			DESCRIPTION 
				"Description."
			::= { ionbConfiguration 4 }
		
		-- 1.3.6.1.4.1.331.1.2.1.6.2.1.4.1
		analogTable OBJECT-TYPE
			SYNTAX SEQUENCE OF AnalogEntry
			MAX-ACCESS not-accessible
			STATUS current
			DESCRIPTION
				"Description."
			::= { ionbDeviceAnalogValues 1 }
		
		-- 1.3.6.1.4.1.331.1.2.1.6.2.1.4.1.1
		analogEntry OBJECT-TYPE
			SYNTAX AnalogEntry
			MAX-ACCESS not-accessible
			STATUS current
			DESCRIPTION
				"Description."
			INDEX { deviceCTA, analogIdx }
			::= { analogTable 1 }
		
		AnalogEntry ::=
			SEQUENCE { 
				analogIdx
					PositiveIntegerButNotZero,
				analogName
					OCTET STRING,
				analogUnit
					OCTET STRING,
				analogRangeMin
					OCTET STRING,
				analogRangeMax
					OCTET STRING,
				analogValueWritable
					TruthValue,
				analogValue
					OCTET STRING
			 }

		-- 1.3.6.1.4.1.331.1.2.1.6.2.1.4.1.1.1
		analogIdx OBJECT-TYPE
			SYNTAX PositiveIntegerButNotZero
			MAX-ACCESS read-only
			STATUS current
			DESCRIPTION
				"Second table index (first index is deviceCTA)."
			::= { analogEntry 1 }
		
		-- 1.3.6.1.4.1.331.1.2.1.6.2.1.4.1.1.2
		analogName OBJECT-TYPE
			SYNTAX OCTET STRING
			MAX-ACCESS read-only
			STATUS current
			DESCRIPTION
				"Analog value name."
			::= { analogEntry 2 }
		
		-- 1.3.6.1.4.1.331.1.2.1.6.2.1.4.1.1.3
		analogUnit OBJECT-TYPE
			SYNTAX OCTET STRING
			MAX-ACCESS read-only
			STATUS current
			DESCRIPTION
				"Analog value unit."
			::= { analogEntry 3 }
		
		-- 1.3.6.1.4.1.331.1.2.1.6.2.1.4.1.1.4
		analogRangeMin OBJECT-TYPE
			SYNTAX OCTET STRING
			MAX-ACCESS read-only
			STATUS current
			DESCRIPTION
				"Analog value lower range.
				String representation of float value."
			::= { analogEntry 4 }
		
		-- 1.3.6.1.4.1.331.1.2.1.6.2.1.4.1.1.5
		analogRangeMax OBJECT-TYPE
			SYNTAX OCTET STRING
			MAX-ACCESS read-only
			STATUS current
			DESCRIPTION
				"Analog value upper range.
				String representation of float value."
			::= { analogEntry 5 }
		
		-- 1.3.6.1.4.1.331.1.2.1.6.2.1.4.1.1.6
		analogValueWritable OBJECT-TYPE
			SYNTAX TruthValue
			MAX-ACCESS read-only
			STATUS current
			DESCRIPTION
				"Analog value is writable (true) or just read only (false)."
			::= { analogEntry 6 }
		
		-- 1.3.6.1.4.1.331.1.2.1.6.2.1.4.1.1.7
		analogValue OBJECT-TYPE
			SYNTAX OCTET STRING
			MAX-ACCESS read-write
			STATUS current
			DESCRIPTION
				"Analog value.
				String representation of float value."
			::= { analogEntry 7 }
		
		-- 1.3.6.1.4.1.331.1.2.1.6.2.1.10
		ionbConformance OBJECT-IDENTITY
			STATUS current
			DESCRIPTION 
				"Description."
			::= { ionbConfiguration 10 }
		
		-- 1.3.6.1.4.1.331.1.2.1.6.2.1.10.1
		ionbConfigurationGroup OBJECT-GROUP
			OBJECTS { deviceCTA, deviceReboot, alarmID, alarmText, alarmMasked, 
				alarmMaskApplyToCTA, statusIdx, statusName, statusDescriptionOff, statusDescriptionOn, 
				statusValueWritable, statusValue, analogIdx, analogName, analogUnit, 
				analogRangeMin, analogRangeMax, analogValueWritable, analogValue }
			STATUS current
			DESCRIPTION 
				"Description."
			::= { ionbConformance 1 }
		
	
	END

--
-- IONB-MIB.mib
--
