-- file automatically created


TELDAT-TRAP-H323-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


h323TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the H323 event subsystem."
    REVISION "201401200930Z"
    DESCRIPTION "Initial implementation"
        ::= { telEventTraps 131 }


h323EventsGroup	OBJECT IDENTIFIER	::= { h323TrapsMIB 1 }

h323Notifications	OBJECT IDENTIFIER	::= { h323TrapsMIB 2 }
h323NotificationsPrefix	OBJECT IDENTIFIER	::= { h323Notifications 0 }

h323EventObjects1 OBJECT-IDENTITY
    STATUS current
    DESCRIPTION
        "Event H323.1
        An event has been received."
    ::= { h323EventsGroup 1 }

h3231_Event OBJECT-TYPE
    SYNTAX DisplayString
    MAX-ACCESS accessible-for-notify
    STATUS current
    DESCRIPTION
        "Parameter 'Event' in event H323.1"
    ::= { h323EventObjects1 1 }

h3231_parameter OBJECT-TYPE
    SYNTAX DisplayString
    MAX-ACCESS accessible-for-notify
    STATUS current
    DESCRIPTION
        "Parameter 'parameter' in event H323.1"
    ::= { h323EventObjects1 2 }

h3231_interface OBJECT-TYPE
    SYNTAX DisplayString
    MAX-ACCESS accessible-for-notify
    STATUS current
    DESCRIPTION
        "Parameter 'interface' in event H323.1"
    ::= { h323EventObjects1 3 }

h3231_line OBJECT-TYPE
    SYNTAX Integer32
    MAX-ACCESS accessible-for-notify
    STATUS current
    DESCRIPTION
        "Parameter 'line' in event H323.1"
    ::= { h323EventObjects1 4 }

h323EventObjects2 OBJECT-IDENTITY
    STATUS current
    DESCRIPTION
        "Event H323.2
        Line state has changed."
    ::= { h323EventsGroup 2 }

h3232_new_state OBJECT-TYPE
    SYNTAX DisplayString
    MAX-ACCESS accessible-for-notify
    STATUS current
    DESCRIPTION
        "Parameter 'new_state' in event H323.2"
    ::= { h323EventObjects2 1 }

h3232_interface OBJECT-TYPE
    SYNTAX DisplayString
    MAX-ACCESS accessible-for-notify
    STATUS current
    DESCRIPTION
        "Parameter 'interface' in event H323.2"
    ::= { h323EventObjects2 2 }

h3232_line OBJECT-TYPE
    SYNTAX Integer32
    MAX-ACCESS accessible-for-notify
    STATUS current
    DESCRIPTION
        "Parameter 'line' in event H323.2"
    ::= { h323EventObjects2 3 }

h323EventObjects3 OBJECT-IDENTITY
    STATUS current
    DESCRIPTION
        "Event H323.3
        A call event has arrived."
    ::= { h323EventsGroup 3 }

h3233_Event OBJECT-TYPE
    SYNTAX DisplayString
    MAX-ACCESS accessible-for-notify
    STATUS current
    DESCRIPTION
        "Parameter 'Event' in event H323.3"
    ::= { h323EventObjects3 1 }

h3233_mode OBJECT-TYPE
    SYNTAX DisplayString
    MAX-ACCESS accessible-for-notify
    STATUS current
    DESCRIPTION
        "Parameter 'mode' in event H323.3"
    ::= { h323EventObjects3 2 }

h3233_interface OBJECT-TYPE
    SYNTAX DisplayString
    MAX-ACCESS accessible-for-notify
    STATUS current
    DESCRIPTION
        "Parameter 'interface' in event H323.3"
    ::= { h323EventObjects3 3 }

h3233_line OBJECT-TYPE
    SYNTAX Integer32
    MAX-ACCESS accessible-for-notify
    STATUS current
    DESCRIPTION
        "Parameter 'line' in event H323.3"
    ::= { h323EventObjects3 4 }

h323EventObjects4 OBJECT-IDENTITY
    STATUS current
    DESCRIPTION
        "Event H323.4
        This message indicates the transmission or the reception
        of a RAS packet, or a timeout."
    ::= { h323EventsGroup 4 }

h3234_Event OBJECT-TYPE
    SYNTAX DisplayString
    MAX-ACCESS accessible-for-notify
    STATUS current
    DESCRIPTION
        "Parameter 'Event' in event H323.4"
    ::= { h323EventObjects4 1 }

h323EventObjects5 OBJECT-IDENTITY
    STATUS current
    DESCRIPTION
        "Event H323.5
        This message gives information about the delay and variance measured in
        a communication."
    ::= { h323EventsGroup 5 }

h3235_num OBJECT-TYPE
    SYNTAX Integer32
    MAX-ACCESS accessible-for-notify
    STATUS current
    DESCRIPTION
        "Parameter 'num' in event H323.5"
    ::= { h323EventObjects5 1 }

h3235_jitter OBJECT-TYPE
    SYNTAX Integer32
    MAX-ACCESS accessible-for-notify
    STATUS current
    DESCRIPTION
        "Parameter 'jitter' in event H323.5"
    ::= { h323EventObjects5 2 }

h3235_interface OBJECT-TYPE
    SYNTAX DisplayString
    MAX-ACCESS accessible-for-notify
    STATUS current
    DESCRIPTION
        "Parameter 'interface' in event H323.5"
    ::= { h323EventObjects5 3 }

h3235_line OBJECT-TYPE
    SYNTAX Integer32
    MAX-ACCESS accessible-for-notify
    STATUS current
    DESCRIPTION
        "Parameter 'line' in event H323.5"
    ::= { h323EventObjects5 4 }

h323EventObjects6 OBJECT-IDENTITY
    STATUS current
    DESCRIPTION
        "Event H323.6
        This message shows the percentage of lost frames in the last second."
    ::= { h323EventsGroup 6 }

h3236_num OBJECT-TYPE
    SYNTAX Integer32
    MAX-ACCESS accessible-for-notify
    STATUS current
    DESCRIPTION
        "Parameter 'num' in event H323.6"
    ::= { h323EventObjects6 1 }

h3236_interface OBJECT-TYPE
    SYNTAX DisplayString
    MAX-ACCESS accessible-for-notify
    STATUS current
    DESCRIPTION
        "Parameter 'interface' in event H323.6"
    ::= { h323EventObjects6 2 }

h3236_line OBJECT-TYPE
    SYNTAX Integer32
    MAX-ACCESS accessible-for-notify
    STATUS current
    DESCRIPTION
        "Parameter 'line' in event H323.6"
    ::= { h323EventObjects6 3 }

h323EventObjects7 OBJECT-IDENTITY
    STATUS current
    DESCRIPTION
        "Event H323.7
        A global event has been received."
    ::= { h323EventsGroup 7 }

h3237_Event OBJECT-TYPE
    SYNTAX DisplayString
    MAX-ACCESS accessible-for-notify
    STATUS current
    DESCRIPTION
        "Parameter 'Event' in event H323.7"
    ::= { h323EventObjects7 1 }

h3237_parameter OBJECT-TYPE
    SYNTAX DisplayString
    MAX-ACCESS accessible-for-notify
    STATUS current
    DESCRIPTION
        "Parameter 'parameter' in event H323.7"
    ::= { h323EventObjects7 2 }

h323EventObjects8 OBJECT-IDENTITY
    STATUS current
    DESCRIPTION
        "Event H323.8
        Display H323 Radvision traces."
    ::= { h323EventsGroup 8 }

h3238_text OBJECT-TYPE
    SYNTAX DisplayString
    MAX-ACCESS accessible-for-notify
    STATUS current
    DESCRIPTION
        "Parameter 'text' in event H323.8"
    ::= { h323EventObjects8 1 }

h323EventObjects9 OBJECT-IDENTITY
    STATUS current
    DESCRIPTION
        "Event H323.9
        Frequently Time Out Events."
    ::= { h323EventsGroup 9 }

h3239_Type OBJECT-TYPE
    SYNTAX DisplayString
    MAX-ACCESS accessible-for-notify
    STATUS current
    DESCRIPTION
        "Parameter 'Type' in event H323.9"
    ::= { h323EventObjects9 1 }

h3239_Reason OBJECT-TYPE
    SYNTAX DisplayString
    MAX-ACCESS accessible-for-notify
    STATUS current
    DESCRIPTION
        "Parameter 'Reason' in event H323.9"
    ::= { h323EventObjects9 2 }

h3239_interface OBJECT-TYPE
    SYNTAX DisplayString
    MAX-ACCESS accessible-for-notify
    STATUS current
    DESCRIPTION
        "Parameter 'interface' in event H323.9"
    ::= { h323EventObjects9 3 }

h3239_line OBJECT-TYPE
    SYNTAX Integer32
    MAX-ACCESS accessible-for-notify
    STATUS current
    DESCRIPTION
        "Parameter 'line' in event H323.9"
    ::= { h323EventObjects9 4 }

h323EventObjects10 OBJECT-IDENTITY
    STATUS current
    DESCRIPTION
        "Event H323.10
        Unfrequently Time Out Events."
    ::= { h323EventsGroup 10 }

h32310_Type OBJECT-TYPE
    SYNTAX DisplayString
    MAX-ACCESS accessible-for-notify
    STATUS current
    DESCRIPTION
        "Parameter 'Type' in event H323.10"
    ::= { h323EventObjects10 1 }

h32310_Reason OBJECT-TYPE
    SYNTAX DisplayString
    MAX-ACCESS accessible-for-notify
    STATUS current
    DESCRIPTION
        "Parameter 'Reason' in event H323.10"
    ::= { h323EventObjects10 2 }

h32310_interface OBJECT-TYPE
    SYNTAX DisplayString
    MAX-ACCESS accessible-for-notify
    STATUS current
    DESCRIPTION
        "Parameter 'interface' in event H323.10"
    ::= { h323EventObjects10 3 }

h32310_line OBJECT-TYPE
    SYNTAX Integer32
    MAX-ACCESS accessible-for-notify
    STATUS current
    DESCRIPTION
        "Parameter 'line' in event H323.10"
    ::= { h323EventObjects10 4 }

h323EventObjects11 OBJECT-IDENTITY
    STATUS current
    DESCRIPTION
        "Event H323.11
        RTP synchronize."
    ::= { h323EventsGroup 11 }

h32311_interface OBJECT-TYPE
    SYNTAX DisplayString
    MAX-ACCESS accessible-for-notify
    STATUS current
    DESCRIPTION
        "Parameter 'interface' in event H323.11"
    ::= { h323EventObjects11 1 }

h32311_line OBJECT-TYPE
    SYNTAX Integer32
    MAX-ACCESS accessible-for-notify
    STATUS current
    DESCRIPTION
        "Parameter 'line' in event H323.11"
    ::= { h323EventObjects11 2 }

h323EventObjects12 OBJECT-IDENTITY
    STATUS current
    DESCRIPTION
        "Event H323.12
        RTP mean delay out."
    ::= { h323EventsGroup 12 }

h32312_delay OBJECT-TYPE
    SYNTAX Integer32
    MAX-ACCESS accessible-for-notify
    STATUS current
    DESCRIPTION
        "Parameter 'delay' in event H323.12"
    ::= { h323EventObjects12 1 }

h32312_interface OBJECT-TYPE
    SYNTAX DisplayString
    MAX-ACCESS accessible-for-notify
    STATUS current
    DESCRIPTION
        "Parameter 'interface' in event H323.12"
    ::= { h323EventObjects12 2 }

h32312_line OBJECT-TYPE
    SYNTAX Integer32
    MAX-ACCESS accessible-for-notify
    STATUS current
    DESCRIPTION
        "Parameter 'line' in event H323.12"
    ::= { h323EventObjects12 3 }

h323EventObjects13 OBJECT-IDENTITY
    STATUS current
    DESCRIPTION
        "Event H323.13
        Lost a too delayed frame."
    ::= { h323EventsGroup 13 }

h32313_CurrDelay OBJECT-TYPE
    SYNTAX Integer32
    MAX-ACCESS accessible-for-notify
    STATUS current
    DESCRIPTION
        "Parameter 'CurrDelay' in event H323.13"
    ::= { h323EventObjects13 1 }

h32313_PlyDelay OBJECT-TYPE
    SYNTAX Integer32
    MAX-ACCESS accessible-for-notify
    STATUS current
    DESCRIPTION
        "Parameter 'PlyDelay' in event H323.13"
    ::= { h323EventObjects13 2 }

h32313_interface OBJECT-TYPE
    SYNTAX DisplayString
    MAX-ACCESS accessible-for-notify
    STATUS current
    DESCRIPTION
        "Parameter 'interface' in event H323.13"
    ::= { h323EventObjects13 3 }

h32313_line OBJECT-TYPE
    SYNTAX Integer32
    MAX-ACCESS accessible-for-notify
    STATUS current
    DESCRIPTION
        "Parameter 'line' in event H323.13"
    ::= { h323EventObjects13 4 }

h323EventObjects14 OBJECT-IDENTITY
    STATUS current
    DESCRIPTION
        "Event H323.14
        Display several statistical values for current delay computation."
    ::= { h323EventsGroup 14 }

h32314_text OBJECT-TYPE
    SYNTAX DisplayString
    MAX-ACCESS accessible-for-notify
    STATUS current
    DESCRIPTION
        "Parameter 'text' in event H323.14"
    ::= { h323EventObjects14 1 }

h32314_interface OBJECT-TYPE
    SYNTAX DisplayString
    MAX-ACCESS accessible-for-notify
    STATUS current
    DESCRIPTION
        "Parameter 'interface' in event H323.14"
    ::= { h323EventObjects14 2 }

h32314_line OBJECT-TYPE
    SYNTAX Integer32
    MAX-ACCESS accessible-for-notify
    STATUS current
    DESCRIPTION
        "Parameter 'line' in event H323.14"
    ::= { h323EventObjects14 3 }

h323EventObjects15 OBJECT-IDENTITY
    STATUS current
    DESCRIPTION
        "Event H323.15
        Trace for R&D debugging purposes."
    ::= { h323EventsGroup 15 }

h32315_text OBJECT-TYPE
    SYNTAX DisplayString
    MAX-ACCESS accessible-for-notify
    STATUS current
    DESCRIPTION
        "Parameter 'text' in event H323.15"
    ::= { h323EventObjects15 1 }

h32315_misc OBJECT-TYPE
    SYNTAX Integer32
    MAX-ACCESS accessible-for-notify
    STATUS current
    DESCRIPTION
        "Parameter 'misc' in event H323.15"
    ::= { h323EventObjects15 2 }

h32315_interface OBJECT-TYPE
    SYNTAX DisplayString
    MAX-ACCESS accessible-for-notify
    STATUS current
    DESCRIPTION
        "Parameter 'interface' in event H323.15"
    ::= { h323EventObjects15 3 }

h32315_line OBJECT-TYPE
    SYNTAX Integer32
    MAX-ACCESS accessible-for-notify
    STATUS current
    DESCRIPTION
        "Parameter 'line' in event H323.15"
    ::= { h323EventObjects15 4 }

h323EventObjects16 OBJECT-IDENTITY
    STATUS current
    DESCRIPTION
        "Event H323.16
        Fax trace event."
    ::= { h323EventsGroup 16 }

h32316_text OBJECT-TYPE
    SYNTAX DisplayString
    MAX-ACCESS accessible-for-notify
    STATUS current
    DESCRIPTION
        "Parameter 'text' in event H323.16"
    ::= { h323EventObjects16 1 }

h32316_num OBJECT-TYPE
    SYNTAX Integer32
    MAX-ACCESS accessible-for-notify
    STATUS current
    DESCRIPTION
        "Parameter 'num' in event H323.16"
    ::= { h323EventObjects16 2 }

h32316_interface OBJECT-TYPE
    SYNTAX DisplayString
    MAX-ACCESS accessible-for-notify
    STATUS current
    DESCRIPTION
        "Parameter 'interface' in event H323.16"
    ::= { h323EventObjects16 3 }

h32316_line OBJECT-TYPE
    SYNTAX Integer32
    MAX-ACCESS accessible-for-notify
    STATUS current
    DESCRIPTION
        "Parameter 'line' in event H323.16"
    ::= { h323EventObjects16 4 }

h323EventObjects17 OBJECT-IDENTITY
    STATUS current
    DESCRIPTION
        "Event H323.17
        For future use."
    ::= { h323EventsGroup 17 }

h32317_text OBJECT-TYPE
    SYNTAX DisplayString
    MAX-ACCESS accessible-for-notify
    STATUS current
    DESCRIPTION
        "Parameter 'text' in event H323.17"
    ::= { h323EventObjects17 1 }

h323EventObjects18 OBJECT-IDENTITY
    STATUS current
    DESCRIPTION
        "Event H323.18
        Report actions, status and error related to H323 initialization process."
    ::= { h323EventsGroup 18 }

h32318_text OBJECT-TYPE
    SYNTAX DisplayString
    MAX-ACCESS accessible-for-notify
    STATUS current
    DESCRIPTION
        "Parameter 'text' in event H323.18"
    ::= { h323EventObjects18 1 }

h323EventObjects19 OBJECT-IDENTITY
    STATUS current
    DESCRIPTION
        "Event H323.19
        Codec added or removed from call."
    ::= { h323EventsGroup 19 }

h32319_action OBJECT-TYPE
    SYNTAX DisplayString
    MAX-ACCESS accessible-for-notify
    STATUS current
    DESCRIPTION
        "Parameter 'action' in event H323.19"
    ::= { h323EventObjects19 1 }

h32319_called-number OBJECT-TYPE
    SYNTAX DisplayString
    MAX-ACCESS accessible-for-notify
    STATUS current
    DESCRIPTION
        "Parameter 'called-number' in event H323.19"
    ::= { h323EventObjects19 2 }

h32319_calling-number OBJECT-TYPE
    SYNTAX DisplayString
    MAX-ACCESS accessible-for-notify
    STATUS current
    DESCRIPTION
        "Parameter 'calling-number' in event H323.19"
    ::= { h323EventObjects19 3 }

h32319_codec_str OBJECT-TYPE
    SYNTAX DisplayString
    MAX-ACCESS accessible-for-notify
    STATUS current
    DESCRIPTION
        "Parameter 'codec_str' in event H323.19"
    ::= { h323EventObjects19 4 }

h32319_nob OBJECT-TYPE
    SYNTAX Integer32
    MAX-ACCESS accessible-for-notify
    STATUS current
    DESCRIPTION
        "Parameter 'nob' in event H323.19"
    ::= { h323EventObjects19 5 }

h32319_vad OBJECT-TYPE
    SYNTAX DisplayString
    MAX-ACCESS accessible-for-notify
    STATUS current
    DESCRIPTION
        "Parameter 'vad' in event H323.19"
    ::= { h323EventObjects19 6 }

h323EventObjects20 OBJECT-IDENTITY
    STATUS current
    DESCRIPTION
        "Event H323.20
        This message describes the (un)registration of an user and its localization."
    ::= { h323EventsGroup 20 }

h32320_Event OBJECT-TYPE
    SYNTAX DisplayString
    MAX-ACCESS accessible-for-notify
    STATUS current
    DESCRIPTION
        "Parameter 'Event' in event H323.20"
    ::= { h323EventObjects20 1 }

h32320_user OBJECT-TYPE
    SYNTAX DisplayString
    MAX-ACCESS accessible-for-notify
    STATUS current
    DESCRIPTION
        "Parameter 'user' in event H323.20"
    ::= { h323EventObjects20 2 }

h32320_ep OBJECT-TYPE
    SYNTAX DisplayString
    MAX-ACCESS accessible-for-notify
    STATUS current
    DESCRIPTION
        "Parameter 'ep' in event H323.20"
    ::= { h323EventObjects20 3 }

h32320_ipaddr OBJECT-TYPE
    SYNTAX DisplayString
    MAX-ACCESS accessible-for-notify
    STATUS current
    DESCRIPTION
        "Parameter 'ipaddr' in event H323.20"
    ::= { h323EventObjects20 4 }

h32320_ipport OBJECT-TYPE
    SYNTAX Integer32
    MAX-ACCESS accessible-for-notify
    STATUS current
    DESCRIPTION
        "Parameter 'ipport' in event H323.20"
    ::= { h323EventObjects20 5 }

h323EventObjects21 OBJECT-IDENTITY
    STATUS current
    DESCRIPTION
        "Event H323.21
        User registration has expired because further RRQ or URQ have not been received."
    ::= { h323EventsGroup 21 }

h32321_User OBJECT-TYPE
    SYNTAX DisplayString
    MAX-ACCESS accessible-for-notify
    STATUS current
    DESCRIPTION
        "Parameter 'User' in event H323.21"
    ::= { h323EventObjects21 1 }

h32321_ep OBJECT-TYPE
    SYNTAX DisplayString
    MAX-ACCESS accessible-for-notify
    STATUS current
    DESCRIPTION
        "Parameter 'ep' in event H323.21"
    ::= { h323EventObjects21 2 }

h32321_ipaddr OBJECT-TYPE
    SYNTAX DisplayString
    MAX-ACCESS accessible-for-notify
    STATUS current
    DESCRIPTION
        "Parameter 'ipaddr' in event H323.21"
    ::= { h323EventObjects21 3 }

h32321_ipport OBJECT-TYPE
    SYNTAX Integer32
    MAX-ACCESS accessible-for-notify
    STATUS current
    DESCRIPTION
        "Parameter 'ipport' in event H323.21"
    ::= { h323EventObjects21 4 }

h323EventObjects22 OBJECT-IDENTITY
    STATUS current
    DESCRIPTION
        "Event H323.22
        This message describes the response to an ARQ to start / establish a call"
    ::= { h323EventsGroup 22 }

h32322_User OBJECT-TYPE
    SYNTAX DisplayString
    MAX-ACCESS accessible-for-notify
    STATUS current
    DESCRIPTION
        "Parameter 'User' in event H323.22"
    ::= { h323EventObjects22 1 }

h32322_ep OBJECT-TYPE
    SYNTAX DisplayString
    MAX-ACCESS accessible-for-notify
    STATUS current
    DESCRIPTION
        "Parameter 'ep' in event H323.22"
    ::= { h323EventObjects22 2 }

h32322_direction OBJECT-TYPE
    SYNTAX DisplayString
    MAX-ACCESS accessible-for-notify
    STATUS current
    DESCRIPTION
        "Parameter 'direction' in event H323.22"
    ::= { h323EventObjects22 3 }

h32322_ipaddr OBJECT-TYPE
    SYNTAX DisplayString
    MAX-ACCESS accessible-for-notify
    STATUS current
    DESCRIPTION
        "Parameter 'ipaddr' in event H323.22"
    ::= { h323EventObjects22 4 }

h32322_ipport OBJECT-TYPE
    SYNTAX Integer32
    MAX-ACCESS accessible-for-notify
    STATUS current
    DESCRIPTION
        "Parameter 'ipport' in event H323.22"
    ::= { h323EventObjects22 5 }

h323EventObjects23 OBJECT-IDENTITY
    STATUS current
    DESCRIPTION
        "Event H323.23
        Error contacting current Gatekeeper, change to the alternate Gatekeeper.
        "
    ::= { h323EventsGroup 23 }

h32323_old_gk OBJECT-TYPE
    SYNTAX DisplayString
    MAX-ACCESS accessible-for-notify
    STATUS current
    DESCRIPTION
        "Parameter 'old_gk' in event H323.23"
    ::= { h323EventObjects23 1 }

h32323_new_gk OBJECT-TYPE
    SYNTAX DisplayString
    MAX-ACCESS accessible-for-notify
    STATUS current
    DESCRIPTION
        "Parameter 'new_gk' in event H323.23"
    ::= { h323EventObjects23 2 }


h323Notification1 NOTIFICATION-TYPE
    OBJECTS { 
              h3231_Event, 
              h3231_parameter,
              h3231_interface,
              h3231_line 
            }
    STATUS current
    DESCRIPTION
        "Notification of Event H323.1

        Message: 'Event: $1 $2 line $3-$4'

        Parameters list:
              $1: h3231_Event
              $2: h3231_parameter
              $3: h3231_interface
              $4: h3231_line

        An event has been received."
    ::= { h323NotificationsPrefix 1 }

h323Notification2 NOTIFICATION-TYPE
    OBJECTS { 
              h3232_new_state, 
              h3232_interface,
              h3232_line 
            }
    STATUS current
    DESCRIPTION
        "Notification of Event H323.2

        Message: 'State terminal changed to $1 line $2-$3'

        Parameters list:
              $1: h3232_new_state
              $2: h3232_interface
              $3: h3232_line

        Line state has changed."
    ::= { h323NotificationsPrefix 2 }

h323Notification3 NOTIFICATION-TYPE
    OBJECTS { 
              h3233_Event, 
              h3233_mode,
              h3233_interface,
              h3233_line 
            }
    STATUS current
    DESCRIPTION
        "Notification of Event H323.3

        Message: 'Call event. State: $1 Mode: $2 line: $3-$4'

        Parameters list:
              $1: h3233_Event
              $2: h3233_mode
              $3: h3233_interface
              $4: h3233_line

        A call event has arrived."
    ::= { h323NotificationsPrefix 3 }

h323Notification4 NOTIFICATION-TYPE
    OBJECTS { 
              h3234_Event 
            }
    STATUS current
    DESCRIPTION
        "Notification of Event H323.4

        Message: 'RAS event. Event: $1'

        Parameters list:
              $1: h3234_Event

        This message indicates the transmission or the reception
        of a RAS packet, or a timeout."
    ::= { h323NotificationsPrefix 4 }

h323Notification5 NOTIFICATION-TYPE
    OBJECTS { 
              h3235_num, 
              h3235_jitter,
              h3235_interface,
              h3235_line 
            }
    STATUS current
    DESCRIPTION
        "Notification of Event H323.5

        Message: 'Delay: $1 ms Delay variance: $2 ms line: $3-$4'

        Parameters list:
              $1: h3235_num
              $2: h3235_jitter
              $3: h3235_interface
              $4: h3235_line

        This message gives information about the delay and variance measured in
        a communication."
    ::= { h323NotificationsPrefix 5 }

h323Notification6 NOTIFICATION-TYPE
    OBJECTS { 
              h3236_num, 
              h3236_interface,
              h3236_line 
            }
    STATUS current
    DESCRIPTION
        "Notification of Event H323.6

        Message: 'Lost frames $1 per 100 line: $2-$3'

        Parameters list:
              $1: h3236_num
              $2: h3236_interface
              $3: h3236_line

        This message shows the percentage of lost frames in the last second."
    ::= { h323NotificationsPrefix 6 }

h323Notification7 NOTIFICATION-TYPE
    OBJECTS { 
              h3237_Event, 
              h3237_parameter 
            }
    STATUS current
    DESCRIPTION
        "Notification of Event H323.7

        Message: 'Event: $1 $2'

        Parameters list:
              $1: h3237_Event
              $2: h3237_parameter

        A global event has been received."
    ::= { h323NotificationsPrefix 7 }

h323Notification8 NOTIFICATION-TYPE
    OBJECTS { 
              h3238_text 
            }
    STATUS current
    DESCRIPTION
        "Notification of Event H323.8

        Message: '$1'

        Parameters list:
              $1: h3238_text

        Display H323 Radvision traces."
    ::= { h323NotificationsPrefix 8 }

h323Notification9 NOTIFICATION-TYPE
    OBJECTS { 
              h3239_Type, 
              h3239_Reason,
              h3239_interface,
              h3239_line 
            }
    STATUS current
    DESCRIPTION
        "Notification of Event H323.9

        Message: 'Time Out (type: $1 by $2) line $3-$4'

        Parameters list:
              $1: h3239_Type
              $2: h3239_Reason
              $3: h3239_interface
              $4: h3239_line

        Frequently Time Out Events."
    ::= { h323NotificationsPrefix 9 }

h323Notification10 NOTIFICATION-TYPE
    OBJECTS { 
              h32310_Type, 
              h32310_Reason,
              h32310_interface,
              h32310_line 
            }
    STATUS current
    DESCRIPTION
        "Notification of Event H323.10

        Message: 'Time Out (type: $1 by $2) line $3-$4'

        Parameters list:
              $1: h32310_Type
              $2: h32310_Reason
              $3: h32310_interface
              $4: h32310_line

        Unfrequently Time Out Events."
    ::= { h323NotificationsPrefix 10 }

h323Notification11 NOTIFICATION-TYPE
    OBJECTS { 
              h32311_interface, 
              h32311_line 
            }
    STATUS current
    DESCRIPTION
        "Notification of Event H323.11

        Message: 'Synchronizing Timestamp ln $1-$2'

        Parameters list:
              $1: h32311_interface
              $2: h32311_line

        RTP synchronize."
    ::= { h323NotificationsPrefix 11 }

h323Notification12 NOTIFICATION-TYPE
    OBJECTS { 
              h32312_delay, 
              h32312_interface,
              h32312_line 
            }
    STATUS current
    DESCRIPTION
        "Notification of Event H323.12

        Message: 'Mean Delay Out: Delay $1 ln $2-$3'

        Parameters list:
              $1: h32312_delay
              $2: h32312_interface
              $3: h32312_line

        RTP mean delay out."
    ::= { h323NotificationsPrefix 12 }

h323Notification13 NOTIFICATION-TYPE
    OBJECTS { 
              h32313_CurrDelay, 
              h32313_PlyDelay,
              h32313_interface,
              h32313_line 
            }
    STATUS current
    DESCRIPTION
        "Notification of Event H323.13

        Message: 'Lost Frame current delay $1 Playing delay $2 ln $3-$4'

        Parameters list:
              $1: h32313_CurrDelay
              $2: h32313_PlyDelay
              $3: h32313_interface
              $4: h32313_line

        Lost a too delayed frame."
    ::= { h323NotificationsPrefix 13 }

h323Notification14 NOTIFICATION-TYPE
    OBJECTS { 
              h32314_text, 
              h32314_interface,
              h32314_line 
            }
    STATUS current
    DESCRIPTION
        "Notification of Event H323.14

        Message: 'RTP:$1 ln $2-$3'

        Parameters list:
              $1: h32314_text
              $2: h32314_interface
              $3: h32314_line

        Display several statistical values for current delay computation."
    ::= { h323NotificationsPrefix 14 }

h323Notification15 NOTIFICATION-TYPE
    OBJECTS { 
              h32315_text, 
              h32315_misc,
              h32315_interface,
              h32315_line 
            }
    STATUS current
    DESCRIPTION
        "Notification of Event H323.15

        Message: 'DBG:$1 $2 ln $3-$4'

        Parameters list:
              $1: h32315_text
              $2: h32315_misc
              $3: h32315_interface
              $4: h32315_line

        Trace for R&D debugging purposes."
    ::= { h323NotificationsPrefix 15 }

h323Notification16 NOTIFICATION-TYPE
    OBJECTS { 
              h32316_text, 
              h32316_num,
              h32316_interface,
              h32316_line 
            }
    STATUS current
    DESCRIPTION
        "Notification of Event H323.16

        Message: 'FAX:$1 $2 line $3-$4'

        Parameters list:
              $1: h32316_text
              $2: h32316_num
              $3: h32316_interface
              $4: h32316_line

        Fax trace event."
    ::= { h323NotificationsPrefix 16 }

h323Notification17 NOTIFICATION-TYPE
    OBJECTS { 
              h32317_text 
            }
    STATUS current
    DESCRIPTION
        "Notification of Event H323.17

        Message: '$1'

        Parameters list:
              $1: h32317_text

        For future use."
    ::= { h323NotificationsPrefix 17 }

h323Notification18 NOTIFICATION-TYPE
    OBJECTS { 
              h32318_text 
            }
    STATUS current
    DESCRIPTION
        "Notification of Event H323.18

        Message: '$1'

        Parameters list:
              $1: h32318_text

        Report actions, status and error related to H323 initialization process."
    ::= { h323NotificationsPrefix 18 }

h323Notification19 NOTIFICATION-TYPE
    OBJECTS { 
              h32319_action, 
              h32319_called-number,
              h32319_calling-number,
              h32319_codec_str,
              h32319_nob,
              h32319_vad 
            }
    STATUS current
    DESCRIPTION
        "Notification of Event H323.19

        Message: 'H245 Codec $1 Call: $2/$3 (called/calling), codec $4, nob $5, vad $6'

        Parameters list:
              $1: h32319_action
              $2: h32319_called-number
              $3: h32319_calling-number
              $4: h32319_codec_str
              $5: h32319_nob
              $6: h32319_vad

        Codec added or removed from call."
    ::= { h323NotificationsPrefix 19 }

h323Notification20 NOTIFICATION-TYPE
    OBJECTS { 
              h32320_Event, 
              h32320_user,
              h32320_ep,
              h32320_ipaddr,
              h32320_ipport 
            }
    STATUS current
    DESCRIPTION
        "Notification of Event H323.20

        Message: 'Event $1 for user $2 placed at ep $3 IP $4 port $5'

        Parameters list:
              $1: h32320_Event
              $2: h32320_user
              $3: h32320_ep
              $4: h32320_ipaddr
              $5: h32320_ipport

        This message describes the (un)registration of an user and its localization."
    ::= { h323NotificationsPrefix 20 }

h323Notification21 NOTIFICATION-TYPE
    OBJECTS { 
              h32321_User, 
              h32321_ep,
              h32321_ipaddr,
              h32321_ipport 
            }
    STATUS current
    DESCRIPTION
        "Notification of Event H323.21

        Message: 'User $1 (at ep $2 IP $3 port $4) register has expired due to timeout!'

        Parameters list:
              $1: h32321_User
              $2: h32321_ep
              $3: h32321_ipaddr
              $4: h32321_ipport

        User registration has expired because further RRQ or URQ have not been received."
    ::= { h323NotificationsPrefix 21 }

h323Notification22 NOTIFICATION-TYPE
    OBJECTS { 
              h32322_User, 
              h32322_ep,
              h32322_direction,
              h32322_ipaddr,
              h32322_ipport 
            }
    STATUS current
    DESCRIPTION
        "Notification of Event H323.22

        Message: 'Adm granted to user $1 (at endpoint $2). $3 IP $4 port $5'

        Parameters list:
              $1: h32322_User
              $2: h32322_ep
              $3: h32322_direction
              $4: h32322_ipaddr
              $5: h32322_ipport

        This message describes the response to an ARQ to start / establish a call"
    ::= { h323NotificationsPrefix 22 }

h323Notification23 NOTIFICATION-TYPE
    OBJECTS { 
              h32323_old_gk, 
              h32323_new_gk 
            }
    STATUS current
    DESCRIPTION
        "Notification of Event H323.23

        Message: 'RAS: Problems with Gatekeeper $1. Trying with $2'

        Parameters list:
              $1: h32323_old_gk
              $2: h32323_new_gk

        Error contacting current Gatekeeper, change to the alternate Gatekeeper.
        "
    ::= { h323NotificationsPrefix 23 }


END
