IBM-Director-Server-MIB DEFINITIONS ::= BEGIN

IMPORTS
   MODULE-IDENTITY, OBJECT-TYPE, Integer32,
   Unsigned32                                 FROM SNMPv2-SMI
   DisplayString, MacAddress                  FROM SNMPv2-TC
   MODULE-COMPLIANCE, OBJECT-GROUP            FROM SNMPv2-CONF
   ibm                                        FROM IBM-REC-MIB;

directorServerMIB MODULE-IDENTITY
   LAST-UPDATED "200307090000Z"
   ORGANIZATION "IBM Corp."
   CONTACT-INFO
      "IBM Corporation"
   DESCRIPTION
      "This module defines objects for the IBM Director Server portion
       of the MIB tree."
   ::= { dmiMibs 3 }

ibmProd     OBJECT IDENTIFIER ::= { ibm 6 }

director    OBJECT IDENTIFIER ::= { ibmProd 159 }

dmiMibs     OBJECT IDENTIFIER ::= { director 200 }

dmtfGroups  OBJECT IDENTIFIER ::= { directorServerMIB 1 }

componentidTable OBJECT-TYPE
   SYNTAX      SEQUENCE OF SComponentid
   MAX-ACCESS  not-accessible
   STATUS      current
   DESCRIPTION
      "This group defines attributes common to all components.This
       group is required."
   ::= {dmtfGroups 1}

componentidEntry OBJECT-TYPE
   SYNTAX      SComponentid
   MAX-ACCESS  not-accessible
   STATUS      current
   DESCRIPTION
      "INDEX INTEGER value is DmiComponentIndex"
   INDEX       {a1Index}
   ::= {componentidTable 1}

SComponentid ::= SEQUENCE {
   a1Index                                         Unsigned32,
   a1Manufacturer                                  DisplayString,
   a1Product                                       DisplayString,
   a1Version                                       DisplayString,
   a1SerialNumber                                  DisplayString
}

a1Index OBJECT-TYPE
   SYNTAX      Unsigned32
   MAX-ACCESS  read-only
   STATUS      current
   DESCRIPTION
      "The name of the manufacturer that produces this component."
   ::= {componentidEntry 5}

a1Manufacturer OBJECT-TYPE
   SYNTAX      DisplayString
   MAX-ACCESS  read-only
   STATUS      current
   DESCRIPTION
      "The name of the manufacturer that produces this component."
   ::= {componentidEntry 1}

a1Product OBJECT-TYPE
   SYNTAX      DisplayString
   MAX-ACCESS  read-only
   STATUS      current
   DESCRIPTION
      "The name of the component."
   ::= {componentidEntry 2}

a1Version OBJECT-TYPE
   SYNTAX      DisplayString
   MAX-ACCESS  read-only
   STATUS      current
   DESCRIPTION
      "The version for the component."
   ::= {componentidEntry 3}

a1SerialNumber OBJECT-TYPE
   SYNTAX      DisplayString
   MAX-ACCESS  read-only
   STATUS      current
   DESCRIPTION
      "The serial number for this instance of this component."
   ::= {componentidEntry 4}

remoteSystemsTable OBJECT-TYPE
   SYNTAX      SEQUENCE OF SRemoteSystems
   MAX-ACCESS  not-accessible
   STATUS      current
   DESCRIPTION
      "Table of remote systems defined for managing under the server."
   ::= {dmtfGroups 11}

remoteSystemsEntry OBJECT-TYPE
   SYNTAX      SRemoteSystems
   MAX-ACCESS  not-accessible
   STATUS      current
   DESCRIPTION
      "INDEX INTEGER value is DmiComponentIndex"
   INDEX           {a11SystemTag}
   ::= {remoteSystemsTable 1}

SRemoteSystems ::= SEQUENCE {
   a11SystemTag                                    Unsigned32,
   a11SystemName                                   DisplayString,
   a11ProtocolName                                 DisplayString,
   a11NetworkAddress                               DisplayString,
   a11SystemState                                  INTEGER,
   a11Server                                       INTEGER,
   a11DirectorServer                               INTEGER,
   a11OperatingSystemType                          INTEGER,
   a11OsMajorVersion                               Unsigned32,
   a11OsMinorVersion                               Unsigned32,
   a11SystemModelId                                DisplayString,
   a11SystemModelName                              DisplayString,
   a11SystemOnlineNotify                           INTEGER,
   a11SystemOfflineNotify                          INTEGER,
   a11PresenceCheckInterval                        Unsigned32,
   a11MacAddress                                   MacAddress
}

a11SystemTag OBJECT-TYPE
   SYNTAX      Unsigned32
   MAX-ACCESS  read-only
   STATUS      current
   DESCRIPTION
      "Unique ID number of this remote system on the server."
   ::= {remoteSystemsEntry 1}

a11SystemName OBJECT-TYPE
   SYNTAX      DisplayString
   MAX-ACCESS  read-only
   STATUS      current
   DESCRIPTION
      "Displayable name of the given system."
   ::= {remoteSystemsEntry 2}

a11ProtocolName OBJECT-TYPE
   SYNTAX      DisplayString
   MAX-ACCESS  read-only
   STATUS      current
   DESCRIPTION
      "This is the type of network protocol used for communication with the given system."
   ::= {remoteSystemsEntry 3}

a11NetworkAddress OBJECT-TYPE
   SYNTAX      DisplayString
   MAX-ACCESS  read-only
   STATUS      current
   DESCRIPTION
      "This is the network address of the given system."
   ::= {remoteSystemsEntry 4}

a11SystemState OBJECT-TYPE
   SYNTAX      INTEGER {
                  offline(0),
                  online(1),
                  offlineWithErrorCondition(2),
                  onlineWithErrorCondition(3)
               }
   MAX-ACCESS  read-only
   STATUS      current
   DESCRIPTION
      "This reflects the on-line/off-line state of the given system."
   ::= {remoteSystemsEntry 5}

a11Server OBJECT-TYPE
   SYNTAX      INTEGER {
                  false(0),
                  true(1)
               }
   MAX-ACCESS  read-only
   STATUS      current
   DESCRIPTION
      "This indicates if the system is some sort of server system."
   ::= {remoteSystemsEntry 6}

a11DirectorServer OBJECT-TYPE
   SYNTAX      INTEGER {
                  false(0),
                  true(1)
               }
   MAX-ACCESS  read-only
   STATUS      current
   DESCRIPTION
      "This indicates if the system is a IBM Director Server system."
   ::= {remoteSystemsEntry 7}

a11OperatingSystemType OBJECT-TYPE
   SYNTAX      INTEGER {
                  unknown(0),
                  ibmOs2(1),
                  microsoftWindows(2),
                  novellNetware(3),
                  microsoftWindowsNt(4),
                  ibmAix(5),
                  banyanVines(6),
                  ibmPcdos(7),
                  scoXenix(8),
                  unixSystemV(9),
                  ibmWorkplaceOs(10),
                  microsoftWindows95(11),
                  ibmOs400(12),
                  linux(13)
               }
   MAX-ACCESS  read-only
   STATUS      current
   DESCRIPTION
      "The primary operating system running on the given system."
   ::= {remoteSystemsEntry 8}

a11OsMajorVersion OBJECT-TYPE
   SYNTAX      Unsigned32
   MAX-ACCESS  read-only
   STATUS      current
   DESCRIPTION
      "The major version of primary operating system running on the given system."
   ::= {remoteSystemsEntry 9}

a11OsMinorVersion OBJECT-TYPE
   SYNTAX      Unsigned32
   MAX-ACCESS  read-only
   STATUS      current
   DESCRIPTION
      "The minor version of primary operating system running on the given system."
   ::= {remoteSystemsEntry 10}

a11SystemModelId OBJECT-TYPE
   SYNTAX      DisplayString
   MAX-ACCESS  read-only
   STATUS      current
   DESCRIPTION
      "These are the model identifier values for the given system.
       Systems which are the same non-zero model identifier are the same type of
       system."
   ::= {remoteSystemsEntry 11}

a11SystemModelName OBJECT-TYPE
   SYNTAX      DisplayString
   MAX-ACCESS  read-only
   STATUS      current
   DESCRIPTION
      "This is the model name for the given system, if known."
   ::= {remoteSystemsEntry 12}

a11SystemOnlineNotify OBJECT-TYPE
   SYNTAX      INTEGER {
                  sev0(0),
                  sev1(1),
                  sev2(2),
                  sev3(3),
                  sev4(4),
                  sev5(5),
                  sev6(6),
                  sev7(7),
                  noDefault(254),
                  disabled(255)
               }
   MAX-ACCESS  read-only
   STATUS      current
   DESCRIPTION
      "Severity of alert generated when system becomes on-line, if enabled."
   ::= {remoteSystemsEntry 13}

a11SystemOfflineNotify OBJECT-TYPE
   SYNTAX      INTEGER {
                  sev0(0),
                  sev1(1),
                  sev2(2),
                  sev3(3),
                  sev4(4),
                  sev5(5),
                  sev6(6),
                  sev7(7),
                  noDefault(254),
                  disabled(255)
               }
   MAX-ACCESS  read-only
   STATUS      current
   DESCRIPTION
      "Severity of alert generated when system becomes off-line, if enabled."
   ::= {remoteSystemsEntry 14}

a11PresenceCheckInterval OBJECT-TYPE
   SYNTAX      Unsigned32
   MAX-ACCESS  read-only
   STATUS      current
   DESCRIPTION
      "This is the time between attempts by the server to verify the
       presence of the remote system, in seconds."
   ::= {remoteSystemsEntry 15}

a11MacAddress OBJECT-TYPE
   SYNTAX      MacAddress
   MAX-ACCESS  read-only
   STATUS      current
   DESCRIPTION
      "Media Access Control (MAC) address of remote system, if known."
   ::= {remoteSystemsEntry 16}

remoteSystemGroupsTable OBJECT-TYPE
   SYNTAX      SEQUENCE OF SRemoteSystemGroups
   MAX-ACCESS  not-accessible
   STATUS      current
   DESCRIPTION
      "Table of remote system groups defined for managing under the server."
   ::= {dmtfGroups 12}

remoteSystemGroupsEntry OBJECT-TYPE
   SYNTAX      SRemoteSystemGroups
   MAX-ACCESS  not-accessible
   STATUS      current
   DESCRIPTION
      "INDEX INTEGER value is DmiComponentIndex"
   INDEX       {a12GroupTag}
   ::= {remoteSystemGroupsTable 1}

SRemoteSystemGroups ::= SEQUENCE {
   a12GroupTag                                     Unsigned32,
   a12GroupName                                    DisplayString,
   a12RequiredKeywordsCombination                  INTEGER,
   a12Keywords                                     DisplayString,
   a12SystemOnlineNotifyDefault                    INTEGER,
   a12SystemOfflineNotifyDefault                   INTEGER,
   a12DefaultPresenceCheckInterval                 Unsigned32,
   a12DiscoveryStartFlag                           Integer32
}

a12GroupTag OBJECT-TYPE
   SYNTAX      Unsigned32
   MAX-ACCESS  read-only
   STATUS      current
   DESCRIPTION
      "Unique ID number of this system group on the server."
   ::= {remoteSystemGroupsEntry 1}

a12GroupName OBJECT-TYPE
   SYNTAX      DisplayString
   MAX-ACCESS  read-only
   STATUS      current
   DESCRIPTION
      "Displayable name of the given group."
   ::= {remoteSystemGroupsEntry 2}

a12RequiredKeywordsCombination OBJECT-TYPE
   SYNTAX      INTEGER {
                  allKeywordsMustMatch(0),
                  anyOfTheKeywordsMayMatch(1),
                  exactlyOneKeywordsMustMatch(2)
               }
   MAX-ACCESS  read-only
   STATUS      current
   DESCRIPTION
      "This reflects whether all, any, or one of the keywords for
       the group must be matched during a discovery request in order for a remote
       system to be discovered."
   ::= {remoteSystemGroupsEntry 3}

a12Keywords OBJECT-TYPE
   SYNTAX      DisplayString
   MAX-ACCESS  read-only
   STATUS      current
   DESCRIPTION
      "List of keywords which are used for finding remote systems
       during a discovery request."
   ::= {remoteSystemGroupsEntry 4}

a12SystemOnlineNotifyDefault OBJECT-TYPE
   SYNTAX      INTEGER {
                  sev0(0),
                  sev1(1),
                  sev2(2),
                  sev3(3),
                  sev4(4),
                  sev5(5),
                  sev6(6),
                  sev7(7),
                  noDefault(254),
                  disabled(255)
               }
   MAX-ACCESS  read-only
   STATUS      current
   DESCRIPTION
      "On-line notification default for systems in this group, if enabled."
   ::= {remoteSystemGroupsEntry 5}

a12SystemOfflineNotifyDefault OBJECT-TYPE
   SYNTAX      INTEGER {
                  sev0(0),
                  sev1(1),
                  sev2(2),
                  sev3(3),
                  sev4(4),
                  sev5(5),
                  sev6(6),
                  sev7(7),
                  noDefault(254),
                  disabled(255)
               }
   MAX-ACCESS  read-only
   STATUS      current
   DESCRIPTION
      "Off-line notification default for systems in this group, if enabled."
   ::= {remoteSystemGroupsEntry 6}

a12DefaultPresenceCheckInterval OBJECT-TYPE
   SYNTAX      Unsigned32
   MAX-ACCESS  read-only
   STATUS      current
   DESCRIPTION
      "This is the default time between attempts by the
       server to verify the presence of the system in this group, in seconds.
       0 = No group-specific default."
   ::= {remoteSystemGroupsEntry 7}

a12DiscoveryStartFlag OBJECT-TYPE
   SYNTAX      Integer32
   MAX-ACCESS  read-write
   STATUS      current
   DESCRIPTION
      "The value of this flag is not significant.  To start a discovery
       request on the given System Group, write any value to this field."
   ::= {remoteSystemGroupsEntry 8}

remoteSystemGroupMapTable OBJECT-TYPE
   SYNTAX      SEQUENCE OF SRemoteSystemGroupMap
   MAX-ACCESS  not-accessible
   STATUS      current
   DESCRIPTION
      "Table mapping the membership of remote system in groups in the server."
   ::= {dmtfGroups 13}

remoteSystemGroupMapEntry OBJECT-TYPE
   SYNTAX      SRemoteSystemGroupMap
   MAX-ACCESS  not-accessible
   STATUS      current
   DESCRIPTION
      "INDEX INTEGER value is DmiComponentIndex"
   INDEX       {a13SystemTag, a13GroupTag}
   ::= {remoteSystemGroupMapTable 1}

SRemoteSystemGroupMap ::= SEQUENCE {
   a13SystemTag                                    Unsigned32,
   a13GroupTag                                     Unsigned32
}

a13SystemTag OBJECT-TYPE
   SYNTAX      Unsigned32
   MAX-ACCESS  read-only
   STATUS      current
   DESCRIPTION
      "Unique ID number of remote system."
   ::= {remoteSystemGroupMapEntry 1}

a13GroupTag OBJECT-TYPE
   SYNTAX      Unsigned32
   MAX-ACCESS  read-only
   STATUS      current
   DESCRIPTION
      "Unique ID number of group containing the remote system."
   ::= {remoteSystemGroupMapEntry 2}

directorServerMIBConformance OBJECT IDENTIFIER ::= { directorServerMIB 2 }

directorServerMIBGroups      OBJECT IDENTIFIER ::= { directorServerMIBConformance 1 }
directorServerMIBCompliances OBJECT IDENTIFIER ::= { directorServerMIBConformance 2 }

directorServerMIBCompliance MODULE-COMPLIANCE
   STATUS  current
   DESCRIPTION
      "The compliance statement for this module."
   MODULE  -- this module
   MANDATORY-GROUPS { directorServerMIBGroup }
   ::= { directorServerMIBCompliances 1 }

directorServerMIBGroup OBJECT-GROUP
   OBJECTS { a1Index, a1Manufacturer, a1Product, a1Version,
             a1SerialNumber, a11SystemTag, a11SystemName, a11ProtocolName,
             a11NetworkAddress, a11SystemState, a11Server, a11DirectorServer,
             a11OperatingSystemType, a11OsMajorVersion,
             a11OsMinorVersion, a11SystemModelId, a11SystemModelName, a11SystemOnlineNotify,
             a11SystemOfflineNotify, a11PresenceCheckInterval, a11MacAddress,
             a12GroupTag, a12GroupName, a12RequiredKeywordsCombination,
             a12Keywords, a12SystemOnlineNotifyDefault, a12SystemOfflineNotifyDefault,
             a12DefaultPresenceCheckInterval, a12DiscoveryStartFlag, a13SystemTag,
             a13GroupTag }
   STATUS  current
   DESCRIPTION
      "The objects group for objects defined in this module."
   ::= { directorServerMIBGroups 1 }

END
