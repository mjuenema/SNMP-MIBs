--MibName=wsa5Agent
--
--******************************************************************************
--*  Web Server Group Agent MIB                                                *
--******************************************************************************

WSA5AGENT-MIB DEFINITIONS ::= BEGIN

    IMPORTS
        OBJECT-TYPE, DisplayString
        FROM RFC1155-SMI;

-- Base OID  1.3.6.1.4.1.791.2.10.2.83

    cai         OBJECT IDENTIFIER ::= { enterprises 791 }

    caiSysMgr   OBJECT IDENTIFIER ::= { cai 2 }

    tng         OBJECT IDENTIFIER ::= { caiSysMgr 10 }

    unix-nt     OBJECT IDENTIFIER ::= { tng 2 }

    wsa5Agent   OBJECT IDENTIFIER ::= { unix-nt 83 }

    wsa5ServerGroup           OBJECT IDENTIFIER   ::=  {  wsa5Agent 1   }
    wsa5ServersGroup          OBJECT IDENTIFIER   ::=  {  wsa5Agent 2   }
    wsa5BadLinkGroup          OBJECT IDENTIFIER   ::=  {  wsa5Agent 3   }
    wsa5TopURLGroup           OBJECT IDENTIFIER   ::=  {  wsa5Agent 4   }
    wsa5URLAvailCounterGroup  OBJECT IDENTIFIER   ::=  {  wsa5Agent 5   }
    wsa5URLMntrGroup          OBJECT IDENTIFIER   ::=  {  wsa5Agent 6   }
    wsa5AvailIISCounterGroup  OBJECT IDENTIFIER   ::=  {  wsa5Agent 7   }
    wsa5AvailCounterGroup     OBJECT IDENTIFIER   ::=  {  wsa5Agent 8   }
    wsa5PolledCounterGroup    OBJECT IDENTIFIER   ::=  {  wsa5Agent 9   }
    wsa5DetailGroup    	      OBJECT IDENTIFIER   ::=  {  wsa5Agent 10  }
    wsa5AgentGroup            OBJECT IDENTIFIER   ::=  {  wsa5Agent 11  }
    wsa5PolledIISCounterGroup OBJECT IDENTIFIER   ::=  {  wsa5Agent 12  }
    wsa5SHGroup               OBJECT IDENTIFIER   ::=  {  wsa5Agent 13  }
    wsa5LocalActionGroup      OBJECT IDENTIFIER   ::=  {  wsa5Agent 14  }

--******************************************************************************
--* wsa5ServerGroup - Site and summary information                               *
--******************************************************************************

        wsa5ServerName OBJECT-TYPE
                SYNTAX  DisplayString
                ACCESS  read-only
                STATUS  mandatory
                DESCRIPTION
                "The host name of the computer."
                ::=  {  wsa5ServerGroup 1   }

        wsa5ServerSummaryStatus OBJECT-TYPE
                SYNTAX  INTEGER
                {
                    Ok(1),
                    Warning(2),
                    Critical(3)
                }
                ACCESS  read-only
                STATUS  mandatory
                DESCRIPTION
                "The status of the monitored server."
                ::=  {  wsa5ServerGroup 2   }

        wsa5ServerPollingInterval OBJECT-TYPE
                SYNTAX  INTEGER
                ACCESS  read-write
                STATUS  mandatory
                DESCRIPTION
                "Poll interval for the server group in seconds."
                ::=  {  wsa5ServerGroup 3   }

        wsa5ServerResetCounts OBJECT-TYPE
                SYNTAX  INTEGER
                {
                    Reset(1)
                }
                ACCESS  read-write
                STATUS  mandatory
                DESCRIPTION
                "Resets all history counts to zero when set."
                ::=  {  wsa5ServerGroup 4   }

        wsa5ServerResetTS OBJECT-TYPE
                SYNTAX  INTEGER
                ACCESS  read-only
                STATUS  mandatory
                DESCRIPTION
                "Time of last reset in ctime form."
                ::=  {  wsa5ServerGroup 5   }

        wsa5ServerResetTSEdit OBJECT-TYPE
                SYNTAX  DisplayString
                ACCESS  read-only
                STATUS  mandatory
                DESCRIPTION
                "Time of last reset in display form."
                ::=  {  wsa5ServerGroup 6   }

        wsa5ServerResetDays OBJECT-TYPE
                SYNTAX  INTEGER
                ACCESS  read-write
                STATUS  mandatory
                DESCRIPTION
                "Number of days between automatic history count resets."
                ::=  {  wsa5ServerGroup 7   }

        wsa5ServerPort OBJECT-TYPE
                SYNTAX  INTEGER
                ACCESS  read-only
                STATUS  mandatory
                DESCRIPTION
                "Port the server is listening on."
                ::=  {  wsa5ServerGroup 9   }

        wsa5ServerLBHost OBJECT-TYPE
                SYNTAX  DisplayString
                ACCESS  read-write
                STATUS  mandatory
                DESCRIPTION
                "Host name for Agent Collector."
                ::=  {  wsa5ServerGroup 10   }

        wsa5ServerLBPort OBJECT-TYPE
                SYNTAX  DisplayString
                ACCESS  read-write
                STATUS  mandatory
                DESCRIPTION
                "Agent Collector name."
                ::=  {  wsa5ServerGroup 11   }

	wsa5ServerLBEnaDis OBJECT-TYPE
		SYNTAX      INTEGER {Enable(1), Disable(2)}
		ACCESS      read-write
		STATUS      mandatory
		DESCRIPTION "Enable or disable the Agent Collector."
		::= {wsa5ServerGroup 12}

        wsa5SuperAgentRequest OBJECT-TYPE
                SYNTAX  DisplayString
                ACCESS  read-write
                STATUS  mandatory
                DESCRIPTION
                "Super Agent service request."
                ::=  {  wsa5ServerGroup 13   }

        wsa5ServerSetBaseLine OBJECT-TYPE
                SYNTAX  INTEGER {
                                set(1)
                               }
                ACCESS  write-only
                STATUS  mandatory
                DESCRIPTION
                "Immediately set Adaptive Configuration values."
                ::=  {  wsa5ServerGroup 14   }

        wsa5ServerBaseLineWarnWeight OBJECT-TYPE
                SYNTAX  INTEGER 
                ACCESS  read-write
                STATUS  mandatory
                DESCRIPTION
                "Adaptive Configuration warning weighing factor."
                ::=  {  wsa5ServerGroup 15   }

        wsa5ServerBaseLineCritWeight OBJECT-TYPE
                SYNTAX  INTEGER 
                ACCESS  read-write
                STATUS  mandatory
                DESCRIPTION
                "Adaptive Configuration critical weighing factor."
                ::=  {  wsa5ServerGroup 16   }

	wsa5ServerBaseLineEnaDis OBJECT-TYPE
		SYNTAX      INTEGER {disable(1), enable(2)}
		ACCESS      read-write
		STATUS      mandatory
		DESCRIPTION "Enable or disable Active Adaptive Configuration."
		::= {  wsa5ServerGroup 17  }

	wsa5ServerBaseLineTimer OBJECT-TYPE
		SYNTAX      INTEGER
		ACCESS      read-write
		STATUS      mandatory
		DESCRIPTION "Active Adaptive Configuration timer."
		::= {  wsa5ServerGroup 18  }
                
        wsa5ServerExportConfigSet OBJECT-TYPE
                SYNTAX  DisplayString
                ACCESS  read-write
                STATUS  mandatory
                DESCRIPTION
                "Name of config to export to."
                ::=  {  wsa5ServerGroup 19   }
                
        wsa5ServerImportConfigSet OBJECT-TYPE
                SYNTAX  DisplayString
                ACCESS  read-write
                STATUS  mandatory
                DESCRIPTION
                "Name of config to import from."
                ::=  {  wsa5ServerGroup 20   }


--******************************************************************************
--* wsa5ServersGroup - Servers                                                  *
--******************************************************************************

        wsa5ServersTableEntries OBJECT-TYPE
                SYNTAX  INTEGER
                ACCESS  read-only
                STATUS  mandatory
                DESCRIPTION
                "The number of entries in the table."
                ::=  {  wsa5ServersGroup 1  }

        wsa5ServersSummaryStatus OBJECT-TYPE
                SYNTAX  INTEGER
                {
                    Normal(1),
                    Warning(2),
                    Critical(3)
                }
                ACCESS  read-only
                STATUS  mandatory
                DESCRIPTION
                "Summary status of the servers group."
                ::=  {  wsa5ServersGroup 2  }

        wsa5ServersPollingInterval OBJECT-TYPE
                SYNTAX  INTEGER
                ACCESS  read-write
                STATUS  mandatory
                DESCRIPTION
                "Poll interval for the servers group in seconds."
                ::=  {  wsa5ServersGroup 3  }

        wsa5ServersWarningCount OBJECT-TYPE
                SYNTAX  INTEGER
                ACCESS  read-only
                STATUS  mandatory
                DESCRIPTION
                "The number of entries in the table with warning status."
                ::=  {  wsa5ServersGroup 4  }

        wsa5ServersCriticalCount OBJECT-TYPE
                SYNTAX  INTEGER
                ACCESS  read-only
                STATUS  mandatory
                DESCRIPTION
                "The number of entries in the table with critical status."
                ::=  {  wsa5ServersGroup 5  }


        wsa5ServersTable OBJECT-TYPE
                SYNTAX  SEQUENCE OF Wsa5ServersEntry
                ACCESS  not-accessible
                STATUS  mandatory
                DESCRIPTION
                "The list of all monitored servers."
                ::=  {  wsa5ServersGroup 6}

        wsa5ServersEntry OBJECT-TYPE
                 SYNTAX  Wsa5ServersEntry
                 ACCESS  not-accessible
                 STATUS  mandatory
                 DESCRIPTION
                 "The wsa5ServersTable entry."
                 INDEX { wsa5ServersMID, wsa5ServersAID, wsa5ServersIID }
                     ::=  { wsa5ServersTable 1 }

        Wsa5ServersEntry ::= SEQUENCE
        {
            wsa5ServersName           DisplayString,
            wsa5ServersStatus         INTEGER,
            wsa5ServersSStatus        INTEGER,
            wsa5ServersDStatus        INTEGER,
            wsa5ServersHStatus        INTEGER,
            wsa5ServersEStatus        INTEGER,
            wsa5ServersWStatus        INTEGER,
            wsa5ServersWLocalAction   DisplayString,
            wsa5ServersCLocalAction   DisplayString,
            wsa5ServersABCfg          DisplayString,
            wsa5ServersHost           DisplayString,
            wsa5ServersInst           DisplayString,
            wsa5ServersPrevStatus     INTEGER,
            wsa5ServersState          INTEGER,
	    wsa5ServersDelete	     INTEGER,
	    wsa5ServersStoppedStatus  INTEGER,
            wsa5ServersMID            DisplayString,
            wsa5ServersAID            DisplayString,
            wsa5ServersIID            DisplayString
        }

        wsa5ServersName OBJECT-TYPE
                SYNTAX  DisplayString
                ACCESS  read-only
                STATUS  mandatory
                DESCRIPTION
                "The name of the server."
                ::=  {  wsa5ServersEntry 1   }

        wsa5ServersStatus OBJECT-TYPE
                SYNTAX  INTEGER
                {
                    Normal(1),
                    Warning(2),
                    Critical(3)
                }
                ACCESS  read-only
                STATUS  mandatory
                DESCRIPTION
                "Summary status of the server."
                ::=  {  wsa5ServersEntry 2   }

        wsa5ServersSStatus OBJECT-TYPE
                SYNTAX  INTEGER
                {
                    Normal(1),
                    Warning(2),
                    Critical(3)
                }
                ACCESS  read-only
                STATUS  mandatory
                DESCRIPTION
                "Summary status of the server services."
                ::=  {  wsa5ServersEntry 3   }

        wsa5ServersDStatus OBJECT-TYPE
                SYNTAX  INTEGER
                {
                    Normal(1),
                    Warning(2),
                    Critical(3)
                }
                ACCESS  read-only
                STATUS  mandatory
                DESCRIPTION
                "Summary status of the server disks."
                ::=  {  wsa5ServersEntry 4   }

        wsa5ServersHStatus OBJECT-TYPE
                SYNTAX  INTEGER
                {
                    Normal(1),
                    Warning(2),
                    Critical(3)
                }
                ACCESS  read-only
                STATUS  mandatory
                DESCRIPTION
                "Summary status of the server health."
                ::=  {  wsa5ServersEntry 5   }

        wsa5ServersEStatus OBJECT-TYPE
                SYNTAX  INTEGER
                {
                    Normal(1),
                    Warning(2),
                    Critical(3)
                }
                ACCESS  read-only
                STATUS  mandatory
                DESCRIPTION
                "Summary status of the server events."
                ::=  {  wsa5ServersEntry 6   }

        wsa5ServersWStatus OBJECT-TYPE
                SYNTAX  INTEGER
                {
                    Normal(1),
                    Warning(2),
                    Critical(3)
                }
                ACCESS  read-only
                STATUS  mandatory
                DESCRIPTION
                "Summary status of the server WebCrawler."
                ::=  {  wsa5ServersEntry 7   }
		
        wsa5ServersWLocalAction OBJECT-TYPE
                SYNTAX  DisplayString
                ACCESS  read-write
                STATUS  mandatory
                DESCRIPTION
                "Local action to perform for Warning status."
                ::=  {  wsa5ServersEntry 8   }

        wsa5ServersCLocalAction OBJECT-TYPE
                SYNTAX  DisplayString
                ACCESS  read-write
                STATUS  mandatory
                DESCRIPTION
                "Local action to perform for Critical."
                ::=  {  wsa5ServersEntry 9   }

        wsa5ServersABCfg OBJECT-TYPE
                SYNTAX  DisplayString
                ACCESS  read-only
                STATUS  mandatory
                DESCRIPTION
                "Abrowser configuration name for this server."
                ::=  {  wsa5ServersEntry 10   }

        wsa5ServersHost OBJECT-TYPE
                SYNTAX  DisplayString
                ACCESS  read-only
                STATUS  mandatory
                DESCRIPTION
                "Abrowser configuration name for this server."
                ::=  {  wsa5ServersEntry 11   }

        wsa5ServersInst OBJECT-TYPE
                SYNTAX  DisplayString
                ACCESS  read-only
                STATUS  mandatory
                DESCRIPTION
                "Abrowser configuration name for this server."
                ::=  {  wsa5ServersEntry 12   }

        wsa5ServersPrevStatus OBJECT-TYPE
                SYNTAX  INTEGER
                {
                    Normal(1),
                    Warning(2),
                    Critical(3)
                }
                ACCESS  read-only
                STATUS  mandatory
                DESCRIPTION
                "Previous Summary status of the server."
                ::=  {  wsa5ServersEntry 13   }

        wsa5ServersState OBJECT-TYPE
                SYNTAX  INTEGER
                {
                    Stopped(1),
                    Started(2)
                }
                ACCESS  read-only
                STATUS  mandatory
                DESCRIPTION
                "The state of the server agent."
                ::=  {  wsa5ServersEntry 14   }

        wsa5ServersDelete OBJECT-TYPE
                SYNTAX  INTEGER
                {
                    Delete(1)
                }
                ACCESS  read-write
                STATUS  mandatory
                DESCRIPTION
                "Delete this server."
                ::=  {  wsa5ServersEntry 15   }
		
        wsa5ServersStoppedStatus OBJECT-TYPE
                SYNTAX  INTEGER
                {
                    Normal(1),
                    Warning(2),
                    Critical(3)
                }
                ACCESS  read-write
                STATUS  mandatory
                DESCRIPTION
                "Group status if the server agent is stopped."
                ::=  {  wsa5ServersEntry 16   }

        wsa5ServersMID OBJECT-TYPE
                SYNTAX  DisplayString
                ACCESS  read-only
                STATUS  mandatory
                DESCRIPTION
                "The name of the server machine."
                ::=  {  wsa5ServersEntry 17   }

        wsa5ServersAID OBJECT-TYPE
                SYNTAX  DisplayString
                ACCESS  read-only
                STATUS  mandatory
                DESCRIPTION
                "The name of the server agent."
                ::=  {  wsa5ServersEntry 18   }

        wsa5ServersIID OBJECT-TYPE
                SYNTAX  DisplayString
                ACCESS  read-only
                STATUS  mandatory
                DESCRIPTION
                "The name of the server agent instance."
                ::=  {  wsa5ServersEntry 19   }


        wsa5ServersDWLocalAction OBJECT-TYPE
                SYNTAX  DisplayString
                ACCESS  read-write
                STATUS  mandatory
                DESCRIPTION
                "Default local action to perform for Warning status."
                ::=  {  wsa5ServersGroup 7 }

        wsa5ServersDCLocalAction OBJECT-TYPE
                SYNTAX  DisplayString
                ACCESS  read-write
                STATUS  mandatory
                DESCRIPTION
                "Default local action to perform for Critical."
                ::=  {  wsa5ServersGroup 8 }

        wsa5ServersDStoppedStatus OBJECT-TYPE
                SYNTAX  INTEGER
                {
                    Normal(1),
                    Warning(2),
                    Critical(3)
                }
                ACCESS  read-write
                STATUS  mandatory
                DESCRIPTION
                "Default group status if the server agent is stopped."
                ::=  {  wsa5ServersGroup 9 }

        wsa5ServersImpExpFile OBJECT-TYPE
                SYNTAX  DisplayString
                ACCESS  read-write
                STATUS  mandatory
                DESCRIPTION
                "File name for import/export functions."
                ::=  {  wsa5ServersGroup 10 }

        wsa5ServersRequest OBJECT-TYPE
                SYNTAX  INTEGER
                {
                    Import(1),
                    Export(2),
                    RemoveAll(3)
                }
                ACCESS  read-write
                STATUS  mandatory
                DESCRIPTION
                "Request type."
                ::=  {  wsa5ServersGroup 11 }
		
        wsa5ServersCommunity OBJECT-TYPE
                SYNTAX  DisplayString
                ACCESS  read-write
                STATUS  mandatory
                DESCRIPTION
                "SNMP Community name."
                ::=  {  wsa5ServersGroup 12 }
		
        wsa5ServersPort OBJECT-TYPE
                SYNTAX  DisplayString
                ACCESS  read-write
                STATUS  mandatory
                DESCRIPTION
                "SNMP port."
                ::=  {  wsa5ServersGroup 13 }
		
        wsa5ServersThresholds OBJECT-TYPE
                SYNTAX  DisplayString
                ACCESS  read-write
                STATUS  mandatory
                DESCRIPTION
                "Thresholds."
                ::=  {  wsa5ServersGroup 14 }
		
        wsa5ServersWAction OBJECT-TYPE
                SYNTAX  DisplayString
                ACCESS  read-write
                STATUS  mandatory
                DESCRIPTION
                "Warning Action."
                ::=  {  wsa5ServersGroup 15 }
		
        wsa5ServersCAction OBJECT-TYPE
                SYNTAX  DisplayString
                ACCESS  read-write
                STATUS  mandatory
                DESCRIPTION
                "Critical Action."
                ::=  {  wsa5ServersGroup 16 }

	wsa5ServersGPEnaDis OBJECT-TYPE
		SYNTAX      INTEGER {Enable(1), Disable(2)}
		ACCESS      read-write
		STATUS      mandatory
		DESCRIPTION "Enable or disable for the Group."
		::= { wsa5ServersGroup 17 }

		

--******************************************************************************
--* wsa5BadLinkGroup - URL links not found by requestors                        *
--******************************************************************************

        wsa5BLTableEntries OBJECT-TYPE
                SYNTAX  INTEGER
                ACCESS  read-only
                STATUS  mandatory
                DESCRIPTION
                "The number of entries in the table."
                ::=  {  wsa5BadLinkGroup 1   }


        wsa5BLClearTable OBJECT-TYPE
               SYNTAX  INTEGER {
                                Reset(1)
                               }
               ACCESS  read-write
               STATUS  mandatory
               DESCRIPTION
               "Clear the table when set."
               ::=  {  wsa5BadLinkGroup 2   }

        wsa5BLSummaryStatus OBJECT-TYPE
               SYNTAX  INTEGER {
                                Normal(1),
                                Warning(2),
                                Critical(3)
                               }
               ACCESS  read-only
               STATUS  mandatory
               DESCRIPTION
               "Summary status for bad links."
               ::=  {  wsa5BadLinkGroup 3   }

        wsa5BLInterval OBJECT-TYPE
               SYNTAX  INTEGER
               ACCESS  read-write
               STATUS  mandatory
               DESCRIPTION
               "Seconds to poll for changes."
               ::=  {  wsa5BadLinkGroup 4   }

        wsa5BLCircularBuffSize OBJECT-TYPE
               SYNTAX  INTEGER
               ACCESS  read-write
               STATUS  mandatory
               DESCRIPTION
               "Max entries in the table (default 50)(Not a circular buffer)."
               ::=  {  wsa5BadLinkGroup 5   }

        wsa5BLWarningThreshold OBJECT-TYPE
               SYNTAX  INTEGER
               ACCESS  read-write
               STATUS  mandatory
               DESCRIPTION
               "Number of requests on a row before warning is generated."
               ::=  {  wsa5BadLinkGroup 6   }

        wsa5BLCriticalThreshold OBJECT-TYPE
               SYNTAX  INTEGER
               ACCESS  read-write
               STATUS  mandatory
               DESCRIPTION
               "Number of requests on a row before critical is generated."
               ::=  {  wsa5BadLinkGroup 7   }

        wsa5BLWarningCount OBJECT-TYPE
               SYNTAX  INTEGER
               ACCESS  read-only
               STATUS  mandatory
               DESCRIPTION
               "The number of entries in the table with a warning status."
               ::=  {  wsa5BadLinkGroup 8   }

        wsa5BLCriticalCount OBJECT-TYPE
               SYNTAX  INTEGER
               ACCESS  read-only
               STATUS  mandatory
               DESCRIPTION
               "The number of entries in the table with a critical status."
               ::=  {  wsa5BadLinkGroup 9   }

        wsa5BLWarningAction OBJECT-TYPE
               SYNTAX  DisplayString
               ACCESS  read-write
               STATUS  mandatory
               DESCRIPTION
               "Command to be executed when warning threshold is crossed on a row."
               ::=  {  wsa5BadLinkGroup 10   }

        wsa5BLCriticalAction OBJECT-TYPE
               SYNTAX  DisplayString
               ACCESS  read-write
               STATUS  mandatory
               DESCRIPTION
               "Command to be executed when critical threshold is crossed on a row."
               ::=  {  wsa5BadLinkGroup 11   }


        wsa5BLCreateReportURL OBJECT-TYPE
               SYNTAX  INTEGER {
                                Create(1)
                               }
               ACCESS  read-write
               STATUS  mandatory
               DESCRIPTION
               "When triggered, create report using path and file in wsa5BLReportURL."
               ::=  {  wsa5BadLinkGroup 12   }

        wsa5BLReportURL OBJECT-TYPE
               SYNTAX  DisplayString
               ACCESS  read-write
               STATUS  mandatory
               DESCRIPTION
               "Path and filename for report; Relative to DocumentRoot unless starts with '/'."
               ::=  {  wsa5BadLinkGroup 13   }

        wsa5BLTable OBJECT-TYPE
               SYNTAX  SEQUENCE OF Wsa5BLEntry
               ACCESS  not-accessible
               STATUS  mandatory
               DESCRIPTION
               "This table contains a list bad links."
               ::=  {  wsa5BadLinkGroup 14  }

	wsa5BLGPEnaDis OBJECT-TYPE
		SYNTAX      INTEGER {Enable(1), Disable(2)}
		ACCESS      read-write
		STATUS      mandatory
		DESCRIPTION "Enable or disable for the Group."
		::= { wsa5BadLinkGroup 15 }

        wsa5BLEntry OBJECT-TYPE
               SYNTAX  Wsa5BLEntry
               ACCESS  not-accessible
               STATUS  mandatory
               DESCRIPTION
               "This is an entry in the wsa5BLTable"
               INDEX { wsa5BLURL, wsa5BLReferringURL }
               ::=  { wsa5BLTable 1 }

        Wsa5BLEntry ::= SEQUENCE
        {
           wsa5BLURL                              DisplayString,
           wsa5BLReferringURL                     DisplayString,
           wsa5BLFirstAccessTS                    DisplayString,
           wsa5BLlastAccessTS                     DisplayString,
           wsa5BLNumRequests                      INTEGER,
           wsa5BLStatus                           INTEGER
        }

        wsa5BLURL OBJECT-TYPE
               SYNTAX  DisplayString
               ACCESS  read-only
               STATUS  mandatory
               DESCRIPTION
               "Bad URL."
               ::=  {  wsa5BLEntry 1   }

        wsa5BLReferringURL OBJECT-TYPE
               SYNTAX  DisplayString
               ACCESS  read-only
               STATUS  mandatory
               DESCRIPTION
               "Referring URL to Bad URL."
               ::=  {  wsa5BLEntry 2   }

        wsa5BLFirstAccessTS OBJECT-TYPE
               SYNTAX  DisplayString
               ACCESS  read-only
               STATUS  mandatory
               DESCRIPTION
               "Time first bad access occurred (time row added to table)."
               ::=  {  wsa5BLEntry 3   }

        wsa5BLlastAccessTS OBJECT-TYPE
               SYNTAX  DisplayString
               ACCESS  read-only
               STATUS  mandatory
               DESCRIPTION
               "Time of last access to bad URL."
               ::=  {  wsa5BLEntry 4   }

        wsa5BLNumRequests OBJECT-TYPE
               SYNTAX  INTEGER
               ACCESS  read-only
               STATUS  mandatory
               DESCRIPTION
               "Count of requests."
               ::=  {  wsa5BLEntry 5   }

        wsa5BLStatus OBJECT-TYPE
               SYNTAX  INTEGER {
                                Normal(1),
                                Warning(2),
                                Critical(3)
                               }
               ACCESS  read-only
               STATUS  mandatory
               DESCRIPTION
               "Summary status for BL."
               ::=  {  wsa5BLEntry 6   }


--******************************************************************************
--* wsa5TopURLGroup - URLs with highest access rates                             *
--******************************************************************************

        wsa5TopURLTableEntries OBJECT-TYPE
               SYNTAX  INTEGER
               ACCESS  read-only
               STATUS  mandatory
               DESCRIPTION
               "The number of entries in the table."
               ::=  {  wsa5TopURLGroup 1   }

        wsa5TopURLClearTable OBJECT-TYPE
               SYNTAX  INTEGER {
                                Reset(1)
                               }
               ACCESS  read-write
               STATUS  mandatory
               DESCRIPTION
               "Clear the table when set."
               ::=  {  wsa5TopURLGroup 2   }

        wsa5TopURLInterval OBJECT-TYPE
               SYNTAX  INTEGER
               ACCESS  read-write
               STATUS  mandatory
               DESCRIPTION
               "Seconds to poll for changes."
               ::=  {  wsa5TopURLGroup 3   }

        wsa5TopURLCircularBuffSize OBJECT-TYPE
               SYNTAX  INTEGER
               ACCESS  read-write
               STATUS  mandatory
               DESCRIPTION
               "Max entries in the table (default 50)."
               ::=  {  wsa5TopURLGroup 4   }


        wsa5TopURLTable OBJECT-TYPE
               SYNTAX  SEQUENCE OF Wsa5TopURLEntry
               ACCESS  not-accessible
               STATUS  mandatory
               DESCRIPTION
               "This table contains a list of the top URLs by hit count."
               ::=  {  wsa5TopURLGroup 5}

        wsa5TopURLExclude OBJECT-TYPE
               SYNTAX  DisplayString
               ACCESS  read-write
               STATUS  mandatory
               DESCRIPTION
               "Exclude URLs with these extensions."
               ::=  {  wsa5TopURLGroup 6   }

        wsa5TopURLExcludeReset OBJECT-TYPE
               SYNTAX  INTEGER {
                                Reset(1)
                               }
               ACCESS  read-write
               STATUS  mandatory
               DESCRIPTION
               "Reset exclude list to defaults."
               ::=  {  wsa5TopURLGroup 7   }

	wsa5TopURLGPEnaDis OBJECT-TYPE
		SYNTAX      INTEGER {Enable(1), Disable(2)}
		ACCESS      read-write
		STATUS      mandatory
		DESCRIPTION "Enable or disable for the Group."
		::= { wsa5TopURLGroup 8 }

        wsa5TopURLEntry OBJECT-TYPE
               SYNTAX  Wsa5TopURLEntry
               ACCESS  not-accessible
               STATUS  mandatory
               DESCRIPTION
               "This is an entry in the wsa5TopURLTable"
               INDEX { wsa5TopURLRank }
               ::=  { wsa5TopURLTable 1 }

        Wsa5TopURLEntry ::= SEQUENCE
        {
           wsa5TopURLURL          DisplayString,
           wsa5TopURLNumHits      INTEGER,
           wsa5TopURLRank         INTEGER
        }

        wsa5TopURLURL OBJECT-TYPE
               SYNTAX  DisplayString
               ACCESS  read-only
               STATUS  mandatory
               DESCRIPTION
               "URL."
               ::=  {  wsa5TopURLEntry 1   }

        wsa5TopURLNumHits OBJECT-TYPE
               SYNTAX  INTEGER
               ACCESS  read-only
               STATUS  mandatory
               DESCRIPTION
               "Number of hits."
               ::=  {  wsa5TopURLEntry 2   }

        wsa5TopURLRank OBJECT-TYPE
               SYNTAX  INTEGER
               ACCESS  read-only
               STATUS  mandatory
               DESCRIPTION
               "For easy sorting in Abrowser."
               ::=  {  wsa5TopURLEntry 3   }


--******************************************************************************
--* wsa5URLAvailCounterGroup - Counters available for URL monitoring             *
--******************************************************************************

        wsa5URLAvailCounterTableEntries OBJECT-TYPE
               SYNTAX  INTEGER
               ACCESS  read-only
               STATUS  mandatory
               DESCRIPTION
               "The number of entries in the table."
               ::=  {  wsa5URLAvailCounterGroup 1   }

        wsa5URLAvailCounterTable OBJECT-TYPE
           SYNTAX  SEQUENCE OF Wsa5URLAvailCounterEntry
           ACCESS  not-accessible
           STATUS  mandatory
           DESCRIPTION
           "This table contains a list of all monitored AvailCounters"
           ::=  {  wsa5URLAvailCounterGroup 2}

        wsa5URLAvailCounterEntry OBJECT-TYPE
                                SYNTAX  Wsa5URLAvailCounterEntry
                                ACCESS  not-accessible
                                STATUS  mandatory
                                DESCRIPTION
                                "This is an entry in the wsa5URLAvailCounterTable"
                                INDEX { wsa5URLAvailCounterDescription }
                                        ::=  { wsa5URLAvailCounterTable 1 }

        Wsa5URLAvailCounterEntry ::= SEQUENCE {
                        wsa5URLAvailCounterDescription    DisplayString
        }

        wsa5URLAvailCounterDescription OBJECT-TYPE
               SYNTAX  DisplayString
               ACCESS  read-only
               STATUS  mandatory
               DESCRIPTION
               "The description of the AvailCounter"
               ::=  {  wsa5URLAvailCounterEntry 1   }

--******************************************************************************
--* wsa5URLMntrGroup - Monitored URLs                                            *
--******************************************************************************

        wsa5URLMntrTableEntries OBJECT-TYPE
               SYNTAX  INTEGER
               ACCESS  read-only
               STATUS  mandatory
               DESCRIPTION
               "The number of entries in the table."
               ::=  {  wsa5URLMntrGroup 1   }

        wsa5URLMntrInterval OBJECT-TYPE
               SYNTAX  INTEGER
               ACCESS  read-write
               STATUS  mandatory
               DESCRIPTION
               "Seconds between polls for the counter."
               ::=  {  wsa5URLMntrGroup 2   }

        wsa5URLMntrHitRate OBJECT-TYPE
               SYNTAX  INTEGER
               ACCESS  read-write
               STATUS  mandatory
               DESCRIPTION
               "Interval in seconds over which the counter is measured."
               ::=  {  wsa5URLMntrGroup 3   }

--      Add a counter to the table.  The value must include at least the first four of
--      the 6 items listed, separated by commas.
--      <wsa5URLAvailCounterDescription> is a value from wsa5URLAvailCounterDescription in wsa5URLAvailCounterTable.

        wsa5URLMntrAdd OBJECT-TYPE
               SYNTAX  DisplayString
               ACCESS  write-only
               STATUS  mandatory
               DESCRIPTION
               "Add this entry to the table: <url>,<wsa5URLAvailCounterDescription>,<warning threshold>,<critical threshold>,<warning action>,<critical action>."
               ::=  {  wsa5URLMntrGroup 4   }

--      Delete a counter from the table.  The value must include the 2 items listed.
        wsa5URLMntrDelete OBJECT-TYPE
               SYNTAX  DisplayString
               ACCESS  write-only
               STATUS  mandatory
               DESCRIPTION
               "Delete entry from the table: <wsa5URLMntrDesc>,<url>."
               ::=  {  wsa5URLMntrGroup 5   }

        wsa5URLMntrUpdate OBJECT-TYPE
               SYNTAX  DisplayString
               ACCESS  write-only
               STATUS  mandatory
               DESCRIPTION
               "Reserved for future use."
               ::=  {  wsa5URLMntrGroup 6   }

        wsa5URLMntrSummaryStatus OBJECT-TYPE
               SYNTAX  INTEGER {
                                Normal(1),
                                Warning(2),
                                Critical(3)
                               }
               ACCESS  read-only
               STATUS  mandatory
               DESCRIPTION
               "Most severe status of all rows in the table."
               ::=  {  wsa5URLMntrGroup 7   }

        wsa5URLMntrTable OBJECT-TYPE
               SYNTAX  SEQUENCE OF Wsa5URLMntrEntry
               ACCESS  not-accessible
               STATUS  mandatory
               DESCRIPTION
               "This table contains a list of URLs to monitor."
               ::=  {  wsa5URLMntrGroup 8}

        wsa5URLMntrEntry OBJECT-TYPE
               SYNTAX  Wsa5URLMntrEntry
               ACCESS  not-accessible
               STATUS  mandatory
               DESCRIPTION
               "This is an entry in the wsa5URLMntrTable"
               INDEX { wsa5URLMntrURL, wsa5URLMntrDesc}
               ::=  { wsa5URLMntrTable 1 }

        Wsa5URLMntrEntry ::= SEQUENCE
        {
           wsa5URLMntrURL                       DisplayString,
           wsa5URLMntrDesc                      DisplayString,
           wsa5URLMntrValue                     DisplayString,
           wsa5URLMntrWarningThreshold          INTEGER,
           wsa5URLMntrCriticalThreshold         INTEGER,
           wsa5URLMntrWarningAction             DisplayString,
           wsa5URLMntrCriticalAction            DisplayString,
           wsa5URLMntrStatus                    INTEGER,
           wsa5URLMntrEnableDisable             INTEGER,
           wsa5URLMntrDescending                INTEGER,
           wsa5URLMntrReset                     INTEGER,
           wsa5URLMntrResetTime                 DisplayString,
	   wsa5URLMntrValueReported		INTEGER,
	   wsa5URLMntrLagSetting		INTEGER,
	   wsa5URLMntrLagValue			INTEGER
        }

        wsa5URLMntrURL OBJECT-TYPE
               SYNTAX  DisplayString
               ACCESS  read-only
               STATUS  mandatory
               DESCRIPTION
               "URL to monitor."
               ::=  {  wsa5URLMntrEntry 1   }

        wsa5URLMntrDesc OBJECT-TYPE
               SYNTAX  DisplayString
               ACCESS  read-only
               STATUS  mandatory
               DESCRIPTION
               "Description of the monitored value."
               ::=  {  wsa5URLMntrEntry 2   }

        wsa5URLMntrValue OBJECT-TYPE
               SYNTAX  DisplayString
               ACCESS  read-only
               STATUS  mandatory
               DESCRIPTION
               "Peak number of hits per wsa5URLMntrHitRate seconds."
               ::=  {  wsa5URLMntrEntry 3   }

        wsa5URLMntrWarningThreshold OBJECT-TYPE
               SYNTAX  INTEGER
               ACCESS  read-write
               STATUS  mandatory
               DESCRIPTION
               "Warning threshold in MS"
               ::=  {  wsa5URLMntrEntry 4   }

        wsa5URLMntrCriticalThreshold OBJECT-TYPE
               SYNTAX  INTEGER
               ACCESS  read-write
               STATUS  mandatory
               DESCRIPTION
               "Critical threshold in MS"
               ::=  {  wsa5URLMntrEntry 5   }

        wsa5URLMntrWarningAction OBJECT-TYPE
               SYNTAX  DisplayString
               ACCESS  read-write
               STATUS  mandatory
               DESCRIPTION
               "Command to be executed when warning threshold is exceeded."
               ::=  {  wsa5URLMntrEntry 6   }

        wsa5URLMntrCriticalAction OBJECT-TYPE
               SYNTAX  DisplayString
               ACCESS  read-write
               STATUS  mandatory
               DESCRIPTION
               "Command to be executed when critical threshold is exceeded."
               ::=  {  wsa5URLMntrEntry 7  }

        wsa5URLMntrStatus OBJECT-TYPE
               SYNTAX  INTEGER {
                                Normal(1),
                                Warning(2),
                                Critical(3)
                               }
               ACCESS  read-only
               STATUS  mandatory
               DESCRIPTION
               "Status of this URL."
               ::=  {  wsa5URLMntrEntry 8 }

        wsa5URLMntrEnableDisable OBJECT-TYPE
                SYNTAX  INTEGER
                {
                    Enable(1),
                    Disable(2)
                }
                ACCESS  read-write
                STATUS  mandatory
                DESCRIPTION
                "Enable or disable alerts for this URL."
                ::=  {  wsa5URLMntrEntry 9   }

        wsa5URLMntrDescending OBJECT-TYPE
               SYNTAX  INTEGER {
                                No(1),
                                Yes(2)
                               }
               ACCESS  read-only
               STATUS  mandatory
               DESCRIPTION
               "Yes if lower value triggers thresholds."
               ::=  {  wsa5URLMntrEntry 10 }

        wsa5URLMntrReset OBJECT-TYPE
               SYNTAX  INTEGER {
                                Reset(1)
                               }
               ACCESS  write-only
               STATUS  mandatory
               DESCRIPTION
               "Reset value for this counter."
               ::=  {  wsa5URLMntrEntry 11 }

        wsa5URLMntrResetTime OBJECT-TYPE
               SYNTAX  DisplayString
               ACCESS  read-only
               STATUS  mandatory
               DESCRIPTION
               "Time stamp of when this counter was reset."
               ::=  {  wsa5URLMntrEntry 12  }

        wsa5URLMntrValueReported OBJECT-TYPE
               SYNTAX  INTEGER {
                                Summary(1),
                                Average(2)
                               }
               ACCESS  read-write
               STATUS  mandatory
               DESCRIPTION
               "The reported value of the counter is either a summary or average of all servers."
               ::=  {  wsa5URLMntrEntry 13 }
		
        wsa5URLMntrLagSetting OBJECT-TYPE
                SYNTAX  INTEGER
                ACCESS  read-write
                STATUS  mandatory
                DESCRIPTION
                "Lag setting for the counter."
                ::=  {  wsa5URLMntrEntry 14   }
		
        wsa5URLMntrLagValue OBJECT-TYPE
                SYNTAX  INTEGER
                ACCESS  read-only
                STATUS  mandatory
                DESCRIPTION
                "Current Lag value for the counter."
                ::=  {  wsa5URLMntrEntry 15   }


        wsa5URLMntrNumberCritical OBJECT-TYPE
               SYNTAX  INTEGER
               ACCESS  read-only
               STATUS  mandatory
               DESCRIPTION
               "The number of entries in Critical status."
               ::=  {  wsa5URLMntrGroup 9   }

        wsa5URLMntrNumberWarning OBJECT-TYPE
               SYNTAX  INTEGER
               ACCESS  read-write
               STATUS  mandatory
               DESCRIPTION
               "The number of entries in Warning status."
               ::=  {  wsa5URLMntrGroup 10   }

	wsa5URLMntrGPEnaDis OBJECT-TYPE
		SYNTAX      INTEGER {Enable(1), Disable(2)}
		ACCESS      read-write
		STATUS      mandatory
		DESCRIPTION "Enable or disable for the Group."
		::= { wsa5URLMntrGroup 11 }



--******************************************************************************
--* wsa5AvailIISCounterGroup - Counters currently available                     *
--******************************************************************************

        wsa5AvailIISCounterTableEntries OBJECT-TYPE
                SYNTAX  INTEGER
                ACCESS  read-only
                STATUS  mandatory
                DESCRIPTION
                "The number of entries in the table."
                ::=  {  wsa5AvailIISCounterGroup 1   }

        wsa5AvailIISCounterTable OBJECT-TYPE
                SYNTAX  SEQUENCE OF Wsa5AvailIISCounterEntry
                ACCESS  not-accessible
                STATUS  mandatory
                DESCRIPTION
                "The list of all available counters"
                ::=  {  wsa5AvailIISCounterGroup 2}

        wsa5AvailIISCounterEntry OBJECT-TYPE
                 SYNTAX  Wsa5AvailIISCounterEntry
                 ACCESS  not-accessible
                 STATUS  mandatory
                 DESCRIPTION
                 "The wsa5AvailIISCounterTable entry."
                 INDEX { wsa5AvailIISCounterDescription }
                     ::=  { wsa5AvailIISCounterTable 1 }

        Wsa5AvailIISCounterEntry ::= SEQUENCE
        {
            wsa5AvailIISCounterDescription   DisplayString
        }

        wsa5AvailIISCounterDescription OBJECT-TYPE
                SYNTAX  DisplayString
                ACCESS  read-only
                STATUS  mandatory
                DESCRIPTION
                "The description of the available counter"
                ::=  {  wsa5AvailIISCounterEntry 1   }


--******************************************************************************
--* wsa5AvailCounterGroup - Counters currently available                         *
--******************************************************************************

        wsa5AvailCounterTableEntries OBJECT-TYPE
                SYNTAX  INTEGER
                ACCESS  read-only
                STATUS  mandatory
                DESCRIPTION
                "The number of entries in the table."
                ::=  {  wsa5AvailCounterGroup 1   }

        wsa5AvailCounterTable OBJECT-TYPE
                SYNTAX  SEQUENCE OF Wsa5AvailCounterEntry
                ACCESS  not-accessible
                STATUS  mandatory
                DESCRIPTION
                "The list of all available counters"
                ::=  {  wsa5AvailCounterGroup 2}

        wsa5AvailCounterEntry OBJECT-TYPE
                 SYNTAX  Wsa5AvailCounterEntry
                 ACCESS  not-accessible
                 STATUS  mandatory
                 DESCRIPTION
                 "The wsa5AvailCounterTable entry."
                 INDEX { wsa5AvailCounterDescription }
                     ::=  { wsa5AvailCounterTable 1 }

        Wsa5AvailCounterEntry ::= SEQUENCE
        {
            wsa5AvailCounterDescription   DisplayString
        }

        wsa5AvailCounterDescription OBJECT-TYPE
                SYNTAX  DisplayString
                ACCESS  read-only
                STATUS  mandatory
                DESCRIPTION
                "The description of the available counter"
                ::=  {  wsa5AvailCounterEntry 1   }

	    

--******************************************************************************
--* wsa5PolledCounterGroup - Counters being polled                               *
--******************************************************************************

        wsa5PolledCounterTableEntries OBJECT-TYPE
                SYNTAX  INTEGER
                ACCESS  read-only
                STATUS  mandatory
                DESCRIPTION
                "The number of entries in the table."
                ::=  {  wsa5PolledCounterGroup 1   }

        wsa5PolledCounterAdd OBJECT-TYPE
                SYNTAX  DisplayString
                ACCESS  write-only
                STATUS  mandatory
                DESCRIPTION
                "Add this counter to the polled counter table."
                ::=  {  wsa5PolledCounterGroup 2   }

        wsa5PolledCounterDelete OBJECT-TYPE
                SYNTAX  DisplayString
                ACCESS  write-only
                STATUS  mandatory
                DESCRIPTION
                "Delete this counter from the polled counter table."
                ::=  {  wsa5PolledCounterGroup 3   }

        wsa5PolledSummaryStatus OBJECT-TYPE
                SYNTAX  INTEGER
                {
                    Normal(1),
                    Warning(2),
                    Critical(3)
                }
                ACCESS  read-only
                STATUS  mandatory
                DESCRIPTION
                "The summary status of all polled counters."
                ::=  {  wsa5PolledCounterGroup 4   }

        wsa5PollingInterval OBJECT-TYPE
                SYNTAX  INTEGER
                ACCESS  read-write
                STATUS  mandatory
                DESCRIPTION
                "Poll interval for the polled counter group in seconds."
                ::=  {  wsa5PolledCounterGroup 5   }

        wsa5PolledWarningCount OBJECT-TYPE
                SYNTAX  INTEGER
                ACCESS  read-only
                STATUS  mandatory
                DESCRIPTION
                "Number of polled counters in warning state."
                ::=  {  wsa5PolledCounterGroup 6   }

        wsa5PolledCriticalCount OBJECT-TYPE
                SYNTAX  INTEGER
                ACCESS  read-only
                STATUS  mandatory
                DESCRIPTION
                "Number of polled counters in critical state."
                ::=  {  wsa5PolledCounterGroup 7   }

        wsa5PolledCounterTable OBJECT-TYPE
                SYNTAX  SEQUENCE OF Wsa5PolledCounterEntry
                ACCESS  not-accessible
                STATUS  mandatory
                DESCRIPTION
                "The list of all polled counters."
                ::=  {  wsa5PolledCounterGroup 8}

	wsa5PolledGPEnaDis OBJECT-TYPE
		SYNTAX      INTEGER {Enable(1), Disable(2)}
		ACCESS      read-write
		STATUS      mandatory
		DESCRIPTION "Enable or disable for the Group."
		::= { wsa5PolledCounterGroup 9 }


        wsa5PolledCounterUpdate OBJECT-TYPE
               SYNTAX  DisplayString
               ACCESS  write-only
               STATUS  mandatory
	       DESCRIPTION "Update this entry in the table."
               ::=  {  wsa5PolledCounterGroup 10  }
               
        wsa5PolledCounterEntry OBJECT-TYPE
                 SYNTAX  Wsa5PolledCounterEntry
                 ACCESS  not-accessible
                 STATUS  mandatory
                 DESCRIPTION
                 "The wsa5PolledCounterTable entry."
                 INDEX { wsa5Description }
                     ::=  { wsa5PolledCounterTable 1 }

        Wsa5PolledCounterEntry ::= SEQUENCE {
            wsa5Description             DisplayString,
            wsa5Available               INTEGER,
            wsa5WarningThreshold        DisplayString,
            wsa5CriticalThreshold	DisplayString,
            wsa5Value                   DisplayString,
            wsa5WarningCount            INTEGER,
            wsa5CriticalCount           INTEGER,
            wsa5WarningAction           DisplayString,
            wsa5CriticalAction          DisplayString,
            wsa5Status                  INTEGER,
            wsa5EnableDisable           INTEGER,
            wsa5DescendingCounter       INTEGER,
            wsa5Minimum                 DisplayString,
            wsa5Maximum                 DisplayString,
            wsa5Average                 DisplayString,
            wsa5StdDev                  DisplayString,
	    wsa5ValueReported		INTEGER,
	    wsa5LagSetting		INTEGER,
	    wsa5LagValue		INTEGER
        }

        wsa5Description OBJECT-TYPE
                SYNTAX  DisplayString
                ACCESS  read-only
                STATUS  mandatory
                DESCRIPTION
                "The description of the polled counter."
                ::=  {  wsa5PolledCounterEntry 1   }

        wsa5Available OBJECT-TYPE
                SYNTAX  INTEGER
                {
                    Available(1),
                    NotAvailable(2)
                }
                ACCESS  read-only
                STATUS  mandatory
                DESCRIPTION
                "Describes whether this counter is currently available."
                ::=  {  wsa5PolledCounterEntry 2   }

        wsa5WarningThreshold OBJECT-TYPE
                SYNTAX  DisplayString
                ACCESS  read-write
                STATUS  mandatory
                DESCRIPTION
                "Counter value that will trigger warning status if value exceeds it."
                ::=  {  wsa5PolledCounterEntry 3   }

        wsa5CriticalThreshold OBJECT-TYPE
                SYNTAX  DisplayString
                ACCESS  read-write
                STATUS  mandatory
                DESCRIPTION
                "Counter value that will trigger critical status if value exceeds it."
                ::=  {  wsa5PolledCounterEntry 4   }

        wsa5Value OBJECT-TYPE
                SYNTAX  DisplayString
                ACCESS  read-only
                STATUS  mandatory
                DESCRIPTION
                "Value of the polled counter."
                ::=  {  wsa5PolledCounterEntry 5   }

        wsa5WarningCount OBJECT-TYPE
                SYNTAX  INTEGER
                ACCESS  read-only
                STATUS  mandatory
                DESCRIPTION
                "Number of times warning alert generated."
                ::=  {  wsa5PolledCounterEntry 6   }

        wsa5CriticalCount OBJECT-TYPE
                SYNTAX  INTEGER
                ACCESS  read-only
                STATUS  mandatory
                DESCRIPTION
                "Number of times critical alert generated."
                ::=  {  wsa5PolledCounterEntry 7   }

        wsa5WarningAction OBJECT-TYPE
                SYNTAX  DisplayString
                ACCESS  read-write
                STATUS  mandatory
                DESCRIPTION
                "Command to be executed when warning threshold is exceeded."
                ::=  {  wsa5PolledCounterEntry 8   }

        wsa5CriticalAction OBJECT-TYPE
                SYNTAX  DisplayString
                ACCESS  read-write
                STATUS  mandatory
                DESCRIPTION
                "Command to be executed when critical threshold is exceeded."
                ::=  {  wsa5PolledCounterEntry 9   }

        wsa5Status OBJECT-TYPE
                SYNTAX  INTEGER
                {
                    Normal(1),
                    Warning(2),
                    Critical(3)
                }
                ACCESS  read-only
                STATUS  mandatory
                DESCRIPTION
                "Status of the polled counter."
                ::=  {  wsa5PolledCounterEntry 10   }

        wsa5EnableDisable OBJECT-TYPE
                SYNTAX  INTEGER
                {
                    Enable(1),
                    Disable(2)
                }
                ACCESS  read-write
                STATUS  mandatory
                DESCRIPTION
                "Enable or disable alerts for this counter."
                ::=  {  wsa5PolledCounterEntry 11   }

        wsa5DescendingCounter OBJECT-TYPE
                SYNTAX  INTEGER
                {
                    No(1),
                    Yes(2)
                }
                ACCESS  read-write
                STATUS  mandatory
                DESCRIPTION
                "Yes if lower value triggers thresholds, no if higher value triggers thresholds."
                ::=  {  wsa5PolledCounterEntry 12   }

        wsa5Minimum OBJECT-TYPE
               SYNTAX  DisplayString
               ACCESS  read-only
               STATUS  mandatory
               DESCRIPTION
               "The minimum reading since the last reset."
               ::=  {  wsa5PolledCounterEntry 13   }

        wsa5Maximum OBJECT-TYPE
               SYNTAX  DisplayString
               ACCESS  read-only
               STATUS  mandatory
               DESCRIPTION
               "The maximum reading since the last reset."
               ::=  {  wsa5PolledCounterEntry 14   }

        wsa5Average OBJECT-TYPE
               SYNTAX  DisplayString
               ACCESS  read-only
               STATUS  mandatory
               DESCRIPTION
               "The average reading since the last reset."
               ::=  {  wsa5PolledCounterEntry 15   }

        wsa5StdDev OBJECT-TYPE
               SYNTAX  DisplayString
               ACCESS  read-only
               STATUS  mandatory
               DESCRIPTION
               "The standard deviation based on the last 100 readings."
               ::=  {  wsa5PolledCounterEntry 16   }

        wsa5ValueReported OBJECT-TYPE
               SYNTAX  INTEGER {
                                Summary(1),
                                Average(2)
                               }
               ACCESS  read-write
               STATUS  mandatory
               DESCRIPTION
               "The reported value of the counter is either a summary or average of all servers."
               ::=  {  wsa5PolledCounterEntry 17 }
		
        wsa5LagSetting OBJECT-TYPE
                SYNTAX  INTEGER
                ACCESS  read-write
                STATUS  mandatory
                DESCRIPTION
                "Lag setting for the counter."
                ::=  {  wsa5PolledCounterEntry 18   }
		
        wsa5LagValue OBJECT-TYPE
                SYNTAX  INTEGER
                ACCESS  read-only
                STATUS  mandatory
                DESCRIPTION
                "Current Lag value for the counter."
                ::=  {  wsa5PolledCounterEntry 19   }



--******************************************************************************
--* wsa5DetailGroup - Detail table                                              *
--******************************************************************************

        wsa5DetailTableEntries OBJECT-TYPE
                SYNTAX  INTEGER
                ACCESS  read-only
                STATUS  mandatory
                DESCRIPTION
                "The number of entries in the table."
                ::=  {  wsa5DetailGroup 1   }

        wsa5DetailRequest OBJECT-TYPE
                SYNTAX  DisplayString
                ACCESS  write-only
                STATUS  mandatory
                DESCRIPTION
                "Generate Detail table for this request."
                ::=  {  wsa5DetailGroup 2   }


        wsa5DetailTable OBJECT-TYPE
                SYNTAX  SEQUENCE OF Wsa5DetailEntry
                ACCESS  not-accessible
                STATUS  mandatory
                DESCRIPTION
                "The list of details."
                ::=  {  wsa5DetailGroup 3}

        wsa5DetailEntry OBJECT-TYPE
                 SYNTAX  Wsa5DetailEntry
                 ACCESS  not-accessible
                 STATUS  mandatory
                 DESCRIPTION
                 "The wsa5DetailTable entry."
                 INDEX { wsa5DetailServer }
                     ::=  { wsa5DetailTable 1 }

        Wsa5DetailEntry ::= SEQUENCE {
            wsa5DetailServer              DisplayString,
            wsa5DetailValue               DisplayString,
            wsa5DetailValue2              DisplayString,
            wsa5DetailValue3              DisplayString,
            wsa5DetailValue4              DisplayString,
            wsa5DetailValue5              DisplayString,
            wsa5DetailValue6              DisplayString,
            wsa5DetailValue7              DisplayString,
            wsa5DetailValue8              DisplayString,
            wsa5DetailValue9              DisplayString,
            wsa5DetailValue10             DisplayString
        }

        wsa5DetailServer OBJECT-TYPE
                SYNTAX  DisplayString
                ACCESS  read-only
                STATUS  mandatory
                DESCRIPTION
                "The Server name for the entry."
                ::=  {  wsa5DetailEntry 1   }

        wsa5DetailValue OBJECT-TYPE
                SYNTAX  DisplayString
                ACCESS  read-only
                STATUS  mandatory
                DESCRIPTION
                "Detail value for the server."
                ::=  {  wsa5DetailEntry 2   }

        wsa5DetailValue2 OBJECT-TYPE
                SYNTAX  DisplayString
                ACCESS  read-only
                STATUS  mandatory
                DESCRIPTION
                "Detail value for the server."
                ::=  {  wsa5DetailEntry 3   }

        wsa5DetailValue3 OBJECT-TYPE
                SYNTAX  DisplayString
                ACCESS  read-only
                STATUS  mandatory
                DESCRIPTION
                "Detail value for the server."
                ::=  {  wsa5DetailEntry 4   }

        wsa5DetailValue4 OBJECT-TYPE
                SYNTAX  DisplayString
                ACCESS  read-only
                STATUS  mandatory
                DESCRIPTION
                "Detail value for the server."
                ::=  {  wsa5DetailEntry 5   }

        wsa5DetailValue5 OBJECT-TYPE
                SYNTAX  DisplayString
                ACCESS  read-only
                STATUS  mandatory
                DESCRIPTION
                "Detail value for the server."
                ::=  {  wsa5DetailEntry 6   }

        wsa5DetailValue6 OBJECT-TYPE
                SYNTAX  DisplayString
                ACCESS  read-only
                STATUS  mandatory
                DESCRIPTION
                "Detail value for the server."
                ::=  {  wsa5DetailEntry 7   }

        wsa5DetailValue7 OBJECT-TYPE
                SYNTAX  DisplayString
                ACCESS  read-only
                STATUS  mandatory
                DESCRIPTION
                "Detail value for the server."
                ::=  {  wsa5DetailEntry 8   }

        wsa5DetailValue8 OBJECT-TYPE
                SYNTAX  DisplayString
                ACCESS  read-only
                STATUS  mandatory
                DESCRIPTION
                "Detail value for the server."
                ::=  {  wsa5DetailEntry 9   }

        wsa5DetailValue9 OBJECT-TYPE
                SYNTAX  DisplayString
                ACCESS  read-only
                STATUS  mandatory
                DESCRIPTION
                "Detail value for the server."
                ::=  {  wsa5DetailEntry 10   }

        wsa5DetailValue10 OBJECT-TYPE
                SYNTAX  DisplayString
                ACCESS  read-only
                STATUS  mandatory
                DESCRIPTION
                "Detail value for the server."
                ::=  {  wsa5DetailEntry 11   }

        wsa5DetailHeading OBJECT-TYPE
                SYNTAX  DisplayString
                ACCESS  read-only
                STATUS  mandatory
                DESCRIPTION
                "The heading for the table."
                ::=  {  wsa5DetailGroup 4   }




--******************************************************************************
--* wsa5AgentGroup - Agent version and update information                        *
--******************************************************************************

        wsa5AgentDescription OBJECT-TYPE
                SYNTAX  DisplayString
                ACCESS  read-only
                STATUS  mandatory
                DESCRIPTION
                "Description of the agent."
                ::=  {  wsa5AgentGroup 1   }

        wsa5AgentVersion OBJECT-TYPE
                SYNTAX  DisplayString
                ACCESS  read-only
                STATUS  mandatory
                DESCRIPTION
                "Version of the agent."
                ::=  {  wsa5AgentGroup 2   }

        wsa5AgentStartTime OBJECT-TYPE
                SYNTAX  DisplayString
                ACCESS  read-only
                STATUS  mandatory
                DESCRIPTION
                "The time the agent was started."
                ::=  {  wsa5AgentGroup 3   }

        wsa5ServerLastUpdate OBJECT-TYPE
                SYNTAX  DisplayString
                ACCESS  read-only
                STATUS  mandatory
                DESCRIPTION
                "The time the wsa5ServerGroup was last updated"
                ::=  {  wsa5AgentGroup 4   }

        wsa5ServersLastUpdate OBJECT-TYPE
                SYNTAX  DisplayString
                ACCESS  read-only
                STATUS  mandatory
                DESCRIPTION
                "The time the wsa5ServersGroup was last updated"
                ::=  {  wsa5AgentGroup 5   }

        wsa5AvailIISCounterLastUpdate OBJECT-TYPE
                SYNTAX  DisplayString
                ACCESS  read-only
                STATUS  mandatory
                DESCRIPTION
                "The time the wsa5AvailIISCounterGroup was last updated"
                ::=  {  wsa5AgentGroup 6   }

        wsa5PolledCounterLastUpdate OBJECT-TYPE
                SYNTAX  DisplayString
                ACCESS  read-only
                STATUS  mandatory
                DESCRIPTION
                "The time the wsa5PolledCounterGroup was last updated"
                ::=  {  wsa5AgentGroup 7   }

        wsa5PolledIISCounterLastUpdate OBJECT-TYPE
                SYNTAX  DisplayString
                ACCESS  read-only
                STATUS  mandatory
                DESCRIPTION
                "The time the wsa5PolledIISCounterGroup was last updated"
                ::=  {  wsa5AgentGroup 8   }

        wsa5BadLinksLastUpdate OBJECT-TYPE
                SYNTAX  DisplayString
                ACCESS  read-only
                STATUS  mandatory
                DESCRIPTION
                "The time the wsa5LinkGroup was last updated"
                ::=  {  wsa5AgentGroup 9   }

        wsa5URLMntrLastUpdate OBJECT-TYPE
                SYNTAX  DisplayString
                ACCESS  read-only
                STATUS  mandatory
                DESCRIPTION
                "The time the wsa5URLMntrGroup was last updated"
                ::=  {  wsa5AgentGroup 11   }

        wsa5TopURLsLastUpdate OBJECT-TYPE
                SYNTAX  DisplayString
                ACCESS  read-only
                STATUS  mandatory
                DESCRIPTION
                "The time the wsa5TopURLGroup was last updated"
                ::=  {  wsa5AgentGroup 12   }

        wsa5ServerHealthLastUpdate OBJECT-TYPE
               SYNTAX  DisplayString
               ACCESS  read-only
               STATUS  mandatory
               DESCRIPTION
               "The time the wsa5ServerHealthGroup was last updated"
               ::=  {  wsa5AgentGroup 13   }

        wsa5LocalActionLastUpdate OBJECT-TYPE
               SYNTAX  DisplayString
               ACCESS  read-only
               STATUS  mandatory
               DESCRIPTION
               "The last time a local action executed."
               ::=  {  wsa5AgentGroup 14   }

        wsa5CGIstrings OBJECT-TYPE
               SYNTAX  DisplayString
               ACCESS  read-write
               STATUS  mandatory
               DESCRIPTION
               "Comma seperated strings used to identify CGI URLs."
               ::=  {  wsa5AgentGroup 20   }


        wsa5AvailCounterLastUpdate OBJECT-TYPE
               SYNTAX  DisplayString
               ACCESS  read-only
               STATUS  mandatory
               DESCRIPTION
               "The last time a wsa5AvailCounter group was updated."
               ::=  {  wsa5AgentGroup 21   }


        wsa5InstanceName OBJECT-TYPE
               SYNTAX  DisplayString
               ACCESS  read-only
               STATUS  mandatory
               DESCRIPTION
               "The Instance name for this agent."
               ::=  {  wsa5AgentGroup 22   }


        wsa5ErrorMsg OBJECT-TYPE
               SYNTAX  DisplayString
               ACCESS  read-write
               STATUS  mandatory
               DESCRIPTION
               "The Last Error Message as a result of GET/SET of a MIB value."
               ::=  {  wsa5AgentGroup 23   }


--******************************************************************************
--* wsa5PolledIISCounterGroup - Counters being polled                               *
--******************************************************************************

        wsa5PolledIISCounterTableEntries OBJECT-TYPE
                SYNTAX  INTEGER
                ACCESS  read-only
                STATUS  mandatory
                DESCRIPTION
                "The number of entries in the table."
                ::=  {  wsa5PolledIISCounterGroup 1   }

        wsa5PolledIISCounterAdd OBJECT-TYPE
                SYNTAX  DisplayString
                ACCESS  write-only
                STATUS  mandatory
                DESCRIPTION
                "Add this counter to the polled counter table."
                ::=  {  wsa5PolledIISCounterGroup 2   }

        wsa5PolledIISCounterDelete OBJECT-TYPE
                SYNTAX  DisplayString
                ACCESS  write-only
                STATUS  mandatory
                DESCRIPTION
                "Delete this counter from the polled counter table."
                ::=  {  wsa5PolledIISCounterGroup 3   }

        wsa5PolledIISSummaryStatus OBJECT-TYPE
                SYNTAX  INTEGER
                {
                    Normal(1),
                    Warning(2),
                    Critical(3)
                }
                ACCESS  read-only
                STATUS  mandatory
                DESCRIPTION
                "The summary status of all polled counters."
                ::=  {  wsa5PolledIISCounterGroup 4   }

        wsa5PollingIISInterval OBJECT-TYPE
                SYNTAX  INTEGER
                ACCESS  read-write
                STATUS  mandatory
                DESCRIPTION
                "Poll interval for the polled counter group in seconds."
                ::=  {  wsa5PolledIISCounterGroup 5   }

        wsa5PolledIISWarningCount OBJECT-TYPE
                SYNTAX  INTEGER
                ACCESS  read-only
                STATUS  mandatory
                DESCRIPTION
                "Number of polled counters in warning state."
                ::=  {  wsa5PolledIISCounterGroup 6   }

        wsa5PolledIISCriticalCount OBJECT-TYPE
                SYNTAX  INTEGER
                ACCESS  read-only
                STATUS  mandatory
                DESCRIPTION
                "Number of polled counters in critical state."
                ::=  {  wsa5PolledIISCounterGroup 7   }

        wsa5PolledIISCounterTable OBJECT-TYPE
                SYNTAX  SEQUENCE OF Wsa5PolledIISCounterEntry
                ACCESS  not-accessible
                STATUS  mandatory
                DESCRIPTION
                "The list of all polled counters."
                ::=  {  wsa5PolledIISCounterGroup 8}

	wsa5IISPolledGPEnaDis OBJECT-TYPE
		SYNTAX      INTEGER {Enable(1), Disable(2)}
		ACCESS      read-write
		STATUS      mandatory
		DESCRIPTION "Enable or disable for the Group."
		::= { wsa5PolledIISCounterGroup 9 }


        wsa5PolledIISCounterUpdate OBJECT-TYPE
               SYNTAX  DisplayString
               ACCESS  write-only
               STATUS  mandatory
	       DESCRIPTION "Update this entry in the table."
               ::=  {  wsa5PolledIISCounterGroup 10  }
               
        wsa5PolledIISCounterEntry OBJECT-TYPE
                 SYNTAX  Wsa5PolledIISCounterEntry
                 ACCESS  not-accessible
                 STATUS  mandatory
                 DESCRIPTION
                 "The wsa5PolledIISCounterTable entry."
                 INDEX { wsa5IISDescription }
                     ::=  { wsa5PolledIISCounterTable 1 }

        Wsa5PolledIISCounterEntry ::= SEQUENCE {
            wsa5IISDescription          DisplayString,
            wsa5IISAvailable            INTEGER,
            wsa5IISWarningThreshold     DisplayString,
            wsa5IISCriticalThreshold	DisplayString,
            wsa5IISValue                DisplayString,
            wsa5IISWarningCount         INTEGER,
            wsa5IISCriticalCount        INTEGER,
            wsa5IISWarningAction        DisplayString,
            wsa5IISCriticalAction       DisplayString,
            wsa5IISStatus               INTEGER,
            wsa5IISEnableDisable        INTEGER,
            wsa5IISDescendingCounter    INTEGER,
            wsa5IISMinimum              DisplayString,
            wsa5IISMaximum              DisplayString,
            wsa5IISAverage              DisplayString,
            wsa5IISStdDev               DisplayString,
	    wsa5IISValueReported	INTEGER,
	    wsa5IISLagSetting		INTEGER,
	    wsa5IISLagValue		INTEGER
        }

        wsa5IISDescription OBJECT-TYPE
                SYNTAX  DisplayString
                ACCESS  read-only
                STATUS  mandatory
                DESCRIPTION
                "The description of the polled counter."
                ::=  {  wsa5PolledIISCounterEntry 1   }

        wsa5IISAvailable OBJECT-TYPE
                SYNTAX  INTEGER
                {
                    Available(1),
                    NotAvailable(2)
                }
                ACCESS  read-only
                STATUS  mandatory
                DESCRIPTION
                "Describes whether this counter is currently available."
                ::=  {  wsa5PolledIISCounterEntry 2   }

        wsa5IISWarningThreshold OBJECT-TYPE
                SYNTAX  DisplayString
                ACCESS  read-write
                STATUS  mandatory
                DESCRIPTION
                "Counter value that will trigger warning status if value exceeds it."
                ::=  {  wsa5PolledIISCounterEntry 3   }

        wsa5IISCriticalThreshold OBJECT-TYPE
                SYNTAX  DisplayString
                ACCESS  read-write
                STATUS  mandatory
                DESCRIPTION
                "Counter value that will trigger critical status if value exceeds it."
                ::=  {  wsa5PolledIISCounterEntry 4   }

        wsa5IISValue OBJECT-TYPE
                SYNTAX  DisplayString
                ACCESS  read-only
                STATUS  mandatory
                DESCRIPTION
                "Value of the polled counter."
                ::=  {  wsa5PolledIISCounterEntry 5   }

        wsa5IISWarningCount OBJECT-TYPE
                SYNTAX  INTEGER
                ACCESS  read-only
                STATUS  mandatory
                DESCRIPTION
                "Number of times warning alert generated."
                ::=  {  wsa5PolledIISCounterEntry 6   }

        wsa5IISCriticalCount OBJECT-TYPE
                SYNTAX  INTEGER
                ACCESS  read-only
                STATUS  mandatory
                DESCRIPTION
                "Number of times critical alert generated."
                ::=  {  wsa5PolledIISCounterEntry 7   }

        wsa5IISWarningAction OBJECT-TYPE
                SYNTAX  DisplayString
                ACCESS  read-write
                STATUS  mandatory
                DESCRIPTION
                "Command to be executed when warning threshold is exceeded."
                ::=  {  wsa5PolledIISCounterEntry 8   }

        wsa5IISCriticalAction OBJECT-TYPE
                SYNTAX  DisplayString
                ACCESS  read-write
                STATUS  mandatory
                DESCRIPTION
                "Command to be executed when critical threshold is exceeded."
                ::=  {  wsa5PolledIISCounterEntry 9   }

        wsa5IISStatus OBJECT-TYPE
                SYNTAX  INTEGER
                {
                    Normal(1),
                    Warning(2),
                    Critical(3)
                }
                ACCESS  read-only
                STATUS  mandatory
                DESCRIPTION
                "Status of the polled counter."
                ::=  {  wsa5PolledIISCounterEntry 10   }

        wsa5IISEnableDisable OBJECT-TYPE
                SYNTAX  INTEGER
                {
                    Enable(1),
                    Disable(2)
                }
                ACCESS  read-write
                STATUS  mandatory
                DESCRIPTION
                "Enable or disable alerts for this counter."
                ::=  {  wsa5PolledIISCounterEntry 11   }

        wsa5IISDescendingCounter OBJECT-TYPE
                SYNTAX  INTEGER
                {
                    No(1),
                    Yes(2)
                }
                ACCESS  read-write
                STATUS  mandatory
                DESCRIPTION
                "Yes if lower value triggers thresholds, no if higher value triggers thresholds."
                ::=  {  wsa5PolledIISCounterEntry 12   }

        wsa5IISMinimum OBJECT-TYPE
               SYNTAX  DisplayString
               ACCESS  read-only
               STATUS  mandatory
               DESCRIPTION
               "The minimum reading since the last reset."
               ::=  {  wsa5PolledIISCounterEntry 13   }

        wsa5IISMaximum OBJECT-TYPE
               SYNTAX  DisplayString
               ACCESS  read-only
               STATUS  mandatory
               DESCRIPTION
               "The maximum reading since the last reset."
               ::=  {  wsa5PolledIISCounterEntry 14   }

        wsa5IISAverage OBJECT-TYPE
               SYNTAX  DisplayString
               ACCESS  read-only
               STATUS  mandatory
               DESCRIPTION
               "The average reading since the last reset."
               ::=  {  wsa5PolledIISCounterEntry 15   }

        wsa5IISStdDev OBJECT-TYPE
               SYNTAX  DisplayString
               ACCESS  read-only
               STATUS  mandatory
               DESCRIPTION
               "The standard deviation based on the last 100 readings."
               ::=  {  wsa5PolledIISCounterEntry 16   }

        wsa5IISValueReported OBJECT-TYPE
               SYNTAX  INTEGER {
                                Summary(1),
                                Average(2)
                               }
               ACCESS  read-write
               STATUS  mandatory
               DESCRIPTION
               "The reported value of the counter is either a summary or average of all servers."
               ::=  {  wsa5PolledIISCounterEntry 17 }
		
        wsa5IISLagSetting OBJECT-TYPE
                SYNTAX  INTEGER
                ACCESS  read-write
                STATUS  mandatory
                DESCRIPTION
                "Lag setting for the counter."
                ::=  {  wsa5PolledIISCounterEntry 18   }
		
        wsa5IISLagValue OBJECT-TYPE
                SYNTAX  INTEGER
                ACCESS  read-only
                STATUS  mandatory
                DESCRIPTION
                "Current Lag value for the counter."
                ::=  {  wsa5PolledIISCounterEntry 19   }



--******************************************************************************
--* ServerHealthGroup - overall server performance indicators                  *
--******************************************************************************

        wsa5SHSummaryStatus OBJECT-TYPE
               SYNTAX  INTEGER {
                                Normal(1),
                                Warning(2),
                                Critical(3)
                                }
               ACCESS  read-only
               STATUS  mandatory
               DESCRIPTION
               "Summary status for group."
               ::=  {  wsa5SHGroup 1   }

        wsa5SHPollingInterval OBJECT-TYPE
               SYNTAX  INTEGER
               ACCESS  read-write
               STATUS  mandatory
               DESCRIPTION
               "Seconds to poll for changes."
               ::=  {  wsa5SHGroup 2   }

        wsa5SHCpuUsage OBJECT-TYPE
               SYNTAX  INTEGER
               ACCESS  read-only
               STATUS  mandatory
               DESCRIPTION
               "CPU usage of the web servers."
               ::=  {  wsa5SHGroup 3   }

        wsa5SHCpuWarningThreshold OBJECT-TYPE
               SYNTAX  INTEGER
               ACCESS  read-write
               STATUS  mandatory
               DESCRIPTION
               "Generate a warning if wsa5SHCpuUsage exceeds this."
               ::=  {  wsa5SHGroup 4   }

        wsa5SHCpuCriticalThreshold OBJECT-TYPE
               SYNTAX  INTEGER
               ACCESS  read-write
               STATUS  mandatory
               DESCRIPTION
               "Generate a critical if wsa5SHCpuUsage exceeds this."
               ::=  {  wsa5SHGroup 5   }

        wsa5SHReqRate OBJECT-TYPE
               SYNTAX  INTEGER
               ACCESS  read-only
               STATUS  mandatory
               DESCRIPTION
               "Requests per second."
               ::=  {  wsa5SHGroup 6   }

        wsa5SHReqRateWarningThreshold OBJECT-TYPE
               SYNTAX  INTEGER
               ACCESS  read-write
               STATUS  mandatory
               DESCRIPTION
               "Generate a warning if wsa5SHReqRate exceeds this."
               ::=  {  wsa5SHGroup 7   }

        wsa5SHReqRateCriticalThreshold OBJECT-TYPE
               SYNTAX  INTEGER
               ACCESS  read-write
               STATUS  mandatory
               DESCRIPTION
               "Generate a critical if wsa5SHReqRate exceeds this."
               ::=  {  wsa5SHGroup 8   }

        wsa5SHByteRate OBJECT-TYPE
               SYNTAX  INTEGER
               ACCESS  read-only
               STATUS  mandatory
               DESCRIPTION
               "Kilobytes transferred per second."
               ::=  {  wsa5SHGroup 9   }

        wsa5SHByteRateWarningThreshold OBJECT-TYPE
               SYNTAX  INTEGER
               ACCESS  read-write
               STATUS  mandatory
               DESCRIPTION
               "Generate a warning if wsa5SHByteRate exceeds this."
               ::=  {  wsa5SHGroup 10   }

        wsa5SHByteRateCriticalThreshold OBJECT-TYPE
               SYNTAX  INTEGER
               ACCESS  read-write
               STATUS  mandatory
               DESCRIPTION
               "Generate a critical if wsa5SHByteRate exceeds this."
               ::=  {  wsa5SHGroup 11   }

        wsa5SHWarningAction OBJECT-TYPE
               SYNTAX  DisplayString
               ACCESS  read-write
               STATUS  mandatory
               DESCRIPTION
               "Command to be executed when any warning threshold is exceeded."
               ::=  {  wsa5SHGroup 12   }

        wsa5SHCriticalAction OBJECT-TYPE
               SYNTAX  DisplayString
               ACCESS  read-write
               STATUS  mandatory
               DESCRIPTION
               "Command to be executed when any critical threshold is exceeded."
               ::=  {  wsa5SHGroup 13   }

        wsa5SHProcesses OBJECT-TYPE
               SYNTAX  INTEGER
               ACCESS  read-only
               STATUS  mandatory
               DESCRIPTION
               "Number of current server processes."
               ::=  {  wsa5SHGroup 14   }

        wsa5SHTotalHits OBJECT-TYPE
               SYNTAX  INTEGER
               ACCESS  read-only
               STATUS  mandatory
               DESCRIPTION
               "Totals requests."
               ::=  {  wsa5SHGroup 15   }

        wsa5SHTotalErrors OBJECT-TYPE
               SYNTAX  INTEGER
               ACCESS  read-only
               STATUS  mandatory
               DESCRIPTION
               "Totals error requests."
               ::=  {  wsa5SHGroup 16   }

        wsa5SHTotalGETS OBJECT-TYPE
               SYNTAX  INTEGER
               ACCESS  read-only
               STATUS  mandatory
               DESCRIPTION
               "Totals GET requests."
               ::=  {  wsa5SHGroup 17   }

        wsa5SHTotalPOSTS OBJECT-TYPE
               SYNTAX  INTEGER
               ACCESS  read-only
               STATUS  mandatory
               DESCRIPTION
               "Totals POST requests."
               ::=  {  wsa5SHGroup 18   }

        wsa5SHTotalHEADS OBJECT-TYPE
               SYNTAX  INTEGER
               ACCESS  read-only
               STATUS  mandatory
               DESCRIPTION
               "Totals HEAD requests."
               ::=  {  wsa5SHGroup 19   }

        wsa5SHTotalCGI OBJECT-TYPE
               SYNTAX  INTEGER
               ACCESS  read-only
               STATUS  mandatory
               DESCRIPTION
               "Totals CGI requests."
               ::=  {  wsa5SHGroup 20   }

        wsa5SHServerUptime OBJECT-TYPE
               SYNTAX  INTEGER
               ACCESS  read-only
               STATUS  mandatory
               DESCRIPTION
               "Server uptime in days."
               ::=  {  wsa5SHGroup 21   }

        wsa5SHMaxReqRate OBJECT-TYPE
               SYNTAX  INTEGER
               ACCESS  read-write
               STATUS  mandatory
               DESCRIPTION
               "Max value for the abrowser max requests scale."
               ::=  {  wsa5SHGroup 22   }

        wsa5SHMaxByteRate OBJECT-TYPE
               SYNTAX  INTEGER
               ACCESS  read-write
               STATUS  mandatory
               DESCRIPTION
               "Max value for the abrowser max bytes scale."
               ::=  {  wsa5SHGroup 23   }

	wsa5SHGPEnaDis OBJECT-TYPE
		SYNTAX      INTEGER {Enable(1), Disable(2)}
		ACCESS      read-write
		STATUS      mandatory
		DESCRIPTION "Enable or disable for the Group."
		::= { wsa5SHGroup 24 }
		
        wsa5SHCPULagSetting OBJECT-TYPE
                SYNTAX  INTEGER
                ACCESS  read-write
                STATUS  mandatory
                DESCRIPTION
                "Lag setting for the counter."
                ::=  {  wsa5SHGroup 25   }
		
        wsa5SHCPULagValue OBJECT-TYPE
                SYNTAX  INTEGER
                ACCESS  read-only
                STATUS  mandatory
                DESCRIPTION
                "Current Lag value for the counter."
                ::=  {  wsa5SHGroup 26   }
		
        wsa5SHRSLagSetting OBJECT-TYPE
                SYNTAX  INTEGER
                ACCESS  read-write
                STATUS  mandatory
                DESCRIPTION
                "Lag setting for the counter."
                ::=  {  wsa5SHGroup 27   }
		
        wsa5SHRSLagValue OBJECT-TYPE
                SYNTAX  INTEGER
                ACCESS  read-only
                STATUS  mandatory
                DESCRIPTION
                "Current Lag value for the counter."
                ::=  {  wsa5SHGroup 28   }
		
        wsa5SHKSLagSetting OBJECT-TYPE
                SYNTAX  INTEGER
                ACCESS  read-write
                STATUS  mandatory
                DESCRIPTION
                "Lag setting for the counter."
                ::=  {  wsa5SHGroup 29   }
		
        wsa5SHKSLagValue OBJECT-TYPE
                SYNTAX  INTEGER
                ACCESS  read-only
                STATUS  mandatory
                DESCRIPTION
                "Current Lag value for the counter."
                ::=  {  wsa5SHGroup 30   }


--******************************************************************************
--* Local action log - circular buffer of local actions performed              *
--* Dynamic get, not polled.                                                   *
--******************************************************************************

        wsa5LocalActionTableEntries OBJECT-TYPE
               SYNTAX  INTEGER
               ACCESS  read-only
               STATUS  mandatory
               DESCRIPTION
               "The number of entries in the local action log table."
               ::=  {  wsa5LocalActionGroup 1   }

        wsa5LocalActionCircularBuffSize OBJECT-TYPE
               SYNTAX  INTEGER
               ACCESS  read-write
               STATUS  mandatory
               DESCRIPTION
               "Max entries in the wsa5LocalActionLogTable (default 50)."
               ::=  {  wsa5LocalActionGroup 2   }

        wsa5LocalActionRefresh OBJECT-TYPE
               SYNTAX  INTEGER
               ACCESS  read-write
               STATUS  mandatory
               DESCRIPTION
               "Refresh the table starting with the most recent action."
               ::=  {  wsa5LocalActionGroup 3   }

        wsa5LocalActionStartDateTime OBJECT-TYPE
               SYNTAX  DisplayString
               ACCESS  read-write
               STATUS  mandatory
               DESCRIPTION
               "Refresh the table starting at the specified date and time."
               ::=  {  wsa5LocalActionGroup 4   }

        wsa5LocalActionScrollDown OBJECT-TYPE
               SYNTAX  INTEGER
               ACCESS  read-write
               STATUS  mandatory
               DESCRIPTION
               "Read the next older set of log entries into the table."
               ::=  {  wsa5LocalActionGroup 5   }

        wsa5LocalActionScrollUp OBJECT-TYPE
               SYNTAX  INTEGER
               ACCESS  read-write
               STATUS  mandatory
               DESCRIPTION
               "Read the next newer set of log entries into the table."
               ::=  {  wsa5LocalActionGroup 6   }

        wsa5LocalActionLogTable OBJECT-TYPE
               SYNTAX  SEQUENCE OF Wsa5LocalActionLogEntry
               ACCESS  not-accessible
               STATUS  mandatory
               DESCRIPTION
               "This table contains a list of command actions taken in response to events."
               ::=  {  wsa5LocalActionGroup 7 }

        wsa5LocalActionLogEntry OBJECT-TYPE
                                SYNTAX  Wsa5LocalActionLogEntry
                                ACCESS  not-accessible
                                STATUS  mandatory
                                DESCRIPTION
                                "This is an entry in the wsa5LocalActionTable"
                                INDEX { wsa5LocalActionSequencer }
                                ::=  { wsa5LocalActionLogTable 1 }

        Wsa5LocalActionLogEntry ::= SEQUENCE
        {
           wsa5LocalActionSequencer               INTEGER,
           wsa5LocalActionTimestamp               DisplayString,
           wsa5LocalActionSeverity                INTEGER,
           wsa5LocalActionReason                  DisplayString,
           wsa5LocalActionCommand                 DisplayString
        }

        wsa5LocalActionSequencer OBJECT-TYPE
               SYNTAX  INTEGER
               ACCESS  read-only
               STATUS  mandatory
               DESCRIPTION
               "Table sequencer"
               ::=  {  wsa5LocalActionLogEntry 1   }

        wsa5LocalActionTimestamp OBJECT-TYPE
               SYNTAX  DisplayString
               ACCESS  read-only
               STATUS  mandatory
               DESCRIPTION
               "Time the command was executed (action taken)."
               ::=  {  wsa5LocalActionLogEntry 2   }

-- The Warning and Critical values for severity must match CLocalAction::enum Severity.
        wsa5LocalActionSeverity OBJECT-TYPE
               SYNTAX  INTEGER
               {
                   Normal(1),
                   Warning(2),
                   Critical(3)
               }
               ACCESS  read-only
               STATUS  mandatory
               DESCRIPTION
               "The severity of the event which triggered the action."
               ::=  {  wsa5LocalActionLogEntry 3   }

        wsa5LocalActionReason OBJECT-TYPE
               SYNTAX  DisplayString
               ACCESS  read-only
               STATUS  mandatory
               DESCRIPTION
               "The reason the action was taken."
               ::=  {  wsa5LocalActionLogEntry 4   }

        wsa5LocalActionCommand OBJECT-TYPE
               SYNTAX  DisplayString
               ACCESS  read-only
               STATUS  mandatory
               DESCRIPTION
               "Command executed (action taken)."
               ::=  {  wsa5LocalActionLogEntry 5   }



--******************************************************************************
--*  Traps                                                                     *
--******************************************************************************

    statusNormal TRAP-TYPE
        ENTERPRISE wsa5Agent
        DESCRIPTION "Set status to normal"
        ::= 1

    statusWarning TRAP-TYPE
        ENTERPRISE wsa5Agent
        DESCRIPTION "Set status to warning"
        ::= 2

    statusCritical TRAP-TYPE
        ENTERPRISE wsa5Agent
        DESCRIPTION "Set status to critical"
        ::= 3

    statusDetailTrap TRAP-TYPE
        ENTERPRISE wsa5Agent
--        VARIABLES   {szStatus}
        DESCRIPTION "Status of group or table (row) changed"
        ::= 4
END
