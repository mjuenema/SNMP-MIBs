--MibName=rcSla
-- *****************************************************************
-- RAISECOM-SLA-MIB.mib
--
-- july 2008, wangyuhang
--
-- Copyright(c) 2003-2005 by RAISECOM TECH, Ltd. 
-- All rights reserved.
-- *****************************************************************


RAISECOM-SLA-MIB DEFINITIONS ::= BEGIN      
IMPORTS
    Integer32, 
    Counter32,                                             
    Unsigned32,
    Gauge32,          
    IpAddress                   		FROM SNMPv2-SMI    -- [RFC2578]  
    TimeStamp,
    RowStatus,
    TruthValue,
    MacAddress, DateAndTime, TimeInterval
                                        FROM SNMPv2-TC     -- [RFC2579]
    InterfaceIndex                      FROM IF-MIB        -- [RFC2863]
    EnableVar                           FROM SWITCH-TC
    VlanId,
    VlanIdOrNone                        FROM Q-BRIDGE-MIB  
    iscomSwitch                         FROM RAISECOM-BASE-MIB    
    Dot1agCfmMepId,
    Dot1agCfmMDLevel,
    Dot1agCfmMDLevelOrNone              FROM IEEE8021-CFM-MIB
    InetAddressType, InetAddress        FROM INET-ADDRESS-MIB  -- [RFC4001]    
    
    ;
rcSla  MODULE-IDENTITY
    LAST-UPDATED   "200711020000Z"
    ORGANIZATION   "Raisecom, Inc."
    CONTACT-INFO  
                "       Raise Systems
                        
                Postal: Beijing,
                        China

                   Tel: 86-010-82884499

                E-mail: wangyuhang@raisecom.com"
    DESCRIPTION
        "This MIB module defines objects to SLA "
        REVISION   "200711020000Z"
        DESCRIPTION
            "The initial revision of this MIB."
        ::={ iscomSwitch  36 } 
--
--
RcSlaCfgOperType ::= TEXTUAL-CONVENTION
    STATUS      current
    DESCRIPTION
       "  Specifies the type of operation to be performed. 
        The value 'y1731-echo' will cause the  application to perform a timed echo y1731
    operation directed at the 'rcSlaConfigDestMacAddr' or 'rcSlaConfigRMepId'.
        The value 'y1731-jitter' will cause the  application to perform delay variance analysis.  
        The value 'icmp-echo' will cause the  application to perform a timed echo icmp
    operation directed at the 'rcSlaConfigDestIpAddr'.
        The value 'icmp-jitter' will cause the  application to perform delay variance analysis.   
      " 
    REFERENCE
       "rcSla"
    SYNTAX      INTEGER {
                  y1731-echo               (1),
                  y1731-jitter             (2),
                  icmp-echo                (3),
                  icmp-jitter              (4),
                  y1731-pkt-loss           (5),
                  pw-y1731-echo            (6),
                  pw-y1731-jitter          (7),
                  pw-y1731-pkt-loss        (8),
                  lsp-y1731-echo           (9),
                  lsp-y1731-jitter         (10),
                  lsp-y1731-pkt-loss       (11),
                  section-y1731-echo       (12),
                  section-y1731-jitter     (13),
                  section-y1731-pkt-loss   (14),
                  mpls-all-y1731-echo	   (15),
                  mpls-all-y1731-jitter	   (16),
                  mpls-all-y1731-pkt-loss  (17),
                  lsp-y1731-pkt-sd         (18),
                  mef-availability         (19)
                }
--   
--
RcSlaCfgScheduleStatus ::= TEXTUAL-CONVENTION
    STATUS      current
    DESCRIPTION
       " The RcSlaCfgScheduleStatus textual convention is used to manage the
 	creation and deletion of Schedule.
     	The status column has five defined values: 
     	 - `scheduleInitial', which indicates that the operation dose not be 
     scheduled ;    
     	 - `scheduleCreate', which is supplied by a management station wishing to 
      create a new schedule and to have its status automatically set to active;
     	 - `scheduleBreak', which is supplied by a management station wishing to 
      break a scheduling operationand to have its status automatically set to complete;   
         - `scheduleActive', which indicates that the operation is being scheduled ; 
         - `scheduleComplete', which indicates that the scheduled operation has been over; 
         "
    REFERENCE
       "rcSla"
    SYNTAX      INTEGER {
                  scheduleInitial   (1),
                  scheduleCreate    (2),
                  scheduleBreak     (3),
                  scheduleActive    (4),
                  scheduleComplete  (5)
                }  
                
--                                   

                        
--
RcSlaOWSupport ::= TEXTUAL-CONVENTION
    STATUS      current
    DESCRIPTION
       "  The type  use to  decide whether to support one way Test. " 
    REFERENCE
       "rcSla"
    SYNTAX      INTEGER {
                  sla_unknown        (1),
                  sla_support        (2),
                  sla_no_support     (3)
                  }
  
             

--groupsType
    rcSlaObjectsGroup	OBJECT IDENTIFIER ::= {rcSla 1}  
    rcSlaConfigGroup	OBJECT IDENTIFIER ::= {rcSla 2}  
    rcSlaScheduleGroup	OBJECT IDENTIFIER ::= {rcSla 3}        
    rcSlaThroughputGroup  OBJECT IDENTIFIER ::= {rcSla 4}  
    rcSlaThresholdGroup  OBJECT IDENTIFIER ::= {rcSla 5}

--rcSlaObjectsGroup
	-- rcSlaConfigOperSum
	-- rcSlaActiveOperSum  
                     
-- rcSlaConfigOperSum
                                                                         
	rcSlaConfigOperSum        OBJECT-TYPE
		SYNTAX      Gauge32
   		MAX-ACCESS  read-only
    	STATUS      current
    	DESCRIPTION
            "The total number of operation configured " 
       	::= { rcSlaObjectsGroup 1 }     
    	
-- rcSlaActiveOperSum 
                                                                                              
	rcSlaActiveOperSum        OBJECT-TYPE
		SYNTAX      Gauge32
   		MAX-ACCESS  read-only
    	STATUS      current
    	DESCRIPTION
            "The total number of active configured " 
    	::= { rcSlaObjectsGroup 2 }                
    	
 -- rcSlaY1731OperType 
                                                                                              
	rcSlaY1731OperType        OBJECT-TYPE
		SYNTAX      RcSlaCfgOperType
   		MAX-ACCESS  read-write
    	STATUS      current
    	DESCRIPTION
            "Y.1731 Operation Type : y1731-echo / y1731-jitter" 
        DEFVAL { y1731-echo }
    	::= { rcSlaObjectsGroup 3 }

 -- rcSlaY1731MDLevel
                                                                                              
	rcSlaY1731MDLevel         OBJECT-TYPE
		SYNTAX      Dot1agCfmMDLevelOrNone
   		MAX-ACCESS  read-write
    	STATUS      current
    	DESCRIPTION
            "This object specifies the maintenance domain level to be used by Y.1731 operation." 
        DEFVAL { -1 }      
    	::= { rcSlaObjectsGroup 4 }

 -- rcSlaY1731SVlanId
                                                                                              
    rcSlaY1731SVlanId         OBJECT-TYPE
		SYNTAX      VlanIdOrNone
   		MAX-ACCESS  read-write
    	STATUS      current
    	DESCRIPTION
            "This object specifies the identifier of VLAN for MA to be used by  Y.1731 operation.
				It is an unique identifier for a service instance 
				within a Maintenance Domain specified by rcSlaConfigMDLevel."
        DEFVAL { 0 }
    	::= { rcSlaObjectsGroup 5 }

 -- rcSlaY1731OperQuickInput
                                                                                              
    rcSlaY1731OperQuickInput   OBJECT-TYPE
		SYNTAX      TruthValue
   		MAX-ACCESS  read-write
    	STATUS      current
    	DESCRIPTION
            "Quick creat operation when  learning Rmep by Y.1731"
        DEFVAL { false }
    	::= { rcSlaObjectsGroup 6 } 
    	      	
 -- rcSlaY1731TestPduType  
 
    rcSlaY1731TestPduType      OBJECT-TYPE
		SYNTAX      INTEGER {loopBack(1), delayMeasurement(2), lossMeasurement(3)}
   		MAX-ACCESS  read-write
    	STATUS      current
    	DESCRIPTION
            "Quick input test pdu type"
        DEFVAL { loopBack }
    	::= { rcSlaObjectsGroup 7 } 

 -- rcSlaY1731IngLspName   

    rcSlaY1731IngLspName       OBJECT-TYPE
     	SYNTAX      OCTET STRING (SIZE (0..32))
     	MAX-ACCESS  read-write
        STATUS      current
        DESCRIPTION
            "The ingress LSP name associated with the ma."    
     	::= { rcSlaObjectsGroup 8 } 
  
 -- rcSlaY1731EgrLspName   

    rcSlaY1731EgrLspName       OBJECT-TYPE 
     	SYNTAX      OCTET STRING (SIZE (0..32))
     	MAX-ACCESS  read-write
        STATUS      current
        DESCRIPTION
            "The egress LSP name associated with the ma."    
     	::= { rcSlaObjectsGroup 9 } 

 -- rcSlaY1731L2vcID       

    rcSlaY1731L2vcID           OBJECT-TYPE
        SYNTAX      INTEGER(0..2147483647)
  	    MAX-ACCESS  read-write
        STATUS      current
        DESCRIPTION
            "The VC ID associated with the ma."    
        DEFVAL { 0 }
  	    ::= { rcSlaObjectsGroup 10 }
  	    
 -- rcSlaY1731PwPeerAddrType     

    rcSlaY1731PwPeerAddrType   OBJECT-TYPE
        SYNTAX      InetAddressType
  	    MAX-ACCESS  read-write
        STATUS      current
        DESCRIPTION
			"Denotes the address type of the peer node.  It should be
			set to 'unknown' if PE/PW maintenance protocol is not used
			and the address is unknown."
		DEFVAL { unknown }
  	    ::= { rcSlaObjectsGroup 11 }  	    
  	    
 -- rcSlaY1731PwPeerAddr       

    rcSlaY1731PwPeerAddr      OBJECT-TYPE
        SYNTAX      InetAddress
  	    MAX-ACCESS  read-write
        STATUS      current
        DESCRIPTION
			"This object contains the value of the peer node address
			of the PW/PE maintenance protocol entity.  This object
			SHOULD contain a value of all zeroes if not applicable
			(rcCfmMaExPwPeerAddrType is 'unknown')."
  	    ::= { rcSlaObjectsGroup 12 }
  	    
 -- rcSlaY1731SectionPort       

    rcSlaY1731SectionPort      OBJECT-TYPE
        SYNTAX      Unsigned32
  	    MAX-ACCESS  read-write
        STATUS      current
        DESCRIPTION
			"The section port associated with the ma."
  	    ::= { rcSlaObjectsGroup 13 }

 -- rcSlaY1731PrivateTlv       

    rcSlaY1731PrivateTlv      OBJECT-TYPE
        SYNTAX      EnableVar
        MAX-ACCESS  read-write
        STATUS      current
        DESCRIPTION
            "The private tlv contained in packets.
            A value of TRUE(1) indicates that packets are with private tlv,
            FALSE(2) indicates that packets are not with private tlv."
        ::= { rcSlaObjectsGroup 14 }

 
--------------------------------------------------OperConfigGroup -----------------------  
--rcSlaConfigGroup                                                                                              
		--rcSlaConfigTable    
			--rcSlaConfigEntry 
				--rcSlaConfigOperId
				--rcSlaConfigOwner   
				--rcSlaOneWaySupport
				--rcSlaConfigOperType
				--rcSlaConfigCos   				
				--rcSlaConfigCVlanId 
				--rcSlaConfigSVlanId 
				--rcSlaConfigMDLevel
				--rcSlaConfigRMepId
				--rcSlaConfigDestMacAddr
				--rcSlaConfigDestIpAddr
				--rcSlaConfigJitterInterval
				--rcSlaConfigJitterFrameNums
				--rcSlaConfigScheduleStartTime
				--rcSlaConfigScheduleLife
				--rcSlaConfigSchedulePeriod
				--rcSlaConfigScheduleStatus
				--rcSlaConfigRowStatus   
				--rcSlaConfigParam 
				--rcSlaConfigDscp  
                --rcSlaConfigTestPduType	
                --rcSlaConfigLspIngressName 
                --rcSlaConfigLspEgressName  
                --rcSlaConfigVcId
                --rcSlaConfigPwPeerAddrType
                --rcSlaConfigPwPeerAddr  
                --rcSlaConfigSectionPort 
                --rcSlaConfigScheduleSdBadSeconds
                --rcSlaConfigScheduleSdGoodSeconds 
                --rcSlaConfigAvailabilityMeasurementInterval    
                --rcSlaConfigAvailabilityNumConsecutiveMeasPdus 
                --rcSlaConfigAvailabilityFlrThreshold           
                --rcSlaConfigAvailabilityNumConsecutiveIntervals
                --rcSlaConfigAvailabilityNumConsecutiveHighFlr                  

rcSlaConfigTable  OBJECT-TYPE
    SYNTAX      SEQUENCE OF RcSlaConfigEntry
    MAX-ACCESS  not-accessible
    STATUS      current
    DESCRIPTION
        "This table contains sla  control data."
    ::= { rcSlaConfigGroup 1 }

rcSlaConfigEntry   OBJECT-TYPE
    SYNTAX      RcSlaConfigEntry
    MAX-ACCESS  not-accessible
    STATUS      current
    DESCRIPTION
        "A collection of objects that define three conceptual
    control row : slaY.1731EntryTable, slaIcmpEntryTable, slaSchEntryTable.
   		The 'slaY.1731EntryTable' is used to control y1731 operation .
    	The following objects must be specified in order to create this 
    conceptual row.
    	- rcSlaConfigOperType
    	- rcSlaConfigVlanId
    	- rcSlaConfigMDLevel
    	- rcSlaConfigDestMacAddr 
    	- rcSlaConfigRMepId
    	The ' slaIcmpEntryTable' is used to control ICMP operation .
    	The following objects must be specified in order to create this 
    conceptual row.
    	- rcSlaConfigOperType
    	- rcSlaConfigDestIpAddr
        The ' slaIcmpSchTable' is used to control operation schduled."
	INDEX        { rcSlaConfigOperId }    
    ::={ rcSlaConfigTable 1 }     
    
RcSlaConfigEntry ::= SEQUENCE {
        rcSlaConfigOperId				     Unsigned32,
    	rcSlaConfigOwner				     OCTET STRING (SIZE(0..1024)),
    	rcSlaOneWaySupport                   RcSlaOWSupport,
    	rcSlaConfigOperType		             RcSlaCfgOperType,       
	    rcSlaConfigCos                       Integer32 (0..7 ),  
	    rcSlaConfigCVlanId                   VlanId,
	    rcSlaConfigSVlanId                   VlanId,
	    rcSlaConfigMDLevel		             Dot1agCfmMDLevel,
	    rcSlaConfigRMepId                    Dot1agCfmMepId,
	    rcSlaConfigDestMacAddr               MacAddress,
	    rcSlaConfigDestIpAddr                IpAddress, 
	    rcSlaConfigJitterInterval            Unsigned32,
	    rcSlaConfigJitterFrameNums           Unsigned32,
	    rcSlaConfigScheduleStartTime         TimeStamp,     
	    rcSlaConfigScheduleLife              Unsigned32, 
	    rcSlaConfigSchedulePeriod            Unsigned32,
	    rcSlaConfigScheduleStatus            RcSlaCfgScheduleStatus,
	    rcSlaConfigRowStatus                 RowStatus,   
	    rcSlaConfigParam                     OCTET STRING (SIZE(0..255)),
	    rcSlaConfigTestPduType				 INTEGER,
	    rcSlaConfigDscp                      Integer32 (0..63 ),
        rcSlaConfigTc                        Integer32 (0..7 ),
        rcSlaConfigLspIngressName            OCTET STRING (SIZE(0..32)),
        rcSlaConfigLspEgressName             OCTET STRING (SIZE(0..32)), 
        rcSlaConfigVcId                      Integer32 (1..2147483647 ),
        rcSlaConfigPwPeerAddrType            InetAddressType,
        rcSlaConfigPwPeerAddr                InetAddress, 
        rcSlaConfigSectionPort               Unsigned32, 
        rcSlaConfigScheduleSdBadSeconds      Integer32 (1..360 ),
        rcSlaConfigScheduleSdGoodSeconds     Integer32 (1..1800),
        rcSlaConfigAvailabilityMeasurementInterval        Unsigned32,
        rcSlaConfigAvailabilityNumConsecutiveMeasPdus     Unsigned32,
        rcSlaConfigAvailabilityFlrThreshold               Unsigned32,
        rcSlaConfigAvailabilityNumConsecutiveIntervals    Unsigned32,
        rcSlaConfigAvailabilityNumConsecutiveHighFlr      Unsigned32
     }

rcSlaConfigOperId       OBJECT-TYPE 
	SYNTAX      Unsigned32 
	MAX-ACCESS  not-accessible
    STATUS      current
    DESCRIPTION
            "This object indicates a row in the rcSlaConfigTable.
        This value is an operation number configured by user."
    ::= { rcSlaConfigEntry 1 }   
    
rcSlaConfigOwner       OBJECT-TYPE 
	SYNTAX      OCTET STRING (SIZE(0..1024))
    MAX-ACCESS  read-create
    STATUS      current
    DESCRIPTION
            "This object specifies a string which used by a managing application 
        to identify the entity that created this operation."
    DEFVAL { "raisecom" }
    ::= { rcSlaConfigEntry 2 }  
   
       
rcSlaOneWaySupport     OBJECT-TYPE 
	SYNTAX      RcSlaOWSupport
    MAX-ACCESS  read-only
    STATUS      current
    DESCRIPTION
            "Specifies the type of  decision whether to support one way test.  "
    ::= { rcSlaConfigEntry 3 }
    
rcSlaConfigOperType       OBJECT-TYPE 
	SYNTAX      RcSlaCfgOperType
    MAX-ACCESS  read-create
    STATUS      current
    DESCRIPTION
            "Specifies the type of operation to be performed. "
    ::= { rcSlaConfigEntry 4 }

rcSlaConfigCos       OBJECT-TYPE 
	SYNTAX      Integer32 (0..7 )
    MAX-ACCESS  read-create
    STATUS      current
    DESCRIPTION
          "This object specifies the Class Of Service field 
        in an frame header of SLA PDU to be used by Y.1731 operation."
    ::= { rcSlaConfigEntry 5 }

rcSlaConfigCVlanId       OBJECT-TYPE 
	SYNTAX      VlanId
    MAX-ACCESS  read-create
    STATUS      current
    DESCRIPTION
          "This object specifies the CVlan user configured 
          	in an frame header of SLA PDU to be used by Y.1731 operation.
          	It could be zero when there is no cunsomer vlan"
    ::= { rcSlaConfigEntry 6 }

rcSlaConfigSVlanId       OBJECT-TYPE 
	SYNTAX      VlanId
    MAX-ACCESS  read-create
    STATUS      current
    DESCRIPTION
            "This object specifies the identifier of VLAN for MA to be used by Y.1731 operation.
				It is an unique identifier for a service instance 
				within a Maintenance Domain specified by rcSlaConfigMDLevel."
    ::= { rcSlaConfigEntry 7 }                    

rcSlaConfigMDLevel       OBJECT-TYPE 
	SYNTAX      Dot1agCfmMDLevel
	MAX-ACCESS  read-create
    STATUS      current
    DESCRIPTION
            "This object specifies the maintenance domain level to be used by Y.1731 operation."
    ::= { rcSlaConfigEntry 8 }                    
             

rcSlaConfigRMepId       OBJECT-TYPE 
	SYNTAX      Dot1agCfmMepId
    MAX-ACCESS  read-create
    STATUS      current
    DESCRIPTION
            "This object specifies the Target Remote MEP Identify to be used by Y.1731 operation."
    ::= { rcSlaConfigEntry 9 }                    

rcSlaConfigDestMacAddr       OBJECT-TYPE 
	SYNTAX      MacAddress
    MAX-ACCESS  read-create
    STATUS      current
    DESCRIPTION
            "This object specifies the Target MAC Address Field to be used by Y.1731 operation."
    ::= { rcSlaConfigEntry 10 }

rcSlaConfigDestIpAddr       OBJECT-TYPE 
	SYNTAX      IpAddress
    MAX-ACCESS  read-create
    STATUS      current
    DESCRIPTION
            "This object specifies the Target IP Address Field to be used by ICMP operation."
    ::= { rcSlaConfigEntry 11 }                    

rcSlaConfigJitterInterval       OBJECT-TYPE 
	SYNTAX      Unsigned32 
    MAX-ACCESS  read-create
    STATUS      current
    DESCRIPTION
            "This value specifies the inter-frame delay between Ethernet
        frames that need to be transmitted to the target device.
        This object is applicable to 'Jitter' operation only."
   ::= { rcSlaConfigEntry 12 }                    

rcSlaConfigJitterFrameNums       OBJECT-TYPE 
	SYNTAX      Unsigned32
    MAX-ACCESS  read-create
    STATUS      current
    DESCRIPTION
           "This object specifies the number of frames that need to be transmitted to the target device.  
           		This object is applicable to 'Jitter' operation only."
    ::= { rcSlaConfigEntry 13 }                    

rcSlaConfigScheduleStartTime       OBJECT-TYPE 
	SYNTAX      TimeStamp
    MAX-ACCESS  read-only
    STATUS      current
    DESCRIPTION
            "This object specifies the time when this schedule status will become 'active'.  
            	Value of 0 puts in other status."
    ::= { rcSlaConfigEntry 14 }                    

rcSlaConfigScheduleLife       OBJECT-TYPE 
	SYNTAX      Unsigned32
    MAX-ACCESS  read-create
    STATUS      current
    DESCRIPTION
            "This object specifies the time duration over the whole schedule process. "
    ::= { rcSlaConfigEntry 15 }                    

rcSlaConfigSchedulePeriod       OBJECT-TYPE 
	SYNTAX      Unsigned32
	MAX-ACCESS  read-create
    STATUS      current
    DESCRIPTION
            "This object specifies the duration between two SLA test 
            	which includes all of probes schedule process in test. 
           	Take above example, if all of the rcSlaConfigSchedulePeriod of three operations are set to 60, 
            	then the start time of each test of SLA operation like:
			start time:   T+0 --------  T+9 ----------  T+19-----
           		operation1  operation2    operation3 
			start again:  T+60--------  T+69 ----------  T+79--
           		operation1  operation2    operation3   
			start 3rd time:T+120-------- T+129 ----------T+139--
         		operation1  operation2    operation3"
    ::= { rcSlaConfigEntry 16 }                    

rcSlaConfigScheduleStatus       OBJECT-TYPE 
	SYNTAX      RcSlaCfgScheduleStatus
    MAX-ACCESS  read-create
    STATUS      current
    DESCRIPTION
            "This object specifies the status of Schedule.  
            The status column has five defined values: 
		- `scheduleInitial', which indicates that the operation has not been scheduled ;    
		- `scheduleCreate', which is supplied by a management station wishing to create a new schedule 
				and to have its status set to active;
		- `scheduleBreak', which is supplied by a management station wishing to break a scheduling operation 
				and to have its status set to complete;   
		- `scheduleActive', which indicates that the operation is being scheduled ; 
		- `scheduleComplete', which indicates that the scheduled operation has been over;"
    ::= { rcSlaConfigEntry 17 }                    

rcSlaConfigRowStatus       OBJECT-TYPE 
	SYNTAX      RowStatus
    MAX-ACCESS  read-create
    STATUS      current
    DESCRIPTION
            "The status of the row.
			All columns must have a valid value before a row can be activated. 
			The following objects must be specified obviously in order for row status object to become active.
				rcSlaConfigOperId
				rcSlaConfigOperType
    		For ICMP operation:
    			rcSlaConfigDestIpAddr
			For Y.1731 operation:
       			rcSlaConfigVlanId
    			rcSlaConfigMDLevel
    			rcSlaConfigDestMacAddr

			The following objects about the configuration of operation cannot be modified after creating the row:
				rcSlaConfigOperId
    			rcSlaConfigOwner
    			rcSlaConfigOperType
    			rcSlaConfigCos
    			rcSlaConfigVlanId
				rcSlaConfigMDLevel
				rcSlaConfigDestMacAddr
				rcSlaConfigDestIpAddr
    			rcSlaConfigJitterInterval
				rcSlaConfigJitterFrameNums
				  rcSlaConfigDscp

			The following objects about the schedule configuration of operation can be modified even after creating the row:
    			rcSlaConfigScheduleStartTime
    			rcSlaConfigScheduleLife
    			rcSlaConfigSchedulePeriod
				rcSlaConfigScheduleStatus
			The ahead three objects of above won't be modified until another schedule of this operation start."
    ::= { rcSlaConfigEntry 18 }   
    
rcSlaConfigParam       OBJECT-TYPE 
	SYNTAX      OCTET STRING (SIZE(0..255))
	MAX-ACCESS  read-create
    STATUS      current
    DESCRIPTION
            "This object uses to restore the value of config params which is needed by  all kinds of operation.  
            The meaning of this  object decides by different operation : 
		For Y.1731 operation, this  object means:
		    -- mdlevel (0 - 7) in 0 BYTE
		    -- Cos (0 - 7) in 1 BYTE
		    -- Svlan (1 - 4094） in 2 - 3 BYTE     
		    -- Cvlan (0 - 4094)  in 4 - 5 BYTE
		    -- RmepId (1 - 8191 ) in 6 - 7 BYTE 
		 For ICMP operation:
			-- Ipaddress in 0 - 3 BYTE
			-- Dscp in 4-5 BYTE
		
			mdlevel :  the maintenance domain level to be used by Y.1731 operation.     
			Cos     :  the Class Of Service field in an frame header of SLA PDU to be used by Y.1731 operation.  
			Svlan   :  the identifier of VLAN for MA to be used by Y.1731 operation.
					   It is an unique identifier for a service instance within a Maintenance Domain specified by rcSlaConfigMDLevel.
		    Cvlan   :  the CVlan user configured in an frame header of SLA PDU to be used by Y.1731 operation.
          			   It could be zero when there is no cunsomer vlan   
          	RmepId	:  the Target Remote MEP Identify to be used by Y.1731 operation.          	
          	Ipaddress : the Target IP Address Field to be used by ICMP operation.	   
          	Dscp: the Differentiated Services Code Point field in header of ip	   
		"
    ::= { rcSlaConfigEntry 19 }   
                     
rcSlaConfigTestPduType 	OBJECT-TYPE 
	SYNTAX      INTEGER {loopback(1), delayMeasurement(2), lossMeasurement(3)}
	MAX-ACCESS  read-create
    STATUS      current
    DESCRIPTION      "This object specifies the type of Y1731 echo/jitter packats.
    				Three types are avalibale:
    				loopBack          (1),
					delayMeasurement  (2),
					lossMeasurement   (3)
					"
    ::= { rcSlaConfigEntry 20 }

  rcSlaConfigDscp     OBJECT-TYPE 
	SYNTAX      Integer32 (0..63 )
    MAX-ACCESS  read-create
    STATUS      current
    DESCRIPTION
          "This object specifies the Differentiated Services Code Point field in header of ip."
    ::= { rcSlaConfigEntry 21 }



rcSlaConfigTc              OBJECT-TYPE 
  	SYNTAX     Integer32 (0..7 )
  	MAX-ACCESS  read-create
      STATUS      current
      DESCRIPTION
              "The TC of the label."    
  	::= { rcSlaConfigEntry 22 } 
 	
rcSlaConfigLspIngressName  OBJECT-TYPE 
  	SYNTAX     OCTET STRING (SIZE (0..32))
  	MAX-ACCESS  read-create
      STATUS      current
      DESCRIPTION
              "The ingress LSP name associated with the ma."    
  	::= { rcSlaConfigEntry 23 } 
  
rcSlaConfigLspEgressName   OBJECT-TYPE 
  	SYNTAX     OCTET STRING (SIZE (0..32))
  	MAX-ACCESS  read-create
      STATUS      current
      DESCRIPTION
              "The egress LSP name associated with the ma."    
  	::= { rcSlaConfigEntry 24 } 

rcSlaConfigVcId            OBJECT-TYPE 
  	SYNTAX     Integer32 (1..2147483647 )
  	MAX-ACCESS  read-create
      STATUS      current
      DESCRIPTION
              "The VC ID associated with the ma."    
  	::= { rcSlaConfigEntry 25 }
  	 	 
rcSlaConfigPwPeerAddrType  OBJECT-TYPE 
    SYNTAX        InetAddressType
  	MAX-ACCESS  read-create
      STATUS      current
      DESCRIPTION
              "Denotes the address type of the peer node.  It should be
              set to 'unknown' if PE/PW maintenance protocol is not used
              and the address is unknown."
     DEFVAL { unkown }   
  	::= { rcSlaConfigEntry 26 }
  	
rcSlaConfigPwPeerAddr      OBJECT-TYPE 
    SYNTAX        InetAddress
  	MAX-ACCESS  read-create
      STATUS      current
      DESCRIPTION
              "This object contains the value of the peer node address
           	  of the PW/PE maintenance protocol entity.  This object
              SHOULD contain a value of all zeroes if not applicable
              (rcCfmMaExAisPwPeerAddrType is 'unknown')."
  	::= { rcSlaConfigEntry 27 }  	

rcSlaConfigSectionPort      OBJECT-TYPE 
    SYNTAX       Unsigned32
  	MAX-ACCESS    read-create
      STATUS      current
      DESCRIPTION
              "The section port associated with the ma."  
  	::= { rcSlaConfigEntry 28 }   
 
rcSlaConfigScheduleSdBadSeconds      OBJECT-TYPE 
    SYNTAX        Integer32 (1..360)
  	MAX-ACCESS    read-create
    STATUS      current
    DESCRIPTION
              "The consecutive total number of sd bad seconds."
    DEFVAL{5}
  	::= { rcSlaConfigEntry 29 }   
  	 	
 rcSlaConfigScheduleSdGoodSeconds      OBJECT-TYPE 
    SYNTAX       Integer32 (1..1800)
  	MAX-ACCESS   read-create
    STATUS      current
    DESCRIPTION
              "The consecutive total number of sd good seconds."  
     DEFVAL{1080}         
  	::= { rcSlaConfigEntry 30 }   	

rcSlaConfigAvailabilityMeasurementInterval OBJECT-TYPE
    SYNTAX      Unsigned32 (1..525600)
    UNITS       "minutes"
    MAX-ACCESS  read-create
    STATUS      current
    DESCRIPTION
       "This object specifies the availability Measurement Interval in 
        minutes.

        A Measurement Interval of 15 minutes is to be supported, other intervals
        can be supported.

        This object can only be written at row creation time and cannot be 
        modified once it has been created.
       "
    REFERENCE
       "[MEF SOAM-PM] R16, R17"
    DEFVAL { 15 }
    ::= { rcSlaConfigEntry 31 }

rcSlaConfigAvailabilityNumConsecutiveMeasPdus OBJECT-TYPE
    SYNTAX      Unsigned32 (1..1000000)
    MAX-ACCESS  read-create
    STATUS      current
    DESCRIPTION
       "This object specifies a configurable number of consecutive
        loss measurement PDUs to be used in evaluating the 
        availability/unavailability status of each availability
        indicator per MEF 10.2.1.  Loss Measurement PDUs (LMMs, CCMs or
        SLMs) are sent regularly with a period defined by
        mefSoamLmCfgMessagePeriod.  Therefore, this object, when 
        multiplied by mefSoamLmCfgMessagePeriod, is equivalent to
        the Availability parameter of 'delta_t' as specified by MEF 10.2.1.

        If the mefSoamLmCfgType is lmLMM or lmCCM, this object defines the
        number of LMM or CCM PDUs transmitted during each 'delta_t' period.
        The Availability flr for a given 'delta_t' can be calculated based
        on the counters in the last LMM/R or CCM during this 'delta_t' and
        the last LMM/R or CCM in the previous 'delta_t'.

        If the mefSoamLmCfgType is lmSLM, this object defines the number
        of SLM PDUs transmitted during each 'delta_t' period.  The
        Availability flr for a given 'delta_t' is calculated based on the
        number of those SLM PDUs that are lost.

        If the mefSoamLmCfgType is lmLMM or lmCCM, the number range of 1
        through 10 must be supported. The number range of 10 through 1000000
        may be supported, but is not mandatory.

        If the mefSoamLmCfgType is lmSLM, the number range of 10 through
        100 must be supported. The number range of 100 through 1000000
        may be supported, but is not mandatory.

        This object can only be written at row creation time and cannot be 
        modified once it has been created.
       "
    REFERENCE
       "[MEF 10.2.1] Section 7.9.8; [MEF SOAM-PM] R80, D33, R81" 
    DEFVAL { 10 }
    ::= { rcSlaConfigEntry 32 }

rcSlaConfigAvailabilityFlrThreshold OBJECT-TYPE
    SYNTAX      Unsigned32 (0..100000)
    UNITS       "milli-percent"
    MAX-ACCESS  read-create
    STATUS      current
    DESCRIPTION
       "This object specifies a configurable availability threshold to be
        used in evaluating the availability/unavailability status of an
        availability indicator per MEF 10.2.1. The availability threshold range
        of 0.00 (0) through 1.00 (100000) is supported. This parameter is 
        equivalent to the Availability parameter of 'C' as specified by 
        MEF 10.2.1.

        Units are in milli-percent, where 1 indicates 0.001 percent.

        This object can only be written at row creation time and cannot be 
        modified once it has been created.
       "
    REFERENCE
       "[MEF 10.2.1] Section 7.9.8; [MEF SOAM-PM] R81, R82, D34"
    DEFVAL { 50000 }
    ::= { rcSlaConfigEntry 33 }

rcSlaConfigAvailabilityNumConsecutiveIntervals OBJECT-TYPE
    SYNTAX      Unsigned32 (1..1000)
    MAX-ACCESS  read-create
    STATUS      current
    DESCRIPTION
       "This object specifies a configurable number of consecutive
        availability indicators to be used to determine a change in the
        availability status as indicated by MEF 10.2.1. This parameter is 
        equivalent to the Availability parameter of 'n' as specified
        by MEF 10.2.1.

        The number range of 1 through 10 must be supported. The number range
        of 1 through 1000 may be supported, but is not mandatory.

        This object can only be written at row creation time and cannot be 
        modified once it has been created.
       "
    REFERENCE
       "[MEF 10.2.1] Section 7.9.8; [MEF SOAM-PM] R80, D33" 
    DEFVAL { 10 }
    ::= { rcSlaConfigEntry 34 }

rcSlaConfigAvailabilityNumConsecutiveHighFlr OBJECT-TYPE
    SYNTAX      Unsigned32 (1..1000)
    MAX-ACCESS  read-create
    STATUS      current
    DESCRIPTION
       "This object specifies a configurable number of consecutive
        availability indicators to be used for assessing CHLI.  This
        parameter is equivalent to the Resilency parameter of 'p' as
        specified by MEF 10.2.1.

        rcSlaConfigAvailabilityNumConsecutiveHighFlr must be strictly less than 
        rcSlaConfigAvailabilityNumConsecutiveIntervals. If not, the count of high
        loss intervals over time, mefSoamLmAvailabilityHighLoss, and the count 
        of consecutive high loss levels, mefSoamLmAvailabilityConsecutiveHighLoss,
        is disabled.

        The number range of 1 through 10 must be supported. The number range
        of 1 through 1000 may be supported, but is not mandatory.

        This object can only be written at row creation time and cannot be 
        modified once it has been created.
       "
    REFERENCE
       "[MEF 10.2.1] Section 7.9.8; [MEF SOAM-PM] R86, D35, D36" 
    DEFVAL { 5 }
    ::= { rcSlaConfigEntry 35 }

    
--------------------------------OperScheduleGroup---------------------------               
--rcSlaScheduleGroup
	-- rcSlaLatestTable
		--rcSlaLatestEntry
			--rcSlaLatestTXNum 
			--rcSlaLatestRTTNum
	    	--rcSlaLatestRTTSum
	    	--rcSlaLatestRTTSumJitter
	    	--rcSlaLatestRTTSum2    
	    	--rcSlaLatestRTTMin                    
	    	--rcSlaLatestRTTMax 
	    	--rcSlaLatestRTTNumSD	                    
	       	--rcSlaLatestRTTSumSD                  
	    	--rcSlaLatestRTTSumJitterSD             
 	    	--rcSlaLatestRTTSum2SD                 
	    	--rcSlaLatestRTTMinSD                  
	    	--rcSlaLatestRTTMaxSD  
	    	--rcSlaLatestRTTNumDS                  
	    	--rcSlaLatestRTTSumDS                  
	    	--rcSlaLatestRTTSumJitterDS            
	    	--rcSlaLatestRTTSum2DS                 
	    	--rcSlaLatestRTTMinDS                  
	    	--rcSlaLatestRTTMaxDS   
	    	
	-- rcSlaStatisticTable
		--rcSlaStatisticEntry
			--rcSlaStatisticStartTime   
			--rcSlaStatisticScheduleLife         
        	--rcSlaStatisticSchedulePeriod 		     
	    	--rcSlaStatisticTXNum 
	    	--rcSlaStatisticRTTNum            	 
	    	--rcSlaStatisticRTTSums              	 
	    	--rcSlaStatisticRTTSumJitter   		                
	    	--rcSlaStatisticRTTSum2L               
	    	--rcSlaStatisticRTTSum2H               
	    	--rcSlaStatisticRTTMin                 
	    	--rcSlaStatisticRTTMax  
	    	--rcSlaStatisticRTTNumSD                   
	    	--rcSlaStatisticRTTSumsSD              
	    	--rcSlaStatisticRTTSumJitterSD         
	       	--rcSlaStatisticRTTSum2LSD             
	    	--rcSlaStatisticRTTSum2HSD             
	    	--rcSlaStatisticRTTMinSD                
	    	--rcSlaStatisticRTTMaxSD 
	    	--rcSlaStatisticRTTNumDS                       
	    	--rcSlaStatisticRTTSumsDS              
	    	--rcSlaStatisticRTTSumJitterDS         
	    	--rcSlaStatisticRTTSum2LDS             
	    	--rcSlaStatisticRTTSum2HDS             
	    	--rcSlaStatisticRTTMinDS               
	    	--rcSlaStatisticRTTMaxDS   
	    	
	-- rcSlaPktlmLatestTable
		--rcSlaPktlmLatestEntry
			--rcSlaLatestPktlmTXNum 
			--rcSlaLatestPktlmNum
	    	--rcSlaLatestPktlmSum
	    	--rcSlaLatestPktlmMin
	    	--rcSlaLatestPktlmMax
	    	--rcSlaLatestPktlmNumSD
	       	--rcSlaLatestPktlmSumSD
	    	--rcSlaLatestPktlmMinSD
	    	--rcSlaLatestPktlmMaxSD
	    	--rcSlaLatestPktlmNumDS
	    	--rcSlaLatestPktlmSumDS
	    	--rcSlaLatestPktlmMinDS
	    	--rcSlaLatestPktlmMaxDS
	    	            
	--rcSlaPktlmStatisticTable
		--rcSlaPktlmStatisticEntry
			--rcSlaStatisticPktlmStartTime
			--rcSlaStatisticPktlmScheduleLife
			--rcSlaStatisticPktlmSchedulePeriod
			--rcSlaStatisticPktlmTXNum
			--rcSlaStatisticPktlmNum
			--rcSlaStatisticPktlmSums
			--rcSlaStatisticPktlmMin
			--rcSlaStatisticPktlmMax
			--rcSlaStatistiPktlmNumSD
			--rcSlaStatisticPktlmSumsSD
			--rcSlaStatisticPktlmMinSD
			--rcSlaStatisticPktlmMaxSD
			--rcSlaStatisticPktlmNumDS
			--rcSlaStatisticPktlmSumsDS
			--rcSlaStatisticPktlmMinDS
			--rcSlaStatisticPktlmMaxDS
			--rcSlaStatisticPktSdBadSeconds
			--rcSlaStatisticPktSdGoodSeconds
            --rcSlaStatisticPktSdBadSecondsSD
			--rcSlaStatisticPktSdGoodSecondsSD
			--rcSlaStatisticPktSdBadSecondsDS
			--rcSlaStatisticPktSdGoodSecondsDS   
			--rcSlaStatisticPktlmLossRateSD			
			--rcSlaStatisticPktlmLossRateDS






--rcSlaLatestTable

rcSlaLatestTable  OBJECT-TYPE
    SYNTAX      SEQUENCE OF RcSlaLatestEntry
    MAX-ACCESS  not-accessible
    STATUS      current
    DESCRIPTION
        "This table contains the statistics calculated for the 
        latest sent frames."
    ::= { rcSlaScheduleGroup 1 }

rcSlaLatestEntry   OBJECT-TYPE
    SYNTAX      RcSlaLatestEntry
    MAX-ACCESS  not-accessible
    STATUS      current
    DESCRIPTION
        "A collection of objects that record the latest operation.

        An entry is created only when the operation has been set and scheduled.      
        The entry will start to collect data when rcSlaConfigScheduleStatus 
        is in 'active' state.  The entry will be removed when the 
        rcSlaConfigScheduleStatus is changed to 'complete' state. "
	INDEX        { rcSlaConfigOperId }    
    ::={ rcSlaLatestTable 1 }     
    
RcSlaLatestEntry ::= SEQUENCE {
        rcSlaLatestTXNum   					 Gauge32,  
        rcSlaLatestRTTNum               	 Gauge32,
	    rcSlaLatestRTTSum   			     Gauge32,
	    rcSlaLatestRTTSumJitter   		     Gauge32,  
	    rcSlaLatestRTTSum2                   Gauge32,
	    rcSlaLatestRTTMin                    Gauge32,
	    rcSlaLatestRTTMax                    Gauge32, 
	    rcSlaLatestRTTNumSD                  Gauge32,
	    rcSlaLatestRTTSumSD                  Gauge32,
	    rcSlaLatestRTTSumJitterSD            Gauge32, 
 	    rcSlaLatestRTTSum2SD                 Gauge32,
	    rcSlaLatestRTTMinSD                  Gauge32,
	    rcSlaLatestRTTMaxSD                  Gauge32,
	    rcSlaLatestRTTNumDS                  Gauge32,
	    rcSlaLatestRTTSumDS                  Gauge32,
	    rcSlaLatestRTTSumJitterDS            Gauge32,
	    rcSlaLatestRTTSum2DS                 Gauge32,
	    rcSlaLatestRTTMinDS                  Gauge32,
	    rcSlaLatestRTTMaxDS                  Gauge32
}

rcSlaLatestTXNum       OBJECT-TYPE 
	SYNTAX      Gauge32
    MAX-ACCESS  read-only
    STATUS      current
    DESCRIPTION
            "This object specifies the number of RTT's probe sent in latest test."
    ::= { rcSlaLatestEntry 1 }    
    
rcSlaLatestRTTNum       OBJECT-TYPE 
	SYNTAX      Gauge32
    MAX-ACCESS  read-only
    STATUS      current
    DESCRIPTION
            "This object specifies the number of RTT's probe that were successfully measured in latest test."
    ::= { rcSlaLatestEntry 2 } 
    
rcSlaLatestRTTSum       OBJECT-TYPE 
	SYNTAX      Gauge32
    MAX-ACCESS  read-only
    STATUS      current
    DESCRIPTION
            "This object specifies the sum of RTT's delay that were successfully measured in latest test."
    ::= { rcSlaLatestEntry 3 }
    
rcSlaLatestRTTSumJitter       OBJECT-TYPE 
	SYNTAX      Gauge32
    MAX-ACCESS  read-only
    STATUS      current
    DESCRIPTION
            "This object specifies the number of RTT's jitter that were successfully measured in latest test.  
            	This object is applicable to 'Jitter' operation only."
    ::= { rcSlaLatestEntry 4 }

rcSlaLatestRTTSum2       OBJECT-TYPE 
	SYNTAX      Gauge32
    MAX-ACCESS  read-only
    STATUS      current
    DESCRIPTION
            "This object specifies the sum of squares of RTT's delay that are successfully measured in latest test. 
            	This object is applicable to 'Jitter' operation only."
    ::= { rcSlaLatestEntry 5 }

rcSlaLatestRTTMin       OBJECT-TYPE 
	SYNTAX      Gauge32
    MAX-ACCESS  read-only
    STATUS      current
    DESCRIPTION
            "This object specifies the minimum of RTT's that were successfully measured in latest test. 
            	This object is applicable to 'Jitter' operation only."
    ::= { rcSlaLatestEntry 6 }                    

rcSlaLatestRTTMax       OBJECT-TYPE 
	SYNTAX      Gauge32
    MAX-ACCESS  read-only
    STATUS      current
    DESCRIPTION
            "This object specifies the maximum of RTT's that were successfully measured in latest test. 
            	This object is applicable to 'Jitter' operation only."
    ::= { rcSlaLatestEntry 7 }                    
 
rcSlaLatestRTTNumSD       OBJECT-TYPE 
	SYNTAX      Gauge32
    MAX-ACCESS  read-only
    STATUS      current
    DESCRIPTION
            "This object specifies the number of RTT's probe 
            	that were successfully measured from source to destination in latest test."
    ::= { rcSlaLatestEntry 8 }        

rcSlaLatestRTTSumSD       OBJECT-TYPE 
	SYNTAX      Gauge32
    MAX-ACCESS  read-only
    STATUS      current
    DESCRIPTION
            "This object specifies the sum of RTT's delay 
            	that were successfully measured from source to destination in latest test."
    ::= { rcSlaLatestEntry 9 }                    

rcSlaLatestRTTSumJitterSD       OBJECT-TYPE 
	SYNTAX      Gauge32
    MAX-ACCESS  read-only
    STATUS      current
    DESCRIPTION
            "This object specifies the number of RTT's jitter that were successfully measured from source to destination in latest test. 
            	This object is applicable to 'Jitter' operation only."
    ::= { rcSlaLatestEntry 10 }                    

rcSlaLatestRTTSum2SD       OBJECT-TYPE 
	SYNTAX      Gauge32
    MAX-ACCESS  read-only
    STATUS      current
    DESCRIPTION
            "This object specifies the sum of squares of RTT's delay that are successfully measured from source to destination in latest test. 
            	This object is applicable to 'Jitter' operation only."
    ::= { rcSlaLatestEntry 11 }                    

rcSlaLatestRTTMinSD       OBJECT-TYPE 
	SYNTAX      Gauge32
    MAX-ACCESS  read-only
    STATUS      current
    DESCRIPTION
            "This object specifies the minimum of RTT's that were successfully measured from source to destination in latest test. 
            	This object is applicable to 'Jitter' operation only."
    ::= { rcSlaLatestEntry 12 }                    

rcSlaLatestRTTMaxSD       OBJECT-TYPE 
	SYNTAX      Gauge32
    MAX-ACCESS  read-only
    STATUS      current
    DESCRIPTION
            "This object specifies the maximum of RTT's that were successfully measured from source to destination in latest test. 
            	This object is applicable to 'Jitter' operation only."
    ::= { rcSlaLatestEntry 13 }              
                                     
rcSlaLatestRTTNumDS       OBJECT-TYPE 
	SYNTAX      Gauge32
    MAX-ACCESS  read-only
    STATUS      current
    DESCRIPTION
            "This object specifies the number of RTT's probe 
            	that were successfully measured from destination to source in latest test."
    ::= { rcSlaLatestEntry 14 }                                       

rcSlaLatestRTTSumDS       OBJECT-TYPE 
	SYNTAX      Gauge32
    MAX-ACCESS  read-only
    STATUS      current
    DESCRIPTION
            "This object specifies the sum of RTT's delay 
            	that were successfully measured from destination to source in latest test."
    ::= { rcSlaLatestEntry 15 }                    

rcSlaLatestRTTSumJitterDS       OBJECT-TYPE 
	SYNTAX      Gauge32
    MAX-ACCESS  read-only
    STATUS      current
    DESCRIPTION
            "This object specifies the number of RTT's jitter that were successfully measured from destination to source in latest test. 
            	This object is applicable to 'Jitter' operation only."
    ::= { rcSlaLatestEntry 16 }                    

rcSlaLatestRTTSum2DS       OBJECT-TYPE 
	SYNTAX      Gauge32
    MAX-ACCESS  read-only
    STATUS      current
    DESCRIPTION
            "This object specifies the sum of squares of RTT's delay that are successfully measured from destination to source in latest test. 
            	This object is applicable to 'Jitter' operation only."
    ::= { rcSlaLatestEntry 17 }                    

rcSlaLatestRTTMinDS       OBJECT-TYPE 
	SYNTAX      Gauge32
    MAX-ACCESS  read-only
    STATUS      current
    DESCRIPTION
            "This object specifies the minimum of RTT's that were successfully measured from destination to source in latest test. 
            	This object is applicable to 'Jitter' operation only."
    ::= { rcSlaLatestEntry 18 }                    

rcSlaLatestRTTMaxDS       OBJECT-TYPE 
	SYNTAX      Gauge32
    MAX-ACCESS  read-only
    STATUS      current
    DESCRIPTION
            "This object specifies the maximum of RTT's that were successfully measured from destination to source in latest test. 
            	This object is applicable to 'Jitter' operation only."
    ::= { rcSlaLatestEntry 19 }                    


-- rcSlaStatisticTable
--  

rcSlaStatisticTable  OBJECT-TYPE
    SYNTAX      SEQUENCE OF RcSlaStatisticEntry
    MAX-ACCESS  not-accessible
    STATUS      current
    DESCRIPTION
        "The 'SlaStatistic' statistics table contains summarized
    information of the results for a conceptual control row."
    ::= { rcSlaScheduleGroup 2 }

rcSlaStatisticEntry   OBJECT-TYPE
    SYNTAX      RcSlaStatisticEntry
    MAX-ACCESS  not-accessible
    STATUS      current
    DESCRIPTION
        "This entry contains the objects which accumulate the
    results of a series of 'Jitter' operations over a time 
    period stored in rcSlaConfigScheduleLife. 
        An entry is created only when the operation has been set and scheduled.      
        The entry will start to collect data when rcSlaConfigScheduleStatus 
    is in 'active' state.  The entry will stop to collect data when the 
    rcSlaConfigScheduleStatus is changed to 'complete' state.
         "
	INDEX        { rcSlaConfigOperId,
	               rcSlaStatisticStartTime
	             }    
    ::={ rcSlaStatisticTable 1 }     
    
    RcSlaStatisticEntry ::= SEQUENCE {
        rcSlaStatisticStartTime   		     TimeStamp,  
        rcSlaStatisticScheduleLife           Unsigned32,
        rcSlaStatisticSchedulePeriod         Unsigned32,
	    rcSlaStatisticTXNum             	 Counter32,
	    rcSlaStatisticRTTNum              	 Counter32,
	    rcSlaStatisticRTTSums              	 Counter32,
	    rcSlaStatisticRTTSumJitter   		 Counter32,               
	    rcSlaStatisticRTTSum2L               Counter32,
	    rcSlaStatisticRTTSum2H               Counter32,
	    rcSlaStatisticRTTMin                 Gauge32,
	    rcSlaStatisticRTTMax                 Gauge32,  
	    rcSlaStatisticRTTNumSD               Counter32,
	    rcSlaStatisticRTTSumsSD              Counter32,
	    rcSlaStatisticRTTSumJitterSD         Counter32,
	    rcSlaStatisticRTTSum2LSD             Counter32,
	    rcSlaStatisticRTTSum2HSD             Counter32,
	    rcSlaStatisticRTTMinSD               Gauge32, 
	    rcSlaStatisticRTTMaxSD               Gauge32, 
	    rcSlaStatisticRTTNumDS               Counter32,
	    rcSlaStatisticRTTSumsDS              Counter32,
	    rcSlaStatisticRTTSumJitterDS         Counter32,
	    rcSlaStatisticRTTSum2LDS             Counter32,
	    rcSlaStatisticRTTSum2HDS             Counter32,
	    rcSlaStatisticRTTMinDS               Gauge32,
	    rcSlaStatisticRTTMaxDS               Gauge32
	 
}


rcSlaStatisticStartTime       OBJECT-TYPE 
	SYNTAX      TimeStamp
    MAX-ACCESS  not-accessible
    STATUS      current
    DESCRIPTION
            "This object specifies the time when the operation starts to be scheduled."   
            
    ::= { rcSlaStatisticEntry 1 }      
     
rcSlaStatisticScheduleLife       OBJECT-TYPE 
	SYNTAX      Unsigned32
    MAX-ACCESS  read-only
    STATUS      current
    DESCRIPTION
            "This object specifies the time duration over the whole schedule process. "
    ::= { rcSlaStatisticEntry 2 }  
    
rcSlaStatisticSchedulePeriod       OBJECT-TYPE 
	SYNTAX      Unsigned32
    MAX-ACCESS  read-only
    STATUS      current
    DESCRIPTION
            "This object specifies the number of RTT's probe that were successfully measured in schedule."
    ::= { rcSlaStatisticEntry 3 }   
      
rcSlaStatisticTXNum       OBJECT-TYPE 
	SYNTAX      Counter32
    MAX-ACCESS  read-only
    STATUS      current
    DESCRIPTION
            "This object specifies the duration between two SLA test 
            	which includes all of probes schedule process in test. "
    ::= { rcSlaStatisticEntry 4 }    
    
rcSlaStatisticRTTNum       OBJECT-TYPE 
	SYNTAX      Counter32
    MAX-ACCESS  read-only
    STATUS      current
    DESCRIPTION
            "This object specifies the duration between two SLA test 
            	which includes all successful probes schedule process in test. 
           	Take above example, if all of the rcSlaConfigSchedulePeriod of three operations are set to 60, 
            	then the start time of each test of SLA operation like:
			start time:   T+0 --------  T+9 ----------  T+19-----
           		operation1  operation2    operation3 
			start again:  T+60--------  T+69 ----------  T+79--
           		operation1  operation2    operation3   
			start 3rd time:T+120-------- T+129 ----------T+139--
         		operation1  operation2    operation3"
    ::= { rcSlaStatisticEntry 5 }                   

rcSlaStatisticRTTSums        OBJECT-TYPE 
	SYNTAX      Counter32
    MAX-ACCESS  read-only
    STATUS      current
    DESCRIPTION
            "This object specifies the sum of RTT's delay that were successfully measured in schedule."
    ::= { rcSlaStatisticEntry 6 }        
    
rcSlaStatisticRTTSumJitter       OBJECT-TYPE 
	SYNTAX      Counter32
    MAX-ACCESS  read-only
    STATUS      current
    DESCRIPTION
            "This object specifies the number of RTT's jitter that were successfully measured in Schedule.  
            	This object is applicable to 'Jitter' operation only."
    ::= { rcSlaStatisticEntry 7 }

rcSlaStatisticRTTSum2L       OBJECT-TYPE 
	SYNTAX      Counter32
    MAX-ACCESS  read-only
    STATUS      current
    DESCRIPTION
            "This object specifies the sum of squares of RTT's delay that are successfully measured in Schedule.
            	 This object is applicable to 'Jitter' operation only. (low order 32 bits)"
    ::= { rcSlaStatisticEntry 8 }

rcSlaStatisticRTTSum2H       OBJECT-TYPE 
	SYNTAX      Counter32
    MAX-ACCESS  read-only
    STATUS      current
    DESCRIPTION
            "This object specifies the sum of squares of RTT's delay that are successfully measured in Schedule. 
            	This object is applicable to 'Jitter' operation only. (high order 32 bits)"
    ::= { rcSlaStatisticEntry 9 }                    

rcSlaStatisticRTTMin       OBJECT-TYPE 
	SYNTAX      Gauge32
    MAX-ACCESS  read-only
    STATUS      current
    DESCRIPTION
            "This object specifies the minimum of RTT's that were successfully measured in Schedule. 
            	This object is applicable to 'Jitter' operation only."
    ::= { rcSlaStatisticEntry 10 }                    

rcSlaStatisticRTTMax       OBJECT-TYPE 
	SYNTAX      Gauge32
    MAX-ACCESS  read-only
    STATUS      current
    DESCRIPTION
            "This object specifies the maximum of RTT's that were successfully measured in Schedule. 
            	This object is applicable to 'Jitter' operation only."
    ::= { rcSlaStatisticEntry 11 }                    
                  
rcSlaStatisticRTTNumSD       OBJECT-TYPE 
	SYNTAX      Counter32
    MAX-ACCESS  read-only
    STATUS      current
    DESCRIPTION
            "This object specifies the number of RTT's probe 
            	that were successfully measured from source to destination in Schedule."
    ::= { rcSlaStatisticEntry 12 }  
    
rcSlaStatisticRTTSumsSD       OBJECT-TYPE 
	SYNTAX      Counter32
    MAX-ACCESS  read-only
    STATUS      current
    DESCRIPTION
            "This object specifies the sum of RTT's delay 
            	that were successfully measured from source to destination in Schedule."
    ::= { rcSlaStatisticEntry 13 }                    

rcSlaStatisticRTTSumJitterSD       OBJECT-TYPE 
	SYNTAX      Counter32
    MAX-ACCESS  read-only
    STATUS      current
    DESCRIPTION
            "This object specifies the number of RTT's jitter that were successfully measured from source to destination in Schedule.
            	This object is applicable to 'Jitter' operation only."
    ::= { rcSlaStatisticEntry 14 }                    

rcSlaStatisticRTTSum2LSD       OBJECT-TYPE 
	SYNTAX      Counter32
    MAX-ACCESS  read-only
    STATUS      current
    DESCRIPTION
            "This object specifies the sum of squares of RTT's delay that are successfully measured from source to destination in Schedule. 
            	This object is applicable to 'Jitter' operation only. (low order 32 bits)"
    ::= { rcSlaStatisticEntry 15 }                    

rcSlaStatisticRTTSum2HSD       OBJECT-TYPE 
	SYNTAX      Counter32
    MAX-ACCESS  read-only
    STATUS      current
    DESCRIPTION
            "This object specifies the sum of squares of RTT's delay that are successfully measured from source to destination in Schedule. 
            	This object is applicable to 'Jitter' operation only. (high order 32 bits)"
    ::= { rcSlaStatisticEntry 16 }                    

rcSlaStatisticRTTMinSD       OBJECT-TYPE 
	SYNTAX      Gauge32
    MAX-ACCESS  read-only
    STATUS      current
    DESCRIPTION
            "This object specifies the minimum of RTT's that were successfully measured from source to destination in Schedule. 
            	This object is applicable to 'Jitter' operation only."
    ::= { rcSlaStatisticEntry 17 }                    

rcSlaStatisticRTTMaxSD       OBJECT-TYPE 
	SYNTAX      Gauge32
    MAX-ACCESS  read-only
    STATUS      current
    DESCRIPTION
            "This object specifies the maximum of RTT's that were successfully measured from source to destination in Schedule. 
            	This object is applicable to 'Jitter' operation only."
    ::= { rcSlaStatisticEntry 18 }    

rcSlaStatisticRTTNumDS       OBJECT-TYPE 
	SYNTAX      Counter32
    MAX-ACCESS  read-only
    STATUS      current
    DESCRIPTION
            "This object specifies the number of RTT's probe 
            	that were successfully measured from destination to source in Schedule."
    ::= { rcSlaStatisticEntry 19 } 
                    

rcSlaStatisticRTTSumsDS       OBJECT-TYPE 
	SYNTAX      Counter32
    MAX-ACCESS  read-only
    STATUS      current
    DESCRIPTION
            "This object specifies the sum of RTT's delay 
            that were successfully measured from destination to source in Schedule."
    ::= { rcSlaStatisticEntry 20 }                    

rcSlaStatisticRTTSumJitterDS       OBJECT-TYPE 
	SYNTAX      Counter32
    MAX-ACCESS  read-only
    STATUS      current
    DESCRIPTION
            "This object specifies the number of RTT's jitter that were successfully measured from destination to source in Schedule.  
            	This object is applicable to 'Jitter' operation only."
    ::= { rcSlaStatisticEntry 21 }                    

rcSlaStatisticRTTSum2LDS       OBJECT-TYPE 
	SYNTAX      Counter32
    MAX-ACCESS  read-only
    STATUS      current
    DESCRIPTION
            "This object specifies the sum of squares of RTT's delay that are successfully measured from destination to source in Schedule. 
            	This object is applicable to 'Jitter' operation only. (low order 32 bits)"
    ::= { rcSlaStatisticEntry 22 }  
    

rcSlaStatisticRTTSum2HDS       OBJECT-TYPE 
	SYNTAX      Counter32
    MAX-ACCESS  read-only
    STATUS      current
    DESCRIPTION
            "This object specifies the sum of squares of RTT's delay that are successfully measured from destination to source in Schedule. 
            	This object is applicable to 'Jitter' operation only. (hige order 32 bits)"
    ::= { rcSlaStatisticEntry 23 }  
    

rcSlaStatisticRTTMinDS       OBJECT-TYPE 
	SYNTAX      Gauge32
    MAX-ACCESS  read-only
    STATUS      current
    DESCRIPTION
            "This object specifies the minimum of RTT's that were successfully measured from destination to source in Schedule. 
            	This object is applicable to 'Jitter' operation only. "
    ::= { rcSlaStatisticEntry 24 }  
    

rcSlaStatisticRTTMaxDS       OBJECT-TYPE 
	SYNTAX      Gauge32
    MAX-ACCESS  read-only
    STATUS      current
    DESCRIPTION
            "This object specifies the maximum of RTT's that were successfully measured from destination to source in Schedule. 
            	This object is applicable to 'Jitter' operation only."
    ::= { rcSlaStatisticEntry 25 }        
-- rcSlaPktlmLatestTable
--      
rcSlaPktlmLatestTable  OBJECT-TYPE
    SYNTAX      SEQUENCE OF RcSlaPktlmLatestEntry
    MAX-ACCESS  not-accessible
    STATUS      current
    DESCRIPTION
        "This table contains the statistics calculated for the 
        latest sent frames."
    ::= { rcSlaScheduleGroup 3 } 
 
 rcSlaPktlmLatestEntry   OBJECT-TYPE
    SYNTAX      RcSlaPktlmLatestEntry
    MAX-ACCESS  not-accessible
    STATUS      current
    DESCRIPTION
        "A collection of objects that record the latest operation.

        An entry is created only when the operation has been set and scheduled.
        The entry will start to collect data when rcSlaConfigScheduleStatus 
        is in 'active' state.  The entry will be removed when the 
        rcSlaConfigScheduleStatus is changed to 'complete' state. "
	INDEX        { rcSlaConfigOperId }
    ::={ rcSlaPktlmLatestTable 1 }

RcSlaPktlmLatestEntry ::= SEQUENCE {
	    rcSlaLatestPktlmTXNum                  Gauge32,
	    rcSlaLatestPktlmNum                    Gauge32,
	    rcSlaLatestPktlmSum                    Gauge32,
	    rcSlaLatestPktlmMin                    Gauge32,
	    rcSlaLatestPktlmMax                    Gauge32,
	    rcSlaLatestPktlmNumSD                  Gauge32,
	    rcSlaLatestPktlmSumSD                  Gauge32,
	    rcSlaLatestPktlmMinSD                  Gauge32,
	    rcSlaLatestPktlmMaxSD                  Gauge32,
	    rcSlaLatestPktlmNumDS                  Gauge32,
	    rcSlaLatestPktlmSumDS                  Gauge32,
	    rcSlaLatestPktlmMinDS                  Gauge32,
	    rcSlaLatestPktlmMaxDS                  Gauge32,
        rcSlaLatestPktlmMaxDS                  Gauge32,
        rcSlaLatestPktlmLossRateSD             Integer32 (0..10000),
        rcSlaLatestPktlmLossRateDS             Integer32 (0..10000)

}

rcSlaLatestPktlmTXNum       OBJECT-TYPE
	SYNTAX      Gauge32
    MAX-ACCESS  read-only
    STATUS      current
    DESCRIPTION
            "This object specifies the number of packet loss measurement sent in latest test."
    ::= { rcSlaPktlmLatestEntry 1 }

rcSlaLatestPktlmNum       OBJECT-TYPE
	SYNTAX      Gauge32
    MAX-ACCESS  read-only
    STATUS      current
    DESCRIPTION
            "This object specifies the number of packet loss measurement probe that were successfully measured in latest test."
    ::= { rcSlaPktlmLatestEntry 2 }

rcSlaLatestPktlmSum       OBJECT-TYPE
	SYNTAX      Gauge32
    MAX-ACCESS  read-only
    STATUS      current
    DESCRIPTION
            "This object specifies the sum of packet loss measurement that were successfully measured in latest test."
    ::= { rcSlaPktlmLatestEntry 3 }
    
rcSlaLatestPktlmMin       OBJECT-TYPE
	SYNTAX      Gauge32
    MAX-ACCESS  read-only
    STATUS      current
    DESCRIPTION
            "This object specifies the minimum of packet loss measurement that were successfully measured in latest test."
    ::= { rcSlaPktlmLatestEntry 4 }

rcSlaLatestPktlmMax       OBJECT-TYPE
	SYNTAX      Gauge32
    MAX-ACCESS  read-only
    STATUS      current
    DESCRIPTION
            "This object specifies the maximum of packet loss measurement that were successfully measured in latest test."
    ::= { rcSlaPktlmLatestEntry 5 }

rcSlaLatestPktlmNumSD       OBJECT-TYPE
	SYNTAX      Gauge32
    MAX-ACCESS  read-only
    STATUS      current
    DESCRIPTION
            "This object specifies the number of packet loss measurement that were successfully measured from source to destination in latest test."
    ::= { rcSlaPktlmLatestEntry 6 }

rcSlaLatestPktlmSumSD       OBJECT-TYPE
	SYNTAX      Gauge32
    MAX-ACCESS  read-only
    STATUS      current
    DESCRIPTION
            "This object specifies the sum of packet loss measurement that were successfully measured from source to destination in latest test."
    ::= { rcSlaPktlmLatestEntry 7 }

rcSlaLatestPktlmMinSD       OBJECT-TYPE
	SYNTAX      Gauge32
    MAX-ACCESS  read-only
    STATUS      current
    DESCRIPTION
            "This object specifies the minimum of packet loss measurement that were successfully measured from source to destination in latest test."
    ::= { rcSlaPktlmLatestEntry 8 }

rcSlaLatestPktlmMaxSD       OBJECT-TYPE
	SYNTAX      Gauge32
    MAX-ACCESS  read-only
    STATUS      current
    DESCRIPTION
            "This object specifies the maximum of packet loss measurement that were successfully measured from source to destination in latest test."
    ::= { rcSlaPktlmLatestEntry 9 }

rcSlaLatestPktlmNumDS       OBJECT-TYPE
	SYNTAX      Gauge32
    MAX-ACCESS  read-only
    STATUS      current
    DESCRIPTION
            "This object specifies the number of packet loss measurement that were successfully measured from destination to source in latest test."
    ::= { rcSlaPktlmLatestEntry 10 }

rcSlaLatestPktlmSumDS       OBJECT-TYPE
	SYNTAX      Gauge32
    MAX-ACCESS  read-only
    STATUS      current
    DESCRIPTION
            "This object specifies the sum of packet loss measurement that were successfully measured from destination to source in latest test."
    ::= { rcSlaPktlmLatestEntry 11 }

rcSlaLatestPktlmMinDS       OBJECT-TYPE
	SYNTAX      Gauge32
    MAX-ACCESS  read-only
    STATUS      current
    DESCRIPTION
            "This object specifies the minimum of packet loss measurement that were successfully measured from destination to source in latest test."
    ::= { rcSlaPktlmLatestEntry 12 }

rcSlaLatestPktlmMaxDS       OBJECT-TYPE
	SYNTAX      Gauge32
    MAX-ACCESS  read-only
    STATUS      current
    DESCRIPTION
            "This object specifies the maximum of packet loss measurement that were successfully measured from destination to source in latest test."
    ::= { rcSlaPktlmLatestEntry 13 }  
 rcSlaLatestPktlmLossRateSD      OBJECT-TYPE 
    SYNTAX        Integer32 (0..10000)
    MAX-ACCESS    read-only
    STATUS      current
    DESCRIPTION
              "The packet loss rate of loss measure operation in the direction of SD."
    DEFVAL{0}
    ::= { rcSlaPktlmLatestEntry 14 }   
        
 rcSlaLatestPktlmLossRateDS      OBJECT-TYPE 
    SYNTAX       Integer32 (0..10000)
    MAX-ACCESS    read-only
    STATUS      current
    DESCRIPTION
              "The packet loss rate of loss measure operation in the direction of DS."  
     DEFVAL{0}         
    ::= { rcSlaPktlmLatestEntry 15 } 

-- rcSlaPktlmStatisticTable
--  

rcSlaPktlmStatisticTable  OBJECT-TYPE
    SYNTAX      SEQUENCE OF RcSlaPktlmStatisticEntry
    MAX-ACCESS  not-accessible
    STATUS      current
    DESCRIPTION
        "The 'SlaPktlmStatistic' statistics table contains summarized
    information of the results for a conceptual control row."
    ::= { rcSlaScheduleGroup 4 }

rcSlaPktlmStatisticEntry   OBJECT-TYPE
    SYNTAX      RcSlaPktlmStatisticEntry
    MAX-ACCESS  not-accessible
    STATUS      current
    DESCRIPTION
        "An entry is created only when the operation has been set and scheduled.      
        The entry will start to collect data when rcSlaConfigScheduleStatus 
    is in 'active' state.  The entry will stop to collect data when the 
    rcSlaConfigScheduleStatus is changed to 'complete' state.
         "
	INDEX        { rcSlaConfigOperId,
	               rcSlaStatisticPktlmStartTime
	             }    
    ::={ rcSlaPktlmStatisticTable 1 }     
    
    RcSlaPktlmStatisticEntry ::= SEQUENCE {
        rcSlaStatisticPktlmStartTime   		   TimeStamp,  
        rcSlaStatisticPktlmScheduleLife        Unsigned32,
        rcSlaStatisticPktlmSchedulePeriod      Unsigned32,
        rcSlaStatisticPktlmTXNum               Counter32,
        rcSlaStatisticPktlmNum                 Counter32,
        rcSlaStatisticPktlmSums                Counter32,
        rcSlaStatisticPktlmMin                 Gauge32,
        rcSlaStatisticPktlmMax                 Gauge32,  
        rcSlaStatistiPktlmNumSD                Counter32,
        rcSlaStatisticPktlmSumsSD              Counter32,
        rcSlaStatisticPktlmMinSD               Gauge32, 
        rcSlaStatisticPktlmMaxSD               Gauge32, 
        rcSlaStatisticPktlmNumDS               Counter32,
        rcSlaStatisticPktlmSumsDS              Counter32,
        rcSlaStatisticPktlmMinDS               Gauge32,
        rcSlaStatisticPktlmMaxDS               Gauge32, 
        rcSlaStatisticPktSdBadSeconds          Integer32 (0..360),
        rcSlaStatisticPktSdGoodSeconds         Integer32 (0..1800),
        rcSlaStatisticPktSdBadSecondsSD        Integer32 (0..360),
        rcSlaStatisticPktSdGoodSecondsSD       Integer32 (0..1800),
        rcSlaStatisticPktSdBadSecondsDS        Integer32 (0..360),
        rcSlaStatisticPktSdGoodSecondsDS       Integer32 (0..1800),
        rcSlaStatisticPktlmLossRateSD          Integer32 (0..10000),
        rcSlaStatisticPktlmLossRateDS          Integer32 (0..10000)

}


rcSlaStatisticPktlmStartTime       OBJECT-TYPE 
	SYNTAX      TimeStamp
    MAX-ACCESS  not-accessible
    STATUS      current
    DESCRIPTION
            "This object specifies the time when the operation starts to be scheduled."   
            
    ::= { rcSlaPktlmStatisticEntry 1 }      
     
rcSlaStatisticPktlmScheduleLife       OBJECT-TYPE 
	SYNTAX      Unsigned32
    MAX-ACCESS  read-only
    STATUS      current
    DESCRIPTION
            "This object specifies the time duration over the whole schedule process. "
    ::= { rcSlaPktlmStatisticEntry 2 }  
    
rcSlaStatisticPktlmSchedulePeriod       OBJECT-TYPE 
	SYNTAX      Unsigned32
    MAX-ACCESS  read-only
    STATUS      current
    DESCRIPTION
            "This object specifies the number of packet loss measurement probe that were successfully measured in schedule."
    ::= { rcSlaPktlmStatisticEntry 3 }   
      
rcSlaStatisticPktlmTXNum       OBJECT-TYPE 
	SYNTAX      Counter32
    MAX-ACCESS  read-only
    STATUS      current
    DESCRIPTION
            "This object specifies the duration between two SLA test 
            	which includes all of probes schedule process in test. "
    ::= { rcSlaPktlmStatisticEntry 4 }    
    
rcSlaStatisticPktlmNum       OBJECT-TYPE 
	SYNTAX      Counter32
    MAX-ACCESS  read-only
    STATUS      current
    DESCRIPTION
            "This object specifies the duration between two SLA test 
            	which includes all successful probes schedule process in test. 
           	Take above example, if all of the rcSlaConfigSchedulePeriod of three operations are set to 60, 
            	then the start time of each test of SLA operation like:
			start time:   T+0 --------  T+9 ----------  T+19-----
           		operation1  operation2    operation3 
			start again:  T+60--------  T+69 ----------  T+79--
           		operation1  operation2    operation3   
			start 3rd time:T+120-------- T+129 ----------T+139--
         		operation1  operation2    operation3"
    ::= { rcSlaPktlmStatisticEntry 5 }                   

rcSlaStatisticPktlmSums        OBJECT-TYPE 
	SYNTAX      Counter32
    MAX-ACCESS  read-only
    STATUS      current
    DESCRIPTION
            "This object specifies the sum of packet loss measurement that were successfully measured in schedule."
    ::= { rcSlaPktlmStatisticEntry 6 }        
    
rcSlaStatisticPktlmMin       OBJECT-TYPE 
	SYNTAX      Gauge32
    MAX-ACCESS  read-only
    STATUS      current
    DESCRIPTION
            "This object specifies the minimum of packet loss measurement that were successfully measured in Schedule."
    ::= { rcSlaPktlmStatisticEntry 7 }                    

rcSlaStatisticPktlmMax       OBJECT-TYPE 
	SYNTAX      Gauge32
    MAX-ACCESS  read-only
    STATUS      current
    DESCRIPTION
            "This object specifies the maximum of packet loss measurement that were successfully measured in Schedule. "
    ::= { rcSlaPktlmStatisticEntry 8 }                    
                  
rcSlaStatistiPktlmNumSD       OBJECT-TYPE 
	SYNTAX      Counter32
    MAX-ACCESS  read-only
    STATUS      current
    DESCRIPTION
            "This object specifies the number of packet loss measurement 
            	that were successfully measured from source to destination in Schedule."
    ::= { rcSlaPktlmStatisticEntry 9 }  
    
rcSlaStatisticPktlmSumsSD       OBJECT-TYPE 
	SYNTAX      Counter32
    MAX-ACCESS  read-only
    STATUS      current
    DESCRIPTION
            "This object specifies the sum of packet loss measurement  
            	that were successfully measured from source to destination in Schedule."
    ::= { rcSlaPktlmStatisticEntry 10 }                    

rcSlaStatisticPktlmMinSD       OBJECT-TYPE 
	SYNTAX      Gauge32
    MAX-ACCESS  read-only
    STATUS      current
    DESCRIPTION
            "This object specifies the minimum of packet loss measurement that were successfully measured from source to destination in Schedule. "
    ::= { rcSlaPktlmStatisticEntry 11 }                    

rcSlaStatisticPktlmMaxSD       OBJECT-TYPE 
	SYNTAX      Gauge32
    MAX-ACCESS  read-only
    STATUS      current
    DESCRIPTION
            "This object specifies the maximum of packet loss measurement that were successfully measured from source to destination in Schedule. "
    ::= { rcSlaPktlmStatisticEntry 12 }    

rcSlaStatisticPktlmNumDS       OBJECT-TYPE 
	SYNTAX      Counter32
    MAX-ACCESS  read-only
    STATUS      current
    DESCRIPTION
            "This object specifies the number of packet loss measurement  
            	that were successfully measured from destination to source in Schedule."
    ::= { rcSlaPktlmStatisticEntry 13 } 
                    

rcSlaStatisticPktlmSumsDS       OBJECT-TYPE 
	SYNTAX      Counter32
    MAX-ACCESS  read-only
    STATUS      current
    DESCRIPTION
            "This object specifies the sum of packet loss measurement  
            that were successfully measured from destination to source in Schedule."
    ::= { rcSlaPktlmStatisticEntry 14 }                    

rcSlaStatisticPktlmMinDS       OBJECT-TYPE 
	SYNTAX      Gauge32
    MAX-ACCESS  read-only
    STATUS      current
    DESCRIPTION
            "This object specifies the minimum of packet loss measurement that were successfully measured from destination to source in Schedule. "
    ::= { rcSlaPktlmStatisticEntry 15 }  
    

rcSlaStatisticPktlmMaxDS       OBJECT-TYPE 
	SYNTAX      Gauge32
    MAX-ACCESS  read-only
    STATUS      current
    DESCRIPTION
            "This object specifies the maximum of packet loss measurement that were successfully measured from destination to source in Schedule." 
    ::= { rcSlaPktlmStatisticEntry 16 }  
    
 rcSlaStatisticPktSdBadSeconds      OBJECT-TYPE 
    SYNTAX        Integer32 (0..360)
  	MAX-ACCESS    read-only
    STATUS      current
    DESCRIPTION
              "The consecutive total number of sd bad seconds."
    DEFVAL{0}
  	::= { rcSlaPktlmStatisticEntry 17 }   
  	 	
 rcSlaStatisticPktSdGoodSeconds      OBJECT-TYPE 
    SYNTAX       Integer32 (0..1800)
  	MAX-ACCESS    read-only
    STATUS      current
    DESCRIPTION
              "The consecutive total number of sd good seconds."  
     DEFVAL{0}         
    ::= { rcSlaPktlmStatisticEntry 18 }           
 rcSlaStatisticPktSdBadSecondsSD      OBJECT-TYPE 
    SYNTAX        Integer32 (0..360)
    MAX-ACCESS    read-only
    STATUS      current
    DESCRIPTION
              "The consecutive total number of sd bad seconds in the direction of SD."
    DEFVAL{0}
    ::= { rcSlaPktlmStatisticEntry 19 }   
        
 rcSlaStatisticPktSdGoodSecondsSD      OBJECT-TYPE 
    SYNTAX       Integer32 (0..1800)
    MAX-ACCESS    read-only
    STATUS      current
    DESCRIPTION
              "The consecutive total number of sd good seconds in the direction of SD."  
     DEFVAL{0}         
    ::= { rcSlaPktlmStatisticEntry 20 }    

 rcSlaStatisticPktSdBadSecondsDS      OBJECT-TYPE 
    SYNTAX        Integer32 (0..360)
    MAX-ACCESS    read-only
    STATUS      current
    DESCRIPTION
              "The consecutive total number of sd bad seconds in the direction of DS."
    DEFVAL{0}
    ::= { rcSlaPktlmStatisticEntry 21 }   
        
 rcSlaStatisticPktSdGoodSecondsDS      OBJECT-TYPE 
    SYNTAX       Integer32 (0..1800)
    MAX-ACCESS    read-only
    STATUS      current
    DESCRIPTION
              "The consecutive total number of sd good seconds in the direction of DS."  
     DEFVAL{0}         
    ::= { rcSlaPktlmStatisticEntry 22 }     
    
 rcSlaStatisticPktlmLossRateSD      OBJECT-TYPE 
    SYNTAX        Integer32 (0..10000)
    MAX-ACCESS    read-only
    STATUS      current
    DESCRIPTION
              "The packet loss rate of loss measure operation in the direction of SD."
    DEFVAL{0}
    ::= { rcSlaPktlmStatisticEntry 23 }   
        
 rcSlaStatisticPktlmLossRateDS      OBJECT-TYPE 
    SYNTAX       Integer32 (0..10000)
    MAX-ACCESS    read-only
    STATUS      current
    DESCRIPTION
              "The packet loss rate of loss measure operation in the direction of DS."  
     DEFVAL{0}         
    ::= { rcSlaPktlmStatisticEntry 24 }  


----rcSlaExEthResultTable
rcSlaExEthResultTable  OBJECT-TYPE
    SYNTAX      SEQUENCE OF RcSlaExEthResultEntry
    MAX-ACCESS  not-accessible
    STATUS      current
    DESCRIPTION
        "This table contains sla eth result information."
    ::= { rcSlaScheduleGroup 5 }

rcSlaExEthResultEntry   OBJECT-TYPE
    SYNTAX      RcSlaExEthResultEntry
    MAX-ACCESS  not-accessible
    STATUS      current
    DESCRIPTION
        "This table contains sla eth result information."
	INDEX        { rcSlaExEthMdLevel, 
	               rcSlaExEthSVlanId,
	               rcSlaExEthDMac,
	               rcSlaExEthDMepId}    
    ::={ rcSlaExEthResultTable 1 }     
    
    RcSlaExEthResultEntry ::= SEQUENCE {
        rcSlaExEthMdLevel                         Dot1agCfmMDLevel,
        rcSlaExEthSVlanId                         VlanId,
        rcSlaExEthDMac                            MacAddress,
        rcSlaExEthDMepId                          Dot1agCfmMepId,
    	rcSlaExEthCurrDelay                       Counter32,      
	    rcSlaExEthCurrDelaySD                     Counter32,
	    rcSlaExEthCurrDelayDS                     Counter32,
	    rcSlaExEthCurrJitter                      Counter32,
	    rcSlaExEthCurrJitterSD                    Counter32,
	    rcSlaExEthCurrJitterDS                    Counter32,
        rcSlaExEthCurrPktLossRateSD               Counter32,
        rcSlaExEthCurrPktLossRateDS               Counter32,
}

rcSlaExEthMdLevel       OBJECT-TYPE 
	SYNTAX        Dot1agCfmMDLevel
	MAX-ACCESS    not-accessible
    STATUS        current
    DESCRIPTION
            "This object specifies the maintenance domain level to be used by Y.1731 operation."
    ::= { rcSlaExEthResultEntry 1 }                    


rcSlaExEthSVlanId       OBJECT-TYPE 
	SYNTAX        VlanId
    MAX-ACCESS    not-accessible
    STATUS        current
    DESCRIPTION
            "This object specifies the identifier of VLAN for MA to be used by Y.1731 operation.
				It is an unique identifier for a service instance 
				within a Maintenance Domain specified by rcSlaConfigMDLevel."
    ::= { rcSlaExEthResultEntry 2 }     
    
rcSlaExEthDMac       OBJECT-TYPE 
	SYNTAX        MacAddress
    MAX-ACCESS    not-accessible
    STATUS        current
    DESCRIPTION
            "This object specifies the Target MAC Address Field to be used by Y.1731 operation."
    ::= { rcSlaExEthResultEntry 3 }     
    
rcSlaExEthDMepId       OBJECT-TYPE 
	SYNTAX        Dot1agCfmMepId
    MAX-ACCESS    not-accessible
    STATUS        current
    DESCRIPTION
            "This object specifies the Target Remote MEP Identify to be used by Y.1731 operation."
    ::= { rcSlaExEthResultEntry 4 }     
 	    
rcSlaExEthCurrDelay       OBJECT-TYPE 
	SYNTAX      Counter32
	MAX-ACCESS  read-only
    STATUS      current
    DESCRIPTION
            "The RTT delay of the last test."
    ::= { rcSlaExEthResultEntry 5 }     
    
rcSlaExEthCurrDelaySD       OBJECT-TYPE 
	SYNTAX      Counter32
	MAX-ACCESS  read-only
    STATUS      current
    DESCRIPTION
            "The delay of the last test from source to destination."
    ::= { rcSlaExEthResultEntry 6}     
    
rcSlaExEthCurrDelayDS       OBJECT-TYPE 
	SYNTAX      Counter32
	MAX-ACCESS  read-only
    STATUS      current
    DESCRIPTION
            "The delay of the last test from destination to source."
    ::= { rcSlaExEthResultEntry 7 }     
    
rcSlaExEthCurrJitter       OBJECT-TYPE 
	SYNTAX      Counter32
	MAX-ACCESS  read-only
    STATUS      current
    DESCRIPTION
            "The RTT jitter of the last test."
    ::= { rcSlaExEthResultEntry 8 }     

rcSlaExEthCurrJitterSD       OBJECT-TYPE 
	SYNTAX      Counter32
	MAX-ACCESS  read-only
    STATUS      current
    DESCRIPTION
            "The jitter of the last test from source to destination."
    ::= { rcSlaExEthResultEntry 9 }     
    
rcSlaExEthCurrJitterDS       OBJECT-TYPE 
	SYNTAX      Counter32
	MAX-ACCESS  read-only
    STATUS      current
    DESCRIPTION
            "The jitter of the last test from destination to source."
    ::= { rcSlaExEthResultEntry 10 }     
    
rcSlaExEthCurrPktLossRateSD       OBJECT-TYPE 
    SYNTAX      Counter32
    MAX-ACCESS  read-only
    STATUS      current
    DESCRIPTION
            "The pkt loss rate of the last test from source to destination."
    ::= { rcSlaExEthResultEntry 11 }     
    
rcSlaExEthCurrPktLossRateDS       OBJECT-TYPE 
    SYNTAX      Counter32
    MAX-ACCESS  read-only
    STATUS      current
    DESCRIPTION
            "The pkt loss rate of the last test from destination to source."
    ::= { rcSlaExEthResultEntry 12 }     



----rcSlaExPwResultTable
rcSlaExPwResultTable  OBJECT-TYPE
    SYNTAX      SEQUENCE OF RcSlaExPwResultEntry
    MAX-ACCESS  not-accessible
    STATUS      current
    DESCRIPTION
        "This table contains sla pw result information."
    ::= { rcSlaScheduleGroup 6 }

rcSlaExPwResultEntry   OBJECT-TYPE
    SYNTAX      RcSlaExPwResultEntry
    MAX-ACCESS  not-accessible
    STATUS      current
    DESCRIPTION
        "This table contains sla pw result information."
	INDEX        { rcSlaExPwMdLevel,
	               rcSlaExPwVcId,
	               rcSlaExPwPeerAddrType,
	               rcSlaExPwPeerAddr}    
    ::={ rcSlaExPwResultTable 1 }     
    
    RcSlaExPwResultEntry ::= SEQUENCE {
        rcSlaExPwMdLevel                         Dot1agCfmMDLevel,
        rcSlaExPwVcId                            Integer32 (1..2147483647 ),
        rcSlaExPwPeerAddrType                    InetAddressType,
        rcSlaExPwPeerAddr                        InetAddress,
    	rcSlaExPwCurrDelay                       Counter32,      
	    rcSlaExPwCurrDelaySD                     Counter32,
	    rcSlaExPwCurrDelayDS                     Counter32,
	    rcSlaExPwCurrJitter                      Counter32,
	    rcSlaExPwCurrJitterSD                    Counter32,
	    rcSlaExPwCurrJitterDS                    Counter32,
        rcSlaExPwCurrPktLossRateSD               Counter32,
        rcSlaExPwCurrPktLossRateDS               Counter32,
}

rcSlaExPwMdLevel       OBJECT-TYPE 
	SYNTAX        Dot1agCfmMDLevel
	MAX-ACCESS    not-accessible
    STATUS        current
    DESCRIPTION
            "This object specifies the maintenance domain level to be used by Y.1731 operation."
    ::= { rcSlaExPwResultEntry 1 }                    

rcSlaExPwVcId            OBJECT-TYPE 
  	SYNTAX        Integer32 (1..2147483647 )
  	MAX-ACCESS    not-accessible
      STATUS      current
      DESCRIPTION
              "The VC ID associated with the ma."    
    ::= { rcSlaExPwResultEntry 2 }     
  	 	 
rcSlaExPwPeerAddrType  OBJECT-TYPE 
    SYNTAX        InetAddressType
  	MAX-ACCESS    not-accessible
      STATUS      current
      DESCRIPTION
              "Denotes the address type of the peer node.  It should be
              set to 'unknown' if PE/PW maintenance protocol is not used
              and the address is unknown."
     DEFVAL { unkown }   
    ::= { rcSlaExPwResultEntry 3 }     
  	
rcSlaExPwPeerAddr      OBJECT-TYPE 
    SYNTAX        InetAddress
  	MAX-ACCESS    not-accessible
      STATUS      current
      DESCRIPTION
              "This object contains the value of the peer node address
           	  of the PW/PE maintenance protocol entity.  This object
              SHOULD contain a value of all zeroes if not applicable
              (rcCfmMaExAisPwPeerAddrType is 'unknown')."
    ::= { rcSlaExPwResultEntry 4 }     
    
rcSlaExPwCurrDelay       OBJECT-TYPE 
	SYNTAX      Counter32
	MAX-ACCESS  read-only
    STATUS      current
    DESCRIPTION
            "The RTT delay of the last test."
    ::= { rcSlaExPwResultEntry 5 }     
    
rcSlaExPwCurrDelaySD       OBJECT-TYPE 
	SYNTAX      Counter32
	MAX-ACCESS  read-only
    STATUS      current
    DESCRIPTION
            "The delay of the last test from source to destination."
    ::= { rcSlaExPwResultEntry 6 }     
    
rcSlaExPwCurrDelayDS       OBJECT-TYPE 
	SYNTAX      Counter32
	MAX-ACCESS  read-only
    STATUS      current
    DESCRIPTION
            "The delay of the last test from destination to source."
    ::= { rcSlaExPwResultEntry 7 }     
    
rcSlaExPwCurrJitter       OBJECT-TYPE 
	SYNTAX      Counter32
	MAX-ACCESS  read-only
    STATUS      current
    DESCRIPTION
            "The RTT jitter of the last test."
    ::= { rcSlaExPwResultEntry 8 }     

rcSlaExPwCurrJitterSD       OBJECT-TYPE 
	SYNTAX      Counter32
	MAX-ACCESS  read-only
    STATUS      current
    DESCRIPTION
            "The jitter of the last test from source to destination."
    ::= { rcSlaExPwResultEntry 9 }     
    
rcSlaExPwCurrJitterDS       OBJECT-TYPE 
	SYNTAX      Counter32
	MAX-ACCESS  read-only
    STATUS      current
    DESCRIPTION
            "The jitter of the last test from destination to source."
    ::= { rcSlaExPwResultEntry 10 }     
    
rcSlaExPwCurrPktLossRateSD       OBJECT-TYPE 
    SYNTAX      Counter32
    MAX-ACCESS  read-only
    STATUS      current
    DESCRIPTION
            "The pkt loss rate of the last test from source to destination."
    ::= { rcSlaExPwResultEntry 11 }     
    
rcSlaExPwCurrPktLossRateDS       OBJECT-TYPE 
    SYNTAX      Counter32
    MAX-ACCESS  read-only
    STATUS      current
    DESCRIPTION
            "The pkt loss rate of the last test from destination to source."
    ::= { rcSlaExPwResultEntry 12 }     


----rcSlaExLspResultTable
rcSlaExLspResultTable  OBJECT-TYPE
    SYNTAX      SEQUENCE OF RcSlaExLspResultEntry
    MAX-ACCESS  not-accessible
    STATUS      current
    DESCRIPTION
        "This table contains sla lsp result information."
    ::= { rcSlaScheduleGroup 7 }

rcSlaExLspResultEntry   OBJECT-TYPE
    SYNTAX      RcSlaExLspResultEntry
    MAX-ACCESS  not-accessible
    STATUS      current
    DESCRIPTION
        "This table contains sla lsp result information."
	INDEX        { rcSlaExLspMdLevel,
	               rcSlaExLspIngressName,
	               rcSlaExLspEgressName }    
    ::={ rcSlaExLspResultTable 1 }     
    
    RcSlaExLspResultEntry ::= SEQUENCE {
        rcSlaExLspMdLevel                         Dot1agCfmMDLevel,
        rcSlaExLspIngressName                     OCTET STRING (SIZE(0..32)),
        rcSlaExLspEgressName                      OCTET STRING (SIZE(0..32)),
    	rcSlaExLspCurrDelay                       Counter32,      
	    rcSlaExLspCurrDelaySD                     Counter32,
	    rcSlaExLspCurrDelayDS                     Counter32,
	    rcSlaExLspCurrJitter                      Counter32,
	    rcSlaExLspCurrJitterSD                    Counter32,
	    rcSlaExLspCurrJitterDS                    Counter32,
        rcSlaExLspCurrPktLossRateSD               Counter32,
        rcSlaExLspCurrPktLossRateDS               Counter32,
}

rcSlaExLspMdLevel       OBJECT-TYPE 
	SYNTAX        Dot1agCfmMDLevel
	MAX-ACCESS    not-accessible
    STATUS        current
    DESCRIPTION
            "This object specifies the maintenance domain level to be used by Y.1731 operation."
    ::= { rcSlaExLspResultEntry 1 }                    
 	
rcSlaExLspIngressName  OBJECT-TYPE 
  	SYNTAX        OCTET STRING (SIZE (0..32))
  	MAX-ACCESS    not-accessible
      STATUS      current
      DESCRIPTION
              "The ingress LSP name associated with the ma."    
    ::= { rcSlaExLspResultEntry 2 }     
  
rcSlaExLspEgressName   OBJECT-TYPE 
  	SYNTAX        OCTET STRING (SIZE (0..32))
  	MAX-ACCESS    not-accessible
      STATUS      current
      DESCRIPTION
              "The egress LSP name associated with the ma."    
    ::= { rcSlaExLspResultEntry 3 }     
    
rcSlaExLspCurrDelay       OBJECT-TYPE 
	SYNTAX      Counter32
	MAX-ACCESS  read-only
    STATUS      current
    DESCRIPTION
            "The RTT delay of the last test."
    ::= { rcSlaExLspResultEntry 4 }     
    
rcSlaExLspCurrDelaySD       OBJECT-TYPE 
	SYNTAX      Counter32
	MAX-ACCESS  read-only
    STATUS      current
    DESCRIPTION
            "The delay of the last test from source to destination."
    ::= { rcSlaExLspResultEntry 5 }     
    
rcSlaExLspCurrDelayDS       OBJECT-TYPE 
	SYNTAX      Counter32
	MAX-ACCESS  read-only
    STATUS      current
    DESCRIPTION
            "The delay of the last test from destination to source."
    ::= { rcSlaExLspResultEntry 6 }     
    
rcSlaExLspCurrJitter       OBJECT-TYPE 
	SYNTAX      Counter32
	MAX-ACCESS  read-only
    STATUS      current
    DESCRIPTION
            "The RTT jitter of the last test."
    ::= { rcSlaExLspResultEntry 7 }     

rcSlaExLspCurrJitterSD       OBJECT-TYPE 
	SYNTAX      Counter32
	MAX-ACCESS  read-only
    STATUS      current
    DESCRIPTION
            "The jitter of the last test from source to destination."
    ::= { rcSlaExLspResultEntry 8 }     
    
rcSlaExLspCurrJitterDS       OBJECT-TYPE 
	SYNTAX      Counter32
	MAX-ACCESS  read-only
    STATUS      current
    DESCRIPTION
            "The jitter of the last test from destination to source."
    ::= { rcSlaExLspResultEntry 9 }     
    
rcSlaExLspCurrPktLossRateSD       OBJECT-TYPE 
    SYNTAX      Counter32
    MAX-ACCESS  read-only
    STATUS      current
    DESCRIPTION
            "The pkt loss rate of the last test from source to destination."
    ::= { rcSlaExLspResultEntry 10 }     
    
rcSlaExLspCurrPktLossRateDS       OBJECT-TYPE 
    SYNTAX      Counter32
    MAX-ACCESS  read-only
    STATUS      current
    DESCRIPTION
            "The pkt loss rate of the last test from destination to source."
    ::= { rcSlaExLspResultEntry 11 }     


----rcSlaExSectionResultTable
rcSlaExSectionResultTable  OBJECT-TYPE
    SYNTAX      SEQUENCE OF RcSlaExSectionResultEntry
    MAX-ACCESS  not-accessible
    STATUS      current
    DESCRIPTION
        "This table contains sla section result information."
    ::= { rcSlaScheduleGroup 8 }

rcSlaExSectionResultEntry   OBJECT-TYPE
    SYNTAX      RcSlaExSectionResultEntry
    MAX-ACCESS  not-accessible
    STATUS      current
    DESCRIPTION
        "This table contains sla section result information."
	INDEX        { rcSlaExSectionMdLevel,
	               rcSlaExSectionPort}    
    ::={ rcSlaExSectionResultTable 1 }     
    
    RcSlaExSectionResultEntry ::= SEQUENCE {
        rcSlaExSectionMdLevel                         Dot1agCfmMDLevel,
        rcSlaExSectionPort                            Unsigned32,
    	rcSlaExSectionCurrDelay                       Counter32,      
	    rcSlaExSectionCurrDelaySD                     Counter32,
	    rcSlaExSectionCurrDelayDS                     Counter32,
	    rcSlaExSectionCurrJitter                      Counter32,
	    rcSlaExSectionCurrJitterSD                    Counter32,
	    rcSlaExSectionCurrJitterDS                    Counter32,
        rcSlaExSectionCurrPktLossRateSD               Counter32,
        rcSlaExSectionCurrPktLossRateDS               Counter32,
}

rcSlaExSectionMdLevel       OBJECT-TYPE 
	SYNTAX        Dot1agCfmMDLevel
	MAX-ACCESS    not-accessible
    STATUS        current
    DESCRIPTION
            "This object specifies the maintenance domain level to be used by Y.1731 operation."
    ::= { rcSlaExSectionResultEntry 1 }                    

rcSlaExSectionPort      OBJECT-TYPE 
    SYNTAX        Unsigned32
  	MAX-ACCESS    not-accessible
      STATUS      current
      DESCRIPTION
              "The section port associated with the ma."  
    ::= { rcSlaExSectionResultEntry 2 }     
    
rcSlaExSectionCurrDelay       OBJECT-TYPE 
	SYNTAX      Counter32
	MAX-ACCESS  read-only
    STATUS      current
    DESCRIPTION
            "The RTT delay of the last test."
    ::= { rcSlaExSectionResultEntry 3 }     
    
rcSlaExSectionCurrDelaySD       OBJECT-TYPE 
	SYNTAX      Counter32
	MAX-ACCESS  read-only
    STATUS      current
    DESCRIPTION
            "The delay of the last test from source to destination."
    ::= { rcSlaExSectionResultEntry 4 }     
    
rcSlaExSectionCurrDelayDS       OBJECT-TYPE 
	SYNTAX      Counter32
	MAX-ACCESS  read-only
    STATUS      current
    DESCRIPTION
            "The delay of the last test from destination to source."
    ::= { rcSlaExSectionResultEntry 5 }     
    
rcSlaExSectionCurrJitter       OBJECT-TYPE 
	SYNTAX      Counter32
	MAX-ACCESS  read-only
    STATUS      current
    DESCRIPTION
            "The RTT jitter of the last test."
    ::= { rcSlaExSectionResultEntry 6 }     

rcSlaExSectionCurrJitterSD       OBJECT-TYPE 
	SYNTAX      Counter32
	MAX-ACCESS  read-only
    STATUS      current
    DESCRIPTION
            "The jitter of the last test from source to destination."
    ::= { rcSlaExSectionResultEntry 7 }     
    
rcSlaExSectionCurrJitterDS       OBJECT-TYPE 
	SYNTAX      Counter32
	MAX-ACCESS  read-only
    STATUS      current
    DESCRIPTION
            "The jitter of the last test from destination to source."
    ::= { rcSlaExSectionResultEntry 8 }     
    
rcSlaExSectionCurrPktLossRateSD       OBJECT-TYPE 
    SYNTAX      Counter32
    MAX-ACCESS  read-only
    STATUS      current
    DESCRIPTION
            "The pkt loss rate of the last test from source to destination."
    ::= { rcSlaExSectionResultEntry 9 }     
    
rcSlaExSectionCurrPktLossRateDS       OBJECT-TYPE 
    SYNTAX      Counter32
    MAX-ACCESS  read-only
    STATUS      current
    DESCRIPTION
            "The pkt loss rate of the last test from destination to source."
    ::= { rcSlaExSectionResultEntry 10 }     


-- *****************************************************************************
-- Ethernet Loss Measurement Current Availability Statistic Table
-- *****************************************************************************

rcSlaCurrentAvailStatsTable OBJECT-TYPE
    SYNTAX      SEQUENCE OF RcSlaCurrentAvailStatsEntry
    MAX-ACCESS  not-accessible
    STATUS      current
    DESCRIPTION
       "This object contains the current results for a SOAM Loss Measurement
        session for availability statistics gathered during the interval 
        indicated by mefSoamLmCfgAvailabilityMeasurementInterval.

        Each row in the table represents a Loss Measurement session for
        the defined MEP. This table uses four indices. The first three indices
        are the indices of the Maintenance Domain, MaNet, and MEP tables. The 
        fourth index is the specific LM session on the selected MEP.

        Instances of this managed object are created automatically
        by the SNMP Agent when the Loss Measurement session is running.

        The objects in this table apply regardless of the value of 
        mefSoamLmCfgType unless otherwise specified in the object description.

        Except for rcSlaAvailStatsCurrentIndex,
        rcSlaAvailStatsCurrentStartTime, rcSlaAvailStatsCurrentElapsedTime
        and mefSoamLmCurrentAvailStatsSuspect, each object in this table applies
        only if the corresponding bit is set in mefSoamLmCfgMeasurementEnable.

        The objects in this table may be persistent upon reboot or restart
        of a device.
       "
    REFERENCE
       "[MEF SOAM-PM] D9, D18"
    ::= { rcSlaScheduleGroup 9 }

rcSlaCurrentAvailStatsEntry OBJECT-TYPE
    SYNTAX      RcSlaCurrentAvailStatsEntry
    MAX-ACCESS  not-accessible
    STATUS      current
    DESCRIPTION
       "The conceptual row of rcSlaCurrentAvailStatsTable"
    INDEX      {rcSlaConfigOperId }
    ::= { rcSlaCurrentAvailStatsTable 1 }

RcSlaCurrentAvailStatsEntry ::= SEQUENCE {
    rcSlaCurrentAvailStatsIndex                Unsigned32,
    rcSlaCurrentAvailStatsStartTime            DateAndTime,
    rcSlaCurrentAvailStatsElapsedTime          TimeInterval,
    rcSlaCurrentAvailStatsSuspect              TruthValue,

    rcSlaCurrentAvailStatsForwardHighLoss      Unsigned32,
    rcSlaCurrentAvailStatsBackwardHighLoss     Unsigned32,
    rcSlaCurrentAvailStatsForwardConsecutiveHighLoss  Unsigned32,
    rcSlaCurrentAvailStatsBackwardConsecutiveHighLoss  Unsigned32,

    rcSlaCurrentAvailStatsForwardAvailable     Gauge32,
    rcSlaCurrentAvailStatsBackwardAvailable    Gauge32,
    rcSlaCurrentAvailStatsForwardUnavailable   Gauge32,
    rcSlaCurrentAvailStatsBackwardUnavailable  Gauge32,
    rcSlaCurrentAvailStatsForwardMinFlr        Unsigned32,
    rcSlaCurrentAvailStatsForwardMaxFlr        Unsigned32,
    rcSlaCurrentAvailStatsForwardAvgFlr        Unsigned32,
    rcSlaCurrentAvailStatsBackwardMinFlr       Unsigned32,
    rcSlaCurrentAvailStatsBackwardMaxFlr       Unsigned32,
    rcSlaCurrentAvailStatsBackwardAvgFlr       Unsigned32
}

rcSlaCurrentAvailStatsIndex OBJECT-TYPE
    SYNTAX      Unsigned32
    MAX-ACCESS  read-only
    STATUS      current
    DESCRIPTION
       "The index for the current availability Measurement Interval for this
        PM session.  This value will become the value for
        mefSoamLmHistoryAvailStatsIndex once the Measurement Interval
        is completed.  The duration of the Measurement Interval is specified
        by mefSoamLmCfgAvailabilityMeasurementInterval.

        Measurement Interval indexes are assigned sequentially by
        the SNMP Agent.  The first Measurement Interval that occurs after
        the session is started is assigned index 1.
       "
    ::= { rcSlaCurrentAvailStatsEntry 1 }

rcSlaCurrentAvailStatsStartTime OBJECT-TYPE
    SYNTAX      DateAndTime
    MAX-ACCESS  read-only
    STATUS      current
    DESCRIPTION
       "The time that the current Measurement Interval started.
       "
    REFERENCE
       "[MEF SOAM-PM] R87, R112"
    ::= { rcSlaCurrentAvailStatsEntry 2 }

rcSlaCurrentAvailStatsElapsedTime OBJECT-TYPE
    SYNTAX      TimeInterval
    MAX-ACCESS  read-only
    STATUS      current
    DESCRIPTION
       "The time that the current Measurement Interval has been running, in 0.01
        seconds.
       "
    REFERENCE
       "[MEF SOAM-PM] R24, R87, R112"
    ::= { rcSlaCurrentAvailStatsEntry 3 }

rcSlaCurrentAvailStatsSuspect OBJECT-TYPE
    SYNTAX      TruthValue
    MAX-ACCESS  read-only
    STATUS      current
    DESCRIPTION
       "Whether the Measurement Interval has been marked as suspect.

        The object is set to false at the start of a measurement
        interval. It is set to true when there is a discontinuity in the 
        performance measurements during the Measurement Interval.  Conditions
        for a discontinuity include, but are not limited to the following:

        1 - The local time-of-day clock is adjusted by at least 10 seconds
        2 - The conducting of a performance measurement is halted before the
            current Measurement Interval is completed
        3 - A local test, failure, or reconfiguration that disrupts service
       "
    REFERENCE
       "[MEF SOAM-PM] R39, R40, R41"
    ::= { rcSlaCurrentAvailStatsEntry 4 }

rcSlaCurrentAvailStatsForwardHighLoss OBJECT-TYPE
    SYNTAX      Unsigned32
    MAX-ACCESS  read-only
    STATUS      current
    DESCRIPTION
       "This object is the number of high loss intervals (HLI) over
        time in the forward direction. 

        The value starts at 0 and increments for every HLI that occurs.
        This parameter is equivalent to 'L Sub T' found in MEF 10.2.1.
       "
    REFERENCE
       "[MEF 10.2.1] 6.9.9; [MEF SOAM-PM] R87"
    ::= { rcSlaCurrentAvailStatsEntry 5 }

rcSlaCurrentAvailStatsBackwardHighLoss OBJECT-TYPE
    SYNTAX      Unsigned32
    MAX-ACCESS  read-only
    STATUS      current
    DESCRIPTION
       "This object is the number of high loss intervals (HLI) over
        time in the backwards direction. 

        The value starts at 0 and increments for every HLI that occurs.
        This parameter is equivalent to 'L Sub T' found in MEF 10.2.1.
       "
    REFERENCE
       "[MEF 10.2.1] 6.9.9; [MEF SOAM-PM] R87"
    ::= { rcSlaCurrentAvailStatsEntry 6 }

rcSlaCurrentAvailStatsForwardConsecutiveHighLoss OBJECT-TYPE
    SYNTAX      Unsigned32
    MAX-ACCESS  read-only
    STATUS      current
    DESCRIPTION
       "This object is the number of consecutive high loss intervals
        (CHLI) over time in the forward direction. 

        The value starts at 0 and increments for every HLI that occurs
        that is determined to fall within a CHLI.
        This parameter is equivalent to 'B Sub T' found in MEF 10.2.1.
       "
    REFERENCE
       "[MEF 10.2.1] 6.9.9; [MEF SOAM-PM] R87"
    ::= { rcSlaCurrentAvailStatsEntry 7 }

rcSlaCurrentAvailStatsBackwardConsecutiveHighLoss OBJECT-TYPE
    SYNTAX      Unsigned32
    MAX-ACCESS  read-only
    STATUS      current
    DESCRIPTION
       "This object is the number of consecutive high loss intervals
        (CHLI) over time in the backward direction. 

        The value starts at 0 and increments for every HLI that occurs
        that is determined to fall within a CHLI.
        This parameter is equivalent to 'B Sub T' found in MEF 10.2.1.
       "
    REFERENCE
       "[MEF 10.2.1] 6.9.9; [MEF SOAM-PM] R87"
    ::= { rcSlaCurrentAvailStatsEntry 8 }

rcSlaCurrentAvailStatsForwardAvailable OBJECT-TYPE
    SYNTAX      Gauge32
    MAX-ACCESS  read-only
    STATUS      current
    DESCRIPTION
       "This object contains the number of availability indicators 
        evaluated as available in the forward direction by this MEP during
        this Measurement Interval.
       "
    REFERENCE
       "[MEF SOAM-PM] R87; [MEF 10.2.1]"
    ::= { rcSlaCurrentAvailStatsEntry 9 }

rcSlaCurrentAvailStatsBackwardAvailable OBJECT-TYPE
    SYNTAX      Gauge32
    MAX-ACCESS  read-only
    STATUS      current
    DESCRIPTION
       "This object contains the number of availability indicators 
        evaluated as available in the backward direction by this MEP during
        this Measurement Interval.
       "
    REFERENCE
       "[MEF SOAM-PM] R87"
    ::= { rcSlaCurrentAvailStatsEntry 10 }

rcSlaCurrentAvailStatsForwardUnavailable OBJECT-TYPE
    SYNTAX      Gauge32
    MAX-ACCESS  read-only
    STATUS      current
    DESCRIPTION
       "This object contains the number of availability indicators 
        evaluated as unavailable in the forward direction by this MEP during
        this Measurement Interval.
       "
    REFERENCE
       "[MEF SOAM-PM] R87"
    ::= { rcSlaCurrentAvailStatsEntry 11 }

rcSlaCurrentAvailStatsBackwardUnavailable OBJECT-TYPE
    SYNTAX      Gauge32
    MAX-ACCESS  read-only
    STATUS      current
    DESCRIPTION
       "This object contains the number of availability indicators 
        evaluated as unavailable in the backward direction by this MEP
        during this Measurement Interval.
       "
    REFERENCE
       "[MEF SOAM-PM] R87"
    ::= { rcSlaCurrentAvailStatsEntry 12 }

rcSlaCurrentAvailStatsForwardMinFlr OBJECT-TYPE
    SYNTAX      Unsigned32 (0..100000)
    UNITS       "milli-percent"
    MAX-ACCESS  read-only
    STATUS      current
    DESCRIPTION
       "This object contains the minimum one-way availability flr in the forward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
       "
    REFERENCE
       "[MEF SOAM-PM] D37"
    ::= { rcSlaCurrentAvailStatsEntry 13 }

rcSlaCurrentAvailStatsForwardMaxFlr OBJECT-TYPE
    SYNTAX      Unsigned32 (0..100000)
    UNITS       "milli-percent"
    MAX-ACCESS  read-only
    STATUS      current
    DESCRIPTION
       "This object contains the maximum one-way availability flr in the forward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
      "
    REFERENCE
       "[MEF SOAM-PM] D37"
    ::= { rcSlaCurrentAvailStatsEntry 14 }

rcSlaCurrentAvailStatsForwardAvgFlr OBJECT-TYPE
    SYNTAX      Unsigned32 (0..100000)
    UNITS       "milli-percent"
    MAX-ACCESS  read-only
    STATUS      current
    DESCRIPTION
       "This object contains the average one-way availability flr in the forward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
       "
    REFERENCE
       "[MEF SOAM-PM] D37"
    ::= { rcSlaCurrentAvailStatsEntry 15 }

rcSlaCurrentAvailStatsBackwardMinFlr OBJECT-TYPE
    SYNTAX      Unsigned32 (0..100000)
    UNITS       "milli-percent"
    MAX-ACCESS  read-only
    STATUS      current
    DESCRIPTION
       "This object contains the minimum one-way availability flr in the backward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
       "
    REFERENCE
       "[MEF SOAM-PM] D37"
    ::= { rcSlaCurrentAvailStatsEntry 16 }

rcSlaCurrentAvailStatsBackwardMaxFlr OBJECT-TYPE
    SYNTAX      Unsigned32 (0..100000)
    UNITS       "milli-percent"
    MAX-ACCESS  read-only
    STATUS      current
    DESCRIPTION
       "This object contains the maximum one-way availability flr in the backward
        direction, from among the set of availability flr values calculated by
        the MEP in this Measurement Interval.  There is one availability flr 
        value for each 'delta_t' time period within the Measurement Interval, as
        specified in MEF 10.2.1.

        The flr value is a ratio that is expressed 
        as a percent with a value of 0 (ratio 0.00) through 100000 (ratio 1.00).

        Units are in milli-percent, where 1 indicates 0.001 percent.
      "
    REFERENCE
       "[MEF SOAM-PM] D37"
    ::= { rcSlaCurrentAvailStatsEntry 17 }

rcSlaCurrentAvailStatsBackwardAvgFlr OBJECT-TYPE
    SYNTAX      Unsigned32 (0..100000)
    UNITS       "milli-percent"
    MAX-ACCESS  read-only
    STATUS      current
    DESCRIPTION
       "This object contains the average one-way availability flr in the backward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
       "
    REFERENCE
       "[MEF SOAM-PM] D37"
    ::= { rcSlaCurrentAvailStatsEntry 18 }


-- *****************************************************************************
-- Ethernet Loss Measurement Availability History Statistic Table
-- *****************************************************************************

rcSlaHistoryAvailStatsTable OBJECT-TYPE
    SYNTAX      SEQUENCE OF RcSlaHistoryAvailStatsEntry
    MAX-ACCESS  not-accessible
    STATUS      current
    DESCRIPTION
       "This table contains the results for availability history Measurement
        Intervals in a SOAM Loss Measurement session.

        Rows of this table object are created automatically
        by the SNMP Agent when the Loss Measurement session is running and a 
        Measurement Interval is completed.

        Each row in the table represents the history statistics for a Loss
        Measurement session availability Measurement Interval for the defined
        MEP. This table uses five indices. The first three indices are the indices of
        the Maintenance Domain, MaNet, and MEP tables. The fourth index is the
        specific LM session on the selected MEP. The fifth index index the
        specific Measurement Interval.

        At least 32 completed Measurement Intervals are to be supported. 96
        completed Measurement Intervals are recommended to be supported. If
        there are at least 32 rows in the table and a new Measurement Interval
        completes and a new row is to be added to the table, the oldest completed
        Measurement Interval can be deleted (row deletion). If the availability
        Measurement Interval is other than 15 minutes then a minimum of 8 hours of 
        completed Measurement Intervals are to be supported and 24 hours are
        recommended to be supported.

        Except for mefSoamLmHistoryAvailStatsIndex, 
        mefSoamLmHistoryAvailStatsEndTime, mefSoamLmHistoryAvailStatsElapsedTime and 
        mefSoamLmHistoryAvailStatsSuspect, each object in this table applies only
        if the corresponding bit is set in mefSoamLmCfgMeasurementEnable.

        The rows and objects in this table are to be persistent upon reboot 
        or restart of a device.
       "
    REFERENCE
       "[MEF SOAM-PM] R7, R15, R21, D8, R25"
    ::= { rcSlaScheduleGroup 10 }

rcSlaHistoryAvailStatsEntry OBJECT-TYPE
    SYNTAX      RcSlaHistoryAvailStatsEntry
    MAX-ACCESS  not-accessible
    STATUS      current
    DESCRIPTION
            "The conceptual row of rcSlaHistoryAvailStatsTable"
    INDEX      {rcSlaConfigOperId,
                rcSlaHistoryAvailStatsIndex}
    ::= { rcSlaHistoryAvailStatsTable 1 }

RcSlaHistoryAvailStatsEntry ::= SEQUENCE {
    rcSlaHistoryAvailStatsIndex                  Unsigned32,
    rcSlaHistoryAvailStatsEndTime                DateAndTime,
    rcSlaHistoryAvailStatsElapsedTime            TimeInterval,
    rcSlaHistoryAvailStatsSuspect                TruthValue,
    rcSlaHistoryAvailStatsForwardHighLoss        Unsigned32,
    rcSlaHistoryAvailStatsBackwardHighLoss       Unsigned32,
    rcSlaHistoryAvailStatsForwardConsecutiveHighLoss  Unsigned32,
    rcSlaHistoryAvailStatsBackwardConsecutiveHighLoss  Unsigned32,

    rcSlaHistoryAvailStatsForwardAvailable       Gauge32,
    rcSlaHistoryAvailStatsBackwardAvailable      Gauge32,
    rcSlaHistoryAvailStatsForwardUnavailable     Gauge32,
    rcSlaHistoryAvailStatsBackwardUnavailable    Gauge32,
    rcSlaHistoryAvailStatsForwardMinFlr          Unsigned32,
    rcSlaHistoryAvailStatsForwardMaxFlr          Unsigned32,
    rcSlaHistoryAvailStatsForwardAvgFlr          Unsigned32,
    rcSlaHistoryAvailStatsBackwardMinFlr         Unsigned32,
    rcSlaHistoryAvailStatsBackwardMaxFlr         Unsigned32,
    rcSlaHistoryAvailStatsBackwardAvgFlr         Unsigned32
}

rcSlaHistoryAvailStatsIndex OBJECT-TYPE
    SYNTAX      Unsigned32
    MAX-ACCESS  not-accessible
    STATUS      current
    DESCRIPTION
       "The index for the availability Measurement Interval within this
        PM session.

        Measurement Interval indexes are assigned sequentially by
        the SNMP Agent.  The first Measurement Interval that occurs after
        the session is started is assigned index 1.  Measurement Intervals
        for availability (stored in this table) are based on 
        mefSoamLmCfgAvailabilityMeasurementInterval and are indexed independently
        of Measurement Intervals for FLR (stored in mefSoamLmHistoryStatsTable).

        Referential integrity is necessary, i.e., the index needs to be
        persistent upon a reboot or restart of a device.  The index
        is never reused while this session is active until it wraps to zero.
        The index value keeps increasing up to that time.
       "
    ::= { rcSlaHistoryAvailStatsEntry 1 }

rcSlaHistoryAvailStatsEndTime OBJECT-TYPE
    SYNTAX      DateAndTime
    MAX-ACCESS  read-only
    STATUS      current
    DESCRIPTION
       "The time that the Measurement Interval ended.
       "
    REFERENCE
       "[MEF SOAM-PM] R23, R87, R112"
    ::= { rcSlaHistoryAvailStatsEntry 2 }

rcSlaHistoryAvailStatsElapsedTime OBJECT-TYPE
    SYNTAX      TimeInterval
    MAX-ACCESS  read-only
    STATUS      current
    DESCRIPTION
       "The length of time that the Measurement Interval ran for,
        in 0.01 seconds.
       "
    REFERENCE
       "[MEF SOAM-PM] R24, R87, R112"
    ::= { rcSlaHistoryAvailStatsEntry 3 }

rcSlaHistoryAvailStatsSuspect OBJECT-TYPE
    SYNTAX      TruthValue
    MAX-ACCESS  read-only
    STATUS      current
    DESCRIPTION
       "Whether the Measurement Interval has been marked as suspect.

        The object is set to true when there is a discontinuity in the 
        performance measurements during the Measurement Interval.  Conditions
        for a discontinuity include, but are not limited to the following:

        1 - The local time-of-day clock is adjusted by at least 10 seconds
        2 - The conducting of a performance measurement is halted before the
            current Measurement Interval is completed
        3 - A local test, failure, or reconfiguration that disrupts service
"
    REFERENCE
       "[MEF SOAM-PM] R39, R40, R41, R42"
    ::= { rcSlaHistoryAvailStatsEntry 4 }

rcSlaHistoryAvailStatsForwardHighLoss OBJECT-TYPE
    SYNTAX      Unsigned32
    MAX-ACCESS  read-only
    STATUS      current
    DESCRIPTION
       "This object is the number of high loss intervals (HLI) over
        time in the forward direction. 

        The value starts at 0 and increments for every HLI that occurs.
        This parameter is equivalent to 'L Sub T' found in MEF 10.2.1.
       "
    REFERENCE
       "[MEF 10.2.1] 6.9.9; [MEF SOAM-PM] R87"
    ::= { rcSlaHistoryAvailStatsEntry 5 }

rcSlaHistoryAvailStatsBackwardHighLoss OBJECT-TYPE
    SYNTAX      Unsigned32
    MAX-ACCESS  read-only
    STATUS      current
    DESCRIPTION
       "This object is the number of high loss intervals (HLI) over
        time in the backward direction. 

        The value starts at 0 and increments for every HLI that occurs.
        This parameter is equivalent to 'L Sub T' found in MEF 10.2.1.
       "
    REFERENCE
       "[MEF 10.2.1] 6.9.9; [MEF SOAM-PM] R87"
    ::= { rcSlaHistoryAvailStatsEntry 6 }

rcSlaHistoryAvailStatsForwardConsecutiveHighLoss OBJECT-TYPE
    SYNTAX      Unsigned32
    MAX-ACCESS  read-only
    STATUS      current
    DESCRIPTION
       "This object is the number of consecutive high loss intervals
        (CHLI) over time in the forward direction. 

        The value starts at 0 and increments for every HLI that occurs 
        that is determined to fall within a CHLI.
        This parameter is equivalent to 'B Sub T' found in MEF 10.2.1.
       "
    REFERENCE
       "[MEF 10.2.1] 6.9.9; [MEF SOAM-PM] R87"
    ::= { rcSlaHistoryAvailStatsEntry 7 }

rcSlaHistoryAvailStatsBackwardConsecutiveHighLoss OBJECT-TYPE
    SYNTAX      Unsigned32
    MAX-ACCESS  read-only
    STATUS      current
    DESCRIPTION
       "This object is the number of consecutive high loss intervals
        (CHLI) over time in the forward direction. 

        The value starts at 0 and increments for every HLI that occurs
        that is determined to fall within a CHLI.
        This parameter is equivalent to 'B Sub T' found in MEF 10.2.1.
       "
    REFERENCE
       "[MEF 10.2.1] 6.9.9; [MEF SOAM-PM] R87"
    ::= { rcSlaHistoryAvailStatsEntry 8 }

rcSlaHistoryAvailStatsForwardAvailable OBJECT-TYPE
    SYNTAX      Gauge32
    MAX-ACCESS  read-only
    STATUS      current
    DESCRIPTION
       "This object contains the number of availability indicators 
        evaluated as available in the forward direction by this MEP during
        this Measurement Interval.
       "
    REFERENCE
       "[MEF SOAM-PM] R87; [MEF 10.2.1]"
    ::= { rcSlaHistoryAvailStatsEntry 9 }

rcSlaHistoryAvailStatsBackwardAvailable OBJECT-TYPE
    SYNTAX      Gauge32
    MAX-ACCESS  read-only
    STATUS      current
    DESCRIPTION
       "This object contains the number of availability indicators 
        evaluated as available in the backward direction by this MEP during
        this Measurement Interval.
       "
    REFERENCE
       "[MEF SOAM-PM] R87"
    ::= { rcSlaHistoryAvailStatsEntry 10 }

rcSlaHistoryAvailStatsForwardUnavailable OBJECT-TYPE
    SYNTAX      Gauge32
    MAX-ACCESS  read-only
    STATUS      current
    DESCRIPTION
       "This object contains the number of availability indicators 
        evaluated as unavailable in the forward direction by this MEP during
        this Measurement Interval.
       "
    REFERENCE
       "[MEF SOAM-PM] R87"
    ::= { rcSlaHistoryAvailStatsEntry 11 }


rcSlaHistoryAvailStatsBackwardUnavailable OBJECT-TYPE
    SYNTAX      Gauge32
    MAX-ACCESS  read-only
    STATUS      current
    DESCRIPTION
       "This object contains the number of availability indicators 
        evaluated as unavailable in the backward direction by this MEP
        during this Measurement Interval.
       "
    REFERENCE
       "[MEF SOAM-PM] R87"
    ::= { rcSlaHistoryAvailStatsEntry 12 }

rcSlaHistoryAvailStatsForwardMinFlr OBJECT-TYPE
    SYNTAX      Unsigned32 (0..100000)
    UNITS       "milli-percent"
    MAX-ACCESS  read-only
    STATUS      current
    DESCRIPTION
       "This object contains the minimum one-way availability flr in the forward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
       "
    REFERENCE
       "[MEF SOAM-PM] D37"
    ::= { rcSlaHistoryAvailStatsEntry 13 }

rcSlaHistoryAvailStatsForwardMaxFlr OBJECT-TYPE
    SYNTAX      Unsigned32 (0..100000)
    UNITS       "milli-percent"
    MAX-ACCESS  read-only
    STATUS      current
    DESCRIPTION
       "This object contains the maximum one-way availability flr in the forward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
      "
    REFERENCE
       "[MEF SOAM-PM] D37"
    ::= { rcSlaHistoryAvailStatsEntry 14 }

rcSlaHistoryAvailStatsForwardAvgFlr OBJECT-TYPE
    SYNTAX      Unsigned32 (0..100000)
    UNITS       "milli-percent"
    MAX-ACCESS  read-only
    STATUS      current
    DESCRIPTION
       "This object contains the average one-way availability flr in the forward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
       "
    REFERENCE
       "[MEF SOAM-PM] D37"
    ::= { rcSlaHistoryAvailStatsEntry 15 }

rcSlaHistoryAvailStatsBackwardMinFlr OBJECT-TYPE
    SYNTAX      Unsigned32 (0..100000)
    UNITS       "milli-percent"
    MAX-ACCESS  read-only
    STATUS      current
    DESCRIPTION
       "This object contains the minimum one-way availability flr in the backward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
       "
    REFERENCE
       "[MEF SOAM-PM] D37"
    ::= { rcSlaHistoryAvailStatsEntry 16 }

rcSlaHistoryAvailStatsBackwardMaxFlr OBJECT-TYPE
    SYNTAX      Unsigned32 (0..100000)
    UNITS       "milli-percent"
    MAX-ACCESS  read-only
    STATUS      current
    DESCRIPTION
       "This object contains the maximum one-way availability flr in the backward
        direction, from among the set of availability flr values calculated by
        the MEP in this Measurement Interval.  There is one availability flr 
        value for each 'delta_t' time period within the Measurement Interval, as
        specified in MEF 10.2.1.

        The flr value is a ratio that is expressed 
        as a percent with a value of 0 (ratio 0.00) through 100000 (ratio 1.00).

        Units are in milli-percent, where 1 indicates 0.001 percent.
      "
    REFERENCE
       "[MEF SOAM-PM] D37"
    ::= { rcSlaHistoryAvailStatsEntry 17 }

rcSlaHistoryAvailStatsBackwardAvgFlr OBJECT-TYPE
    SYNTAX      Unsigned32 (0..100000)
    UNITS       "milli-percent"
    MAX-ACCESS  read-only
    STATUS      current
    DESCRIPTION
       "This object contains the average one-way availability flr in the backward
        direction, from among the set of availability flr values calculated by
        the MEP in this Measurement Interval.  There is one availability flr 
        value for each 'delta_t' time period within the Measurement Interval, as
        specified in MEF 10.2.1.

        The flr value is a ratio that is expressed as a 
        percent with a value of 0 (ratio 0.00) through 100000 (ratio 1.00).

        Units are in milli-percent, where 1 indicates 0.001 percent.
       "
    REFERENCE
       "[MEF SOAM-PM] D37"
    ::= { rcSlaHistoryAvailStatsEntry 18 }
    
--------------------------------------------------rcSlaThroughputGroup -----------------------  
--rcSlaThroughputGroup                                                                                              
		--rcSlaCThroughputConfigTable    
			--rcSlaThroughputConfigEntry 
				--rcSlaThroughputIndex
				--rcSlaThroughputOperId
				--rcSlaThroughputObject   
				--rcSlaThroughputPktLength
				--rcSlaThroughputCount
				--rcSlaThroughputDuration   				
				--rcSlaThroughputEnable
				--rcSlaThroughputStatus
				--rcSlaThroughputRowStatus
				--rcSlaThroughputCompleteNum
				--rcSlaThroughputMeasureStartTime
				--rcSlaThroughputMeasureLastTime
				--rcSlaThroughputMeasureEndTime
				--rcSlaThroughputFailedNum    	
				
	--rcSlaCThroughputResultTable    
			--rcSlaThroughputResultEntry 
				--rcSlaThroughputResultId
				--rcSlaThroughputCfgId
				--rcSlaThroughputStartTime   
				--rcSlaThroughputEndTime				
				--rcSlaThroughputLastTime
				--rcSlaThroughputLocalSendPStatics 	
				--rcSlaThroughputLocalSendBStatics 
				--rcSlaThroughputLocalReceivePStatics 
				--rcSlaThroughputLocalReceiveBStatics 
				--rcSlaThroughputRemoteSendPStatics 
				--rcSlaThroughputRemoteSendBStatics 
				--rcSlaThroughputRemoteReceivePStatics 
				--rcSlaThroughputRemoteReceiveBStatics 				
				            

rcSlaThroughputConfigTable  OBJECT-TYPE
    SYNTAX      SEQUENCE OF RcSlaThroughputConfigEntry
    MAX-ACCESS  not-accessible
    STATUS      deprecated
    DESCRIPTION
        "This table contains sla  control data."
    ::= { rcSlaThroughputGroup 1 }

rcSlaThroughputConfigEntry   OBJECT-TYPE
    SYNTAX      RcSlaThroughputConfigEntry
    MAX-ACCESS  not-accessible
    STATUS      deprecated
    DESCRIPTION
        "A collection of objects that define three conceptual
    control row : slaY.1731EntryTable, slaIcmpEntryTable, slaSchEntryTable.
   		The 'slaY.1731EntryTable' is used to control y1731 operation .
    	The following objects must be specified in order to create this 
    conceptual row.
    	- rcSlaConfigOperType
    	- rcSlaConfigVlanId
    	- rcSlaConfigMDLevel
    	- rcSlaConfigDestMacAddr 
    	- rcSlaConfigRMepId
    	The ' slaIcmpEntryTable' is used to control ICMP operation .
    	The following objects must be specified in order to create this 
    conceptual row.
    	- rcSlaConfigOperType
    	- rcSlaConfigDestIpAddr
        The ' slaIcmpSchTable' is used to control operation schduled."
	INDEX        { rcSlaThroughputIndex }    
    ::={ rcSlaThroughputConfigTable 1 }     
    
RcSlaThroughputConfigEntry ::= SEQUENCE {
        rcSlaThroughputIndex			     Unsigned32 (0..100 ), 
        rcSlaThroughputOperId			     Unsigned32,
    	rcSlaThroughputObject                Unsigned32 (125..1000000),
    	rcSlaThroughputPktLength             INTEGER,       
	    rcSlaThroughputCount	             Unsigned32,  
	    rcSlaThroughputDuration              Unsigned32,
	    rcSlaThroughputEnable                TruthValue,
	    rcSlaThroughputStatus                INTEGER,  
	    rcSlaThroughputFailedNum             Unsigned32,
	    rcSlaThroughputCompleteNum           Unsigned32,
	    rcSlaThroughputMeasureStartTime      Unsigned32,
		rcSlaThroughputMeasureLastTime       Unsigned32,
		rcSlaThroughputMeasureEndTime        Unsigned32,
	    rcSlaThroughputRowStatus             RowStatus
	 }

rcSlaThroughputIndex       OBJECT-TYPE 
	SYNTAX      Unsigned32 (0..100 ) 
	MAX-ACCESS  not-accessible
    STATUS      deprecated
    DESCRIPTION
            "This object indicates a row in the rcSlaConfigTable.
        This value is an operation number configured by user."
    ::= { rcSlaThroughputConfigEntry 1 }  
    
rcSlaThroughputOperId       OBJECT-TYPE 
	SYNTAX      Unsigned32 
	MAX-ACCESS  read-write
    STATUS      deprecated
    DESCRIPTION
            "This object indicates a row in the rcSlaConfigTable.
        This value is an operation number configured by user."
    ::= { rcSlaThroughputConfigEntry 2 }  
    
rcSlaThroughputObject       OBJECT-TYPE 
	SYNTAX      Unsigned32 (125..1000000) 
	MAX-ACCESS  read-write
    STATUS      deprecated
    DESCRIPTION
            "This object indicates a row in the rcSlaConfigTable.
        This value is an operation number configured by user."
    ::= { rcSlaThroughputConfigEntry 3 }  
    
rcSlaThroughputPktLength       OBJECT-TYPE 
	SYNTAX       INTEGER{
	            length64      (0),
	            length128     (1),
	            length256     (2),
	            length512     (3),
	            length1024    (4),
	            length1280    (5),
	            length1518    (6)
	            }
 
	MAX-ACCESS  read-write
    STATUS      deprecated
    DESCRIPTION
            "This object indicates a row in the rcSlaConfigTable.
        This value is an operation number configured by user."
    ::= { rcSlaThroughputConfigEntry 4 }     
    
rcSlaThroughputCount       OBJECT-TYPE 
	SYNTAX      Unsigned32 
	MAX-ACCESS  read-write
    STATUS      deprecated
    DESCRIPTION
            "This object indicates a row in the rcSlaConfigTable.
        This value is an operation number configured by user."
    ::= { rcSlaThroughputConfigEntry 5 }  
    
rcSlaThroughputDuration       OBJECT-TYPE 
	SYNTAX      Unsigned32 
	MAX-ACCESS  read-write
    STATUS      deprecated
    DESCRIPTION
            "This object indicates a row in the rcSlaConfigTable.
        This value is an operation number configured by user."
    ::= { rcSlaThroughputConfigEntry 6 }  
    
rcSlaThroughputEnable       OBJECT-TYPE 
	SYNTAX      TruthValue 
	MAX-ACCESS  read-write
    STATUS      deprecated
    DESCRIPTION
            "This object indicates a row in the rcSlaConfigTable.
        This value is an operation number configured by user."
    ::= { rcSlaThroughputConfigEntry 7 }  
    
rcSlaThroughputStatus       OBJECT-TYPE 
    SYNTAX      INTEGER {
                  	throughput_init		(1),
	              	throughput_Active   (2),
                  	throughput_Complete (3),
                 	throughput_Disturb  (4)    
                  }  
                
	MAX-ACCESS  read-only
    STATUS      deprecated
    DESCRIPTION
            "This object indicates a row in the rcSlaConfigTable.
        This value is an operation number configured by user."
    ::= { rcSlaThroughputConfigEntry 8 }     
    
rcSlaThroughputCompleteNum       OBJECT-TYPE 
	SYNTAX      Unsigned32 
	MAX-ACCESS  read-only
    STATUS      deprecated
    DESCRIPTION
            "This object indicates a row in the rcSlaConfigTable.
        This value is an operation number configured by user."
    ::= { rcSlaThroughputConfigEntry 9 } 

rcSlaThroughputFailedNum       OBJECT-TYPE 
	SYNTAX      Unsigned32 
	MAX-ACCESS  read-only
    STATUS      deprecated
    DESCRIPTION
            "This object indicates a row in the rcSlaConfigTable.
        This value is an operation number configured by user."
    ::= { rcSlaThroughputConfigEntry 10 }    
    
    
rcSlaThroughputMeasureStartTime       OBJECT-TYPE 
	SYNTAX      Unsigned32 
	MAX-ACCESS  read-write
    STATUS      deprecated
    DESCRIPTION
            "This object indicates a row in the rcSlaConfigTable.
        This value is an operation number configured by user."
    ::= { rcSlaThroughputConfigEntry 11 } 
  
rcSlaThroughputMeasureEndTime       OBJECT-TYPE 
	SYNTAX      Unsigned32 
	MAX-ACCESS  read-write
    STATUS      deprecated
    DESCRIPTION
            "This object indicates a row in the rcSlaConfigTable.
        This value is an operation number configured by user."
    ::= { rcSlaThroughputConfigEntry 12 } 


rcSlaThroughputMeasureLastTime       OBJECT-TYPE 
	SYNTAX      Unsigned32 
	MAX-ACCESS  read-write
    STATUS      deprecated
    DESCRIPTION
            "This object indicates a row in the rcSlaConfigTable.
        This value is an operation number configured by user."
    ::= { rcSlaThroughputConfigEntry 13 } 
    
    
rcSlaThroughputRowStatus       OBJECT-TYPE 
	SYNTAX      RowStatus 
	MAX-ACCESS  read-write
    STATUS      deprecated
    DESCRIPTION
            "This object indicates a row in the rcSlaConfigTable.
        This value is an operation number configured by user."
    ::= { rcSlaThroughputConfigEntry 14 } 
    
    
    
 rcSlaThroughputResultTable  OBJECT-TYPE
    SYNTAX      SEQUENCE OF RcSlaThroughputResultEntry
    MAX-ACCESS  not-accessible
    STATUS      deprecated
    DESCRIPTION
        "This table contains sla  control data."
    ::= { rcSlaThroughputGroup 2 }

rcSlaThroughputResultEntry   OBJECT-TYPE
    SYNTAX      RcSlaThroughputResultEntry
    MAX-ACCESS  not-accessible
    STATUS      deprecated
    DESCRIPTION
        "A collection of objects that define three conceptual
    control row : slaY.1731EntryTable, slaIcmpEntryTable, slaSchEntryTable.
   		The 'slaY.1731EntryTable' is used to control y1731 operation .
    	The following objects must be specified in order to create this 
    conceptual row.
    	- rcSlaConfigOperType
    	- rcSlaConfigVlanId
    	- rcSlaConfigMDLevel
    	- rcSlaConfigDestMacAddr 
    	- rcSlaConfigRMepId
    	The ' slaIcmpEntryTable' is used to control ICMP operation .
    	The following objects must be specified in order to create this 
    conceptual row.
    	- rcSlaConfigOperType
    	- rcSlaConfigDestIpAddr
        The ' slaIcmpSchTable' is used to control operation schduled."
	INDEX        {  rcSlaThroughputIndex,
					rcSlaThroughputResultId }    
    ::={ rcSlaThroughputResultTable 1 }     
    
RcSlaThroughputResultEntry ::= SEQUENCE {
        rcSlaThroughputResultId			     Unsigned32, 
       	rcSlaThroughputTestStartTime         Unsigned32,
    	rcSlaThroughputTestEndTime           Unsigned32, 
    	rcSlaThroughputTestLastTime          Unsigned32,      
	    rcSlaThroughputLocalSendPStatics     Counter64,
	    rcSlaThroughputLocalSendBStatics     Counter64,
	    rcSlaThroughputLocalReceivePStatics  Counter64,
	    rcSlaThroughputLocalReceiveBStatics  Counter64,
	    rcSlaThroughputRemoteSendPStatics    Counter64,
	    rcSlaThroughputRemoteSendBStatics    Counter64,
	    rcSlaThroughputRemoteReceivePStatics Counter64,
	    rcSlaThroughputRemoteReceiveBStatics Counter64
	}

rcSlaThroughputResultId       OBJECT-TYPE 
	SYNTAX      Unsigned32
	MAX-ACCESS  not-accessible
    STATUS      deprecated
    DESCRIPTION
            "This object indicates a row in the rcSlaConfigTable.
        This value is an operation number configured by user."
    ::= { rcSlaThroughputResultEntry 1 }  
    
    
rcSlaThroughputTestStartTime       OBJECT-TYPE 
	SYNTAX      Unsigned32 
	MAX-ACCESS  read-write
    STATUS      deprecated
    DESCRIPTION
            "This object indicates a row in the rcSlaConfigTable.
        This value is an operation number configured by user."
    ::= { rcSlaThroughputResultEntry 2 } 
  
rcSlaThroughputTestEndTime       OBJECT-TYPE 
	SYNTAX      Unsigned32 
	MAX-ACCESS  read-write
    STATUS      deprecated
    DESCRIPTION
            "This object indicates a row in the rcSlaConfigTable.
        This value is an operation number configured by user."
    ::= { rcSlaThroughputResultEntry 3 } 


rcSlaThroughputTestLastTime       OBJECT-TYPE 
	SYNTAX      Unsigned32 
	MAX-ACCESS  read-write
    STATUS      deprecated
    DESCRIPTION
            "This object indicates a row in the rcSlaConfigTable.
        This value is an operation number configured by user."
    ::= { rcSlaThroughputResultEntry 4 } 

rcSlaThroughputLocalSendPStatics       OBJECT-TYPE 
	SYNTAX      Counter64 
	MAX-ACCESS  read-write
    STATUS      deprecated
    DESCRIPTION
            "This object indicates a row in the rcSlaConfigTable.
        This value is an operation number configured by user."
    ::= { rcSlaThroughputResultEntry 5 } 

rcSlaThroughputLocalSendBStatics       OBJECT-TYPE 
	SYNTAX      Counter64 
	MAX-ACCESS  read-write
    STATUS      deprecated
    DESCRIPTION
            "This object indicates a row in the rcSlaConfigTable.
        This value is an operation number configured by user."
    ::= { rcSlaThroughputResultEntry 6 } 
    
rcSlaThroughputLocalReceivePStatics       OBJECT-TYPE 
	SYNTAX      Counter64 
	MAX-ACCESS  read-write
    STATUS      deprecated
    DESCRIPTION
            "This object indicates a row in the rcSlaConfigTable.
        This value is an operation number configured by user."
    ::= { rcSlaThroughputResultEntry 7 } 

rcSlaThroughputLocalReceiveBStatics       OBJECT-TYPE 
	SYNTAX      Counter64 
	MAX-ACCESS  read-write
    STATUS      deprecated
    DESCRIPTION
            "This object indicates a row in the rcSlaConfigTable.
        This value is an operation number configured by user."
    ::= { rcSlaThroughputResultEntry 8 } 

rcSlaThroughputRemoteSendPStatics       OBJECT-TYPE 
	SYNTAX      Counter64 
	MAX-ACCESS  read-write
    STATUS      deprecated
    DESCRIPTION
            "This object indicates a row in the rcSlaConfigTable.
        This value is an operation number configured by user."
    ::= { rcSlaThroughputResultEntry 9 } 

rcSlaThroughputRemoteSendBStatics       OBJECT-TYPE 
	SYNTAX      Counter64 
	MAX-ACCESS  read-write
    STATUS      deprecated
    DESCRIPTION
            "This object indicates a row in the rcSlaConfigTable.
        This value is an operation number configured by user."
    ::= { rcSlaThroughputResultEntry 10 } 

rcSlaThroughputRemoteReceivePStatics       OBJECT-TYPE 
	SYNTAX      Counter64 
	MAX-ACCESS  read-write
    STATUS      deprecated
    DESCRIPTION
            "This object indicates a row in the rcSlaConfigTable.
        This value is an operation number configured by user."
    ::= { rcSlaThroughputResultEntry 11 } 

rcSlaThroughputRemoteReceiveBStatics       OBJECT-TYPE 
	SYNTAX      Counter64 
	MAX-ACCESS  read-write
    STATUS      deprecated
    DESCRIPTION
            "This object indicates a row in the rcSlaConfigTable.
        This value is an operation number configured by user."
    ::= { rcSlaThroughputResultEntry 12 }   
    
rcSlaThroughputResultTrap NOTIFICATION-TYPE
        OBJECTS {   rcSlaThroughputResultId
                }
        STATUS  deprecated
        DESCRIPTION
          ""
       ::= { rcSlaThroughputGroup 4 }
 ---告警阈值表
rcSlaThresholdTable  OBJECT-TYPE
    SYNTAX      SEQUENCE OF RcSlaThresholdEntry
    MAX-ACCESS  not-accessible
    STATUS      current
    DESCRIPTION
        "This table contains sla trap threshold."
    ::= { rcSlaThresholdGroup 1 }

rcSlaThresholdEntry   OBJECT-TYPE
    SYNTAX      RcSlaThresholdEntry
    MAX-ACCESS  not-accessible
    STATUS      current
    DESCRIPTION
        "The entry of rcSlaThresholdTable."
	INDEX        { rcSlaTrapOperId }    
    ::={ rcSlaThresholdTable 1 }     
    
RcSlaThresholdEntry ::= SEQUENCE {
        rcSlaTrapOperId                      Unsigned32,
        rcSlaTrapEnableType			         BITS, 
       	rcSlaPktLossRateCurrThreshold        INTEGER,
    	rcSlaPktLossRateAverThreshold        INTEGER, 
    	rcSlaDelayCurrThreshold              Counter32,      
	    rcSlaDelayCurrThresholdSD            Counter32,
	    rcSlaDelayCurrThresholdDS            Counter32,
	    rcSlaDelayAverThreshold              Counter32,
	    rcSlaDelayAverThresholdSD            Counter32,
	    rcSlaDelayAverThresholdDS            Counter32,
	    rcSlaJitterCurrThreshold             Counter32,
	    rcSlaJitterCurrThresholdSD           Counter32,
	    rcSlaJitterCurrThresholdDS           Counter32,
	    rcSlaJitterAverThreshold             Counter32,
	    rcSlaJitterAverThresholdSD           Counter32,
        rcSlaJitterAverThresholdDS           Counter32,
        rcSlaPktLossRateCurrThresholdSD      Counter32,
        rcSlaPktLossRateCurrThresholdDS      Counter32,
        rcSlaPktLossRateAverThresholdSD      Counter32,
        rcSlaPktLossRateAverThresholdDS      Counter32
	}
 
rcSlaTrapOperId           OBJECT-TYPE 
	SYNTAX      Unsigned32 
	MAX-ACCESS  not-accessible
    STATUS      current
    DESCRIPTION
            "This object indicates a row in the rcSlaThresholdTable.
        This value is an operation number configured by user."
    ::= { rcSlaThresholdEntry 1 }  
 
rcSlaTrapEnableType       OBJECT-TYPE 
	SYNTAX      BITS
	MAX-ACCESS  read-write
    STATUS      current
    DESCRIPTION
            "The enable status of threshold trap."
    ::= { rcSlaThresholdEntry 2 }  

rcSlaPktLossRateCurrThreshold       OBJECT-TYPE 
	SYNTAX      INTEGER(0..10000)
	MAX-ACCESS  read-write
    STATUS      current
    DESCRIPTION
            "The pkt loss rate threshold of the last test."
    ::= { rcSlaThresholdEntry 3 }
    
rcSlaPktLossRateAverThreshold       OBJECT-TYPE 
	SYNTAX      INTEGER(0..10000)
	MAX-ACCESS  read-write
    STATUS      current
    DESCRIPTION
            "The average pkt loss rate threshold of all test."
    ::= { rcSlaThresholdEntry 4 }       
    
rcSlaDelayCurrThreshold       OBJECT-TYPE 
	SYNTAX      Counter32
	MAX-ACCESS  read-write
    STATUS      current
    DESCRIPTION
            "The RTT delay threshold of the last test."
    ::= { rcSlaThresholdEntry 5 }   
    
rcSlaDelayCurrThresholdSD       OBJECT-TYPE 
	SYNTAX      Counter32
	MAX-ACCESS  read-write
    STATUS      current
    DESCRIPTION
            "The delay threshold of the last test from source to destination."
    ::= { rcSlaThresholdEntry 6 }   
    
rcSlaDelayCurrThresholdDS       OBJECT-TYPE 
	SYNTAX      Counter32
	MAX-ACCESS  read-write
    STATUS      current
    DESCRIPTION
            "The delay threshold of the last test from destination to source."
    ::= { rcSlaThresholdEntry 7 }     
    
rcSlaDelayAverThreshold       OBJECT-TYPE 
	SYNTAX      Counter32
	MAX-ACCESS  read-write
    STATUS      current
    DESCRIPTION
            "The RTT average delay threshold of all test."
    ::= { rcSlaThresholdEntry 8 }         
    
rcSlaDelayAverThresholdSD       OBJECT-TYPE 
	SYNTAX      Counter32
	MAX-ACCESS  read-write
    STATUS      current
    DESCRIPTION
            "The average delay threshold of all test from source to destination."
    ::= { rcSlaThresholdEntry 9 }     
    
rcSlaDelayAverThresholdDS       OBJECT-TYPE 
	SYNTAX      Counter32
	MAX-ACCESS  read-write
    STATUS      current
    DESCRIPTION
            "The average delay threshold of all test from destination to source."
    ::= { rcSlaThresholdEntry 10 }     
    
rcSlaJitterCurrThreshold       OBJECT-TYPE 
	SYNTAX      Counter32
	MAX-ACCESS  read-write
    STATUS      current
    DESCRIPTION
            "The RTT jitter threshold of the last test."
    ::= { rcSlaThresholdEntry 11 }       
    
rcSlaJitterCurrThresholdSD       OBJECT-TYPE 
	SYNTAX      Counter32
	MAX-ACCESS  read-write
    STATUS      current
    DESCRIPTION
            "The jitter threshold of the last test from source to destination."
    ::= { rcSlaThresholdEntry 12 }     
    
rcSlaJitterCurrThresholdDS       OBJECT-TYPE 
	SYNTAX      Counter32
	MAX-ACCESS  read-write
    STATUS      current
    DESCRIPTION
            "The jitter threshold of the last test from destination to source."
    ::= { rcSlaThresholdEntry 13 }       
    
rcSlaJitterAverThreshold       OBJECT-TYPE 
	SYNTAX      Counter32
	MAX-ACCESS  read-write
    STATUS      current
    DESCRIPTION
            "The RTT average jitter threshold of all test."
    ::= { rcSlaThresholdEntry 14 }    
        
rcSlaJitterAverThresholdSD       OBJECT-TYPE 
	SYNTAX      Counter32
	MAX-ACCESS  read-write
    STATUS      current
    DESCRIPTION
            "The average jitter threshold of all test from source to destination."
    ::= { rcSlaThresholdEntry 15 }    
    
rcSlaJitterAverThresholdDS       OBJECT-TYPE 
	SYNTAX      Counter32
	MAX-ACCESS  read-write
    STATUS      current
    DESCRIPTION
            "The average jitter threshold of all test from destination to source."
    ::= { rcSlaThresholdEntry 16 }   
rcSlaPktLossRateCurrThresholdSD     OBJECT-TYPE 
    SYNTAX      Counter32
    MAX-ACCESS  read-write
    STATUS      current
    DESCRIPTION
            "The pkt loss rate threshold of the last test from source to destination."
    ::= { rcSlaThresholdEntry 17 }   
rcSlaPktLossRateCurrThresholdDS     OBJECT-TYPE 
    SYNTAX      Counter32
    MAX-ACCESS  read-write
    STATUS      current
    DESCRIPTION
            "The pkt loss rate threshold of the last test from destination to source."
    ::= { rcSlaThresholdEntry 18 }   
rcSlaPktLossRateAverThresholdSD     OBJECT-TYPE 
    SYNTAX      Counter32
    MAX-ACCESS  read-write
    STATUS      current
    DESCRIPTION
            "The average pkt loss rate threshold of all test from source to destination."
    ::= { rcSlaThresholdEntry 19 }   
rcSlaPktLossRateAverThresholdDS     OBJECT-TYPE 
    SYNTAX      Counter32
    MAX-ACCESS  read-write
    STATUS      current
    DESCRIPTION
            "The average pkt loss rate threshold of all test from destination to source."
    ::= { rcSlaThresholdEntry 20 }   
    
 ---告警信息表
rcSlaThresholdTestResultTable  OBJECT-TYPE
    SYNTAX      SEQUENCE OF RcSlaThresholdTestResultEntry
    MAX-ACCESS  not-accessible
    STATUS      current
    DESCRIPTION
        "This table contains sla test result."
    ::= { rcSlaThresholdGroup 2 }

rcSlaThresholdTestResultEntry   OBJECT-TYPE
    SYNTAX      RcSlaThresholdTestResultEntry
    MAX-ACCESS  not-accessible
    STATUS      current
    DESCRIPTION
        "The entry of rcSlaThresholdTestResultTable."
	INDEX        { rcSlaTrapOperId }    
    ::={ rcSlaThresholdTestResultTable 1 }     
    
RcSlaThresholdTestResultEntry ::= SEQUENCE {
        rcSlaCurrResultTrap			         BITS, 
       	rcSlaAverResultTrap                  BITS,
    	rcSlaPktCurrLossRate                 INTEGER,    
    	rcSlaPktAverLossRate                 INTEGER,
    	rcSlaCurrDelay                       Counter32,      
	    rcSlaCurrDelaySD                     Counter32,
	    rcSlaCurrDelayDS                     Counter32,
	    rcSlaAverDelay                       Counter32,
	    rcSlaAverDelaySD                     Counter32,
	    rcSlaAverDelayDS                     Counter32,
	    rcSlaCurrJitter                      Counter32,
	    rcSlaCurrJitterSD                    Counter32,
	    rcSlaCurrJitterDS                    Counter32,
	    rcSlaAverJitter                      Counter32,
	    rcSlaAverJitterSD                    Counter32,
        rcSlaAverJitterDS                    Counter32,
        rcSlaPktCurrLossRateSD               Counter32,
        rcSlaPktCurrLossRateDS               Counter32,
        rcSlaPktAverLossRateSD               Counter32,
        rcSlaPktAverLossRateDS               Counter32
	}

rcSlaCurrResultTrap       OBJECT-TYPE 
	SYNTAX      BITS
	MAX-ACCESS  read-only
    STATUS      current
    DESCRIPTION
            "The sla result trap status of the last test."
    ::= { rcSlaThresholdTestResultEntry 1 }  

rcSlaAverResultTrap       OBJECT-TYPE 
	SYNTAX      BITS
	MAX-ACCESS  read-only
    STATUS      current
    DESCRIPTION
            "The sla average result trap status of all test."
    ::= { rcSlaThresholdTestResultEntry 2 }  
    
rcSlaPktCurrLossRate       OBJECT-TYPE 
	SYNTAX      INTEGER(0..10000)
	MAX-ACCESS  read-only
    STATUS      current
    DESCRIPTION
            "The pkt loss rate of the last test."
    ::= { rcSlaThresholdTestResultEntry 3 }     
    
rcSlaPktAverLossRate       OBJECT-TYPE 
	SYNTAX      INTEGER(0..10000)
	MAX-ACCESS  read-only
    STATUS      current
    DESCRIPTION
            "The average pkt loss rate of all test."
    ::= { rcSlaThresholdTestResultEntry 4 }     
    
rcSlaCurrDelay       OBJECT-TYPE 
	SYNTAX      Counter32
	MAX-ACCESS  read-only
    STATUS      current
    DESCRIPTION
            "The RTT delay of the last test."
    ::= { rcSlaThresholdTestResultEntry 5 }     
    
rcSlaCurrDelaySD       OBJECT-TYPE 
	SYNTAX      Counter32
	MAX-ACCESS  read-only
    STATUS      current
    DESCRIPTION
            "The delay of the last test from source to destination."
    ::= { rcSlaThresholdTestResultEntry 6 }       
    
rcSlaCurrDelayDS       OBJECT-TYPE 
	SYNTAX      Counter32
	MAX-ACCESS  read-only
    STATUS      current
    DESCRIPTION
            "The delay of the last test from destination to source."
    ::= { rcSlaThresholdTestResultEntry 7 }       
    
rcSlaAverDelay       OBJECT-TYPE 
	SYNTAX      Counter32
	MAX-ACCESS  read-only
    STATUS      current
    DESCRIPTION
            "The RTT average delay of all test."
    ::= { rcSlaThresholdTestResultEntry 8 }   

rcSlaAverDelaySD       OBJECT-TYPE 
	SYNTAX      Counter32
	MAX-ACCESS  read-only
    STATUS      current
    DESCRIPTION
            "The average delay of all test from source to destination."
    ::= { rcSlaThresholdTestResultEntry 9 } 

rcSlaAverDelayDS       OBJECT-TYPE 
	SYNTAX      Counter32
	MAX-ACCESS  read-only
    STATUS      current
    DESCRIPTION
            "The average delay of all test from destination to source."
    ::= { rcSlaThresholdTestResultEntry 10 } 

rcSlaCurrJitter       OBJECT-TYPE 
	SYNTAX      Counter32
	MAX-ACCESS  read-only
    STATUS      current
    DESCRIPTION
            "The RTT jitter of the last test."
    ::= { rcSlaThresholdTestResultEntry 11 } 

rcSlaCurrJitterSD       OBJECT-TYPE 
	SYNTAX      Counter32
	MAX-ACCESS  read-only
    STATUS      current
    DESCRIPTION
            "The jitter of the last test from source to destination."
    ::= { rcSlaThresholdTestResultEntry 12 } 
    
rcSlaCurrJitterDS       OBJECT-TYPE 
	SYNTAX      Counter32
	MAX-ACCESS  read-only
    STATUS      current
    DESCRIPTION
            "The jitter of the last test from destination to source."
    ::= { rcSlaThresholdTestResultEntry 13 }    
    
rcSlaAverJitter       OBJECT-TYPE 
	SYNTAX      Counter32
	MAX-ACCESS  read-only
    STATUS      current
    DESCRIPTION
            "The RTT average jitter of all test."
    ::= { rcSlaThresholdTestResultEntry 14 }      
    
rcSlaAverJitterSD       OBJECT-TYPE 
	SYNTAX      Counter32
	MAX-ACCESS  read-only
    STATUS      current
    DESCRIPTION
            "The average jitter of all test from source to destination."
    ::= { rcSlaThresholdTestResultEntry 15 }       
    
rcSlaAverJitterDS       OBJECT-TYPE 
	SYNTAX      Counter32
	MAX-ACCESS  read-only
    STATUS      current
    DESCRIPTION
            "The average jitter of all test from destination to source."
    ::= { rcSlaThresholdTestResultEntry 16 }       

rcSlaPktCurrLossRateSD       OBJECT-TYPE 
    SYNTAX      Counter32
    MAX-ACCESS  read-only
    STATUS      current
    DESCRIPTION
            "The pkt loss rate of the last test from source to destination."
    ::= { rcSlaThresholdTestResultEntry 17 }       
rcSlaPktCurrLossRateDS       OBJECT-TYPE 
    SYNTAX      Counter32
    MAX-ACCESS  read-only
    STATUS      current
    DESCRIPTION
            "The pkt loss rate of the last test from destination to source."
    ::= { rcSlaThresholdTestResultEntry 18 }       
rcSlaPktAverLossRateSD       OBJECT-TYPE 
    SYNTAX      Counter32
    MAX-ACCESS  read-only
    STATUS      current
    DESCRIPTION
            "The average pkt loss rate of all test from source to destination."
    ::= { rcSlaThresholdTestResultEntry 19 }       
rcSlaPktAverLossRateDS       OBJECT-TYPE 
    SYNTAX      Counter32
    MAX-ACCESS  read-only
    STATUS      current
    DESCRIPTION
            "The average pkt loss rate of all test from destination to source."
    ::= { rcSlaThresholdTestResultEntry 20 }       


--阈值告警    
rcSlaThresholdTrapGroup  OBJECT IDENTIFIER ::= {rcSlaThresholdGroup 3} 

rcSlaCurrTestResultBeyondTrap   NOTIFICATION-TYPE
        OBJECTS {   rcSlaCurrResultTrap,
                    rcSlaPktCurrLossRate,
                    rcSlaPktLossRateCurrThreshold,
                    rcSlaCurrDelay,
                    rcSlaDelayCurrThreshold,
                    rcSlaCurrDelaySD,
                    rcSlaDelayCurrThresholdSD,
                    rcSlaCurrDelayDS,
                    rcSlaDelayCurrThresholdDS,
                    rcSlaCurrJitter,
                    rcSlaJitterCurrThreshold,
                    rcSlaCurrJitterSD,
                    rcSlaJitterCurrThresholdSD,
                    rcSlaCurrJitterDS,
                    rcSlaJitterCurrThresholdDS,                  
                    rcSlaPktCurrLossRateSD,
                    rcSlaPktLossRateCurrThresholdSD,
                    rcSlaPktCurrLossRateDS,
                    rcSlaPktLossRateCurrThresholdDS
                }
        STATUS  current
        DESCRIPTION
          "Send this trap when result beyond threshold of the last test."
       ::= { rcSlaThresholdTrapGroup 1 }

rcSlaAverTestResultBeyondTrap   NOTIFICATION-TYPE
        OBJECTS {   rcSlaAverResultTrap,
                    rcSlaPktAverLossRate,
                    rcSlaPktLossRateAverThreshold,
                    rcSlaAverDelay,
                    rcSlaDelayAverThreshold,
                    rcSlaAverDelaySD,
                    rcSlaDelayAverThresholdSD,
                    rcSlaAverDelayDS,
                    rcSlaDelayAverThresholdDS,
                    rcSlaAverJitter,
                    rcSlaJitterAverThreshold,
                    rcSlaAverJitterSD,
                    rcSlaJitterAverThresholdSD,
                    rcSlaAverJitterDS,
                    rcSlaJitterAverThresholdDS,                   
                    rcSlaPktAverLossRateSD,
                    rcSlaPktLossRateAverThresholdSD,
                    rcSlaPktAverLossRateDS,
                    rcSlaPktLossRateAverThresholdDS
                }
        STATUS  current
        DESCRIPTION
          "Send this trap when average result beyond threshold of all test."
       ::= { rcSlaThresholdTrapGroup 2 }
END
