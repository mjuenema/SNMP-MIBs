--  =================================================================
-- Copyright (C) 2009 by  HUAWEI TECHNOLOGIES. All rights reserved
-- 
-- Description:
-- Reference:
-- Version: V1.0
-- History:
-- 2011-01-12,<contents>
-- =================================================================

    HUAWEI-SECURITY-IPS-MIB DEFINITIONS ::= BEGIN
 
        IMPORTS
	   	IpAddress, Counter32, Gauge32, OBJECT-TYPE, MODULE-IDENTITY
			FROM SNMPv2-SMI 
		MODULE-COMPLIANCE, OBJECT-GROUP, NOTIFICATION-GROUP          
		            FROM SNMPv2-CONF
    		enterprises			
		            FROM RFC1155-SMI;     
    
        hwSecIpsTraps MODULE-IDENTITY 
            LAST-UPDATED "200304100900Z"	
            ORGANIZATION 
                "Huawei Technologies co.,Ltd."
            CONTACT-INFO 
                "
                R&D BeiJing, Huawei Technologies co.,Ltd.
                Huawei Bld.,NO.3 Xinxi Rd.,
                Shang-Di Information Industry Base,
                Hai-Dian District Beijing P.R. China
                Zip:100085
                Http://www.huawei.com
                E-mail:support@huawei.com
                "
            DESCRIPTION 
                "
                V1.00
                The HUAWEI-SECSTAT-MIB contains objects to manage the security statistics for firewall product.
                "
            ::= { hwSecIPS 1 }

--
-- Node definitions
--                       
 	-- 1.3.6.1.4.1.2011
	huawei OBJECT IDENTIFIER ::= { enterprises 2011 }
        
        -- 1.3.6.1.4.1.2011.6
        huaweiUtility OBJECT IDENTIFIER ::= { huawei 6 }
        
        -- 1.3.6.1.4.1.2011.6.122
        hwSecurity OBJECT IDENTIFIER ::= { huaweiUtility 122 }          
        
        -- 1.3.6.1.4.1.2011.6.122.43
        hwSecIPS OBJECT IDENTIFIER ::= { hwSecurity 43 }
        
        -- 1.3.6.1.4.1.2011.6.122.43.1
        hwSecIpsTraps OBJECT IDENTIFIER ::= { hwSecIPS 1 } 
        
        -- 1.3.6.1.4.1.2011.6.122.43.1.1
        hwSecIpsObjests OBJECT IDENTIFIER ::= { hwSecIpsTraps 1 } 
                
        -- 1.3.6.1.4.1.2011.6.122.43.1.1.1
        hwSecIpsDetectObjects OBJECT IDENTIFIER ::= { hwSecIpsObjests 1 }
        
        -- 1.3.6.1.4.1.2011.6.122.43.1.1.1.1
        hwSecIpsDetectProtoType OBJECT-TYPE
            SYNTAX OCTET STRING (SIZE (0..255))
            MAX-ACCESS accessible-for-notify
            STATUS current
            DESCRIPTION
                "
                protocol name (type)
                "
            ::= { hwSecIpsDetectObjects 1 }
        
        -- 1.3.6.1.4.1.2011.6.122.43.1.1.1.2
        hwSecIpsDetectAction OBJECT-TYPE
            SYNTAX OCTET STRING (SIZE (0..255))
            MAX-ACCESS accessible-for-notify
            STATUS current
            DESCRIPTION
                "
                signature action
                "
            ::= { hwSecIpsDetectObjects 2 }
        
      -- 1.3.6.1.4.1.2011.6.122.43.1.1.1.3
        hwSecIpsDetectSrcIp OBJECT-TYPE
            SYNTAX IpAddress
            MAX-ACCESS accessible-for-notify
            STATUS current
            DESCRIPTION
                "
                source IP address
                "
            ::= { hwSecIpsDetectObjects 3 } 
            
      -- 1.3.6.1.4.1.2011.6.122.43.1.1.1.4
        hwSecIpsDetectDstIp OBJECT-TYPE
            SYNTAX IpAddress
            MAX-ACCESS accessible-for-notify
            STATUS current
            DESCRIPTION
                "
                destination IP address
                "
            ::= { hwSecIpsDetectObjects 4 }

      -- 1.3.6.1.4.1.2011.6.122.43.1.1.1.5
        hwSecIpsDetectSrcPort OBJECT-TYPE
            SYNTAX Gauge32
            MAX-ACCESS accessible-for-notify
            STATUS current
            DESCRIPTION
                "
                source port
                "
            ::= { hwSecIpsDetectObjects 5 }
 
       -- 1.3.6.1.4.1.2011.6.122.43.1.1.1.6
        hwSecIpsDetectDstPort OBJECT-TYPE
            SYNTAX Gauge32
            MAX-ACCESS accessible-for-notify
            STATUS current
            DESCRIPTION
                "
                destination port
                "
            ::= { hwSecIpsDetectObjects 6 }
 
        -- 1.3.6.1.4.1.2011.6.122.43.1.1.1.7
        hwSecIpsDetectSrcVrf OBJECT-TYPE
            SYNTAX OCTET STRING (SIZE (0..255))
            MAX-ACCESS accessible-for-notify
            STATUS current
            DESCRIPTION
                "
                source vpn-instance name
                "
            ::= { hwSecIpsDetectObjects 7 }
       
         -- 1.3.6.1.4.1.2011.6.122.43.1.1.1.8
        hwSecIpsDetectDstVrf OBJECT-TYPE
            SYNTAX OCTET STRING (SIZE (0..255))
            MAX-ACCESS accessible-for-notify
            STATUS current
            DESCRIPTION
                "
                destination vpn-instance name
                "
            ::= { hwSecIpsDetectObjects 8 }
      
          -- 1.3.6.1.4.1.2011.6.122.43.1.1.1.9
        hwSecIpsDetectDirection OBJECT-TYPE
            SYNTAX OCTET STRING (SIZE (0..255))
            MAX-ACCESS accessible-for-notify
            STATUS current
            DESCRIPTION
                "
                direction
                "
            ::= { hwSecIpsDetectObjects 9 }
     
          -- 1.3.6.1.4.1.2011.6.122.43.1.1.1.10
        hwSecIpsDetectEventNum OBJECT-TYPE
            SYNTAX Gauge32
            MAX-ACCESS accessible-for-notify
            STATUS current
            DESCRIPTION
                "
                the number of hitting signature
                "
            ::= { hwSecIpsDetectObjects 10 }
     
           -- 1.3.6.1.4.1.2011.6.122.43.1.1.1.11
        hwSecIpsDetectName OBJECT-TYPE
            SYNTAX OCTET STRING (SIZE (0..255))
            MAX-ACCESS accessible-for-notify
            STATUS current
            DESCRIPTION
                "
                signature name
                "
            ::= { hwSecIpsDetectObjects 11 }

             -- 1.3.6.1.4.1.2011.6.122.43.1.1.1.12
        hwSecIpsDetectLevel OBJECT-TYPE
            SYNTAX OCTET STRING (SIZE (0..255))
            MAX-ACCESS accessible-for-notify
            STATUS current
            DESCRIPTION
                "
                signature level
                "
            ::= { hwSecIpsDetectObjects 12 }
      
              -- 1.3.6.1.4.1.2011.6.122.43.1.1.1.13
        hwSecIpsDetectId OBJECT-TYPE
            SYNTAX Gauge32
            MAX-ACCESS accessible-for-notify
            STATUS current
            DESCRIPTION
                "
                signature Id
                "
            ::= { hwSecIpsDetectObjects 13 }
  
              -- 1.3.6.1.4.1.2011.6.122.43.1.1.1.14
        hwSecIpsDetectClassType OBJECT-TYPE
            SYNTAX OCTET STRING (SIZE (0..255))
            MAX-ACCESS accessible-for-notify
            STATUS current
            DESCRIPTION
                "
                signature class type
                "
            ::= { hwSecIpsDetectObjects 14 }
  
              -- 1.3.6.1.4.1.2011.6.122.43.1.1.1.15
        hwSecIpsDetectClassTypeId OBJECT-TYPE
            SYNTAX OCTET STRING (SIZE (0..255))
            MAX-ACCESS accessible-for-notify
            STATUS current
            DESCRIPTION
                "
                signature class type Id
                "
            ::= { hwSecIpsDetectObjects 15 }
  
              -- 1.3.6.1.4.1.2011.6.122.43.1.1.1.16
        hwSecIpsDetectRel OBJECT-TYPE
            SYNTAX OCTET STRING (SIZE (0..255))
            MAX-ACCESS accessible-for-notify
            STATUS current
            DESCRIPTION
                "
                signature reliability
                "
            ::= { hwSecIpsDetectObjects 16 }
            
        -- 1.3.6.1.4.1.2011.6.122.43.1.1.1.17
        hwSecIpsDetectPolicyId OBJECT-TYPE
            SYNTAX Gauge32
            MAX-ACCESS accessible-for-notify
            STATUS current
            DESCRIPTION
                "
                policy Id
                "
            ::= { hwSecIpsDetectObjects 17 }

              -- 1.3.6.1.4.1.2011.6.122.43.1.1.2
        hwSecIpsSysObjests OBJECT IDENTIFIER ::= { hwSecIpsObjests 2 }

             -- 1.3.6.1.4.1.2011.6.122.43.1.1.2.1
        hwSecIpsSysSlotId OBJECT-TYPE
            SYNTAX Gauge32
            MAX-ACCESS accessible-for-notify
            STATUS current
            DESCRIPTION
                "
                IPS process unit slot Id
                "
            ::= { hwSecIpsSysObjests 1}

              -- 1.3.6.1.4.1.2011.6.122.43.1.1.2.2
        hwSecIpsSysCpuId OBJECT-TYPE
            SYNTAX Gauge32
            MAX-ACCESS accessible-for-notify
            STATUS current
            DESCRIPTION
                "
                IPS process unit CPU Id
                "
            ::= { hwSecIpsSysObjests 2}

             -- 1.3.6.1.4.1.2011.6.122.43.1.1.2.3
        hwSecIpsSysMemPercent OBJECT-TYPE
            SYNTAX Gauge32
            MAX-ACCESS accessible-for-notify
            STATUS current
            DESCRIPTION
                "
                memory used percent
                "
            ::= { hwSecIpsSysObjests 3}

             -- 1.3.6.1.4.1.2011.6.122.43.1.1.2.4
        hwSecIpsSysMemThreshold OBJECT-TYPE
            SYNTAX Gauge32
            MAX-ACCESS accessible-for-notify
            STATUS current
            DESCRIPTION
                "
                memory used threshold
                "
            ::= { hwSecIpsSysObjests 4}

                  
 			-- ===============================================
			-- definition of traps.      
			-- ===============================================
			-- 1.3.6.1.4.1.2011.6.122.43.1.2    
		    hwSecIpsAlert OBJECT IDENTIFIER ::= { hwSecIpsTraps 2 }
       	  -- 1.3.6.1.4.1.2011.6.122.43.1.2.1    	
            hwSecIpsDetectAlert NOTIFICATION-TYPE
            OBJECTS { hwSecIpsDetectProtoType, hwSecIpsDetectAction, hwSecIpsDetectSrcIp, hwSecIpsDetectDstIp, hwSecIpsDetectSrcPort, 
                  hwSecIpsDetectDstPort, hwSecIpsDetectSrcVrf, hwSecIpsDetectDstVrf, hwSecIpsDetectDirection, hwSecIpsDetectEventNum,
                   hwSecIpsDetectName, hwSecIpsDetectLevel, hwSecIpsDetectId, hwSecIpsDetectClassType, hwSecIpsDetectClassTypeId, hwSecIpsDetectRel
                  }
            STATUS current
            DESCRIPTION 
                "the warning of IPS detecting attack."
            ::= { hwSecIpsAlert 1 }
    
     		-- 1.3.6.1.4.1.2011.6.122.43.1.2.2    	
            hwSecIpsSysAlert NOTIFICATION-TYPE
            OBJECTS { hwSecIpsSysSlotId, hwSecIpsSysCpuId, hwSecIpsSysMemPercent, hwSecIpsSysMemThreshold
                    }
            STATUS current
            DESCRIPTION 
                "the warning of over memory used threshold.."
            ::= { hwSecIpsAlert 2 }
    
    	--conformance
        hwIPSConformance OBJECT IDENTIFIER ::= { hwSecIPS 2 }

        hwIPSCompliances OBJECT IDENTIFIER ::= { hwIPSConformance 1 }

        
        hwIPSCompliance MODULE-COMPLIANCE
            STATUS current
            DESCRIPTION 
                "Compliance statement for agents that provide full support for 
                hwBaseTrapMIB."
            MODULE -- this module
                MANDATORY-GROUPS { hwIPSObjectGroup, hwIPSTrapGroup }
            ::= { hwIPSCompliances 1 }

        
        hwIPSTrapGroups OBJECT IDENTIFIER ::= { hwIPSConformance 2 }

        
        hwIPSObjectGroup OBJECT-GROUP
            OBJECTS { hwSecIpsDetectProtoType, hwSecIpsDetectAction, hwSecIpsDetectSrcIp, hwSecIpsDetectDstIp, hwSecIpsDetectSrcPort, 
                  hwSecIpsDetectDstPort, hwSecIpsDetectSrcVrf, hwSecIpsDetectDstVrf, hwSecIpsDetectDirection, hwSecIpsDetectEventNum,
                   hwSecIpsDetectName, hwSecIpsDetectLevel, hwSecIpsDetectId, hwSecIpsDetectClassType, hwSecIpsDetectClassTypeId, hwSecIpsDetectRel,
                   hwSecIpsSysSlotId, hwSecIpsSysCpuId, hwSecIpsSysMemPercent, hwSecIpsSysMemThreshold
                  }
            STATUS current
            DESCRIPTION 
                "Group for ips trap objects."
            ::= { hwIPSTrapGroups 1 }

        
        hwIPSTrapGroup NOTIFICATION-GROUP
            NOTIFICATIONS { hwSecIpsDetectAlert, hwSecIpsSysAlert }
            STATUS current
            DESCRIPTION 
                "Group for all ips traps."
            ::= { hwIPSTrapGroups 2 }
  
    END

--
-- HUAWEI-SECURITY-IPS-MIB
--
