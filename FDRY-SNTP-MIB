FDRY-SNTP-MIB DEFINITIONS ::= BEGIN

IMPORTS
	MODULE-IDENTITY, OBJECT-TYPE,
			Integer32, Unsigned32	   	FROM SNMPv2-SMI	  			-- [RFC2578]
	RowStatus							FROM SNMPv2-TC 				-- [RFC2579]
	InetAddressType, InetAddress		FROM INET-ADDRESS-MIB		-- [RFC 4001]
	fdrySntp	 					   	FROM FOUNDRY-SN-ROOT-MIB 	-- [snroo101]
	;

fdrySntpMIB MODULE-IDENTITY
    LAST-UPDATED "201006020000Z"  -- 04 June 2010
    ORGANIZATION "Brocade Communications Systems, Inc."
    CONTACT-INFO
             "Technical Support Center
              130 Holger Way,
              San Jose, CA  95134
              Email:  ipsupport@brocade.com
              Phone: 1-800-752-8061
              URL:  www.brocade.com "
    DESCRIPTION
              "The Brocade Communications Systems proprietary MIB module for
               Simple Network Time Protocol(SNTP). It has new table combines
               Ipv4 and Ipv6 Simple Network Time Protocol server configuration.

               Copyright 1996-2010 Brocade Communications Systems, Inc.
               All rights reserved.
               This Brocade Communications Systems SNMP Management Information Base Specification
               embodies Brocade Communications Systems' confidential and proprietary
               intellectual property. Brocade Communications Systems retains all
               title and ownership in the Specification, including any revisions.

               This Specification is supplied AS IS, and Brocade Communications Systems makes
               no warranty, either express or implied, as to the use,
               operation, condition, or performance of the specification, and any unintended
               consequence it may on the user environment."

    REVISION        "201006020000Z"  -- 04 June 2010
    DESCRIPTION  "Changed the ORGANIZATION, CONTACT-INFO and DESCRIPTION fields."

    REVISION 	"200802250000Z"  -- 25 February 2008
    DESCRIPTION	"Initial version, obsoletes the earlier snNTPServerTable."

	::= { fdrySntp 1 }

	--
	-- Top level components of this MIB.
	--

	fdrySntpServer OBJECT IDENTIFIER ::= { fdrySntpMIB 1 }

	--
	-- Ipv4/Ipv6  SNTP server table
	--

	fdrySntpServerTable			 OBJECT-TYPE
		SYNTAX  SEQUENCE OF FdrySntpServerTable
		MAX-ACCESS  not-accessible
		STATUS  current
		DESCRIPTION
			  "Simple Network Time Protocol(SNTP) server table.
			   This table is not supported in NI devices from R5.3"
		::= { fdrySntpServer 1 }

	fdrySntpServerEntry			 OBJECT-TYPE
		SYNTAX  FdrySntpServerTable
		MAX-ACCESS  not-accessible
		STATUS  current
		DESCRIPTION
			  "An entry in the SNTP server table. This table uses running index as the Index to the table.
			  	Reasons to go for running index Scheme than IP addresses:
				1.	The table will be Virtual Routing and Forwarding(VRF) independent
					that multiple VRFs could share the same address type and address.
				2.	Index with address type and address could be potentially 17 unsigned integer, parsing and finding next index takes CPU time.
					The PDU gets to be huge too!
				3. 	IP address is just another attribute, they are supposed to be list of servers."

		INDEX   { fdrySntpServerIndex }
		::= { fdrySntpServerTable 1 }

	FdrySntpServerTable ::= SEQUENCE {
		fdrySntpServerIndex
			Unsigned32,
		fdrySntpServerAddrType
			InetAddressType,
		fdrySntpServerAddr
			InetAddress,
		fdrySntpServerVersion
			Integer32,
		fdrySntpServerRowStatus
			RowStatus
		}

	fdrySntpServerIndex OBJECT-TYPE
		SYNTAX  Unsigned32
		MAX-ACCESS  not-accessible
		STATUS  current
		DESCRIPTION
			  "The index to the SNTP server Table. Maximum 3 Sntp servers are supported."
		::= { fdrySntpServerEntry 1 }

	fdrySntpServerAddrType 			 OBJECT-TYPE
		SYNTAX  InetAddressType
		MAX-ACCESS  read-create
		STATUS  current
		DESCRIPTION
			  "SNTP server IP address Type. Supported address types are ipv4(1) and ipv6(2)"
		DEFVAL  { ipv4 }
		::= { fdrySntpServerEntry 2 }

	fdrySntpServerAddr 			 OBJECT-TYPE
		SYNTAX  InetAddress
		MAX-ACCESS  read-create
		STATUS  current
		DESCRIPTION
			  "SNTP server IP address."
		::= { fdrySntpServerEntry 3 }

	fdrySntpServerVersion		 OBJECT-TYPE
		SYNTAX  Integer32 (1..4)
		MAX-ACCESS  read-create
		STATUS  current
		DESCRIPTION
			"SNTP server version."
		DEFVAL  { 3 }
		::= { fdrySntpServerEntry 4 }

	fdrySntpServerRowStatus		 OBJECT-TYPE
		SYNTAX  RowStatus
		MAX-ACCESS  read-create
		STATUS  current
		DESCRIPTION
			"This variable is used to create, modify, or
			delete a row in this table. When a row in this
			table is in active(1) state, no objects in that row
			can be modified except this object.
			 "
		::= { fdrySntpServerEntry 5 }

END
