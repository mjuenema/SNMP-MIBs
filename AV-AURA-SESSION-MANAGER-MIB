-- Avaya Aura Session Manager MIB
-- Copyright (c) 2008-2009 by Avaya Inc. All rights reserved. 
-- MIB version 1.0.0 
-- Avaya Compas ID: NA

AV-AURA-SESSION-MANAGER-MIB DEFINITIONS ::= BEGIN

-- Add your MIB specific imports in the below import section.
IMPORTS 
MODULE-IDENTITY, OBJECT-TYPE, NOTIFICATION-TYPE, enterprises
    FROM SNMPv2-SMI
InetAddressIPv6
    FROM INET-ADDRESS-MIB
MODULE-COMPLIANCE, OBJECT-GROUP
    FROM SNMPv2-CONF
SnmpAdminString
    FROM SNMP-FRAMEWORK-MIB
DateAndTime
    FROM SNMPv2-TC;

        
--
-- The following are defined in Avaya Aura Session Manager-MIB
--

avAuraSessMgrMibs MODULE-IDENTITY
       LAST-UPDATED "201507070743Z" -- 07 July 2015
       ORGANIZATION "Avaya, Inc."
       CONTACT-INFO "Avaya Customer Services

                     Postal: Avaya, Inc.
                             211 Mount Airy Rd
                             Basking Ridge. NJ 07920
                             USA
                             Tel: +1 908 953 6000
                             WWW: http://www.avaya.com"
       DESCRIPTION "This MIB module is for exposing Avaya Aura Session Manager inventory information via SNMP GET."
       
       REVISION 	"201507070743Z" -- 07 July 2015
       DESCRIPTION "MIB Version 1.0.0 - autobuild. Generated via the MIBTOOL."
             
       
       ::= { mibs 36 }

avaya              OBJECT IDENTIFIER ::= { enterprises 6889 }
products           OBJECT IDENTIFIER ::= { avaya 1 }
mibs               OBJECT IDENTIFIER ::= { avaya 2 }

avAuraSessMgrProd OBJECT IDENTIFIER ::= { products 36 }

avAuraSessMgrMibNotifications OBJECT IDENTIFIER ::= { avAuraSessMgrMibs 0 }

avAuraSessMgrMibObjects OBJECT IDENTIFIER ::= { avAuraSessMgrMibs 1 }
avAuraSessMgrMibConformance OBJECT IDENTIFIER ::= { avAuraSessMgrMibs 2 }

-- Avaya Aura Session Manager Notifications (avAuraSessMgrMibNotifications) will be added here
-- --------------------------------------------------------------------
-- According to RFC 2578 section 8.5, the next to last sub-identifier
-- in the name of any newly defined notification must have the value
-- zero. This is to achieve compatibility with SNMPv1 traps.
-- ----------------------------------------------------------------------
avSessMgrTALM00100 NOTIFICATION-TYPE
	STATUS current
	DESCRIPTION
	"Test alarm for testing only, no recovery action necessary(Indeterminate)"
	::= { avAuraSessMgrMibNotifications 31001 }

avSessMgrTALM00101 NOTIFICATION-TYPE
	STATUS current
	DESCRIPTION
	"Clear event for test alarm(Indeterminate)"
	::= { avAuraSessMgrMibNotifications 31002 }

avSessMgrMMTC20011 NOTIFICATION-TYPE
	STATUS current
	DESCRIPTION
	"Postgres database sanity check failed; the database is unaccessible(Major)"
	::= { avAuraSessMgrMibNotifications 321 }

avSessMgrMMTC20012 NOTIFICATION-TYPE
	STATUS current
	DESCRIPTION
	"Postgres database sanity check passed(Major)"
	::= { avAuraSessMgrMibNotifications 322 }

avSessMgrMMTC20013 NOTIFICATION-TYPE
	STATUS current
	DESCRIPTION
	"SIP A/S Service Host(s) sanity check failed; call processing is down(Minor)"
	::= { avAuraSessMgrMibNotifications 323 }

avSessMgrMMTC20015 NOTIFICATION-TYPE
	STATUS current
	DESCRIPTION
	"SIP A/S Service Director sanity check failed; call processing is down(Minor)"
	::= { avAuraSessMgrMibNotifications 325 }

avSessMgrMMTC20017 NOTIFICATION-TYPE
	STATUS current
	DESCRIPTION
	"SIP A/S Management Server sanity check failed; SIP A/S admin is unavailable(Minor)"
	::= { avAuraSessMgrMibNotifications 327 }

avSessMgrMMTC20019 NOTIFICATION-TYPE
	STATUS current
	DESCRIPTION
	"SAL-Agent sanity check failed; alarms are not being processed(Minor)"
	::= { avAuraSessMgrMibNotifications 329 }

avSessMgrMMTC20020 NOTIFICATION-TYPE
	STATUS current
	DESCRIPTION
	"SAL-Agent sanity check passed(Minor)"
	::= { avAuraSessMgrMibNotifications 330 }

avSessMgrMMTC20021 NOTIFICATION-TYPE
	STATUS current
	DESCRIPTION
	"Management jboss sanity check failed; services are unavailable(Minor)"
	::= { avAuraSessMgrMibNotifications 3211 }

avSessMgrMMTC20022 NOTIFICATION-TYPE
	STATUS current
	DESCRIPTION
	"Management jboss sanity check passed(Minor)"
	::= { avAuraSessMgrMibNotifications 3212 }

avSessMgrMMTC20025 NOTIFICATION-TYPE
	STATUS current
	DESCRIPTION
	"Security Module sanity check failed; call processing is down(Major)"
	::= { avAuraSessMgrMibNotifications 3213 }

avSessMgrMMTC20026 NOTIFICATION-TYPE
	STATUS current
	DESCRIPTION
	"Security Module sanity check passed(Major)"
	::= { avAuraSessMgrMibNotifications 3214 }

avSessMgrMMTC20029 NOTIFICATION-TYPE
	STATUS current
	DESCRIPTION
	"Call Processing SAR is not deployed(Major)"
	::= { avAuraSessMgrMibNotifications 3215 }

avSessMgrMMTC20030 NOTIFICATION-TYPE
	STATUS current
	DESCRIPTION
	"Call Processing SAR is deployed successfully(Major)"
	::= { avAuraSessMgrMibNotifications 3216 }

avSessMgrMMTC20031 NOTIFICATION-TYPE
	STATUS current
	DESCRIPTION
	"Data Distribution/Redundancy is down(Minor)"
	::= { avAuraSessMgrMibNotifications 3217 }

avSessMgrMMTC20032 NOTIFICATION-TYPE
	STATUS current
	DESCRIPTION
	"Data Distribution/Redundancy is up(Minor)"
	::= { avAuraSessMgrMibNotifications 3218 }

avSessMgrMMTC20047 NOTIFICATION-TYPE
	STATUS current
	DESCRIPTION
	"Session Manager using default authentication file(Warning)"
	::= { avAuraSessMgrMibNotifications 3219 }

avSessMgrMMTC20057 NOTIFICATION-TYPE
	STATUS current
	DESCRIPTION
	"Session Manager using unique authentication file(Warning)"
	::= { avAuraSessMgrMibNotifications 3220 }

avSessMgrMMTC20048 NOTIFICATION-TYPE
	STATUS current
	DESCRIPTION
	"Certificates nearing expiration date(Warning)"
	::= { avAuraSessMgrMibNotifications 3221 }

avSessMgrMMTC20058 NOTIFICATION-TYPE
	STATUS current
	DESCRIPTION
	"Certificate was successfully renewed(Warning)"
	::= { avAuraSessMgrMibNotifications 3222 }

avSessMgrMMTC20049 NOTIFICATION-TYPE
	STATUS current
	DESCRIPTION
	"Certificates nearing expiration date(Major)"
	::= { avAuraSessMgrMibNotifications 3223 }

avSessMgrMMTC20050 NOTIFICATION-TYPE
	STATUS current
	DESCRIPTION
	"Certificates nearing expiration date(Critical)"
	::= { avAuraSessMgrMibNotifications 3225 }

avSessMgrMMTC20051 NOTIFICATION-TYPE
	STATUS current
	DESCRIPTION
	"Cassandra database sanity check failed; the database is unaccessible(Major)"
	::= { avAuraSessMgrMibNotifications 3227 }

avSessMgrMMTC20052 NOTIFICATION-TYPE
	STATUS current
	DESCRIPTION
	"Cassandra database sanity check passed(Major)"
	::= { avAuraSessMgrMibNotifications 3228 }

avSessMgrMMTC20053 NOTIFICATION-TYPE
	STATUS current
	DESCRIPTION
	"Cassandra error while running compaction on SSTable files(Minor)"
	::= { avAuraSessMgrMibNotifications 3229 }

avSessMgrMMTC20054 NOTIFICATION-TYPE
	STATUS current
	DESCRIPTION
	"Compaction performed successfully on SSTable files(Minor)"
	::= { avAuraSessMgrMibNotifications 3230 }

avSessMgrMMTC20055 NOTIFICATION-TYPE
	STATUS current
	DESCRIPTION
	"Cassandra error while taking backup of call log records(Warning)"
	::= { avAuraSessMgrMibNotifications 3231 }

avSessMgrMMTC20056 NOTIFICATION-TYPE
	STATUS current
	DESCRIPTION
	"Cassandra backup successfully completed(Warning)"
	::= { avAuraSessMgrMibNotifications 3232 }

avSessMgrMAMA20100 NOTIFICATION-TYPE
	STATUS current
	DESCRIPTION
	"Security Module Management Agent is unable to connect to SIP A/S Management Server(Minor)"
	::= { avAuraSessMgrMibNotifications 331 }

avSessMgrMAMA20101 NOTIFICATION-TYPE
	STATUS current
	DESCRIPTION
	"Security Module Management Agent connected to SIP A/S Management Server(Minor)"
	::= { avAuraSessMgrMibNotifications 332 }

avSessMgrMAMA20102 NOTIFICATION-TYPE
	STATUS current
	DESCRIPTION
	"Security Module Management Agent is not able to configure Security Module(Major)"
	::= { avAuraSessMgrMibNotifications 333 }

avSessMgrMAMA20103 NOTIFICATION-TYPE
	STATUS current
	DESCRIPTION
	"Security Module Management Agent is able to configure Security Module(Major)"
	::= { avAuraSessMgrMibNotifications 334 }

avSessMgrMWD20202 NOTIFICATION-TYPE
	STATUS current
	DESCRIPTION
	"Service monitored by Watchdog has totally failed.(Minor)"
	::= { avAuraSessMgrMibNotifications 341 }

avSessMgrMWD20200 NOTIFICATION-TYPE
	STATUS current
	DESCRIPTION
	"Service monitored by Watchdog has started.(Minor)"
	::= { avAuraSessMgrMibNotifications 342 }

avSessMgrMWD20204 NOTIFICATION-TYPE
	STATUS current
	DESCRIPTION
	"WebSphere not responding(Major)"
	::= { avAuraSessMgrMibNotifications 343 }

avSessMgrMWD20205 NOTIFICATION-TYPE
	STATUS current
	DESCRIPTION
	"WebSphere service has started(Major)"
	::= { avAuraSessMgrMibNotifications 344 }

avSessMgrCSVH58003 NOTIFICATION-TYPE
	STATUS current
	DESCRIPTION
	"Product version not found. Certain operations may not work properly.(Minor)"
	::= { avAuraSessMgrMibNotifications 3101 }

avSessMgrCSVH58005 NOTIFICATION-TYPE
	STATUS current
	DESCRIPTION
	"Product version has invalid format. Certain operations may not work properly.(Minor)"
	::= { avAuraSessMgrMibNotifications 3103 }

avSessMgrCSVH58007 NOTIFICATION-TYPE
	STATUS current
	DESCRIPTION
	"Product type not found. System will likely exhibit widespread failures.(Major)"
	::= { avAuraSessMgrMibNotifications 3105 }

avSessMgrCSVH58009 NOTIFICATION-TYPE
	STATUS current
	DESCRIPTION
	"Product type not found. System will likely exhibit widespread failures.(Major)"
	::= { avAuraSessMgrMibNotifications 3107 }

avSessMgrCDAO50001 NOTIFICATION-TYPE
	STATUS current
	DESCRIPTION
	"The database connection is down.  Administration updates will not function during this outage.(Minor)"
	::= { avAuraSessMgrMibNotifications 351 }

avSessMgrCDAO50005 NOTIFICATION-TYPE
	STATUS current
	DESCRIPTION
	"The database connection has been restored.  Administration updates will now be processed.(Minor)"
	::= { avAuraSessMgrMibNotifications 352 }

avSessMgrCDAO50002 NOTIFICATION-TYPE
	STATUS current
	DESCRIPTION
	"Administration relating to the certain screen(s) may have caused a database query failure (SQL Exception).(Minor)"
	::= { avAuraSessMgrMibNotifications 353 }

avSessMgrCDAO50008 NOTIFICATION-TYPE
	STATUS current
	DESCRIPTION
	"The SQL query error has been corrected.(Minor)"
	::= { avAuraSessMgrMibNotifications 354 }

avSessMgrCDAO50003 NOTIFICATION-TYPE
	STATUS current
	DESCRIPTION
	"Administration relating to the certain screen(s) may have recently created an entry in the database which will not be actualized in the runtime system due to an error with imposed restrictions.(Minor)"
	::= { avAuraSessMgrMibNotifications 355 }

avSessMgrCDAO50007 NOTIFICATION-TYPE
	STATUS current
	DESCRIPTION
	"Invalid data in the database has been corrected.(Minor)"
	::= { avAuraSessMgrMibNotifications 356 }

avSessMgrCDAO50009 NOTIFICATION-TYPE
	STATUS current
	DESCRIPTION
	"A file I/O error occurred trying to write the local DNS server configuration or zone files.(Minor)"
	::= { avAuraSessMgrMibNotifications 357 }

avSessMgrCDAO50010 NOTIFICATION-TYPE
	STATUS current
	DESCRIPTION
	"The file I/O error with the local DNS server configuration or zone files has been corrected.(Minor)"
	::= { avAuraSessMgrMibNotifications 358 }

avSessMgrCDAO50011 NOTIFICATION-TYPE
	STATUS current
	DESCRIPTION
	"The Session Manager Instance cannot be resolved.(Major)"
	::= { avAuraSessMgrMibNotifications 359 }

avSessMgrCDAO50016 NOTIFICATION-TYPE
	STATUS current
	DESCRIPTION
	"The Session Manager Instance is now resolved.(Major)"
	::= { avAuraSessMgrMibNotifications 360 }

avSessMgrCDAO50012 NOTIFICATION-TYPE
	STATUS current
	DESCRIPTION
	"Multiple Session Manager IP addresses map to the local Session Manager Instance. Double check administration screen(s), or real DNS such as /etc/hosts.(Minor)"
	::= { avAuraSessMgrMibNotifications 3511 }

avSessMgrCDAO50015 NOTIFICATION-TYPE
	STATUS current
	DESCRIPTION
	"The local Session Manager Instance now resolves to one IP address.(Minor)"
	::= { avAuraSessMgrMibNotifications 3512 }

avSessMgrCDAO50013 NOTIFICATION-TYPE
	STATUS current
	DESCRIPTION
	"DNS resolved to multiple IP addresses for Security Module.(Minor)"
	::= { avAuraSessMgrMibNotifications 3513 }

avSessMgrCDAO50017 NOTIFICATION-TYPE
	STATUS current
	DESCRIPTION
	"DNS no longer resolves to multiple IP addresses for the Security Module.(Minor)"
	::= { avAuraSessMgrMibNotifications 3514 }

avSessMgrCDAO50018 NOTIFICATION-TYPE
	STATUS current
	DESCRIPTION
	"JGroups Keystore has not been replicated(Major)"
	::= { avAuraSessMgrMibNotifications 3523 }

avSessMgrCDAO50019 NOTIFICATION-TYPE
	STATUS current
	DESCRIPTION
	"The JGroups Keystore was successfully replicated(Major)"
	::= { avAuraSessMgrMibNotifications 3524 }

avSessMgrCDAO50020 NOTIFICATION-TYPE
	STATUS current
	DESCRIPTION
	"There is a problem with the Call Detail Recording (CDR) system. Call accounting is not operational.(Minor)"
	::= { avAuraSessMgrMibNotifications 3515 }

avSessMgrCDAO50021 NOTIFICATION-TYPE
	STATUS current
	DESCRIPTION
	"The Call Detail Recording System is now operational.(Minor)"
	::= { avAuraSessMgrMibNotifications 3516 }

avSessMgrCDAO50024 NOTIFICATION-TYPE
	STATUS current
	DESCRIPTION
	"BSM Entity Links to core subtended CM not administered.(Major)"
	::= { avAuraSessMgrMibNotifications 3517 }

avSessMgrCDAO50025 NOTIFICATION-TYPE
	STATUS current
	DESCRIPTION
	"The Missing BSM Entity Link has been added.(Major)"
	::= { avAuraSessMgrMibNotifications 3518 }

avSessMgrCDAO50026 NOTIFICATION-TYPE
	STATUS current
	DESCRIPTION
	"The BSM cannot find the avaya-lsp entry in /etc/hosts.(Major)"
	::= { avAuraSessMgrMibNotifications 3519 }

avSessMgrCDAO50027 NOTIFICATION-TYPE
	STATUS current
	DESCRIPTION
	"The missing BSM avaya-lsp entry in /etc/hosts has been added.(Major)"
	::= { avAuraSessMgrMibNotifications 3520 }

avSessMgrCDAO50022 NOTIFICATION-TYPE
	STATUS current
	DESCRIPTION
	"Entity Link Missing for Route Through.(Warning)"
	::= { avAuraSessMgrMibNotifications 3521 }

avSessMgrCDAO50023 NOTIFICATION-TYPE
	STATUS current
	DESCRIPTION
	"The missing Entity Link for Session manger to Route Through has been inserted.(Warning)"
	::= { avAuraSessMgrMibNotifications 3522 }

avSessMgrCDAO50031 NOTIFICATION-TYPE
	STATUS current
	DESCRIPTION
	"No matching entity link(Minor)"
	::= { avAuraSessMgrMibNotifications 395 }

avSessMgrCDAO50032 NOTIFICATION-TYPE
	STATUS current
	DESCRIPTION
	"Missing entity link was added(Minor)"
	::= { avAuraSessMgrMibNotifications 396 }

avSessMgrCSRE52005 NOTIFICATION-TYPE
	STATUS current
	DESCRIPTION
	"ELIN Entity Link Missing(Minor)"
	::= { avAuraSessMgrMibNotifications 363 }

avSessMgrCSRE52006 NOTIFICATION-TYPE
	STATUS current
	DESCRIPTION
	"ELIN Entity Link has been added.(Minor)"
	::= { avAuraSessMgrMibNotifications 364 }

avSessMgrCMON55001 NOTIFICATION-TYPE
	STATUS current
	DESCRIPTION
	"SIP monitoring state for entity is PARTIALLY UP.(Warning)"
	::= { avAuraSessMgrMibNotifications 371 }

avSessMgrCMON55000 NOTIFICATION-TYPE
	STATUS current
	DESCRIPTION
	"SIP monitoring state for entity is no longer down.(Warning)"
	::= { avAuraSessMgrMibNotifications 372 }

avSessMgrCMON55002 NOTIFICATION-TYPE
	STATUS current
	DESCRIPTION
	"SIP monitoring state for entity is DOWN.(Minor)"
	::= { avAuraSessMgrMibNotifications 373 }

avSessMgrCURE56021 NOTIFICATION-TYPE
	STATUS current
	DESCRIPTION
	"Unable to store subscription for a given user.(Warning)"
	::= { avAuraSessMgrMibNotifications 379 }

avSessMgrCURE56020 NOTIFICATION-TYPE
	STATUS current
	DESCRIPTION
	"No longer failing to store subscriptions.(Warning)"
	::= { avAuraSessMgrMibNotifications 380 }

avSessMgrCURE56027 NOTIFICATION-TYPE
	STATUS current
	DESCRIPTION
	"Session Manager detected that one or more users has been failed over to a non-primary Session Manager while under the manual failback policy.(Minor)"
	::= { avAuraSessMgrMibNotifications 381 }

avSessMgrCURE56028 NOTIFICATION-TYPE
	STATUS current
	DESCRIPTION
	"There are no longer any failed-over users or the failback policy is no longer manual.(Minor)"
	::= { avAuraSessMgrMibNotifications 382 }

avSessMgrCURE56029 NOTIFICATION-TYPE
	STATUS current
	DESCRIPTION
	"1 or more branch users have failed over to Branch Survivability Server.(Minor)"
	::= { avAuraSessMgrMibNotifications 383 }

avSessMgrCURE56030 NOTIFICATION-TYPE
	STATUS current
	DESCRIPTION
	"There are no longer any failed over users active on the Branch Survivability Server.(Minor)"
	::= { avAuraSessMgrMibNotifications 384 }

avSessMgrCURE56010 NOTIFICATION-TYPE
	STATUS current
	DESCRIPTION
	"Unable to process registration for user.(Warning)"
	::= { avAuraSessMgrMibNotifications 385 }

avSessMgrCURE56009 NOTIFICATION-TYPE
	STATUS current
	DESCRIPTION
	"Registration for user is no longer failing.(Warning)"
	::= { avAuraSessMgrMibNotifications 386 }

avSessMgrCURE56018 NOTIFICATION-TYPE
	STATUS current
	DESCRIPTION
	"Unable to process user subscription due to invalid credentials.(Warning)"
	::= { avAuraSessMgrMibNotifications 387 }

avSessMgrCURE56017 NOTIFICATION-TYPE
	STATUS current
	DESCRIPTION
	"Subscription Authorizations are no longer failing.(Warning)"
	::= { avAuraSessMgrMibNotifications 388 }

avSessMgrCURE56001 NOTIFICATION-TYPE
	STATUS current
	DESCRIPTION
	"Unable to process user registration due to invalid credentials.(Warning)"
	::= { avAuraSessMgrMibNotifications 389 }

avSessMgrCURE56000 NOTIFICATION-TYPE
	STATUS current
	DESCRIPTION
	"Registration authorizations are no longer failing.(Warning)"
	::= { avAuraSessMgrMibNotifications 390 }

avSessMgrCCAC54003 NOTIFICATION-TYPE
	STATUS current
	DESCRIPTION
	"The used bandwidth threshold for location has been exceeded(Warning)"
	::= { avAuraSessMgrMibNotifications 391 }

avSessMgrCCAC54004 NOTIFICATION-TYPE
	STATUS current
	DESCRIPTION
	"The used bandwidth threshold for location is no longer being exceeded(Warning)"
	::= { avAuraSessMgrMibNotifications 392 }

avSessMgrPCFF40000 NOTIFICATION-TYPE
	STATUS current
	DESCRIPTION
	"Missing configuration file.(Major)"
	::= { avAuraSessMgrMibNotifications 3201 }

avSessMgrPCFF40002 NOTIFICATION-TYPE
	STATUS current
	DESCRIPTION
	"SMGR connection timeout(Minor)"
	::= { avAuraSessMgrMibNotifications 3203 }

avSessMgrPCFF40003 NOTIFICATION-TYPE
	STATUS current
	DESCRIPTION
	"SMGR connection resolved(Minor)"
	::= { avAuraSessMgrMibNotifications 3204 }

avSessMgrDRSDBG0001 NOTIFICATION-TYPE
	STATUS current
	DESCRIPTION
	"DRS client batch error(Major)"
	::= { avAuraSessMgrMibNotifications 3301 }

avSessMgrArbiter001 NOTIFICATION-TYPE
	STATUS current
	DESCRIPTION
	"SM switched to a different SMGR(Warning)"
	::= { avAuraSessMgrMibNotifications 3401 }

avSessMgrArbiter002 NOTIFICATION-TYPE
	STATUS current
	DESCRIPTION
	"Session Manager does not have a master Session Manager(Warning)"
	::= { avAuraSessMgrMibNotifications 3403 }

avSessMgrArbiter003 NOTIFICATION-TYPE
	STATUS current
	DESCRIPTION
	"GEO Session Managers in Active/Standby mode(Warning)"
	::= { avAuraSessMgrMibNotifications 3404 }

avSessMgrTrustAgent000 NOTIFICATION-TYPE
	STATUS current
	DESCRIPTION
	"A certificate change has been made that requires a restart. Session Manager should be restarted to avoid any potential outages.(Warning)"
	::= { avAuraSessMgrMibNotifications 3500 }

avSessMgrTrustAgent001 NOTIFICATION-TYPE
	STATUS current
	DESCRIPTION
	"Certificate change has been resolved with a restart(Warning)"
	::= { avAuraSessMgrMibNotifications 3501 }

END
