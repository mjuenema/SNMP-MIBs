CAMEDIATIONMANAGER-MIB DEFINITIONS ::= BEGIN
 
--
-- Top-level infrastructure of the CAMEDIATIONMANAGER project enterprise MIB tree
--
 
IMPORTS
    MODULE-IDENTITY, enterprises FROM SNMPv2-SMI;
 
caMediationManager MODULE-IDENTITY
    LAST-UPDATED "201201300000Z"
    ORGANIZATION "www.CA.com"
    CONTACT-INFO   
                 "postal:   
                        One CA Plaza
                        Islandia, NY 11749
                        USA
          email:    support@ca.com"
    DESCRIPTION
                "Top-level infrastructure of the CA Mediation Manager enterprise MIB tree"
    REVISION     "201201300000Z"
    DESCRIPTION
                "First draft"
    ::= { enterprises 29599}

--
--  CAMEDIATIONMANAGER enterprise-specific management objects
--
 
 
END
