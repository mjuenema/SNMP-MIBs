--MibName=caiAdsA2
--
-- ========================================================================
--
--               COMPUTER ASSOCIATES INTERNATIONAL, INC.
--               Proprietary and Confidential Information
--
-- This material contains, and is part of a computer software program
-- which is, proprietary and confidential information owned by COMPUTER
-- ASSOCIATES INTERNATIONAL, INC.  The program, including this material,
-- may not be duplicated, disclosed or reproduced in whole or in part for
-- any purpose without the express written authorization of COMPUTER
-- ASSOCIATES. All authorized reproductions must be marked with this
-- legend.
--                 Computer Associates International, Inc      
--
--                          Copyright (c) 2001
--                       The Software that Manages eBusiness
--                          All rights reserved
--
--
-- ------------------------------------------------------------------------
--
-- Windows Active Directory Services Agent MIB
-- v1.0.0
--


CA-ADSA2-MIB DEFINITIONS ::= BEGIN


IMPORTS
	enterprises   FROM RFC1155-SMI
	OBJECT-TYPE   FROM RFC1155-SMI
	DisplayString FROM RFC1158-MIB;


-- *****************************************************************************
-- Oids of caiAdsA2 agent start with 1.3.6.1.4.1.791.2.10.2.62
-- *****************************************************************************
cai       OBJECT IDENTIFIER ::= { enterprises 791 }
caiSysMgr OBJECT IDENTIFIER ::= { cai 2 }
tng       OBJECT IDENTIFIER ::= { caiSysMgr 10 }
agents    OBJECT IDENTIFIER ::= { tng 2 }
caiAdsA2  OBJECT IDENTIFIER ::= { agents 62 }


-- *****************************************************************************
-- The three big groups
-- *****************************************************************************
adsConfigGroup    OBJECT IDENTIFIER ::= { caiAdsA2 1 }
adsStatusGroup    OBJECT IDENTIFIER ::= { caiAdsA2 2 }
adsAvailableGroup OBJECT IDENTIFIER ::= { caiAdsA2 3 }
adsHistoryGroup   OBJECT IDENTIFIER ::= { caiAdsA2 4 }


-- *****************************************************************************
-- Configuration Groups
-- *****************************************************************************
adsConfigGeneralGroup OBJECT IDENTIFIER ::= { adsConfigGroup 1 }
adsConfigDCtrlGroup   OBJECT IDENTIFIER ::= { adsConfigGroup 2 }
adsConfigDskSpGroup   OBJECT IDENTIFIER ::= { adsConfigGroup 3 }
adsConfigAdsEvGroup   OBJECT IDENTIFIER ::= { adsConfigGroup 4 }
adsConfigAdsPrGroup   OBJECT IDENTIFIER ::= { adsConfigGroup 5 }
adsConfigFrsEvGroup   OBJECT IDENTIFIER ::= { adsConfigGroup 6 }
adsConfigFrsPrGroup   OBJECT IDENTIFIER ::= { adsConfigGroup 7 }
adsConfigDnsEvGroup   OBJECT IDENTIFIER ::= { adsConfigGroup 8 }
adsConfigDnsPrGroup   OBJECT IDENTIFIER ::= { adsConfigGroup 9 }


-- *****************************************************************************
-- Status Groups
-- *****************************************************************************
adsStatusGeneralGroup OBJECT IDENTIFIER ::= { adsStatusGroup 1 }
adsStatusDCtrlGroup   OBJECT IDENTIFIER ::= { adsStatusGroup 2 }
adsStatusDskSpGroup   OBJECT IDENTIFIER ::= { adsStatusGroup 3 }
adsStatusAdsEvGroup   OBJECT IDENTIFIER ::= { adsStatusGroup 4 }
adsStatusAdsPrGroup   OBJECT IDENTIFIER ::= { adsStatusGroup 5 }
adsStatusFrsEvGroup   OBJECT IDENTIFIER ::= { adsStatusGroup 6 }
adsStatusFrsPrGroup   OBJECT IDENTIFIER ::= { adsStatusGroup 7 }
adsStatusDnsEvGroup   OBJECT IDENTIFIER ::= { adsStatusGroup 8 }
adsStatusDnsPrGroup   OBJECT IDENTIFIER ::= { adsStatusGroup 9 }


-- *****************************************************************************
-- Availability Groups
-- *****************************************************************************
adsAvailAdsEvGroup OBJECT IDENTIFIER ::= { adsAvailableGroup 1 }
adsAvailAdsPrGroup OBJECT IDENTIFIER ::= { adsAvailableGroup 2 }
adsAvailFrsEvGroup OBJECT IDENTIFIER ::= { adsAvailableGroup 3 }
adsAvailFrsPrGroup OBJECT IDENTIFIER ::= { adsAvailableGroup 4 }
adsAvailDnsEvGroup OBJECT IDENTIFIER ::= { adsAvailableGroup 5 }
adsAvailDnsPrGroup OBJECT IDENTIFIER ::= { adsAvailableGroup 6 }




-- *****************************************************************************
-- General Config Group
-- *****************************************************************************


adsConfigGeneralAgentVersion OBJECT-TYPE
	SYNTAX DisplayString
	ACCESS read-only
	STATUS mandatory
	DESCRIPTION
		"&<caiAdsA2.100>The currently installed version of the agent."
	::= { adsConfigGeneralGroup 1 }


adsConfigGeneralColdStartTime OBJECT-TYPE
	SYNTAX DisplayString
	ACCESS read-only
	STATUS mandatory
	DESCRIPTION
		"&<caiAdsA2.101>The date and time that the agent was last started."
	::= { adsConfigGeneralGroup 2 }


adsConfigGeneralWarmStartTime OBJECT-TYPE
	SYNTAX DisplayString
	ACCESS read-only
	STATUS mandatory
	DESCRIPTION
		"&<caiAdsA2.102>The date and time that the agent's configuration was last changed."
	::= { adsConfigGeneralGroup 3 }


adsConfigGeneralDCtrlPollTime OBJECT-TYPE
	SYNTAX DisplayString
	ACCESS read-only
	STATUS mandatory
	DESCRIPTION
		"&<caiAdsA2.103>The date and time that the agent last polled the Domain Controllers information."
	::= { adsConfigGeneralGroup 4 }


adsConfigGeneralDskSpPollTime OBJECT-TYPE
	SYNTAX DisplayString
	ACCESS read-only
	STATUS mandatory
	DESCRIPTION
		"&<caiAdsA2.104>The date and time that the agent last polled the Disk Space information."
	::= { adsConfigGeneralGroup 5 }


adsConfigGeneralAdsEvPollTime OBJECT-TYPE
	SYNTAX DisplayString
	ACCESS read-only
	STATUS mandatory
	DESCRIPTION
		"&<caiAdsA2.105>The date and time that the agent last polled the ADS Events information."
	::= { adsConfigGeneralGroup 6 }


adsConfigGeneralAdsPrPollTime OBJECT-TYPE
	SYNTAX DisplayString
	ACCESS read-only
	STATUS mandatory
	DESCRIPTION
		"&<caiAdsA2.106>The date and time that the agent last polled the ADS Performance information."
	::= { adsConfigGeneralGroup 7 }


adsConfigGeneralFrsEvPollTime OBJECT-TYPE
	SYNTAX DisplayString
	ACCESS read-only
	STATUS mandatory
	DESCRIPTION
		"&<caiAdsA2.107>The date and time that the agent last polled the FRS Events information."
	::= { adsConfigGeneralGroup 8 }


adsConfigGeneralFrsPrPollTime OBJECT-TYPE
	SYNTAX DisplayString
	ACCESS read-only
	STATUS mandatory
	DESCRIPTION
		"&<caiAdsA2.108>The date and time that the agent last polled the FRS Performance information."
	::= { adsConfigGeneralGroup 9 }


adsConfigGeneralDnsEvPollTime OBJECT-TYPE
	SYNTAX DisplayString
	ACCESS read-only
	STATUS mandatory
	DESCRIPTION
		"&<caiAdsA2.109>The date and time that the agent last polled the DNS Events information."
	::= { adsConfigGeneralGroup 10 }


adsConfigGeneralDnsPrPollTime OBJECT-TYPE
	SYNTAX DisplayString
	ACCESS read-only
	STATUS mandatory
	DESCRIPTION
		"&<caiAdsA2.110>The date and time that the agent last polled the DNS Performance information."
	::= { adsConfigGeneralGroup 11 }




-- *****************************************************************************
-- Domain Controller Config Group
-- *****************************************************************************


adsConfigDCtrlPollInterval OBJECT-TYPE
	SYNTAX INTEGER
	ACCESS read-write
	STATUS mandatory
	DESCRIPTION
		"&<caiAdsA2.111>The time (in seconds) between the polling of the Domain Controllers information. Valid values are greater than or equal to 30."
	DEFVAL { 120 }
	::= { adsConfigDCtrlGroup 1 }


adsConfigDCtrlPollMethod OBJECT-TYPE
	SYNTAX INTEGER {
		disabled(1),
		poll-interval-only(2),
		poll-interval-and-query(3),
		query-only(4)
	}
	ACCESS read-write
	STATUS mandatory
	DESCRIPTION
		"&<caiAdsA2.112>If set to 'disabled', the agent no more retrieves the Domain Controllers information (not by polling, nor by get request) and sets all statuses to ok. If set to 'poll-interval-only', the agent only retrieves the information by polling, but not by get request. If set to 'poll-interval-and-query', the agent retrieves the information in both cases (polling and get request). If set to 'query-only', the agent only retrieves the information when a get request is made."
	DEFVAL { 2 }
	::= { adsConfigDCtrlGroup 2 }


adsConfigDCtrlAggLag OBJECT-TYPE
	SYNTAX INTEGER
	ACCESS read-write
	STATUS mandatory
	DESCRIPTION
		"&<caiAdsA2.113>The number of consecutive poll intervals on which any status is not in the Ok or Up state, before the aggregate status changes. Valid values are greater than 0."
	DEFVAL { 1 }
	::= { adsConfigDCtrlGroup 3 }


adsConfigDCtrlBindWarn OBJECT-TYPE
	SYNTAX INTEGER
	ACCESS read-write
	STATUS mandatory
	DESCRIPTION
		"&<caiAdsA2.114>Warning threshold (in milliseconds) for the time needed to bind to the domain controller. Valid values are greater than 0 and smaller than or equal to the critical threshold."
	DEFVAL { 3000 }
	::= { adsConfigDCtrlGroup 4 }


adsConfigDCtrlBindCrit OBJECT-TYPE
	SYNTAX INTEGER
	ACCESS read-write
	STATUS mandatory
	DESCRIPTION
		"&<caiAdsA2.115>Critical threshold (in milliseconds) for the time needed to bind to the domain controller. Valid values are greater than 0 and greater than or equal to the warning threshold."
	DEFVAL { 6000 }
	::= { adsConfigDCtrlGroup 5 }


adsConfigDCtrlBindMonitor OBJECT-TYPE
	SYNTAX INTEGER {
		do-not-monitor(1),
		warning-only(2),
		critical-only(3),
		both(4)
	}
	ACCESS read-write
	STATUS mandatory
	DESCRIPTION
		"&<caiAdsA2.116>Flag indicating whether the time needed to bind to the domain controller should be monitored and if so, which threshold should be compared with."
	DEFVAL { 4 }
	::= { adsConfigDCtrlGroup 6 }


adsConfigDCtrlLdapWarn OBJECT-TYPE
	SYNTAX INTEGER
	ACCESS read-write
	STATUS mandatory
	DESCRIPTION
		"&<caiAdsA2.117>Warning threshold (in milliseconds) for the time needed to run a LDAP query to the domain controller. Valid values are greater than 0 and smaller than or equal to the critical threshold."
	DEFVAL { 1000 }
	::= { adsConfigDCtrlGroup 7 }


adsConfigDCtrlLdapCrit OBJECT-TYPE
	SYNTAX INTEGER
	ACCESS read-write
	STATUS mandatory
	DESCRIPTION
		"&<caiAdsA2.118>Critical threshold (in milliseconds) for the time needed to run a LDAP query to the domain controller. Valid values are greater than 0 and greater than or equal to the warning threshold."
	DEFVAL { 2000 }
	::= { adsConfigDCtrlGroup 8 }


adsConfigDCtrlLdapMonitor OBJECT-TYPE
	SYNTAX INTEGER {
		do-not-monitor(1),
		warning-only(2),
		critical-only(3),
		both(4)
	}
	ACCESS read-write
	STATUS mandatory
	DESCRIPTION
		"&<caiAdsA2.119>Flag indicating whether the time needed to run a LDAP query to the domain controller should be monitored and if so, which threshold should be compared with."
	DEFVAL { 4 }
	::= { adsConfigDCtrlGroup 9 }


adsConfigDCtrlLossAction OBJECT-TYPE
	SYNTAX INTEGER {
		remove(1),
		up(2),
		down-warning(3),
		down-critical(4)
	}
	ACCESS read-write
	STATUS mandatory
	DESCRIPTION
		"&<caiAdsA2.120>Flag defining the severity if the loss of a role for a domain controller is detected or whether to remove this watcher in that case."
	DEFVAL { 4 }
	::= { adsConfigDCtrlGroup 10 }




-- *****************************************************************************
-- Disk Space Config Group
-- *****************************************************************************


adsConfigDskSpPollInterval OBJECT-TYPE
	SYNTAX INTEGER
	ACCESS read-write
	STATUS mandatory
	DESCRIPTION
		"&<caiAdsA2.121>The time (in seconds) between the polling of the Disk Space information. Valid values are greater than or equal to 30."
	DEFVAL { 120 }
	::= { adsConfigDskSpGroup 1 }


adsConfigDskSpPollMethod OBJECT-TYPE
	SYNTAX INTEGER {
		disabled(1),
		poll-interval-only(2),
		poll-interval-and-query(3),
		query-only(4)
	}
	ACCESS read-write
	STATUS mandatory
	DESCRIPTION
		"&<caiAdsA2.122>If set to 'disabled', the agent no more retrieves the Disk Space information (not by polling, nor by get request) and sets all statuses to ok. If set to 'poll-interval-only', the agent only retrieves the information by polling, but not by get request. If set to 'poll-interval-and-query', the agent retrieves the information in both cases (polling and get request). If set to 'query-only', the agent only retrieves the information when a get request is made."
	DEFVAL { 2 }
	::= { adsConfigDskSpGroup 2 }


adsConfigDskSpAggLag OBJECT-TYPE
	SYNTAX INTEGER
	ACCESS read-write
	STATUS mandatory
	DESCRIPTION
		"&<caiAdsA2.123>The number of consecutive poll intervals on which any status is not in the Ok or Up state, before the aggregate status changes. Valid values are greater than 0."
	DEFVAL { 1 }
	::= { adsConfigDskSpGroup 3 }


adsConfigDskSpSpaceWarn OBJECT-TYPE
	SYNTAX DisplayString
	ACCESS read-write
	STATUS mandatory
	DESCRIPTION
		"&<caiAdsA2.124>Warning threshold in megabytes, either for the free (by appending a 'F') or for the used disk space. The used space can also be defined as a percentage value of the total disk space (by appending a '%'). Valid values are greater than 0 and smaller (in case of 'free' greater) than or equal to the critical threshold."
	DEFVAL { "512F" }
	::= { adsConfigDskSpGroup 4 }


adsConfigDskSpSpaceCrit OBJECT-TYPE
	SYNTAX DisplayString
	ACCESS read-write
	STATUS mandatory
	DESCRIPTION
		"&<caiAdsA2.125>Critical threshold in megabytes, either for the free (by appending a 'F') or for the used disk space. The used space can also be defined as a percentage value of the total disk space (by appending a '%'). Valid values are greater than 0 and greater (in case of 'free' smaller) than or equal to the warning threshold."
	DEFVAL { "128F" }
	::= { adsConfigDskSpGroup 5 }


adsConfigDskSpSpaceMonitor OBJECT-TYPE
	SYNTAX INTEGER {
		do-not-monitor(1),
		warning-only(2),
		critical-only(3),
		both(4)
	}
	ACCESS read-write
	STATUS mandatory
	DESCRIPTION
		"&<caiAdsA2.126>Flag indicating whether the used disk space should be monitored and if so, which threshold should be compared with."
	DEFVAL { 4 }
	::= { adsConfigDskSpGroup 6 }


adsConfigDskSpLossAction OBJECT-TYPE
	SYNTAX INTEGER {
		remove(1),
		up(2),
		down-warning(3),
		down-critical(4)
	}
	ACCESS read-write
	STATUS mandatory
	DESCRIPTION
		"&<caiAdsA2.127>Flag defining the severity if the loss of a disk space is detected or whether to remove this watcher in that case."
	DEFVAL { 3 }
	::= { adsConfigDskSpGroup 7 }




-- *****************************************************************************
-- Active Directory Service Events Config Group
-- *****************************************************************************


adsConfigAdsEvPollInterval OBJECT-TYPE
	SYNTAX INTEGER
	ACCESS read-write
	STATUS mandatory
	DESCRIPTION
		"&<caiAdsA2.128>The time (in seconds) between the polling of the Active Directory Service Event Logs information. Valid values are greater than or equal to 30."
	DEFVAL { 120 }
	::= { adsConfigAdsEvGroup 1 }


adsConfigAdsEvPollMethod OBJECT-TYPE
	SYNTAX INTEGER {
		disabled(1),
		poll-interval-only(2),
		poll-interval-and-query(3),
		query-only(4)
	}
	ACCESS read-write
	STATUS mandatory
	DESCRIPTION
		"&<caiAdsA2.129>If set to 'disabled', the agent no more retrieves the Active Directory Service Event Logs information (not by polling, nor by get request) and sets all statuses to ok. If set to 'poll-interval-only', the agent only retrieves the information by polling, but not by get request. If set to 'poll-interval-and-query', the agent retrieves the information in both cases (polling and get request). If set to 'query-only', the agent only retrieves the information when a get request is made."
	DEFVAL { 2 }
	::= { adsConfigAdsEvGroup 2 }


adsConfigAdsEvAutoWatch OBJECT-TYPE
	SYNTAX INTEGER {
		no(1),
		yes(2)
	}
	ACCESS read-write
	STATUS mandatory
	DESCRIPTION
		"&<caiAdsA2.130>If this value is 'yes' the agent automatically creates watchers for all entries in the corresponding Available table, which have their individual AutoWatch attribute set to 'yes'. Otherwise no watchers are automatically created."
	DEFVAL { 2 }
	::= { adsConfigAdsEvGroup 3 }


adsConfigAdsEvName OBJECT-TYPE
	SYNTAX DisplayString
	ACCESS read-write
	STATUS mandatory
	DESCRIPTION
		"&<caiAdsA2.131>Name of the watcher to be added/removed, monitoring Active Directory Service Event Logs. Important: This name is arbitrary but case insensitive. When prefixed with the keyword '[OTHER]' then the watcher will not be applied on a new Event Log entry, if any other watcher not using this prefix already matches the entry during the same poll cycle."
	::= { adsConfigAdsEvGroup 4 }


adsConfigAdsEvDescription OBJECT-TYPE
	SYNTAX DisplayString
	ACCESS read-write
	STATUS mandatory
	DESCRIPTION
		"&<caiAdsA2.132>Any description for this watcher."
	::= { adsConfigAdsEvGroup 5 }


adsConfigAdsEvPatterns OBJECT-TYPE
	SYNTAX DisplayString
	ACCESS read-write
	STATUS mandatory
	DESCRIPTION
		"&<caiAdsA2.133>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsConfigAdsEvGroup 6 }


adsConfigAdsEvMonitor OBJECT-TYPE
	SYNTAX INTEGER {
		do-not-monitor(1),
		down-warning(2),
		down-critical(3)
	}
	ACCESS read-write
	STATUS mandatory
	DESCRIPTION
		"&<caiAdsA2.134>Flag indicating whether Active Directory Service Event Logs should be monitored by this watcher and if so, the level of alert to raise."
	DEFVAL { 3 }
	::= { adsConfigAdsEvGroup 7 }


adsConfigAdsEvButton OBJECT-TYPE
	SYNTAX INTEGER {
		none(1),
		add(2),
		remove(3)
	}
	ACCESS read-write
	STATUS mandatory
	DESCRIPTION
		"&<caiAdsA2.135>This attribute is used to add or remove a watcher with the current value of the watcher name attribute in this group."
	::= { adsConfigAdsEvGroup 8 }




-- *****************************************************************************
-- Active Directory Service Performance Config Group
-- *****************************************************************************


adsConfigAdsPrPollInterval OBJECT-TYPE
	SYNTAX INTEGER
	ACCESS read-write
	STATUS mandatory
	DESCRIPTION
		"&<caiAdsA2.136>The time (in seconds) between the polling of the Active Directory Service Performance information. Valid values are greater than or equal to 30."
	DEFVAL { 120 }
	::= { adsConfigAdsPrGroup 1 }


adsConfigAdsPrPollMethod OBJECT-TYPE
	SYNTAX INTEGER {
		disabled(1),
		poll-interval-only(2),
		poll-interval-and-query(3),
		query-only(4)
	}
	ACCESS read-write
	STATUS mandatory
	DESCRIPTION
		"&<caiAdsA2.137>If set to 'disabled', the agent no more retrieves the Active Directory Service Performance information (not by polling, nor by get request) and sets all statuses to ok. If set to 'poll-interval-only', the agent only retrieves the information by polling, but not by get request. If set to 'poll-interval-and-query', the agent retrieves the information in both cases (polling and get request). If set to 'query-only', the agent only retrieves the information when a get request is made."
	DEFVAL { 2 }
	::= { adsConfigAdsPrGroup 2 }


adsConfigAdsPrAutoWatch OBJECT-TYPE
	SYNTAX INTEGER {
		no(1),
		yes(2)
	}
	ACCESS read-write
	STATUS mandatory
	DESCRIPTION
		"&<caiAdsA2.138>If this value is 'yes' the agent automatically creates watchers for all entries in the corresponding Available table, which have their individual AutoWatch attribute set to 'yes'. Otherwise no watchers are automatically created."
	DEFVAL { 2 }
	::= { adsConfigAdsPrGroup 3 }


adsConfigAdsPrName OBJECT-TYPE
	SYNTAX DisplayString
	ACCESS read-write
	STATUS mandatory
	DESCRIPTION
		"&<caiAdsA2.139>Name of the performance watcher to be added/removed. Important: This name is arbitrary but case insensitive."
	::= { adsConfigAdsPrGroup 4 }


adsConfigAdsPrDescription OBJECT-TYPE
	SYNTAX DisplayString
	ACCESS read-write
	STATUS mandatory
	DESCRIPTION
		"&<caiAdsA2.140>Any description for this watcher."
	::= { adsConfigAdsPrGroup 5 }


adsConfigAdsPrExpression OBJECT-TYPE
	SYNTAX DisplayString
	ACCESS read-write
	STATUS mandatory
	DESCRIPTION
		"&<caiAdsA2.141>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsConfigAdsPrGroup 6 }


adsConfigAdsPrCounter0 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.142>The definition of the counter with reference key C0 or L0."
	DEFVAL { 1 }
	::= { adsConfigAdsPrGroup 7 }


adsConfigAdsPrCounter1 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.143>The definition of the counter with reference key C1 or L1."
	DEFVAL { 1 }
	::= { adsConfigAdsPrGroup 8 }


adsConfigAdsPrCounter2 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.144>The definition of the counter with reference key C2 or L2."
	DEFVAL { 1 }
	::= { adsConfigAdsPrGroup 9 }


adsConfigAdsPrCounter3 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.145>The definition of the counter with reference key C3 or L3."
	DEFVAL { 1 }
	::= { adsConfigAdsPrGroup 10 }


adsConfigAdsPrCounter4 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.146>The definition of the counter with reference key C4 or L4."
	DEFVAL { 1 }
	::= { adsConfigAdsPrGroup 11 }


adsConfigAdsPrCounter5 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.147>The definition of the counter with reference key C5 or L5."
	DEFVAL { 1 }
	::= { adsConfigAdsPrGroup 12 }


adsConfigAdsPrCounter6 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.148>The definition of the counter with reference key C6 or L6."
	DEFVAL { 1 }
	::= { adsConfigAdsPrGroup 13 }


adsConfigAdsPrCounter7 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.149>The definition of the counter with reference key C7 or L7."
	DEFVAL { 1 }
	::= { adsConfigAdsPrGroup 14 }


adsConfigAdsPrCounter8 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.150>The definition of the counter with reference key C8 or L8."
	DEFVAL { 1 }
	::= { adsConfigAdsPrGroup 15 }


adsConfigAdsPrCounter9 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.151>The definition of the counter with reference key C9 or L9."
	DEFVAL { 1 }
	::= { adsConfigAdsPrGroup 16 }


adsConfigAdsPrAggLag OBJECT-TYPE
	SYNTAX INTEGER
	ACCESS read-write
	STATUS mandatory
	DESCRIPTION
		"&<caiAdsA2.152>The number of consecutive poll intervals on which any status is not in the Ok or Up state, before the aggregate status changes. Valid values are greater than 0."
	DEFVAL { 1 }
	::= { adsConfigAdsPrGroup 17 }


adsConfigAdsPrWarn OBJECT-TYPE
	SYNTAX DisplayString
	ACCESS read-write
	STATUS mandatory
	DESCRIPTION
		"&<caiAdsA2.153>Warning threshold for the calculated value of the expression. Valid values are greater than 0.0 and smaller than or equal to the critical threshold."
	DEFVAL { "1.0" }
	::= { adsConfigAdsPrGroup 18 }


adsConfigAdsPrCrit OBJECT-TYPE
	SYNTAX DisplayString
	ACCESS read-write
	STATUS mandatory
	DESCRIPTION
		"&<caiAdsA2.154>Critical threshold for the calculated value of the expression. Valid values are greater than 0.0 and greater than or equal to the warning threshold."
	DEFVAL { "2.0" }
	::= { adsConfigAdsPrGroup 19 }


adsConfigAdsPrWcMonitor OBJECT-TYPE
	SYNTAX INTEGER {
		do-not-monitor(1),
		warning-only(2),
		critical-only(3),
		both(4)
	}
	ACCESS read-write
	STATUS mandatory
	DESCRIPTION
		"&<caiAdsA2.155>Flag indicating whether the programmed expression should be monitored and if so, which threshold should be compared with."
	DEFVAL { 4 }
	::= { adsConfigAdsPrGroup 20 }


adsConfigAdsPrMin OBJECT-TYPE
	SYNTAX DisplayString
	ACCESS read-write
	STATUS mandatory
	DESCRIPTION
		"&<caiAdsA2.156>Minimum threshold for the calculated value of the expression. Valid values are greater than 0.0 or equal to -1.0 and smaller than or equal to the maximum threshold. Setting to -1.0 disables the monitoring of the minimum."
	DEFVAL { "1.0" }
	::= { adsConfigAdsPrGroup 21 }


adsConfigAdsPrMax OBJECT-TYPE
	SYNTAX DisplayString
	ACCESS read-write
	STATUS mandatory
	DESCRIPTION
		"&<caiAdsA2.157>Maximum threshold for the calculated value of the expression. Valid values are greater than 0.0 or equal to -1.0 and greater than or equal to the minimum threshold. Setting to -1.0 disables the monitoring of the maximum."
	DEFVAL { "1.0" }
	::= { adsConfigAdsPrGroup 22 }


adsConfigAdsPrMmMonitor OBJECT-TYPE
	SYNTAX INTEGER {
		do-not-monitor(1),
		down-warning(2),
		down-critical(3)
	}
	ACCESS read-write
	STATUS mandatory
	DESCRIPTION
		"&<caiAdsA2.158>Flag indicating whether the programmed expression should be monitored and if so, the level of alert to raise."
	DEFVAL { 1 }
	::= { adsConfigAdsPrGroup 23 }


adsConfigAdsPrButton OBJECT-TYPE
	SYNTAX INTEGER {
		none(1),
		add(2),
		remove(3)
	}
	ACCESS read-write
	STATUS mandatory
	DESCRIPTION
		"&<caiAdsA2.159>This attribute is used to add or remove a watcher with the current value of the watcher name attribute in this group."
	::= { adsConfigAdsPrGroup 24 }




-- *****************************************************************************
-- File Replication Service Events Config Group
-- *****************************************************************************


adsConfigFrsEvPollInterval OBJECT-TYPE
	SYNTAX INTEGER
	ACCESS read-write
	STATUS mandatory
	DESCRIPTION
		"&<caiAdsA2.160>The time (in seconds) between the polling of the File Replication Service Event Logs information. Valid values are greater than or equal to 30."
	DEFVAL { 120 }
	::= { adsConfigFrsEvGroup 1 }


adsConfigFrsEvPollMethod OBJECT-TYPE
	SYNTAX INTEGER {
		disabled(1),
		poll-interval-only(2),
		poll-interval-and-query(3),
		query-only(4)
	}
	ACCESS read-write
	STATUS mandatory
	DESCRIPTION
		"&<caiAdsA2.161>If set to 'disabled', the agent no more retrieves the File Replication Service Event Logs information (not by polling, nor by get request) and sets all statuses to ok. If set to 'poll-interval-only', the agent only retrieves the information by polling, but not by get request. If set to 'poll-interval-and-query', the agent retrieves the information in both cases (polling and get request). If set to 'query-only', the agent only retrieves the information when a get request is made."
	DEFVAL { 2 }
	::= { adsConfigFrsEvGroup 2 }


adsConfigFrsEvAutoWatch OBJECT-TYPE
	SYNTAX INTEGER {
		no(1),
		yes(2)
	}
	ACCESS read-write
	STATUS mandatory
	DESCRIPTION
		"&<caiAdsA2.162>If this value is 'yes' the agent automatically creates watchers for all entries in the corresponding Available table, which have their individual AutoWatch attribute set to 'yes'. Otherwise no watchers are automatically created."
	DEFVAL { 2 }
	::= { adsConfigFrsEvGroup 3 }


adsConfigFrsEvName OBJECT-TYPE
	SYNTAX DisplayString
	ACCESS read-write
	STATUS mandatory
	DESCRIPTION
		"&<caiAdsA2.163>Name of the watcher to be added/removed, monitoring File Replication Service Event Logs. Important: This name is arbitrary but case insensitive. When prefixed with the keyword '[OTHER]' then the watcher will not be applied on a new Event Log entry, if any other watcher not using this prefix already matches the entry during the same poll cycle."
	::= { adsConfigFrsEvGroup 4 }


adsConfigFrsEvDescription OBJECT-TYPE
	SYNTAX DisplayString
	ACCESS read-write
	STATUS mandatory
	DESCRIPTION
		"&<caiAdsA2.164>Any description for this watcher."
	::= { adsConfigFrsEvGroup 5 }


adsConfigFrsEvPatterns OBJECT-TYPE
	SYNTAX DisplayString
	ACCESS read-write
	STATUS mandatory
	DESCRIPTION
		"&<caiAdsA2.165>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsConfigFrsEvGroup 6 }


adsConfigFrsEvMonitor OBJECT-TYPE
	SYNTAX INTEGER {
		do-not-monitor(1),
		down-warning(2),
		down-critical(3)
	}
	ACCESS read-write
	STATUS mandatory
	DESCRIPTION
		"&<caiAdsA2.166>Flag indicating whether File Replication Service Event Logs should be monitored by this watcher and if so, the level of alert to raise."
	DEFVAL { 3 }
	::= { adsConfigFrsEvGroup 7 }


adsConfigFrsEvButton OBJECT-TYPE
	SYNTAX INTEGER {
		none(1),
		add(2),
		remove(3)
	}
	ACCESS read-write
	STATUS mandatory
	DESCRIPTION
		"&<caiAdsA2.167>This attribute is used to add or remove a watcher with the current value of the watcher name attribute in this group."
	::= { adsConfigFrsEvGroup 8 }




-- *****************************************************************************
-- File Replication Service Performance Config Group
-- *****************************************************************************


adsConfigFrsPrPollInterval OBJECT-TYPE
	SYNTAX INTEGER
	ACCESS read-write
	STATUS mandatory
	DESCRIPTION
		"&<caiAdsA2.168>The time (in seconds) between the polling of the File Replication Service Performance information. Valid values are greater than or equal to 30."
	DEFVAL { 120 }
	::= { adsConfigFrsPrGroup 1 }


adsConfigFrsPrPollMethod OBJECT-TYPE
	SYNTAX INTEGER {
		disabled(1),
		poll-interval-only(2),
		poll-interval-and-query(3),
		query-only(4)
	}
	ACCESS read-write
	STATUS mandatory
	DESCRIPTION
		"&<caiAdsA2.169>If set to 'disabled', the agent no more retrieves the File Replication Service Performance information (not by polling, nor by get request) and sets all statuses to ok. If set to 'poll-interval-only', the agent only retrieves the information by polling, but not by get request. If set to 'poll-interval-and-query', the agent retrieves the information in both cases (polling and get request). If set to 'query-only', the agent only retrieves the information when a get request is made."
	DEFVAL { 2 }
	::= { adsConfigFrsPrGroup 2 }


adsConfigFrsPrAutoWatch OBJECT-TYPE
	SYNTAX INTEGER {
		no(1),
		yes(2)
	}
	ACCESS read-write
	STATUS mandatory
	DESCRIPTION
		"&<caiAdsA2.170>If this value is 'yes' the agent automatically creates watchers for all entries in the corresponding Available table, which have their individual AutoWatch attribute set to 'yes'. Otherwise no watchers are automatically created."
	DEFVAL { 2 }
	::= { adsConfigFrsPrGroup 3 }


adsConfigFrsPrName OBJECT-TYPE
	SYNTAX DisplayString
	ACCESS read-write
	STATUS mandatory
	DESCRIPTION
		"&<caiAdsA2.171>Name of the performance watcher to be added/removed. Important: This name is arbitrary but case insensitive."
	::= { adsConfigFrsPrGroup 4 }


adsConfigFrsPrDescription OBJECT-TYPE
	SYNTAX DisplayString
	ACCESS read-write
	STATUS mandatory
	DESCRIPTION
		"&<caiAdsA2.172>Any description for this watcher."
	::= { adsConfigFrsPrGroup 5 }


adsConfigFrsPrExpression OBJECT-TYPE
	SYNTAX DisplayString
	ACCESS read-write
	STATUS mandatory
	DESCRIPTION
		"&<caiAdsA2.173>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsConfigFrsPrGroup 6 }


adsConfigFrsPrCounter0 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.174>The definition of the counter with reference key C0 or L0."
	DEFVAL { 1 }
	::= { adsConfigFrsPrGroup 7 }


adsConfigFrsPrCounter1 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.175>The definition of the counter with reference key C1 or L1."
	DEFVAL { 1 }
	::= { adsConfigFrsPrGroup 8 }


adsConfigFrsPrCounter2 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.176>The definition of the counter with reference key C2 or L2."
	DEFVAL { 1 }
	::= { adsConfigFrsPrGroup 9 }


adsConfigFrsPrCounter3 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.177>The definition of the counter with reference key C3 or L3."
	DEFVAL { 1 }
	::= { adsConfigFrsPrGroup 10 }


adsConfigFrsPrCounter4 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.178>The definition of the counter with reference key C4 or L4."
	DEFVAL { 1 }
	::= { adsConfigFrsPrGroup 11 }


adsConfigFrsPrCounter5 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.179>The definition of the counter with reference key C5 or L5."
	DEFVAL { 1 }
	::= { adsConfigFrsPrGroup 12 }


adsConfigFrsPrCounter6 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.180>The definition of the counter with reference key C6 or L6."
	DEFVAL { 1 }
	::= { adsConfigFrsPrGroup 13 }


adsConfigFrsPrCounter7 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.181>The definition of the counter with reference key C7 or L7."
	DEFVAL { 1 }
	::= { adsConfigFrsPrGroup 14 }


adsConfigFrsPrCounter8 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.182>The definition of the counter with reference key C8 or L8."
	DEFVAL { 1 }
	::= { adsConfigFrsPrGroup 15 }


adsConfigFrsPrCounter9 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.183>The definition of the counter with reference key C9 or L9."
	DEFVAL { 1 }
	::= { adsConfigFrsPrGroup 16 }


adsConfigFrsPrAggLag OBJECT-TYPE
	SYNTAX INTEGER
	ACCESS read-write
	STATUS mandatory
	DESCRIPTION
		"&<caiAdsA2.184>The number of consecutive poll intervals on which any status is not in the Ok or Up state, before the aggregate status changes. Valid values are greater than 0."
	DEFVAL { 1 }
	::= { adsConfigFrsPrGroup 17 }


adsConfigFrsPrWarn OBJECT-TYPE
	SYNTAX DisplayString
	ACCESS read-write
	STATUS mandatory
	DESCRIPTION
		"&<caiAdsA2.185>Warning threshold for the calculated value of the expression. Valid values are greater than 0.0 and smaller than or equal to the critical threshold."
	DEFVAL { "1.0" }
	::= { adsConfigFrsPrGroup 18 }


adsConfigFrsPrCrit OBJECT-TYPE
	SYNTAX DisplayString
	ACCESS read-write
	STATUS mandatory
	DESCRIPTION
		"&<caiAdsA2.186>Critical threshold for the calculated value of the expression. Valid values are greater than 0.0 and greater than or equal to the warning threshold."
	DEFVAL { "2.0" }
	::= { adsConfigFrsPrGroup 19 }


adsConfigFrsPrWcMonitor OBJECT-TYPE
	SYNTAX INTEGER {
		do-not-monitor(1),
		warning-only(2),
		critical-only(3),
		both(4)
	}
	ACCESS read-write
	STATUS mandatory
	DESCRIPTION
		"&<caiAdsA2.187>Flag indicating whether the programmed expression should be monitored and if so, which threshold should be compared with."
	DEFVAL { 4 }
	::= { adsConfigFrsPrGroup 20 }


adsConfigFrsPrMin OBJECT-TYPE
	SYNTAX DisplayString
	ACCESS read-write
	STATUS mandatory
	DESCRIPTION
		"&<caiAdsA2.188>Minimum threshold for the calculated value of the expression. Valid values are greater than 0.0 or equal to -1.0 and smaller than or equal to the maximum threshold. Setting to -1.0 disables the monitoring of the minimum."
	DEFVAL { "1.0" }
	::= { adsConfigFrsPrGroup 21 }


adsConfigFrsPrMax OBJECT-TYPE
	SYNTAX DisplayString
	ACCESS read-write
	STATUS mandatory
	DESCRIPTION
		"&<caiAdsA2.189>Maximum threshold for the calculated value of the expression. Valid values are greater than 0.0 or equal to -1.0 and greater than or equal to the minimum threshold. Setting to -1.0 disables the monitoring of the maximum."
	DEFVAL { "1.0" }
	::= { adsConfigFrsPrGroup 22 }


adsConfigFrsPrMmMonitor OBJECT-TYPE
	SYNTAX INTEGER {
		do-not-monitor(1),
		down-warning(2),
		down-critical(3)
	}
	ACCESS read-write
	STATUS mandatory
	DESCRIPTION
		"&<caiAdsA2.190>Flag indicating whether the programmed expression should be monitored and if so, the level of alert to raise."
	DEFVAL { 1 }
	::= { adsConfigFrsPrGroup 23 }


adsConfigFrsPrButton OBJECT-TYPE
	SYNTAX INTEGER {
		none(1),
		add(2),
		remove(3)
	}
	ACCESS read-write
	STATUS mandatory
	DESCRIPTION
		"&<caiAdsA2.191>This attribute is used to add or remove a watcher with the current value of the watcher name attribute in this group."
	::= { adsConfigFrsPrGroup 24 }




-- *****************************************************************************
-- Domain Name Service Events Config Group
-- *****************************************************************************


adsConfigDnsEvPollInterval OBJECT-TYPE
	SYNTAX INTEGER
	ACCESS read-write
	STATUS mandatory
	DESCRIPTION
		"&<caiAdsA2.192>The time (in seconds) between the polling of the Domain Name Service Event Logs information. Valid values are greater than or equal to 30."
	DEFVAL { 120 }
	::= { adsConfigDnsEvGroup 1 }


adsConfigDnsEvPollMethod OBJECT-TYPE
	SYNTAX INTEGER {
		disabled(1),
		poll-interval-only(2),
		poll-interval-and-query(3),
		query-only(4)
	}
	ACCESS read-write
	STATUS mandatory
	DESCRIPTION
		"&<caiAdsA2.193>If set to 'disabled', the agent no more retrieves the Domain Name Service Event Logs information (not by polling, nor by get request) and sets all statuses to ok. If set to 'poll-interval-only', the agent only retrieves the information by polling, but not by get request. If set to 'poll-interval-and-query', the agent retrieves the information in both cases (polling and get request). If set to 'query-only', the agent only retrieves the information when a get request is made."
	DEFVAL { 2 }
	::= { adsConfigDnsEvGroup 2 }


adsConfigDnsEvAutoWatch OBJECT-TYPE
	SYNTAX INTEGER {
		no(1),
		yes(2)
	}
	ACCESS read-write
	STATUS mandatory
	DESCRIPTION
		"&<caiAdsA2.194>If this value is 'yes' the agent automatically creates watchers for all entries in the corresponding Available table, which have their individual AutoWatch attribute set to 'yes'. Otherwise no watchers are automatically created."
	DEFVAL { 2 }
	::= { adsConfigDnsEvGroup 3 }


adsConfigDnsEvName OBJECT-TYPE
	SYNTAX DisplayString
	ACCESS read-write
	STATUS mandatory
	DESCRIPTION
		"&<caiAdsA2.195>Name of the watcher to be added/removed, monitoring Domain Name Service Event Logs. Important: This name is arbitrary but case insensitive. When prefixed with the keyword '[OTHER]' then the watcher will not be applied on a new Event Log entry, if any other watcher not using this prefix already matches the entry during the same poll cycle."
	::= { adsConfigDnsEvGroup 4 }


adsConfigDnsEvDescription OBJECT-TYPE
	SYNTAX DisplayString
	ACCESS read-write
	STATUS mandatory
	DESCRIPTION
		"&<caiAdsA2.196>Any description for this watcher."
	::= { adsConfigDnsEvGroup 5 }


adsConfigDnsEvPatterns OBJECT-TYPE
	SYNTAX DisplayString
	ACCESS read-write
	STATUS mandatory
	DESCRIPTION
		"&<caiAdsA2.197>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsConfigDnsEvGroup 6 }


adsConfigDnsEvMonitor OBJECT-TYPE
	SYNTAX INTEGER {
		do-not-monitor(1),
		down-warning(2),
		down-critical(3)
	}
	ACCESS read-write
	STATUS mandatory
	DESCRIPTION
		"&<caiAdsA2.198>Flag indicating whether Domain Name Service Event Logs should be monitored by this watcher and if so, the level of alert to raise."
	DEFVAL { 3 }
	::= { adsConfigDnsEvGroup 7 }


adsConfigDnsEvButton OBJECT-TYPE
	SYNTAX INTEGER {
		none(1),
		add(2),
		remove(3)
	}
	ACCESS read-write
	STATUS mandatory
	DESCRIPTION
		"&<caiAdsA2.199>This attribute is used to add or remove a watcher with the current value of the watcher name attribute in this group."
	::= { adsConfigDnsEvGroup 8 }




-- *****************************************************************************
-- Domain Name Service Performance Config Group
-- *****************************************************************************


adsConfigDnsPrPollInterval OBJECT-TYPE
	SYNTAX INTEGER
	ACCESS read-write
	STATUS mandatory
	DESCRIPTION
		"&<caiAdsA2.200>The time (in seconds) between the polling of the Domain Name Service Performance information. Valid values are greater than or equal to 30."
	DEFVAL { 120 }
	::= { adsConfigDnsPrGroup 1 }


adsConfigDnsPrPollMethod OBJECT-TYPE
	SYNTAX INTEGER {
		disabled(1),
		poll-interval-only(2),
		poll-interval-and-query(3),
		query-only(4)
	}
	ACCESS read-write
	STATUS mandatory
	DESCRIPTION
		"&<caiAdsA2.201>If set to 'disabled', the agent no more retrieves the Domain Name Service Performance information (not by polling, nor by get request) and sets all statuses to ok. If set to 'poll-interval-only', the agent only retrieves the information by polling, but not by get request. If set to 'poll-interval-and-query', the agent retrieves the information in both cases (polling and get request). If set to 'query-only', the agent only retrieves the information when a get request is made."
	DEFVAL { 2 }
	::= { adsConfigDnsPrGroup 2 }


adsConfigDnsPrAutoWatch OBJECT-TYPE
	SYNTAX INTEGER {
		no(1),
		yes(2)
	}
	ACCESS read-write
	STATUS mandatory
	DESCRIPTION
		"&<caiAdsA2.202>If this value is 'yes' the agent automatically creates watchers for all entries in the corresponding Available table, which have their individual AutoWatch attribute set to 'yes'. Otherwise no watchers are automatically created."
	DEFVAL { 2 }
	::= { adsConfigDnsPrGroup 3 }


adsConfigDnsPrName OBJECT-TYPE
	SYNTAX DisplayString
	ACCESS read-write
	STATUS mandatory
	DESCRIPTION
		"&<caiAdsA2.203>Name of the performance watcher to be added/removed. Important: This name is arbitrary but case insensitive."
	::= { adsConfigDnsPrGroup 4 }


adsConfigDnsPrDescription OBJECT-TYPE
	SYNTAX DisplayString
	ACCESS read-write
	STATUS mandatory
	DESCRIPTION
		"&<caiAdsA2.204>Any description for this watcher."
	::= { adsConfigDnsPrGroup 5 }


adsConfigDnsPrExpression OBJECT-TYPE
	SYNTAX DisplayString
	ACCESS read-write
	STATUS mandatory
	DESCRIPTION
		"&<caiAdsA2.205>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsConfigDnsPrGroup 6 }


adsConfigDnsPrCounter0 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.206>The definition of the counter with reference key C0 or L0."
	DEFVAL { 1 }
	::= { adsConfigDnsPrGroup 7 }


adsConfigDnsPrCounter1 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.207>The definition of the counter with reference key C1 or L1."
	DEFVAL { 1 }
	::= { adsConfigDnsPrGroup 8 }


adsConfigDnsPrCounter2 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.208>The definition of the counter with reference key C2 or L2."
	DEFVAL { 1 }
	::= { adsConfigDnsPrGroup 9 }


adsConfigDnsPrCounter3 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.209>The definition of the counter with reference key C3 or L3."
	DEFVAL { 1 }
	::= { adsConfigDnsPrGroup 10 }


adsConfigDnsPrCounter4 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.210>The definition of the counter with reference key C4 or L4."
	DEFVAL { 1 }
	::= { adsConfigDnsPrGroup 11 }


adsConfigDnsPrCounter5 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.211>The definition of the counter with reference key C5 or L5."
	DEFVAL { 1 }
	::= { adsConfigDnsPrGroup 12 }


adsConfigDnsPrCounter6 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.212>The definition of the counter with reference key C6 or L6."
	DEFVAL { 1 }
	::= { adsConfigDnsPrGroup 13 }


adsConfigDnsPrCounter7 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.213>The definition of the counter with reference key C7 or L7."
	DEFVAL { 1 }
	::= { adsConfigDnsPrGroup 14 }


adsConfigDnsPrCounter8 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.214>The definition of the counter with reference key C8 or L8."
	DEFVAL { 1 }
	::= { adsConfigDnsPrGroup 15 }


adsConfigDnsPrCounter9 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.215>The definition of the counter with reference key C9 or L9."
	DEFVAL { 1 }
	::= { adsConfigDnsPrGroup 16 }


adsConfigDnsPrAggLag OBJECT-TYPE
	SYNTAX INTEGER
	ACCESS read-write
	STATUS mandatory
	DESCRIPTION
		"&<caiAdsA2.216>The number of consecutive poll intervals on which any status is not in the Ok or Up state, before the aggregate status changes. Valid values are greater than 0."
	DEFVAL { 1 }
	::= { adsConfigDnsPrGroup 17 }


adsConfigDnsPrWarn OBJECT-TYPE
	SYNTAX DisplayString
	ACCESS read-write
	STATUS mandatory
	DESCRIPTION
		"&<caiAdsA2.217>Warning threshold for the calculated value of the expression. Valid values are greater than 0.0 and smaller than or equal to the critical threshold."
	DEFVAL { "1.0" }
	::= { adsConfigDnsPrGroup 18 }


adsConfigDnsPrCrit OBJECT-TYPE
	SYNTAX DisplayString
	ACCESS read-write
	STATUS mandatory
	DESCRIPTION
		"&<caiAdsA2.218>Critical threshold for the calculated value of the expression. Valid values are greater than 0.0 and greater than or equal to the warning threshold."
	DEFVAL { "2.0" }
	::= { adsConfigDnsPrGroup 19 }


adsConfigDnsPrWcMonitor OBJECT-TYPE
	SYNTAX INTEGER {
		do-not-monitor(1),
		warning-only(2),
		critical-only(3),
		both(4)
	}
	ACCESS read-write
	STATUS mandatory
	DESCRIPTION
		"&<caiAdsA2.219>Flag indicating whether the programmed expression should be monitored and if so, which threshold should be compared with."
	DEFVAL { 4 }
	::= { adsConfigDnsPrGroup 20 }


adsConfigDnsPrMin OBJECT-TYPE
	SYNTAX DisplayString
	ACCESS read-write
	STATUS mandatory
	DESCRIPTION
		"&<caiAdsA2.220>Minimum threshold for the calculated value of the expression. Valid values are greater than 0.0 or equal to -1.0 and smaller than or equal to the maximum threshold. Setting to -1.0 disables the monitoring of the minimum."
	DEFVAL { "1.0" }
	::= { adsConfigDnsPrGroup 21 }


adsConfigDnsPrMax OBJECT-TYPE
	SYNTAX DisplayString
	ACCESS read-write
	STATUS mandatory
	DESCRIPTION
		"&<caiAdsA2.221>Maximum threshold for the calculated value of the expression. Valid values are greater than 0.0 or equal to -1.0 and greater than or equal to the minimum threshold. Setting to -1.0 disables the monitoring of the maximum."
	DEFVAL { "1.0" }
	::= { adsConfigDnsPrGroup 22 }


adsConfigDnsPrMmMonitor OBJECT-TYPE
	SYNTAX INTEGER {
		do-not-monitor(1),
		down-warning(2),
		down-critical(3)
	}
	ACCESS read-write
	STATUS mandatory
	DESCRIPTION
		"&<caiAdsA2.222>Flag indicating whether the programmed expression should be monitored and if so, the level of alert to raise."
	DEFVAL { 1 }
	::= { adsConfigDnsPrGroup 23 }


adsConfigDnsPrButton OBJECT-TYPE
	SYNTAX INTEGER {
		none(1),
		add(2),
		remove(3)
	}
	ACCESS read-write
	STATUS mandatory
	DESCRIPTION
		"&<caiAdsA2.223>This attribute is used to add or remove a watcher with the current value of the watcher name attribute in this group."
	::= { adsConfigDnsPrGroup 24 }




-- *****************************************************************************
-- General Status Group
-- *****************************************************************************


adsStatusGeneralTotalCount OBJECT-TYPE
	SYNTAX INTEGER
	ACCESS read-only
	STATUS mandatory
	DESCRIPTION
		"&<caiAdsA2.224>The number of all monitoring watchers."
	::= { adsStatusGeneralGroup 1 }


adsStatusGeneralTotalWarn OBJECT-TYPE
	SYNTAX INTEGER
	ACCESS read-only
	STATUS mandatory
	DESCRIPTION
		"&<caiAdsA2.225>The number of all monitoring watchers in a warning status."
	::= { adsStatusGeneralGroup 2 }


adsStatusGeneralTotalCrit OBJECT-TYPE
	SYNTAX INTEGER
	ACCESS read-only
	STATUS mandatory
	DESCRIPTION
		"&<caiAdsA2.226>The number of all monitored watchers in a critical status."
	::= { adsStatusGeneralGroup 3 }


adsStatusGeneralDCtrlCount OBJECT-TYPE
	SYNTAX INTEGER
	ACCESS read-only
	STATUS mandatory
	DESCRIPTION
		"&<caiAdsA2.227>The number of monitoring Domain Controller watchers."
	::= { adsStatusGeneralGroup 4 }


adsStatusGeneralDCtrlWarn OBJECT-TYPE
	SYNTAX INTEGER
	ACCESS read-only
	STATUS mandatory
	DESCRIPTION
		"&<caiAdsA2.228>The number of monitoring Domain Controller watchers in a warning state."
	::= { adsStatusGeneralGroup 5 }


adsStatusGeneralDCtrlCrit OBJECT-TYPE
	SYNTAX INTEGER
	ACCESS read-only
	STATUS mandatory
	DESCRIPTION
		"&<caiAdsA2.229>The number of monitoring Domain Controller watchers in a critical state."
	::= { adsStatusGeneralGroup 6 }


adsStatusGeneralDskSpCount OBJECT-TYPE
	SYNTAX INTEGER
	ACCESS read-only
	STATUS mandatory
	DESCRIPTION
		"&<caiAdsA2.230>The number of monitoring Disk Space watchers."
	::= { adsStatusGeneralGroup 7 }


adsStatusGeneralDskSpWarn OBJECT-TYPE
	SYNTAX INTEGER
	ACCESS read-only
	STATUS mandatory
	DESCRIPTION
		"&<caiAdsA2.231>The number of monitoring Disk Space watchers in a warning state."
	::= { adsStatusGeneralGroup 8 }


adsStatusGeneralDskSpCrit OBJECT-TYPE
	SYNTAX INTEGER
	ACCESS read-only
	STATUS mandatory
	DESCRIPTION
		"&<caiAdsA2.232>The number of monitoring Disk Space watchers in a critical state."
	::= { adsStatusGeneralGroup 9 }


adsStatusGeneralAdsEvCount OBJECT-TYPE
	SYNTAX INTEGER
	ACCESS read-only
	STATUS mandatory
	DESCRIPTION
		"&<caiAdsA2.233>The number of monitoring Active Directory Service Events watchers."
	::= { adsStatusGeneralGroup 10 }


adsStatusGeneralAdsEvWarn OBJECT-TYPE
	SYNTAX INTEGER
	ACCESS read-only
	STATUS mandatory
	DESCRIPTION
		"&<caiAdsA2.234>The number of monitoring Active Directory Service Events watchers in a warning state."
	::= { adsStatusGeneralGroup 11 }


adsStatusGeneralAdsEvCrit OBJECT-TYPE
	SYNTAX INTEGER
	ACCESS read-only
	STATUS mandatory
	DESCRIPTION
		"&<caiAdsA2.235>The number of monitoring Active Directory Service Events watchers in a critical state."
	::= { adsStatusGeneralGroup 12 }


adsStatusGeneralAdsPrCount OBJECT-TYPE
	SYNTAX INTEGER
	ACCESS read-only
	STATUS mandatory
	DESCRIPTION
		"&<caiAdsA2.236>The number of Active Directory Service Performance watchers."
	::= { adsStatusGeneralGroup 13 }


adsStatusGeneralAdsPrWarn OBJECT-TYPE
	SYNTAX INTEGER
	ACCESS read-only
	STATUS mandatory
	DESCRIPTION
		"&<caiAdsA2.237>The number of Active Directory Service Performance watchers in a warning state."
	::= { adsStatusGeneralGroup 14 }


adsStatusGeneralAdsPrCrit OBJECT-TYPE
	SYNTAX INTEGER
	ACCESS read-only
	STATUS mandatory
	DESCRIPTION
		"&<caiAdsA2.238>The number of Active Directory Service Performance watchers in a critical state."
	::= { adsStatusGeneralGroup 15 }


adsStatusGeneralFrsEvCount OBJECT-TYPE
	SYNTAX INTEGER
	ACCESS read-only
	STATUS mandatory
	DESCRIPTION
		"&<caiAdsA2.239>The number of monitoring File Replication Service Events watchers."
	::= { adsStatusGeneralGroup 16 }


adsStatusGeneralFrsEvWarn OBJECT-TYPE
	SYNTAX INTEGER
	ACCESS read-only
	STATUS mandatory
	DESCRIPTION
		"&<caiAdsA2.240>The number of monitoring File Replication Service Events watchers in a warning state."
	::= { adsStatusGeneralGroup 17 }


adsStatusGeneralFrsEvCrit OBJECT-TYPE
	SYNTAX INTEGER
	ACCESS read-only
	STATUS mandatory
	DESCRIPTION
		"&<caiAdsA2.241>The number of monitoring File Replication Service Events watchers in a critical state."
	::= { adsStatusGeneralGroup 18 }


adsStatusGeneralFrsPrCount OBJECT-TYPE
	SYNTAX INTEGER
	ACCESS read-only
	STATUS mandatory
	DESCRIPTION
		"&<caiAdsA2.242>The number of File Replication Service Performance watchers."
	::= { adsStatusGeneralGroup 19 }


adsStatusGeneralFrsPrWarn OBJECT-TYPE
	SYNTAX INTEGER
	ACCESS read-only
	STATUS mandatory
	DESCRIPTION
		"&<caiAdsA2.243>The number of File Replication Service Performance watchers in a warning state."
	::= { adsStatusGeneralGroup 20 }


adsStatusGeneralFrsPrCrit OBJECT-TYPE
	SYNTAX INTEGER
	ACCESS read-only
	STATUS mandatory
	DESCRIPTION
		"&<caiAdsA2.244>The number of File Replication Service Performance watchers in a critical state."
	::= { adsStatusGeneralGroup 21 }


adsStatusGeneralDnsEvCount OBJECT-TYPE
	SYNTAX INTEGER
	ACCESS read-only
	STATUS mandatory
	DESCRIPTION
		"&<caiAdsA2.245>The number of monitoring Domain Name Service Events watchers."
	::= { adsStatusGeneralGroup 22 }


adsStatusGeneralDnsEvWarn OBJECT-TYPE
	SYNTAX INTEGER
	ACCESS read-only
	STATUS mandatory
	DESCRIPTION
		"&<caiAdsA2.246>The number of monitoring Domain Name Service Events watchers in a warning state."
	::= { adsStatusGeneralGroup 23 }


adsStatusGeneralDnsEvCrit OBJECT-TYPE
	SYNTAX INTEGER
	ACCESS read-only
	STATUS mandatory
	DESCRIPTION
		"&<caiAdsA2.247>The number of monitoring Domain Name Service Events watchers in a critical state."
	::= { adsStatusGeneralGroup 24 }


adsStatusGeneralDnsPrCount OBJECT-TYPE
	SYNTAX INTEGER
	ACCESS read-only
	STATUS mandatory
	DESCRIPTION
		"&<caiAdsA2.248>The number of Domain Name Service Performance watchers."
	::= { adsStatusGeneralGroup 25 }


adsStatusGeneralDnsPrWarn OBJECT-TYPE
	SYNTAX INTEGER
	ACCESS read-only
	STATUS mandatory
	DESCRIPTION
		"&<caiAdsA2.249>The number of Domain Name Service Performance watchers in a warning state."
	::= { adsStatusGeneralGroup 26 }


adsStatusGeneralDnsPrCrit OBJECT-TYPE
	SYNTAX INTEGER
	ACCESS read-only
	STATUS mandatory
	DESCRIPTION
		"&<caiAdsA2.250>The number of Domain Name Service Performance watchers in a critical state."
	::= { adsStatusGeneralGroup 27 }




-- *****************************************************************************
-- Domain Controller Status Group
-- *****************************************************************************


adsStatusDCtrlCount OBJECT-TYPE
	SYNTAX INTEGER
	ACCESS read-only
	STATUS mandatory
	DESCRIPTION
		"&<caiAdsA2.251>The number of entries in the adsStatusDCtrlTable."
	::= { adsStatusDCtrlGroup 1 }


adsStatusDCtrlTable OBJECT-TYPE
	SYNTAX SEQUENCE OF AdsStatusDCtrlRow
	ACCESS not-accessible
	STATUS mandatory
	DESCRIPTION
		"&<caiAdsA2.252>A table containing information about all monitored domain controllers."
	::= { adsStatusDCtrlGroup 2 }


adsStatusDCtrlEntry OBJECT-TYPE
	SYNTAX AdsStatusDCtrlRow
	ACCESS not-accessible
	STATUS mandatory
	DESCRIPTION
		"&<caiAdsA2.253>The table entry."
	INDEX { adsStatusDCtrlRole, adsStatusDCtrlName }
	::= { adsStatusDCtrlTable 1 }


AdsStatusDCtrlRow ::=
	SEQUENCE {
		adsStatusDCtrlRole DisplayString,
		adsStatusDCtrlName DisplayString,
		adsStatusDCtrlSite DisplayString,
		adsStatusDCtrlAggLagValue INTEGER,
		adsStatusDCtrlAggLag INTEGER,
		adsStatusDCtrlAggStatus INTEGER,
		adsStatusDCtrlBindValue INTEGER,
		adsStatusDCtrlBindWarn INTEGER,
		adsStatusDCtrlBindCrit INTEGER,
		adsStatusDCtrlBindMonitor INTEGER,
		adsStatusDCtrlBindStatus INTEGER,
		adsStatusDCtrlLdapValue INTEGER,
		adsStatusDCtrlLdapWarn INTEGER,
		adsStatusDCtrlLdapCrit INTEGER,
		adsStatusDCtrlLdapMonitor INTEGER,
		adsStatusDCtrlLdapStatus INTEGER,
		adsStatusDCtrlLossAction INTEGER,
		adsStatusDCtrlLossStatus INTEGER,
		adsStatusDCtrlCallBackRef DisplayString
	}


adsStatusDCtrlRole OBJECT-TYPE
	SYNTAX DisplayString
	ACCESS read-only
	STATUS mandatory
	DESCRIPTION
		"&<caiAdsA2.254>Role name of the watcher, monitoring a domain controller with this role. The roles could be DOM (for 'Domain Controller'), CAT (for 'Global Catalog'), SCH (for 'Schema Master'), NAM (for 'Domain Naming Master'), INF (for 'Infrastructure Master'), RID (for 'Relative ID Master') or PDC (for 'Primary Domain Controller Emulator')."
	::= { adsStatusDCtrlEntry 1 }


adsStatusDCtrlName OBJECT-TYPE
	SYNTAX DisplayString
	ACCESS read-only
	STATUS mandatory
	DESCRIPTION
		"&<caiAdsA2.255>Domain controller name of the watcher, monitoring a domain controller with this name."
	::= { adsStatusDCtrlEntry 2 }


adsStatusDCtrlSite OBJECT-TYPE
	SYNTAX DisplayString
	ACCESS read-only
	STATUS mandatory
	DESCRIPTION
		"&<caiAdsA2.256>The name of the site, where this monitored domain controller is a member of."
	::= { adsStatusDCtrlEntry 3 }


adsStatusDCtrlAggLagValue OBJECT-TYPE
	SYNTAX INTEGER
	ACCESS read-only
	STATUS mandatory
	DESCRIPTION
		"&<caiAdsA2.257>The number of consecutive poll intervals on which any status was not in the Ok or Up state."
	::= { adsStatusDCtrlEntry 4 }


adsStatusDCtrlAggLag OBJECT-TYPE
	SYNTAX INTEGER
	ACCESS read-write
	STATUS mandatory
	DESCRIPTION
		"&<caiAdsA2.258>The number of consecutive poll intervals on which any status is not in the Ok or Up state, before the aggregate status changes. Valid values are greater than 0."
	DEFVAL { 1 }
	::= { adsStatusDCtrlEntry 5 }


adsStatusDCtrlAggStatus OBJECT-TYPE
	SYNTAX INTEGER {
		unknown(1),
		ok(2),
		warning(3),
		critical(4)
	}
	ACCESS read-only
	STATUS mandatory
	DESCRIPTION
		"&<caiAdsA2.259>The current status of the domain controller as a 'worst case' aggregate of all its statuses."
	::= { adsStatusDCtrlEntry 6 }


adsStatusDCtrlBindValue OBJECT-TYPE
	SYNTAX INTEGER
	ACCESS read-only
	STATUS mandatory
	DESCRIPTION
		"&<caiAdsA2.260>The current value (in milliseconds) of the time needed to bind to the domain controller. If the bind fails for any reason the very large value '999999' is returned, to indicate this failure."
	::= { adsStatusDCtrlEntry 7 }


adsStatusDCtrlBindWarn OBJECT-TYPE
	SYNTAX INTEGER
	ACCESS read-write
	STATUS mandatory
	DESCRIPTION
		"&<caiAdsA2.261>Warning threshold (in milliseconds) for the time needed to bind to the domain controller. Valid values are greater than 0 and smaller than or equal to the critical threshold."
	::= { adsStatusDCtrlEntry 8 }


adsStatusDCtrlBindCrit OBJECT-TYPE
	SYNTAX INTEGER
	ACCESS read-write
	STATUS mandatory
	DESCRIPTION
		"&<caiAdsA2.262>Critical threshold (in milliseconds) for the time needed to bind to the domain controller. Valid values are greater than 0 and greater than or equal to the warning threshold."
	::= { adsStatusDCtrlEntry 9 }


adsStatusDCtrlBindMonitor OBJECT-TYPE
	SYNTAX INTEGER {
		do-not-monitor(1),
		warning-only(2),
		critical-only(3),
		both(4)
	}
	ACCESS read-write
	STATUS mandatory
	DESCRIPTION
		"&<caiAdsA2.263>Flag indicating whether the time needed to bind to the domain controller should be monitored and if so, which threshold should be compared with."
	DEFVAL { 0 }
	::= { adsStatusDCtrlEntry 10 }


adsStatusDCtrlBindStatus OBJECT-TYPE
	SYNTAX INTEGER {
		unknown(1),
		ok(2),
		warning(3),
		critical(4)
	}
	ACCESS read-only
	STATUS mandatory
	DESCRIPTION
		"&<caiAdsA2.264>The current status of the time needed to bind to the domain controller as determined by the thresholds. The status 'unknown' means that the current value could not be retrieved from the system."
	::= { adsStatusDCtrlEntry 11 }


adsStatusDCtrlLdapValue OBJECT-TYPE
	SYNTAX INTEGER
	ACCESS read-only
	STATUS mandatory
	DESCRIPTION
		"&<caiAdsA2.265>The current value (in milliseconds) of the time needed to run a LDAP query to the domain controller.If the query fails for any reason the very large value '999999' is returned, to indicate this failure."
	::= { adsStatusDCtrlEntry 12 }


adsStatusDCtrlLdapWarn OBJECT-TYPE
	SYNTAX INTEGER
	ACCESS read-write
	STATUS mandatory
	DESCRIPTION
		"&<caiAdsA2.266>Warning threshold (in milliseconds) for the time needed to run a LDAP query to the domain controller. Valid values are greater than 0 and smaller than or equal to the critical threshold."
	::= { adsStatusDCtrlEntry 13 }


adsStatusDCtrlLdapCrit OBJECT-TYPE
	SYNTAX INTEGER
	ACCESS read-write
	STATUS mandatory
	DESCRIPTION
		"&<caiAdsA2.267>Critical threshold (in milliseconds) for the time needed to run a LDAP query to the domain controller. Valid values are greater than 0 and greater than or equal to the warning threshold."
	::= { adsStatusDCtrlEntry 14 }


adsStatusDCtrlLdapMonitor OBJECT-TYPE
	SYNTAX INTEGER {
		do-not-monitor(1),
		warning-only(2),
		critical-only(3),
		both(4)
	}
	ACCESS read-write
	STATUS mandatory
	DESCRIPTION
		"&<caiAdsA2.268>Flag indicating whether the time needed to run a LDAP query to the domain controller should be monitored and if so, which threshold should be compared with."
	DEFVAL { 0 }
	::= { adsStatusDCtrlEntry 15 }


adsStatusDCtrlLdapStatus OBJECT-TYPE
	SYNTAX INTEGER {
		unknown(1),
		ok(2),
		warning(3),
		critical(4)
	}
	ACCESS read-only
	STATUS mandatory
	DESCRIPTION
		"&<caiAdsA2.269>The current status of the time needed to run a LDAP query to the domain controller as determined by the thresholds. The status 'unknown' means that the current value could not be retrieved from the system."
	::= { adsStatusDCtrlEntry 16 }


adsStatusDCtrlLossAction OBJECT-TYPE
	SYNTAX INTEGER {
		remove(1),
		up(2),
		down-warning(3),
		down-critical(4)
	}
	ACCESS read-write
	STATUS mandatory
	DESCRIPTION
		"&<caiAdsA2.270>Flag defining the severity if the loss of a role for a domain controller is detected or whether to remove this watcher in that case."
	DEFVAL { 0 }
	::= { adsStatusDCtrlEntry 17 }


adsStatusDCtrlLossStatus OBJECT-TYPE
	SYNTAX INTEGER {
		unknown(1),
		up(2),
		down-warning(3),
		down-critical(4)
	}
	ACCESS read-only
	STATUS mandatory
	DESCRIPTION
		"&<caiAdsA2.271>The current status of the domain controller's loss as determined by the loss action."
	::= { adsStatusDCtrlEntry 18 }


adsStatusDCtrlCallBackRef OBJECT-TYPE
	SYNTAX DisplayString
	ACCESS read-only
	STATUS mandatory
	DESCRIPTION
		"&<caiAdsA2.272>The name of the Call-Back reference that should be invoked in case of a status change."
	::= { adsStatusDCtrlEntry 19 }




-- *****************************************************************************
-- Disk Space Status Group
-- *****************************************************************************


adsStatusDskSpCount OBJECT-TYPE
	SYNTAX INTEGER
	ACCESS read-only
	STATUS mandatory
	DESCRIPTION
		"&<caiAdsA2.273>The number of entries in the adsStatusDskSpTable."
	::= { adsStatusDskSpGroup 1 }


adsStatusDskSpTable OBJECT-TYPE
	SYNTAX SEQUENCE OF AdsStatusDskSpRow
	ACCESS not-accessible
	STATUS mandatory
	DESCRIPTION
		"&<caiAdsA2.274>A table containing information about all monitored Disk Space watchers."
	::= { adsStatusDskSpGroup 2 }


adsStatusDskSpEntry OBJECT-TYPE
	SYNTAX AdsStatusDskSpRow
	ACCESS not-accessible
	STATUS mandatory
	DESCRIPTION
		"&<caiAdsA2.275>The table entry."
	INDEX { adsStatusDskSpType, adsStatusDskSpName }
	::= { adsStatusDskSpTable 1 }


AdsStatusDskSpRow ::=
	SEQUENCE {
		adsStatusDskSpType DisplayString,
		adsStatusDskSpName DisplayString,
		adsStatusDskSpDirName DisplayString,
		adsStatusDskSpDirSize INTEGER,
		adsStatusDskSpAggLagValue INTEGER,
		adsStatusDskSpAggLag INTEGER,
		adsStatusDskSpAggStatus INTEGER,
		adsStatusDskSpSpaceTotal INTEGER,
		adsStatusDskSpSpaceValue INTEGER,
		adsStatusDskSpSpaceWarnValue INTEGER,
		adsStatusDskSpSpaceCritValue INTEGER,
		adsStatusDskSpSpaceWarn DisplayString,
		adsStatusDskSpSpaceCrit DisplayString,
		adsStatusDskSpSpaceMonitor INTEGER,
		adsStatusDskSpSpaceStatus INTEGER,
		adsStatusDskSpLossAction INTEGER,
		adsStatusDskSpLossStatus INTEGER,
		adsStatusDskSpCallBackRef DisplayString
	}


adsStatusDskSpType OBJECT-TYPE
	SYNTAX DisplayString
	ACCESS read-only
	STATUS mandatory
	DESCRIPTION
		"&<caiAdsA2.276>Type name of the watcher, monitoring a disk space with this type. The types could be VOL (for 'System Volume'), FIL (for 'Database Files') or LOG (for 'Database Logs')."
	::= { adsStatusDskSpEntry 1 }


adsStatusDskSpName OBJECT-TYPE
	SYNTAX DisplayString
	ACCESS read-only
	STATUS mandatory
	DESCRIPTION
		"&<caiAdsA2.277>Disk name of the watcher, monitoring a disk space with this name."
	::= { adsStatusDskSpEntry 2 }


adsStatusDskSpDirName OBJECT-TYPE
	SYNTAX DisplayString
	ACCESS read-only
	STATUS mandatory
	DESCRIPTION
		"&<caiAdsA2.278>Name of the directory, which contains the relevant data on the disk space."
	::= { adsStatusDskSpEntry 3 }


adsStatusDskSpDirSize OBJECT-TYPE
	SYNTAX INTEGER
	ACCESS read-only
	STATUS mandatory
	DESCRIPTION
		"&<caiAdsA2.279>Size of the directory, which contains the relevant data on the disk space (in kilobytes)."
	::= { adsStatusDskSpEntry 4 }


adsStatusDskSpAggLagValue OBJECT-TYPE
	SYNTAX INTEGER
	ACCESS read-only
	STATUS mandatory
	DESCRIPTION
		"&<caiAdsA2.280>The number of consecutive poll intervals on which any status was not in the Ok or Up state."
	::= { adsStatusDskSpEntry 5 }


adsStatusDskSpAggLag OBJECT-TYPE
	SYNTAX INTEGER
	ACCESS read-write
	STATUS mandatory
	DESCRIPTION
		"&<caiAdsA2.281>The number of consecutive poll intervals on which any status is not in the Ok or Up state, before the aggregate status changes. Valid values are greater than 0."
	DEFVAL { 1 }
	::= { adsStatusDskSpEntry 6 }


adsStatusDskSpAggStatus OBJECT-TYPE
	SYNTAX INTEGER {
		unknown(1),
		ok(2),
		warning(3),
		critical(4)
	}
	ACCESS read-only
	STATUS mandatory
	DESCRIPTION
		"&<caiAdsA2.282>The current status of the disk space as a 'worst case' aggregate of all its statuses."
	::= { adsStatusDskSpEntry 7 }


adsStatusDskSpSpaceTotal OBJECT-TYPE
	SYNTAX INTEGER
	ACCESS read-only
	STATUS mandatory
	DESCRIPTION
		"&<caiAdsA2.283>The total size of the disk space (in megabytes)."
	::= { adsStatusDskSpEntry 8 }


adsStatusDskSpSpaceValue OBJECT-TYPE
	SYNTAX INTEGER
	ACCESS read-only
	STATUS mandatory
	DESCRIPTION
		"&<caiAdsA2.284>The current value of the used disk space (in megabytes)."
	::= { adsStatusDskSpEntry 9 }


adsStatusDskSpSpaceWarnValue OBJECT-TYPE
	SYNTAX INTEGER
	ACCESS read-only
	STATUS mandatory
	DESCRIPTION
		"&<caiAdsA2.285>The actual warning threshold in used megabytes derived from the configured warning threshold."
	::= { adsStatusDskSpEntry 10 }


adsStatusDskSpSpaceCritValue OBJECT-TYPE
	SYNTAX INTEGER
	ACCESS read-only
	STATUS mandatory
	DESCRIPTION
		"&<caiAdsA2.286>The actual critical threshold in used megabytes derived from the configured critical threshold."
	::= { adsStatusDskSpEntry 11 }


adsStatusDskSpSpaceWarn OBJECT-TYPE
	SYNTAX DisplayString
	ACCESS read-write
	STATUS mandatory
	DESCRIPTION
		"&<caiAdsA2.287>Warning threshold in megabytes, either for the free (by appending a 'F') or for the used disk space. The used space can also be defined as a percentage value of the total disk space (by appending a '%'). Valid values are greater than 0 and smaller (in case of 'free' greater) than or equal to the critical threshold."
	::= { adsStatusDskSpEntry 12 }


adsStatusDskSpSpaceCrit OBJECT-TYPE
	SYNTAX DisplayString
	ACCESS read-write
	STATUS mandatory
	DESCRIPTION
		"&<caiAdsA2.288>Critical threshold in megabytes, either for the free (by appending a 'F') or for the used disk space. The used space can also be defined as a percentage value of the total disk space (by appending a '%'). Valid values are greater than 0 and greater (in case of 'free' smaller) than or equal to the warning threshold."
	::= { adsStatusDskSpEntry 13 }


adsStatusDskSpSpaceMonitor OBJECT-TYPE
	SYNTAX INTEGER {
		do-not-monitor(1),
		warning-only(2),
		critical-only(3),
		both(4)
	}
	ACCESS read-write
	STATUS mandatory
	DESCRIPTION
		"&<caiAdsA2.289>Flag indicating whether the used disk space should be monitored and if so, which threshold should be compared with."
	DEFVAL { 0 }
	::= { adsStatusDskSpEntry 14 }


adsStatusDskSpSpaceStatus OBJECT-TYPE
	SYNTAX INTEGER {
		unknown(1),
		ok(2),
		warning(3),
		critical(4)
	}
	ACCESS read-only
	STATUS mandatory
	DESCRIPTION
		"&<caiAdsA2.290>The current status of the used disk space as determined by the thresholds. The status 'unknown' means that the current value could not be retrieved from the system."
	::= { adsStatusDskSpEntry 15 }


adsStatusDskSpLossAction OBJECT-TYPE
	SYNTAX INTEGER {
		remove(1),
		up(2),
		down-warning(3),
		down-critical(4)
	}
	ACCESS read-write
	STATUS mandatory
	DESCRIPTION
		"&<caiAdsA2.291>Flag defining the severity if the loss of a disk space is detected or whether to remove this watcher in that case."
	DEFVAL { 0 }
	::= { adsStatusDskSpEntry 16 }


adsStatusDskSpLossStatus OBJECT-TYPE
	SYNTAX INTEGER {
		unknown(1),
		up(2),
		down-warning(3),
		down-critical(4)
	}
	ACCESS read-only
	STATUS mandatory
	DESCRIPTION
		"&<caiAdsA2.292>The current status of the disk space's loss as determined by the loss action."
	::= { adsStatusDskSpEntry 17 }


adsStatusDskSpCallBackRef OBJECT-TYPE
	SYNTAX DisplayString
	ACCESS read-only
	STATUS mandatory
	DESCRIPTION
		"&<caiAdsA2.293>The name of the Call-Back reference that should be invoked in case of a status change."
	::= { adsStatusDskSpEntry 18 }




-- *****************************************************************************
-- Active Directory Service Events Status Group
-- *****************************************************************************


adsStatusAdsEvCount OBJECT-TYPE
	SYNTAX INTEGER
	ACCESS read-only
	STATUS mandatory
	DESCRIPTION
		"&<caiAdsA2.294>The number of entries in the adsStatusAdsEvTable."
	::= { adsStatusAdsEvGroup 1 }


adsStatusAdsEvTable OBJECT-TYPE
	SYNTAX SEQUENCE OF AdsStatusAdsEvRow
	ACCESS not-accessible
	STATUS mandatory
	DESCRIPTION
		"&<caiAdsA2.295>A table containing information about all Active Directory Service Event Logs watchers."
	::= { adsStatusAdsEvGroup 2 }


adsStatusAdsEvEntry OBJECT-TYPE
	SYNTAX AdsStatusAdsEvRow
	ACCESS not-accessible
	STATUS mandatory
	DESCRIPTION
		"&<caiAdsA2.296>The table entry."
	INDEX { adsStatusAdsEvName }
	::= { adsStatusAdsEvTable 1 }


AdsStatusAdsEvRow ::=
	SEQUENCE {
		adsStatusAdsEvName DisplayString,
		adsStatusAdsEvDescription DisplayString,
		adsStatusAdsEvLastMatch DisplayString,
		adsStatusAdsEvPatterns DisplayString,
		adsStatusAdsEvMonitor INTEGER,
		adsStatusAdsEvStatus INTEGER,
		adsStatusAdsEvCallBackRef DisplayString,
		adsStatusAdsEvButton INTEGER
	}


adsStatusAdsEvName OBJECT-TYPE
	SYNTAX DisplayString
	ACCESS read-only
	STATUS mandatory
	DESCRIPTION
		"&<caiAdsA2.297>Name of the watcher, monitoring Active Directory Service Event Logs. Important: This name is arbitrary but case insensitive. When prefixed with the keyword '[OTHER]' then the watcher will not be applied on a new Event Log entry, if any other watcher not using this prefix already matches the entry during the same poll cycle."
	::= { adsStatusAdsEvEntry 1 }


adsStatusAdsEvDescription OBJECT-TYPE
	SYNTAX DisplayString
	ACCESS read-write
	STATUS mandatory
	DESCRIPTION
		"&<caiAdsA2.298>Any description for this watcher."
	::= { adsStatusAdsEvEntry 2 }


adsStatusAdsEvLastMatch OBJECT-TYPE
	SYNTAX DisplayString
	ACCESS read-only
	STATUS mandatory
	DESCRIPTION
		"&<caiAdsA2.299>The Event Log entry that matched any of the defined patterns. The entry is formatted as Log/Source/Id/Type/Message."
	::= { adsStatusAdsEvEntry 3 }


adsStatusAdsEvPatterns OBJECT-TYPE
	SYNTAX DisplayString
	ACCESS read-write
	STATUS mandatory
	DESCRIPTION
		"&<caiAdsA2.300>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsStatusAdsEvEntry 4 }


adsStatusAdsEvMonitor OBJECT-TYPE
	SYNTAX INTEGER {
		do-not-monitor(1),
		down-warning(2),
		down-critical(3)
	}
	ACCESS read-write
	STATUS mandatory
	DESCRIPTION
		"&<caiAdsA2.301>Flag indicating whether Active Directory Service Event Logs should be monitored by this watcher and if so, the level of alert to raise."
	DEFVAL { 0 }
	::= { adsStatusAdsEvEntry 5 }


adsStatusAdsEvStatus OBJECT-TYPE
	SYNTAX INTEGER {
		unknown(1),
		up(2),
		down-warning(3),
		down-critical(4)
	}
	ACCESS read-only
	STATUS mandatory
	DESCRIPTION
		"&<caiAdsA2.302>The current status of the watcher. This status must be reset by the Button attribute."
	::= { adsStatusAdsEvEntry 6 }


adsStatusAdsEvCallBackRef OBJECT-TYPE
	SYNTAX DisplayString
	ACCESS read-only
	STATUS mandatory
	DESCRIPTION
		"&<caiAdsA2.303>The name of the Call-Back reference that should be invoked in case of a status change."
	::= { adsStatusAdsEvEntry 7 }


adsStatusAdsEvButton OBJECT-TYPE
	SYNTAX INTEGER {
		none(1),
		remove(2),
		reset(3)
	}
	ACCESS read-write
	STATUS mandatory
	DESCRIPTION
		"&<caiAdsA2.304>This attribute is used to remove this watcher or to reset the watcher's status to 'up'."
	::= { adsStatusAdsEvEntry 8 }




-- *****************************************************************************
-- Active Directory Service Performance Status Group
-- *****************************************************************************


adsStatusAdsPrCount OBJECT-TYPE
	SYNTAX INTEGER
	ACCESS read-only
	STATUS mandatory
	DESCRIPTION
		"&<caiAdsA2.305>The number of entries in the adsStatusAdsPrTable."
	::= { adsStatusAdsPrGroup 1 }


adsStatusAdsPrTable OBJECT-TYPE
	SYNTAX SEQUENCE OF AdsStatusAdsPrRow
	ACCESS not-accessible
	STATUS mandatory
	DESCRIPTION
		"&<caiAdsA2.306>A table containing information about all Active Directory Service Performance watchers."
	::= { adsStatusAdsPrGroup 2 }


adsStatusAdsPrEntry OBJECT-TYPE
	SYNTAX AdsStatusAdsPrRow
	ACCESS not-accessible
	STATUS mandatory
	DESCRIPTION
		"&<caiAdsA2.307>The table entry."
	INDEX { adsStatusAdsPrName }
	::= { adsStatusAdsPrTable 1 }


AdsStatusAdsPrRow ::=
	SEQUENCE {
		adsStatusAdsPrName DisplayString,
		adsStatusAdsPrDescription DisplayString,
		adsStatusAdsPrExpression DisplayString,
		adsStatusAdsPrCounter0 INTEGER,
		adsStatusAdsPrCounter1 INTEGER,
		adsStatusAdsPrCounter2 INTEGER,
		adsStatusAdsPrCounter3 INTEGER,
		adsStatusAdsPrCounter4 INTEGER,
		adsStatusAdsPrCounter5 INTEGER,
		adsStatusAdsPrCounter6 INTEGER,
		adsStatusAdsPrCounter7 INTEGER,
		adsStatusAdsPrCounter8 INTEGER,
		adsStatusAdsPrCounter9 INTEGER,
		adsStatusAdsPrAggLagValue INTEGER,
		adsStatusAdsPrAggLag INTEGER,
		adsStatusAdsPrAggStatus INTEGER,
		adsStatusAdsPrValue DisplayString,
		adsStatusAdsPrWarn DisplayString,
		adsStatusAdsPrCrit DisplayString,
		adsStatusAdsPrWcMonitor INTEGER,
		adsStatusAdsPrWcStatus INTEGER,
		adsStatusAdsPrMin DisplayString,
		adsStatusAdsPrMax DisplayString,
		adsStatusAdsPrMmMonitor INTEGER,
		adsStatusAdsPrMmStatus INTEGER,
		adsStatusAdsPrCallBackRef DisplayString,
		adsStatusAdsPrButton INTEGER
	}


adsStatusAdsPrName OBJECT-TYPE
	SYNTAX DisplayString
	ACCESS read-only
	STATUS mandatory
	DESCRIPTION
		"&<caiAdsA2.308>Name of the Active Directory Service Performance watcher. Important: This name is arbitrary but case insensitive."
	::= { adsStatusAdsPrEntry 1 }


adsStatusAdsPrDescription OBJECT-TYPE
	SYNTAX DisplayString
	ACCESS read-write
	STATUS mandatory
	DESCRIPTION
		"&<caiAdsA2.309>Any description for this watcher."
	::= { adsStatusAdsPrEntry 2 }


adsStatusAdsPrExpression OBJECT-TYPE
	SYNTAX DisplayString
	ACCESS read-write
	STATUS mandatory
	DESCRIPTION
		"&<caiAdsA2.310>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsStatusAdsPrEntry 3 }


adsStatusAdsPrCounter0 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.311>The definition of the counter with reference key C0 or L0. As a general rule, changing the definition of a counter invalidates the values retrieved at the last poll interval. For this reason it will take two polls until a new value is calculated."
	DEFVAL { 0 }
	::= { adsStatusAdsPrEntry 4 }


adsStatusAdsPrCounter1 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.312>The definition of the counter with reference key C1 or L1. As a general rule, changing the definition of a counter invalidates the values retrieved at the last poll interval. For this reason it will take two polls until a new value is calculated."
	DEFVAL { 0 }
	::= { adsStatusAdsPrEntry 5 }


adsStatusAdsPrCounter2 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.313>The definition of the counter with reference key C2 or L2. As a general rule, changing the definition of a counter invalidates the values retrieved at the last poll interval. For this reason it will take two polls until a new value is calculated."
	DEFVAL { 0 }
	::= { adsStatusAdsPrEntry 6 }


adsStatusAdsPrCounter3 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.314>The definition of the counter with reference key C3 or L3. As a general rule, changing the definition of a counter invalidates the values retrieved at the last poll interval. For this reason it will take two polls until a new value is calculated."
	DEFVAL { 0 }
	::= { adsStatusAdsPrEntry 7 }


adsStatusAdsPrCounter4 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.315>The definition of the counter with reference key C4 or L4. As a general rule, changing the definition of a counter invalidates the values retrieved at the last poll interval. For this reason it will take two polls until a new value is calculated."
	DEFVAL { 0 }
	::= { adsStatusAdsPrEntry 8 }


adsStatusAdsPrCounter5 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.316>The definition of the counter with reference key C5 or L5. As a general rule, changing the definition of a counter invalidates the values retrieved at the last poll interval. For this reason it will take two polls until a new value is calculated."
	DEFVAL { 0 }
	::= { adsStatusAdsPrEntry 9 }


adsStatusAdsPrCounter6 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.317>The definition of the counter with reference key C6 or L6. As a general rule, changing the definition of a counter invalidates the values retrieved at the last poll interval. For this reason it will take two polls until a new value is calculated."
	DEFVAL { 0 }
	::= { adsStatusAdsPrEntry 10 }


adsStatusAdsPrCounter7 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.318>The definition of the counter with reference key C7 or L7. As a general rule, changing the definition of a counter invalidates the values retrieved at the last poll interval. For this reason it will take two polls until a new value is calculated."
	DEFVAL { 0 }
	::= { adsStatusAdsPrEntry 11 }


adsStatusAdsPrCounter8 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.319>The definition of the counter with reference key C8 or L8. As a general rule, changing the definition of a counter invalidates the values retrieved at the last poll interval. For this reason it will take two polls until a new value is calculated."
	DEFVAL { 0 }
	::= { adsStatusAdsPrEntry 12 }


adsStatusAdsPrCounter9 OBJECT-TYPE
	SYNTAX INTEGER {
		NONE(1),
		AB_ANR_per_sec(2),
		AB_Browses_per_sec(3),
		AB_Client_Sessions(4),
		AB_Matches_per_sec(5),
		AB_Property_Reads_per_sec(6),
		AB_Proxy_Lookups_per_sec(7),
		AB_Searches_per_sec(8),
		ATQ_Threads_LDAP(9),
		ATQ_Threads_Other(10),
		ATQ_Threads_Total(11),
		DRA_Highest_USN_Committed_-High_part-(12),
		DRA_Highest_USN_Committed_-Low_part-(13),
		DRA_Highest_USN_Issued_-High_part-(14),
		DRA_Highest_USN_Issued_-Low_part-(15),
		DRA_Inbound_Bytes_Compressed_-Between_Sites__After_Compression-_Since_Boot(16),
		DRA_Inbound_Bytes_Compressed_-Between_Sites__After_Compression-_per_sec(17),
		DRA_Inbound_Bytes_Compressed_-Between_Sites__Before_Compression-_Since_Boot(18),
		DRA_Inbound_Bytes_Compressed_-Between_Sites__Before_Compression-_per_sec(19),
		DRA_Inbound_Bytes_Not_Compressed_-Within_Site-_Since_Boot(20),
		DRA_Inbound_Bytes_Not_Compressed_-Within_Site-_per_sec(21),
		DRA_Inbound_Bytes_Total_Since_Boot(22),
		DRA_Inbound_Bytes_Total_per_sec(23),
		DRA_Inbound_Full_Sync_Objects_Remaining(24),
		DRA_Inbound_Object_Updates_Remaining_in_Packet(25),
		DRA_Inbound_Objects_Applied_per_sec(26),
		DRA_Inbound_Objects_Filtered_per_sec(27),
		DRA_Inbound_Objects_per_sec(28),
		DRA_Inbound_Properties_Applied_per_sec(29),
		DRA_Inbound_Properties_Filtered_per_sec(30),
		DRA_Inbound_Properties_Total_per_sec(31),
		DRA_Inbound_Values_-DNs_only-_per_sec(32),
		DRA_Inbound_Values_Total_per_sec(33),
		DRA_Outbound_Bytes_Compressed_-Between_Sites__After_Compression-_Since_Boot(34),
		DRA_Outbound_Bytes_Compressed_-Between_Sites__After_Compression-_per_sec(35),
		DRA_Outbound_Bytes_Compressed_-Between_Sites__Before_Compression-_Since_Boot(36),
		DRA_Outbound_Bytes_Compressed_-Between_Sites__Before_Compression-_per_sec(37),
		DRA_Outbound_Bytes_Not_Compressed_-Within_Site-_Since_Boot(38),
		DRA_Outbound_Bytes_Not_Compressed_-Within_Site-_per_sec(39),
		DRA_Outbound_Bytes_Total_Since_Boot(40),
		DRA_Outbound_Bytes_Total_per_sec(41),
		DRA_Outbound_Objects_Filtered_per_sec(42),
		DRA_Outbound_Objects_per_sec(43),
		DRA_Outbound_Properties_per_sec(44),
		DRA_Outbound_Values_-DNs_only-_per_sec(45),
		DRA_Outbound_Values_Total_per_sec(46),
		DRA_Pending_Replication_Synchronizations(47),
		DRA_Sync_Failures_on_Schema_Mismatch(48),
		DRA_Sync_Requests_Made(49),
		DRA_Sync_Requests_Successful(50),
		DS_percent_Reads_from_DRA(51),
		DS_percent_Reads_from_KCC(52),
		DS_percent_Reads_from_LSA(53),
		DS_percent_Reads_from_NSPI(54),
		DS_percent_Reads_from_SAM(55),
		W2000only--DS_percent_Reads_from_XDS(56),
		DS_percent_Reads_Other(57),
		DS_percent_Searches_from_DRA(58),
		DS_percent_Searches_from_KCC(59),
		DS_percent_Searches_from_LDAP(60),
		DS_percent_Searches_from_LSA(61),
		DS_percent_Searches_from_NSPI(62),
		DS_percent_Searches_from_SAM(63),
		W2000only--DS_percent_Searches_from_XDS(64),
		DS_percent_Searches_Other(65),
		DS_percent_Writes_from_DRA(66),
		DS_percent_Writes_from_KCC(67),
		DS_percent_Writes_from_LDAP(68),
		DS_percent_Writes_from_LSA(69),
		DS_percent_Writes_from_NSPI(70),
		DS_percent_Writes_from_SAM(71),
		W2000only--DS_percent_Writes_from_XDS(72),
		DS_percent_Writes_Other(73),
		DS_Client_Binds_per_sec(74),
		DS_Client_Name_Translations_per_sec(75),
		DS_Directory_Reads_per_sec(76),
		DS_Directory_Searches_per_sec(77),
		DS_Directory_Writes_per_sec(78),
		DS_Monitor_List_Size(79),
		DS_Name_Cache_hit_rate(80),
		DS_Name_Cache_reads(81),
		DS_Notify_Queue_Size(82),
		DS_Search_sub-operations_per_sec(83),
		DS_Security_Descriptor_Propagations_Events(84),
		DS_Security_Descriptor_Propagator_Average_Exclusion_Time(85),
		DS_Security_Descriptor_Propagator_Runtime_Queue(86),
		DS_Security_Descriptor_sub-operations_per_sec(87),
		DS_Server_Binds_per_sec(88),
		DS_Server_Name_Translations_per_sec(89),
		DS_Threads_in_Use(90),
		KDC_AS_Requests(91),
		KDC_TGS_Requests(92),
		Kerberos_Authentications(93),
		LDAP_Active_Threads(94),
		W2000only--LDAP_Bind_Attempts(95),
		LDAP_Bind_Time(96),
		LDAP_Client_Sessions(97),
		LDAP_Searches_per_sec(98),
		W2000only--LDAP_Successful_Binds(99),
		W2000only--LDAP_Successful_Binds_per_sec(100),
		LDAP_UDP_operations_per_sec(101),
		LDAP_Writes_per_sec(102),
		NTLM_Authentications(103),
		W2000only--SAM_Account_Group_Membership_Evaluations_per_sec(104),
		SAM_Display_Information_Queries_per_sec(105),
		SAM_Enumerations_per_sec(106),
		SAM_GC_Evaluations_per_sec(107),
		SAM_Machine_Creation_Attempts_per_sec(108),
		SAM_Membership_Changes_per_sec(109),
		SAM_Non-Transitive_Membership_Evaluations_per_sec(110),
		SAM_Password_Changes_per_sec(111),
		W2000only--SAM_Resource_Group_Membership_Evaluations_per_sec(112),
		W2000only--SAM_Successful_Machine_Creations_per_sec(113),
		SAM_Successful_User_Creations_per_sec(114),
		SAM_Transitive_Membership_Evaluations_per_sec(115),
		SAM_Universal_Group_Membership_Evaluations_per_sec(116),
		SAM_User_Creation_Attempts_per_sec(117),
		W2000only--XDS_Client_Sessions(118),
		W2003only--DRA_Inbound_Link_Value_Updates_Remaining_in_Packet(119),
		W2003only--DRA_Inbound_Total_Updates_Remaining_in_Packet(120),
		W2003only--DRA_Pending_Replication_Operations(121),
		W2003only--DRA_Threads_Getting_NC_Changes(122),
		W2003only--DRA_Threads_Getting_NC_Changes_Holding_Semaphore(123),
		W2003only--DS_percent_Reads_from_NTDSAPI(124),
		W2003only--DS_percent_Searches_from_NTDSAPI(125),
		W2003only--DS_percent_Writes_from_NTDSAPI(126),
		W2003only--LDAP_Closed_Connections_per_sec(127),
		W2003only--LDAP_New_Connections_per_sec(128),
		W2003only--LDAP_New_SSL_Connections_per_sec(129),
		W2003only--SAM_Account_Group_Evaluation_Latency(130),
		W2003only--SAM_Domain_Local_Group_Membership_Evaluations_per_sec(131),
		W2003only--SAM_Global_Group_Membership_Evaluations_per_sec(132),
		W2003only--SAM_Resource_Group_Evaluation_Latency(133),
		W2003only--SAM_Successful_Computer_Creations_per_sec-_Includes_all_requests(134)
	}
	ACCESS read-write
	STATUS mandatory
	DESCRIPTION
		"&<caiAdsA2.320>The definition of the counter with reference key C9 or L9. As a general rule, changing the definition of a counter invalidates the values retrieved at the last poll interval. For this reason it will take two polls until a new value is calculated."
	DEFVAL { 0 }
	::= { adsStatusAdsPrEntry 13 }


adsStatusAdsPrAggLagValue OBJECT-TYPE
	SYNTAX INTEGER
	ACCESS read-only
	STATUS mandatory
	DESCRIPTION
		"&<caiAdsA2.321>The number of consecutive poll intervals on which any status was not in the Ok or Up state."
	::= { adsStatusAdsPrEntry 14 }


adsStatusAdsPrAggLag OBJECT-TYPE
	SYNTAX INTEGER
	ACCESS read-write
	STATUS mandatory
	DESCRIPTION
		"&<caiAdsA2.322>The number of consecutive poll intervals on which any status is not in the Ok or Up state, before the aggregate status changes. Valid values are greater than 0."
	::= { adsStatusAdsPrEntry 15 }


adsStatusAdsPrAggStatus OBJECT-TYPE
	SYNTAX INTEGER {
		unknown(1),
		ok(2),
		warning(3),
		critical(4)
	}
	ACCESS read-only
	STATUS mandatory
	DESCRIPTION
		"&<caiAdsA2.323>The current status of this watcher as a 'worst case' aggregate of all its statuses."
	::= { adsStatusAdsPrEntry 16 }


adsStatusAdsPrValue OBJECT-TYPE
	SYNTAX DisplayString
	ACCESS read-only
	STATUS mandatory
	DESCRIPTION
		"&<caiAdsA2.324>The current value calculated according to the expression. The calculation is done with floating point arithmetic. As a general rule, changing the definition of any counter invalidates the values retrieved at the last poll interval. For this reason it will take two polls until a new value is calculated."
	::= { adsStatusAdsPrEntry 17 }


adsStatusAdsPrWarn OBJECT-TYPE
	SYNTAX DisplayString
	ACCESS read-write
	STATUS mandatory
	DESCRIPTION
		"&<caiAdsA2.325>Warning threshold for the calculated value of the expression. Valid values are greater than 0.0 and smaller than or equal to the critical threshold."
	::= { adsStatusAdsPrEntry 18 }


adsStatusAdsPrCrit OBJECT-TYPE
	SYNTAX DisplayString
	ACCESS read-write
	STATUS mandatory
	DESCRIPTION
		"&<caiAdsA2.326>Critical threshold for the calculated value of the expression. Valid values are greater than 0.0 and greater than or equal to the warning threshold."
	::= { adsStatusAdsPrEntry 19 }


adsStatusAdsPrWcMonitor OBJECT-TYPE
	SYNTAX INTEGER {
		do-not-monitor(1),
		warning-only(2),
		critical-only(3),
		both(4)
	}
	ACCESS read-write
	STATUS mandatory
	DESCRIPTION
		"&<caiAdsA2.327>Flag indicating whether the programmed expression should be monitored against warning/critical thresholds and if so, which threshold should be compared with."
	DEFVAL { 0 }
	::= { adsStatusAdsPrEntry 20 }


adsStatusAdsPrWcStatus OBJECT-TYPE
	SYNTAX INTEGER {
		unknown(1),
		ok(2),
		warning(3),
		critical(4)
	}
	ACCESS read-only
	STATUS mandatory
	DESCRIPTION
		"&<caiAdsA2.328>The current status of the programmed expression as determined by the warning/critical thresholds. The status 'unknown' means that the current value could not be retrieved from the system."
	::= { adsStatusAdsPrEntry 21 }


adsStatusAdsPrMin OBJECT-TYPE
	SYNTAX DisplayString
	ACCESS read-write
	STATUS mandatory
	DESCRIPTION
		"&<caiAdsA2.329>Minimum threshold for the calculated value of the expression. Valid values are greater than 0.0 or equal to -1.0 and smaller than or equal to the maximum threshold. Setting to -1.0 disables the monitoring of the minimum."
	DEFVAL { "-2.0" }
	::= { adsStatusAdsPrEntry 22 }


adsStatusAdsPrMax OBJECT-TYPE
	SYNTAX DisplayString
	ACCESS read-write
	STATUS mandatory
	DESCRIPTION
		"&<caiAdsA2.330>Maximum threshold for the calculated value of the expression. Valid values are greater than 0.0 or equal to -1.0 and greater than or equal to the minimum threshold. Setting to -1.0 disables the monitoring of the maximum."
	DEFVAL { "-2.0" }
	::= { adsStatusAdsPrEntry 23 }


adsStatusAdsPrMmMonitor OBJECT-TYPE
	SYNTAX INTEGER {
		do-not-monitor(1),
		down-warning(2),
		down-critical(3)
	}
	ACCESS read-write
	STATUS mandatory
	DESCRIPTION
		"&<caiAdsA2.331>Flag indicating whether the programmed expression should be monitored against minimum/maximum thresholds and if so, the level of alert to raise."
	DEFVAL { 0 }
	::= { adsStatusAdsPrEntry 24 }


adsStatusAdsPrMmStatus OBJECT-TYPE
	SYNTAX INTEGER {
		unknown(1),
		ok(2),
		warning(3),
		critical(4)
	}
	ACCESS read-only
	STATUS mandatory
	DESCRIPTION
		"&<caiAdsA2.332>The current status of the programmed expression as determined by the minimum/maximum thresholds. The status 'unknown' means that the current value could not be retrieved from the system."
	::= { adsStatusAdsPrEntry 25 }


adsStatusAdsPrCallBackRef OBJECT-TYPE
	SYNTAX DisplayString
	ACCESS read-only
	STATUS mandatory
	DESCRIPTION
		"&<caiAdsA2.333>The name of the Call-Back reference that should be invoked in case of a status change."
	::= { adsStatusAdsPrEntry 26 }


adsStatusAdsPrButton OBJECT-TYPE
	SYNTAX INTEGER {
		none(1),
		remove(2),
		reset-store(3)
	}
	ACCESS read-write
	STATUS mandatory
	DESCRIPTION
		"&<caiAdsA2.334>This attribute is used to remove this watcher or to reset (empty) the store that holds the last N values which are used to calculate the MIN, MAX, AVG or SUM result of the expression. N is defined in the expression too."
	::= { adsStatusAdsPrEntry 27 }




-- *****************************************************************************
-- File Replication Service Events Status Group
-- *****************************************************************************


adsStatusFrsEvCount OBJECT-TYPE
	SYNTAX INTEGER
	ACCESS read-only
	STATUS mandatory
	DESCRIPTION
		"&<caiAdsA2.335>The number of entries in the adsStatusFrsEvTable."
	::= { adsStatusFrsEvGroup 1 }


adsStatusFrsEvTable OBJECT-TYPE
	SYNTAX SEQUENCE OF FrsStatusFrsEvRow
	ACCESS not-accessible
	STATUS mandatory
	DESCRIPTION
		"&<caiAdsA2.336>A table containing information about all File Replication Service Event Logs watchers."
	::= { adsStatusFrsEvGroup 2 }


adsStatusFrsEvEntry OBJECT-TYPE
	SYNTAX FrsStatusFrsEvRow
	ACCESS not-accessible
	STATUS mandatory
	DESCRIPTION
		"&<caiAdsA2.337>The table entry."
	INDEX { adsStatusFrsEvName }
	::= { adsStatusFrsEvTable 1 }


FrsStatusFrsEvRow ::=
	SEQUENCE {
		adsStatusFrsEvName DisplayString,
		adsStatusFrsEvDescription DisplayString,
		adsStatusFrsEvLastMatch DisplayString,
		adsStatusFrsEvPatterns DisplayString,
		adsStatusFrsEvMonitor INTEGER,
		adsStatusFrsEvStatus INTEGER,
		adsStatusFrsEvCallBackRef DisplayString,
		adsStatusFrsEvButton INTEGER
	}


adsStatusFrsEvName OBJECT-TYPE
	SYNTAX DisplayString
	ACCESS read-only
	STATUS mandatory
	DESCRIPTION
		"&<caiAdsA2.338>Name of the watcher, monitoring File Replication Service Event Logs. Important: This name is arbitrary but case insensitive. When prefixed with the keyword '[OTHER]' then the watcher will not be applied on a new Event Log entry, if any other watcher not using this prefix already matches the entry during the same poll cycle."
	::= { adsStatusFrsEvEntry 1 }


adsStatusFrsEvDescription OBJECT-TYPE
	SYNTAX DisplayString
	ACCESS read-write
	STATUS mandatory
	DESCRIPTION
		"&<caiAdsA2.339>Any description for this watcher."
	::= { adsStatusFrsEvEntry 2 }


adsStatusFrsEvLastMatch OBJECT-TYPE
	SYNTAX DisplayString
	ACCESS read-only
	STATUS mandatory
	DESCRIPTION
		"&<caiAdsA2.340>The Event Log entry that matched any of the defined patterns. The entry is formatted as Log/Source/Id/Type/Message."
	::= { adsStatusFrsEvEntry 3 }


adsStatusFrsEvPatterns OBJECT-TYPE
	SYNTAX DisplayString
	ACCESS read-write
	STATUS mandatory
	DESCRIPTION
		"&<caiAdsA2.341>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsStatusFrsEvEntry 4 }


adsStatusFrsEvMonitor OBJECT-TYPE
	SYNTAX INTEGER {
		do-not-monitor(1),
		down-warning(2),
		down-critical(3)
	}
	ACCESS read-write
	STATUS mandatory
	DESCRIPTION
		"&<caiAdsA2.342>Flag indicating whether File Replication Service Event Logs should be monitored by this watcher and if so, the level of alert to raise."
	DEFVAL { 0 }
	::= { adsStatusFrsEvEntry 5 }


adsStatusFrsEvStatus OBJECT-TYPE
	SYNTAX INTEGER {
		unknown(1),
		up(2),
		down-warning(3),
		down-critical(4)
	}
	ACCESS read-only
	STATUS mandatory
	DESCRIPTION
		"&<caiAdsA2.343>The current status of the watcher. This status must be reset by the Button attribute."
	::= { adsStatusFrsEvEntry 6 }


adsStatusFrsEvCallBackRef OBJECT-TYPE
	SYNTAX DisplayString
	ACCESS read-only
	STATUS mandatory
	DESCRIPTION
		"&<caiAdsA2.344>The name of the Call-Back reference that should be invoked in case of a status change."
	::= { adsStatusFrsEvEntry 7 }


adsStatusFrsEvButton OBJECT-TYPE
	SYNTAX INTEGER {
		none(1),
		remove(2),
		reset(3)
	}
	ACCESS read-write
	STATUS mandatory
	DESCRIPTION
		"&<caiAdsA2.345>This attribute is used to remove this watcher or to reset the watcher's status to 'up'."
	::= { adsStatusFrsEvEntry 8 }




-- *****************************************************************************
-- File Replication Service Performance Status Group
-- *****************************************************************************


adsStatusFrsPrCount OBJECT-TYPE
	SYNTAX INTEGER
	ACCESS read-only
	STATUS mandatory
	DESCRIPTION
		"&<caiAdsA2.346>The number of entries in the adsStatusFrsPrTable."
	::= { adsStatusFrsPrGroup 1 }


adsStatusFrsPrTable OBJECT-TYPE
	SYNTAX SEQUENCE OF FrsStatusFrsPrRow
	ACCESS not-accessible
	STATUS mandatory
	DESCRIPTION
		"&<caiAdsA2.347>A table containing information about all File Replication Service Performance watchers."
	::= { adsStatusFrsPrGroup 2 }


adsStatusFrsPrEntry OBJECT-TYPE
	SYNTAX FrsStatusFrsPrRow
	ACCESS not-accessible
	STATUS mandatory
	DESCRIPTION
		"&<caiAdsA2.348>The table entry."
	INDEX { adsStatusFrsPrName }
	::= { adsStatusFrsPrTable 1 }


FrsStatusFrsPrRow ::=
	SEQUENCE {
		adsStatusFrsPrName DisplayString,
		adsStatusFrsPrDescription DisplayString,
		adsStatusFrsPrExpression DisplayString,
		adsStatusFrsPrCounter0 INTEGER,
		adsStatusFrsPrCounter1 INTEGER,
		adsStatusFrsPrCounter2 INTEGER,
		adsStatusFrsPrCounter3 INTEGER,
		adsStatusFrsPrCounter4 INTEGER,
		adsStatusFrsPrCounter5 INTEGER,
		adsStatusFrsPrCounter6 INTEGER,
		adsStatusFrsPrCounter7 INTEGER,
		adsStatusFrsPrCounter8 INTEGER,
		adsStatusFrsPrCounter9 INTEGER,
		adsStatusFrsPrAggLagValue INTEGER,
		adsStatusFrsPrAggLag INTEGER,
		adsStatusFrsPrAggStatus INTEGER,
		adsStatusFrsPrValue DisplayString,
		adsStatusFrsPrWarn DisplayString,
		adsStatusFrsPrCrit DisplayString,
		adsStatusFrsPrWcMonitor INTEGER,
		adsStatusFrsPrWcStatus INTEGER,
		adsStatusFrsPrMin DisplayString,
		adsStatusFrsPrMax DisplayString,
		adsStatusFrsPrMmMonitor INTEGER,
		adsStatusFrsPrMmStatus INTEGER,
		adsStatusFrsPrCallBackRef DisplayString,
		adsStatusFrsPrButton INTEGER
	}


adsStatusFrsPrName OBJECT-TYPE
	SYNTAX DisplayString
	ACCESS read-only
	STATUS mandatory
	DESCRIPTION
		"&<caiAdsA2.349>Name of the File Replication Service Performance watcher. Important: This name is arbitrary but case insensitive."
	::= { adsStatusFrsPrEntry 1 }


adsStatusFrsPrDescription OBJECT-TYPE
	SYNTAX DisplayString
	ACCESS read-write
	STATUS mandatory
	DESCRIPTION
		"&<caiAdsA2.350>Any description for this watcher."
	::= { adsStatusFrsPrEntry 2 }


adsStatusFrsPrExpression OBJECT-TYPE
	SYNTAX DisplayString
	ACCESS read-write
	STATUS mandatory
	DESCRIPTION
		"&<caiAdsA2.351>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsStatusFrsPrEntry 3 }


adsStatusFrsPrCounter0 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.352>The definition of the counter with reference key C0 or L0. As a general rule, changing the definition of a counter invalidates the values retrieved at the last poll interval. For this reason it will take two polls until a new value is calculated."
	DEFVAL { 0 }
	::= { adsStatusFrsPrEntry 4 }


adsStatusFrsPrCounter1 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.353>The definition of the counter with reference key C1 or L1. As a general rule, changing the definition of a counter invalidates the values retrieved at the last poll interval. For this reason it will take two polls until a new value is calculated."
	DEFVAL { 0 }
	::= { adsStatusFrsPrEntry 5 }


adsStatusFrsPrCounter2 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.354>The definition of the counter with reference key C2 or L2. As a general rule, changing the definition of a counter invalidates the values retrieved at the last poll interval. For this reason it will take two polls until a new value is calculated."
	DEFVAL { 0 }
	::= { adsStatusFrsPrEntry 6 }


adsStatusFrsPrCounter3 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.355>The definition of the counter with reference key C3 or L3. As a general rule, changing the definition of a counter invalidates the values retrieved at the last poll interval. For this reason it will take two polls until a new value is calculated."
	DEFVAL { 0 }
	::= { adsStatusFrsPrEntry 7 }


adsStatusFrsPrCounter4 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.356>The definition of the counter with reference key C4 or L4. As a general rule, changing the definition of a counter invalidates the values retrieved at the last poll interval. For this reason it will take two polls until a new value is calculated."
	DEFVAL { 0 }
	::= { adsStatusFrsPrEntry 8 }


adsStatusFrsPrCounter5 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.357>The definition of the counter with reference key C5 or L5. As a general rule, changing the definition of a counter invalidates the values retrieved at the last poll interval. For this reason it will take two polls until a new value is calculated."
	DEFVAL { 0 }
	::= { adsStatusFrsPrEntry 9 }


adsStatusFrsPrCounter6 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.358>The definition of the counter with reference key C6 or L6. As a general rule, changing the definition of a counter invalidates the values retrieved at the last poll interval. For this reason it will take two polls until a new value is calculated."
	DEFVAL { 0 }
	::= { adsStatusFrsPrEntry 10 }


adsStatusFrsPrCounter7 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.359>The definition of the counter with reference key C7 or L7. As a general rule, changing the definition of a counter invalidates the values retrieved at the last poll interval. For this reason it will take two polls until a new value is calculated."
	DEFVAL { 0 }
	::= { adsStatusFrsPrEntry 11 }


adsStatusFrsPrCounter8 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.360>The definition of the counter with reference key C8 or L8. As a general rule, changing the definition of a counter invalidates the values retrieved at the last poll interval. For this reason it will take two polls until a new value is calculated."
	DEFVAL { 0 }
	::= { adsStatusFrsPrEntry 12 }


adsStatusFrsPrCounter9 OBJECT-TYPE
	SYNTAX INTEGER {
		NONE(1),
		Authentications(2),
		Authentications_in_Error(3),
		Bindings(4),
		Bindings_in_Error(5),
		Bytes_of_Files_Installed(6),
		Bytes_of_Staging_Fetched(7),
		Bytes_of_Staging_Generated(8),
		Bytes_of_Staging_Regenerated(9),
		Change_Orders_Aborted(10),
		Change_Orders_Evaporated(11),
		Change_Orders_Issued(12),
		Change_Orders_Morphed(13),
		Change_Orders_Propagated(14),
		Change_Orders_Received(15),
		Change_Orders_Retired(16),
		Change_Orders_Retried(17),
		Change_Orders_Retried_at_Fetch(18),
		Change_Orders_Retried_at_Generate(19),
		Change_Orders_Retried_at_Install(20),
		Change_Orders_Retried_at_Rename(21),
		Change_Orders_Sent(22),
		Communication_Timeouts(23),
		DS_Bindings(24),
		DS_Bindings_in_Error(25),
		DS_Objects(26),
		DS_Objects_in_Error(27),
		DS_Polls(28),
		DS_Polls_with_Changes(29),
		DS_Polls_without_Changes(30),
		DS_Searches(31),
		DS_Searches_in_Error(32),
		Fetch_Blocks_Received(33),
		Fetch_Blocks_Received_in_Bytes(34),
		Fetch_Blocks_Sent(35),
		Fetch_Blocks_Sent_in_Bytes(36),
		Fetch_Requests_Received(37),
		Fetch_Requests_Sent(38),
		Files_Installed(39),
		Files_Installed_with_Error(40),
		Inbound_Change_Orders_Dampened(41),
		Join_Notifications_Received(42),
		Join_Notifications_Sent(43),
		Joins(44),
		KB_of_Staging_Space_Free(45),
		KB_of_Staging_Space_In_Use(46),
		Local_Change_Orders_Aborted(47),
		Local_Change_Orders_Issued(48),
		Local_Change_Orders_Morphed(49),
		Local_Change_Orders_Propagated(50),
		Local_Change_Orders_Retired(51),
		Local_Change_Orders_Retried(52),
		Local_Change_Orders_Retried_at_Fetch(53),
		Local_Change_Orders_Retried_at_Generate(54),
		Local_Change_Orders_Retried_at_Install(55),
		Local_Change_Orders_Retried_at_Rename(56),
		Local_Change_Orders_Sent(57),
		Local_Change_Orders_Sent_At_Join(58),
		Outbound_Change_Orders_Dampened(59),
		Packets_Received(60),
		Packets_Received_in_Bytes(61),
		Packets_Received_in_Error(62),
		Packets_Sent(63),
		Packets_Sent_in_Bytes(64),
		Packets_Sent_in_Error(65),
		Remote_Change_Orders_Aborted(66),
		Remote_Change_Orders_Issued(67),
		Remote_Change_Orders_Morphed(68),
		Remote_Change_Orders_Propagated(69),
		Remote_Change_Orders_Received(70),
		Remote_Change_Orders_Retired(71),
		Remote_Change_Orders_Retried(72),
		Remote_Change_Orders_Retried_at_Fetch(73),
		Remote_Change_Orders_Retried_at_Generate(74),
		Remote_Change_Orders_Retried_at_Install(75),
		Remote_Change_Orders_Retried_at_Rename(76),
		Remote_Change_Orders_Sent(77),
		Replica_Sets_Created(78),
		Replica_Sets_Deleted(79),
		Replica_Sets_Removed(80),
		Replica_Sets_Started(81),
		Staging_Files_Fetched(82),
		Staging_Files_Generated(83),
		Staging_Files_Generated_with_Error(84),
		Staging_Files_Regenerated(85),
		Threads_exited(86),
		Threads_started(87),
		Unjoins(88),
		Usn_Reads(89),
		Usn_Records_Accepted(90),
		Usn_Records_Examined(91),
		Usn_Records_Rejected(92)
	}
	ACCESS read-write
	STATUS mandatory
	DESCRIPTION
		"&<caiAdsA2.361>The definition of the counter with reference key C9 or L9. As a general rule, changing the definition of a counter invalidates the values retrieved at the last poll interval. For this reason it will take two polls until a new value is calculated."
	DEFVAL { 0 }
	::= { adsStatusFrsPrEntry 13 }


adsStatusFrsPrAggLagValue OBJECT-TYPE
	SYNTAX INTEGER
	ACCESS read-only
	STATUS mandatory
	DESCRIPTION
		"&<caiAdsA2.362>The number of consecutive poll intervals on which any status was not in the Ok or Up state."
	::= { adsStatusFrsPrEntry 14 }


adsStatusFrsPrAggLag OBJECT-TYPE
	SYNTAX INTEGER
	ACCESS read-write
	STATUS mandatory
	DESCRIPTION
		"&<caiAdsA2.363>The number of consecutive poll intervals on which any status is not in the Ok or Up state, before the aggregate status changes. Valid values are greater than 0."
	::= { adsStatusFrsPrEntry 15 }


adsStatusFrsPrAggStatus OBJECT-TYPE
	SYNTAX INTEGER {
		unknown(1),
		ok(2),
		warning(3),
		critical(4)
	}
	ACCESS read-only
	STATUS mandatory
	DESCRIPTION
		"&<caiAdsA2.364>The current status of this watcher as a 'worst case' aggregate of all its statuses."
	::= { adsStatusFrsPrEntry 16 }


adsStatusFrsPrValue OBJECT-TYPE
	SYNTAX DisplayString
	ACCESS read-only
	STATUS mandatory
	DESCRIPTION
		"&<caiAdsA2.365>The current value calculated according to the expression. The calculation is done with floating point arithmetic. As a general rule, changing the definition of any counter invalidates the values retrieved at the last poll interval. For this reason it will take two polls until a new value is calculated."
	::= { adsStatusFrsPrEntry 17 }


adsStatusFrsPrWarn OBJECT-TYPE
	SYNTAX DisplayString
	ACCESS read-write
	STATUS mandatory
	DESCRIPTION
		"&<caiAdsA2.366>Warning threshold for the calculated value of the expression. Valid values are greater than 0.0 and smaller than or equal to the critical threshold."
	::= { adsStatusFrsPrEntry 18 }


adsStatusFrsPrCrit OBJECT-TYPE
	SYNTAX DisplayString
	ACCESS read-write
	STATUS mandatory
	DESCRIPTION
		"&<caiAdsA2.367>Critical threshold for the calculated value of the expression. Valid values are greater than 0.0 and greater than or equal to the warning threshold."
	::= { adsStatusFrsPrEntry 19 }


adsStatusFrsPrWcMonitor OBJECT-TYPE
	SYNTAX INTEGER {
		do-not-monitor(1),
		warning-only(2),
		critical-only(3),
		both(4)
	}
	ACCESS read-write
	STATUS mandatory
	DESCRIPTION
		"&<caiAdsA2.368>Flag indicating whether the programmed expression should be monitored against warning/critical thresholds and if so, which threshold should be compared with."
	DEFVAL { 0 }
	::= { adsStatusFrsPrEntry 20 }


adsStatusFrsPrWcStatus OBJECT-TYPE
	SYNTAX INTEGER {
		unknown(1),
		ok(2),
		warning(3),
		critical(4)
	}
	ACCESS read-only
	STATUS mandatory
	DESCRIPTION
		"&<caiAdsA2.369>The current status of the programmed expression as determined by the warning/critical thresholds. The status 'unknown' means that the current value could not be retrieved from the system."
	::= { adsStatusFrsPrEntry 21 }


adsStatusFrsPrMin OBJECT-TYPE
	SYNTAX DisplayString
	ACCESS read-write
	STATUS mandatory
	DESCRIPTION
		"&<caiAdsA2.370>Minimum threshold for the calculated value of the expression. Valid values are greater than 0.0 or equal to -1.0 and smaller than or equal to the maximum threshold. Setting to -1.0 disables the monitoring of the minimum."
	DEFVAL { "-2.0" }
	::= { adsStatusFrsPrEntry 22 }


adsStatusFrsPrMax OBJECT-TYPE
	SYNTAX DisplayString
	ACCESS read-write
	STATUS mandatory
	DESCRIPTION
		"&<caiAdsA2.371>Maximum threshold for the calculated value of the expression. Valid values are greater than 0.0 or equal to -1.0 and greater than or equal to the minimum threshold. Setting to -1.0 disables the monitoring of the maximum."
	DEFVAL { "-2.0" }
	::= { adsStatusFrsPrEntry 23 }


adsStatusFrsPrMmMonitor OBJECT-TYPE
	SYNTAX INTEGER {
		do-not-monitor(1),
		down-warning(2),
		down-critical(3)
	}
	ACCESS read-write
	STATUS mandatory
	DESCRIPTION
		"&<caiAdsA2.372>Flag indicating whether the programmed expression should be monitored against minimum/maximum thresholds and if so, the level of alert to raise."
	DEFVAL { 0 }
	::= { adsStatusFrsPrEntry 24 }


adsStatusFrsPrMmStatus OBJECT-TYPE
	SYNTAX INTEGER {
		unknown(1),
		ok(2),
		warning(3),
		critical(4)
	}
	ACCESS read-only
	STATUS mandatory
	DESCRIPTION
		"&<caiAdsA2.373>The current status of the programmed expression as determined by the minimum/maximum thresholds. The status 'unknown' means that the current value could not be retrieved from the system."
	::= { adsStatusFrsPrEntry 25 }


adsStatusFrsPrCallBackRef OBJECT-TYPE
	SYNTAX DisplayString
	ACCESS read-only
	STATUS mandatory
	DESCRIPTION
		"&<caiAdsA2.374>The name of the Call-Back reference that should be invoked in case of a status change."
	::= { adsStatusFrsPrEntry 26 }


adsStatusFrsPrButton OBJECT-TYPE
	SYNTAX INTEGER {
		none(1),
		remove(2),
		reset-store(3)
	}
	ACCESS read-write
	STATUS mandatory
	DESCRIPTION
		"&<caiAdsA2.375>This attribute is used to remove this watcher or to reset (empty) the store that holds the last N values which are used to calculate the MIN, MAX, AVG or SUM result of the expression. N is defined in the expression too."
	::= { adsStatusFrsPrEntry 27 }




-- *****************************************************************************
-- Domain Name Service Events Status Group
-- *****************************************************************************


adsStatusDnsEvCount OBJECT-TYPE
	SYNTAX INTEGER
	ACCESS read-only
	STATUS mandatory
	DESCRIPTION
		"&<caiAdsA2.376>The number of entries in the adsStatusDnsEvTable."
	::= { adsStatusDnsEvGroup 1 }


adsStatusDnsEvTable OBJECT-TYPE
	SYNTAX SEQUENCE OF DnsStatusDnsEvRow
	ACCESS not-accessible
	STATUS mandatory
	DESCRIPTION
		"&<caiAdsA2.377>A table containing information about all Domain Name Service Event Logs watchers."
	::= { adsStatusDnsEvGroup 2 }


adsStatusDnsEvEntry OBJECT-TYPE
	SYNTAX DnsStatusDnsEvRow
	ACCESS not-accessible
	STATUS mandatory
	DESCRIPTION
		"&<caiAdsA2.378>The table entry."
	INDEX { adsStatusDnsEvName }
	::= { adsStatusDnsEvTable 1 }


DnsStatusDnsEvRow ::=
	SEQUENCE {
		adsStatusDnsEvName DisplayString,
		adsStatusDnsEvDescription DisplayString,
		adsStatusDnsEvLastMatch DisplayString,
		adsStatusDnsEvPatterns DisplayString,
		adsStatusDnsEvMonitor INTEGER,
		adsStatusDnsEvStatus INTEGER,
		adsStatusDnsEvCallBackRef DisplayString,
		adsStatusDnsEvButton INTEGER
	}


adsStatusDnsEvName OBJECT-TYPE
	SYNTAX DisplayString
	ACCESS read-only
	STATUS mandatory
	DESCRIPTION
		"&<caiAdsA2.379>Name of the watcher, monitoring Domain Name Service Event Logs. Important: This name is arbitrary but case insensitive. When prefixed with the keyword '[OTHER]' then the watcher will not be applied on a new Event Log entry, if any other watcher not using this prefix already matches the entry during the same poll cycle."
	::= { adsStatusDnsEvEntry 1 }


adsStatusDnsEvDescription OBJECT-TYPE
	SYNTAX DisplayString
	ACCESS read-write
	STATUS mandatory
	DESCRIPTION
		"&<caiAdsA2.380>Any description for this watcher."
	::= { adsStatusDnsEvEntry 2 }


adsStatusDnsEvLastMatch OBJECT-TYPE
	SYNTAX DisplayString
	ACCESS read-only
	STATUS mandatory
	DESCRIPTION
		"&<caiAdsA2.381>The Event Log entry that matched any of the defined patterns. The entry is formatted as Log/Source/Id/Type/Message."
	::= { adsStatusDnsEvEntry 3 }


adsStatusDnsEvPatterns OBJECT-TYPE
	SYNTAX DisplayString
	ACCESS read-write
	STATUS mandatory
	DESCRIPTION
		"&<caiAdsA2.382>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsStatusDnsEvEntry 4 }


adsStatusDnsEvMonitor OBJECT-TYPE
	SYNTAX INTEGER {
		do-not-monitor(1),
		down-warning(2),
		down-critical(3)
	}
	ACCESS read-write
	STATUS mandatory
	DESCRIPTION
		"&<caiAdsA2.383>Flag indicating whether Domain Name Service Event Logs should be monitored by this watcher and if so, the level of alert to raise."
	DEFVAL { 0 }
	::= { adsStatusDnsEvEntry 5 }


adsStatusDnsEvStatus OBJECT-TYPE
	SYNTAX INTEGER {
		unknown(1),
		up(2),
		down-warning(3),
		down-critical(4)
	}
	ACCESS read-only
	STATUS mandatory
	DESCRIPTION
		"&<caiAdsA2.384>The current status of the watcher. This status must be reset by the Button attribute."
	::= { adsStatusDnsEvEntry 6 }


adsStatusDnsEvCallBackRef OBJECT-TYPE
	SYNTAX DisplayString
	ACCESS read-only
	STATUS mandatory
	DESCRIPTION
		"&<caiAdsA2.385>The name of the Call-Back reference that should be invoked in case of a status change."
	::= { adsStatusDnsEvEntry 7 }


adsStatusDnsEvButton OBJECT-TYPE
	SYNTAX INTEGER {
		none(1),
		remove(2),
		reset(3)
	}
	ACCESS read-write
	STATUS mandatory
	DESCRIPTION
		"&<caiAdsA2.386>This attribute is used to remove this watcher or to reset the watcher's status to 'up'."
	::= { adsStatusDnsEvEntry 8 }




-- *****************************************************************************
-- Domain Name Service Performance Status Group
-- *****************************************************************************


adsStatusDnsPrCount OBJECT-TYPE
	SYNTAX INTEGER
	ACCESS read-only
	STATUS mandatory
	DESCRIPTION
		"&<caiAdsA2.387>The number of entries in the adsStatusDnsPrTable."
	::= { adsStatusDnsPrGroup 1 }


adsStatusDnsPrTable OBJECT-TYPE
	SYNTAX SEQUENCE OF DnsStatusDnsPrRow
	ACCESS not-accessible
	STATUS mandatory
	DESCRIPTION
		"&<caiAdsA2.388>A table containing information about all Domain Name Service Performance watchers."
	::= { adsStatusDnsPrGroup 2 }


adsStatusDnsPrEntry OBJECT-TYPE
	SYNTAX DnsStatusDnsPrRow
	ACCESS not-accessible
	STATUS mandatory
	DESCRIPTION
		"&<caiAdsA2.389>The table entry."
	INDEX { adsStatusDnsPrName }
	::= { adsStatusDnsPrTable 1 }


DnsStatusDnsPrRow ::=
	SEQUENCE {
		adsStatusDnsPrName DisplayString,
		adsStatusDnsPrDescription DisplayString,
		adsStatusDnsPrExpression DisplayString,
		adsStatusDnsPrCounter0 INTEGER,
		adsStatusDnsPrCounter1 INTEGER,
		adsStatusDnsPrCounter2 INTEGER,
		adsStatusDnsPrCounter3 INTEGER,
		adsStatusDnsPrCounter4 INTEGER,
		adsStatusDnsPrCounter5 INTEGER,
		adsStatusDnsPrCounter6 INTEGER,
		adsStatusDnsPrCounter7 INTEGER,
		adsStatusDnsPrCounter8 INTEGER,
		adsStatusDnsPrCounter9 INTEGER,
		adsStatusDnsPrAggLagValue INTEGER,
		adsStatusDnsPrAggLag INTEGER,
		adsStatusDnsPrAggStatus INTEGER,
		adsStatusDnsPrValue DisplayString,
		adsStatusDnsPrWarn DisplayString,
		adsStatusDnsPrCrit DisplayString,
		adsStatusDnsPrWcMonitor INTEGER,
		adsStatusDnsPrWcStatus INTEGER,
		adsStatusDnsPrMin DisplayString,
		adsStatusDnsPrMax DisplayString,
		adsStatusDnsPrMmMonitor INTEGER,
		adsStatusDnsPrMmStatus INTEGER,
		adsStatusDnsPrCallBackRef DisplayString,
		adsStatusDnsPrButton INTEGER
	}


adsStatusDnsPrName OBJECT-TYPE
	SYNTAX DisplayString
	ACCESS read-only
	STATUS mandatory
	DESCRIPTION
		"&<caiAdsA2.390>Name of the Domain Name Service Performance watcher. Important: This name is arbitrary but case insensitive."
	::= { adsStatusDnsPrEntry 1 }


adsStatusDnsPrDescription OBJECT-TYPE
	SYNTAX DisplayString
	ACCESS read-write
	STATUS mandatory
	DESCRIPTION
		"&<caiAdsA2.391>Any description for this watcher."
	::= { adsStatusDnsPrEntry 2 }


adsStatusDnsPrExpression OBJECT-TYPE
	SYNTAX DisplayString
	ACCESS read-write
	STATUS mandatory
	DESCRIPTION
		"&<caiAdsA2.392>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsStatusDnsPrEntry 3 }


adsStatusDnsPrCounter0 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.393>The definition of the counter with reference key C0 or L0. As a general rule, changing the definition of a counter invalidates the values retrieved at the last poll interval. For this reason it will take two polls until a new value is calculated."
	DEFVAL { 0 }
	::= { adsStatusDnsPrEntry 4 }


adsStatusDnsPrCounter1 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.394>The definition of the counter with reference key C1 or L1. As a general rule, changing the definition of a counter invalidates the values retrieved at the last poll interval. For this reason it will take two polls until a new value is calculated."
	DEFVAL { 0 }
	::= { adsStatusDnsPrEntry 5 }


adsStatusDnsPrCounter2 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.395>The definition of the counter with reference key C2 or L2. As a general rule, changing the definition of a counter invalidates the values retrieved at the last poll interval. For this reason it will take two polls until a new value is calculated."
	DEFVAL { 0 }
	::= { adsStatusDnsPrEntry 6 }


adsStatusDnsPrCounter3 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.396>The definition of the counter with reference key C3 or L3. As a general rule, changing the definition of a counter invalidates the values retrieved at the last poll interval. For this reason it will take two polls until a new value is calculated."
	DEFVAL { 0 }
	::= { adsStatusDnsPrEntry 7 }


adsStatusDnsPrCounter4 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.397>The definition of the counter with reference key C4 or L4. As a general rule, changing the definition of a counter invalidates the values retrieved at the last poll interval. For this reason it will take two polls until a new value is calculated."
	DEFVAL { 0 }
	::= { adsStatusDnsPrEntry 8 }


adsStatusDnsPrCounter5 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.398>The definition of the counter with reference key C5 or L5. As a general rule, changing the definition of a counter invalidates the values retrieved at the last poll interval. For this reason it will take two polls until a new value is calculated."
	DEFVAL { 0 }
	::= { adsStatusDnsPrEntry 9 }


adsStatusDnsPrCounter6 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.399>The definition of the counter with reference key C6 or L6. As a general rule, changing the definition of a counter invalidates the values retrieved at the last poll interval. For this reason it will take two polls until a new value is calculated."
	DEFVAL { 0 }
	::= { adsStatusDnsPrEntry 10 }


adsStatusDnsPrCounter7 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.400>The definition of the counter with reference key C7 or L7. As a general rule, changing the definition of a counter invalidates the values retrieved at the last poll interval. For this reason it will take two polls until a new value is calculated."
	DEFVAL { 0 }
	::= { adsStatusDnsPrEntry 11 }


adsStatusDnsPrCounter8 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.401>The definition of the counter with reference key C8 or L8. As a general rule, changing the definition of a counter invalidates the values retrieved at the last poll interval. For this reason it will take two polls until a new value is calculated."
	DEFVAL { 0 }
	::= { adsStatusDnsPrEntry 12 }


adsStatusDnsPrCounter9 OBJECT-TYPE
	SYNTAX INTEGER {
		NONE(1),
		AXFR_Request_Received(2),
		AXFR_Request_Sent(3),
		AXFR_Response_Received(4),
		AXFR_Success_Received(5),
		AXFR_Success_Sent(6),
		Caching_Memory(7),
		Database_Node_Memory(8),
		Dynamic_Update_NoOperation(9),
		Dynamic_Update_NoOperation_per_sec(10),
		Dynamic_Update_Queued(11),
		Dynamic_Update_Received(12),
		Dynamic_Update_Received_per_sec(13),
		Dynamic_Update_Rejected(14),
		Dynamic_Update_TimeOuts(15),
		Dynamic_Update_Written_to_Database(16),
		Dynamic_Update_Written_to_Database_per_sec(17),
		IXFR_Request_Received(18),
		IXFR_Request_Sent(19),
		IXFR_Response_Received(20),
		IXFR_Success_Received(21),
		IXFR_Success_Sent(22),
		IXFR_TCP_Success_Received(23),
		IXFR_UDP_Success_Received(24),
		Nbstat_Memory(25),
		Notify_Received(26),
		Notify_Sent(27),
		Record_Flow_Memory(28),
		Recursive_Queries(29),
		Recursive_Queries_per_sec(30),
		Recursive_Query_Failure(31),
		Recursive_Query_Failure_per_sec(32),
		Recursive_Send_TimeOuts(33),
		Recursive_TimeOut_per_sec(34),
		Secure_Update_Failure(35),
		Secure_Update_Received(36),
		Secure_Update_Received_per_sec(37),
		TCP_Message_Memory(38),
		TCP_Query_Received(39),
		TCP_Query_Received_per_sec(40),
		TCP_Response_Sent(41),
		TCP_Response_Sent_per_sec(42),
		Total_Query_Received(43),
		Total_Query_Received_per_sec(44),
		Total_Response_Sent(45),
		Total_Response_Sent_per_sec(46),
		UDP_Message_Memory(47),
		UDP_Query_Received(48),
		UDP_Query_Received_per_sec(49),
		UDP_Response_Sent(50),
		UDP_Response_Sent_per_sec(51),
		WINS_Lookup_Received(52),
		WINS_Lookup_Received_per_sec(53),
		WINS_Response_Sent(54),
		WINS_Response_Sent_per_sec(55),
		WINS_Reverse_Lookup_Received(56),
		WINS_Reverse_Lookup_Received_per_sec(57),
		WINS_Reverse_Response_Sent(58),
		WINS_Reverse_Response_Sent_per_sec(59),
		Zone_Transfer_Failure(60),
		Zone_Transfer_Request_Received(61),
		Zone_Transfer_SOA_Request_Sent(62),
		Zone_Transfer_Success(63)
	}
	ACCESS read-write
	STATUS mandatory
	DESCRIPTION
		"&<caiAdsA2.402>The definition of the counter with reference key C9 or L9. As a general rule, changing the definition of a counter invalidates the values retrieved at the last poll interval. For this reason it will take two polls until a new value is calculated."
	DEFVAL { 0 }
	::= { adsStatusDnsPrEntry 13 }


adsStatusDnsPrAggLagValue OBJECT-TYPE
	SYNTAX INTEGER
	ACCESS read-only
	STATUS mandatory
	DESCRIPTION
		"&<caiAdsA2.403>The number of consecutive poll intervals on which any status was not in the Ok or Up state."
	::= { adsStatusDnsPrEntry 14 }


adsStatusDnsPrAggLag OBJECT-TYPE
	SYNTAX INTEGER
	ACCESS read-write
	STATUS mandatory
	DESCRIPTION
		"&<caiAdsA2.404>The number of consecutive poll intervals on which any status is not in the Ok or Up state, before the aggregate status changes. Valid values are greater than 0."
	::= { adsStatusDnsPrEntry 15 }


adsStatusDnsPrAggStatus OBJECT-TYPE
	SYNTAX INTEGER {
		unknown(1),
		ok(2),
		warning(3),
		critical(4)
	}
	ACCESS read-only
	STATUS mandatory
	DESCRIPTION
		"&<caiAdsA2.405>The current status of this watcher as a 'worst case' aggregate of all its statuses."
	::= { adsStatusDnsPrEntry 16 }


adsStatusDnsPrValue OBJECT-TYPE
	SYNTAX DisplayString
	ACCESS read-only
	STATUS mandatory
	DESCRIPTION
		"&<caiAdsA2.406>The current value calculated according to the expression. The calculation is done with floating point arithmetic. As a general rule, changing the definition of any counter invalidates the values retrieved at the last poll interval. For this reason it will take two polls until a new value is calculated."
	::= { adsStatusDnsPrEntry 17 }


adsStatusDnsPrWarn OBJECT-TYPE
	SYNTAX DisplayString
	ACCESS read-write
	STATUS mandatory
	DESCRIPTION
		"&<caiAdsA2.407>Warning threshold for the calculated value of the expression. Valid values are greater than 0.0 and smaller than or equal to the critical threshold."
	::= { adsStatusDnsPrEntry 18 }


adsStatusDnsPrCrit OBJECT-TYPE
	SYNTAX DisplayString
	ACCESS read-write
	STATUS mandatory
	DESCRIPTION
		"&<caiAdsA2.408>Critical threshold for the calculated value of the expression. Valid values are greater than 0.0 and greater than or equal to the warning threshold."
	::= { adsStatusDnsPrEntry 19 }


adsStatusDnsPrWcMonitor OBJECT-TYPE
	SYNTAX INTEGER {
		do-not-monitor(1),
		warning-only(2),
		critical-only(3),
		both(4)
	}
	ACCESS read-write
	STATUS mandatory
	DESCRIPTION
		"&<caiAdsA2.409>Flag indicating whether the programmed expression should be monitored against warning/critical thresholds and if so, which threshold should be compared with."
	DEFVAL { 0 }
	::= { adsStatusDnsPrEntry 20 }


adsStatusDnsPrWcStatus OBJECT-TYPE
	SYNTAX INTEGER {
		unknown(1),
		ok(2),
		warning(3),
		critical(4)
	}
	ACCESS read-only
	STATUS mandatory
	DESCRIPTION
		"&<caiAdsA2.410>The current status of the programmed expression as determined by the warning/critical thresholds. The status 'unknown' means that the current value could not be retrieved from the system."
	::= { adsStatusDnsPrEntry 21 }


adsStatusDnsPrMin OBJECT-TYPE
	SYNTAX DisplayString
	ACCESS read-write
	STATUS mandatory
	DESCRIPTION
		"&<caiAdsA2.411>Minimum threshold for the calculated value of the expression. Valid values are greater than 0.0 or equal to -1.0 and smaller than or equal to the maximum threshold. Setting to -1.0 disables the monitoring of the minimum."
	DEFVAL { "-2.0" }
	::= { adsStatusDnsPrEntry 22 }


adsStatusDnsPrMax OBJECT-TYPE
	SYNTAX DisplayString
	ACCESS read-write
	STATUS mandatory
	DESCRIPTION
		"&<caiAdsA2.412>Maximum threshold for the calculated value of the expression. Valid values are greater than 0.0 or equal to -1.0 and greater than or equal to the minimum threshold. Setting to -1.0 disables the monitoring of the maximum."
	DEFVAL { "-2.0" }
	::= { adsStatusDnsPrEntry 23 }


adsStatusDnsPrMmMonitor OBJECT-TYPE
	SYNTAX INTEGER {
		do-not-monitor(1),
		down-warning(2),
		down-critical(3)
	}
	ACCESS read-write
	STATUS mandatory
	DESCRIPTION
		"&<caiAdsA2.413>Flag indicating whether the programmed expression should be monitored against minimum/maximum thresholds and if so, the level of alert to raise."
	DEFVAL { 0 }
	::= { adsStatusDnsPrEntry 24 }


adsStatusDnsPrMmStatus OBJECT-TYPE
	SYNTAX INTEGER {
		unknown(1),
		ok(2),
		warning(3),
		critical(4)
	}
	ACCESS read-only
	STATUS mandatory
	DESCRIPTION
		"&<caiAdsA2.414>The current status of the programmed expression as determined by the minimum/maximum thresholds. The status 'unknown' means that the current value could not be retrieved from the system."
	::= { adsStatusDnsPrEntry 25 }


adsStatusDnsPrCallBackRef OBJECT-TYPE
	SYNTAX DisplayString
	ACCESS read-only
	STATUS mandatory
	DESCRIPTION
		"&<caiAdsA2.415>The name of the Call-Back reference that should be invoked in case of a status change."
	::= { adsStatusDnsPrEntry 26 }


adsStatusDnsPrButton OBJECT-TYPE
	SYNTAX INTEGER {
		none(1),
		remove(2),
		reset-store(3)
	}
	ACCESS read-write
	STATUS mandatory
	DESCRIPTION
		"&<caiAdsA2.416>This attribute is used to remove this watcher or to reset (empty) the store that holds the last N values which are used to calculate the MIN, MAX, AVG or SUM result of the expression. N is defined in the expression too."
	::= { adsStatusDnsPrEntry 27 }




-- *****************************************************************************
-- Active Directory Service Events Available Group
-- *****************************************************************************


adsAvailAdsEvRefresh OBJECT-TYPE
	SYNTAX INTEGER {
		none(1),
		refresh(2)
	}
	ACCESS read-write
	STATUS mandatory
	DESCRIPTION
		"&<caiAdsA2.417>Set this value to 'refresh' to let the agent check again for predefined Active Directory Service Event Logs patterns. The user can not set the value to 'none'."
	::= { adsAvailAdsEvGroup 1 }


adsAvailAdsEvCount OBJECT-TYPE
	SYNTAX INTEGER
	ACCESS read-only
	STATUS mandatory
	DESCRIPTION
		"&<caiAdsA2.418>The number of currently predefined Active Directory Service Event Logs patterns."
	::= { adsAvailAdsEvGroup 2 }


adsAvailAdsEvTable OBJECT-TYPE
	SYNTAX SEQUENCE OF AdsAvailAdsEvRow
	ACCESS not-accessible
	STATUS mandatory
	DESCRIPTION
		"&<caiAdsA2.419>A table containing the predefined Active Directory Service Event Logs patterns available for monitoring. These entries are read from the file 'agents\config\caiAdsA2.ini'."
	::= { adsAvailAdsEvGroup 3 }


adsAvailAdsEvEntry OBJECT-TYPE
	SYNTAX AdsAvailAdsEvRow
	ACCESS not-accessible
	STATUS mandatory
	DESCRIPTION
		"&<caiAdsA2.420>The table entry."
	INDEX { adsAvailAdsEvName }
	::= { adsAvailAdsEvTable 1 }


AdsAvailAdsEvRow ::=
	SEQUENCE {
		adsAvailAdsEvName DisplayString,
		adsAvailAdsEvDescription DisplayString,
		adsAvailAdsEvAutoWatch INTEGER,
		adsAvailAdsEvPatterns DisplayString,
		adsAvailAdsEvMonitor INTEGER
	}


adsAvailAdsEvName OBJECT-TYPE
	SYNTAX DisplayString
	ACCESS read-only
	STATUS mandatory
	DESCRIPTION
		"&<caiAdsA2.421>Name of the watcher, monitoring Active Directory Service Event Logs. Important: This name is arbitrary but case insensitive. When prefixed with the keyword '[OTHER]' then the watcher will not be applied on a new Event Log entry, if any other watcher not using this prefix already matches the entry during the same poll cycle."
	::= { adsAvailAdsEvEntry 1 }


adsAvailAdsEvDescription OBJECT-TYPE
	SYNTAX DisplayString
	ACCESS read-only
	STATUS mandatory
	DESCRIPTION
		"&<caiAdsA2.422>Any description for this watcher."
	::= { adsAvailAdsEvEntry 2 }


adsAvailAdsEvAutoWatch OBJECT-TYPE
	SYNTAX INTEGER {
		no(1),
		yes(2)
	}
	ACCESS read-only
	STATUS mandatory
	DESCRIPTION
		"&<caiAdsA2.423>If this value is 'yes' the agent automatically creates a watcher for this entry at startup. Otherwise the watcher must be created manually."
	::= { adsAvailAdsEvEntry 3 }


adsAvailAdsEvPatterns OBJECT-TYPE
	SYNTAX DisplayString
	ACCESS read-only
	STATUS mandatory
	DESCRIPTION
		"&<caiAdsA2.424>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsAvailAdsEvEntry 4 }


adsAvailAdsEvMonitor OBJECT-TYPE
	SYNTAX INTEGER {
		do-not-monitor(1),
		down-warning(2),
		down-critical(3)
	}
	ACCESS read-only
	STATUS mandatory
	DESCRIPTION
		"&<caiAdsA2.425>Flag indicating whether Active Directory Service Event Logs should be monitored and if so, the level of alert to raise."
	::= { adsAvailAdsEvEntry 5 }




-- *****************************************************************************
-- Active Directory Service Performance Available Group
-- *****************************************************************************


adsAvailAdsPrRefresh OBJECT-TYPE
	SYNTAX INTEGER {
		none(1),
		refresh(2)
	}
	ACCESS read-write
	STATUS mandatory
	DESCRIPTION
		"&<caiAdsA2.426>Set this value to 'refresh' to let the agent check again for predefined Active Directory Service Performance expressions. The user can not set the value to 'none'."
	::= { adsAvailAdsPrGroup 1 }


adsAvailAdsPrCount OBJECT-TYPE
	SYNTAX INTEGER
	ACCESS read-only
	STATUS mandatory
	DESCRIPTION
		"&<caiAdsA2.427>The number of currently predefined Active Directory Service Performance expressions."
	::= { adsAvailAdsPrGroup 2 }


adsAvailAdsPrTable OBJECT-TYPE
	SYNTAX SEQUENCE OF AdsAvailAdsPrRow
	ACCESS not-accessible
	STATUS mandatory
	DESCRIPTION
		"&<caiAdsA2.428>A table containing the predefined Active Directory Service Performance expressions available for monitoring. These entries are read from the file 'agents\config\caiAdsA2.ini'. This table is only filled if the corresponding performance object 'NTDS' can be found on the machine. Otherwise the table will be empty."
	::= { adsAvailAdsPrGroup 3 }


adsAvailAdsPrEntry OBJECT-TYPE
	SYNTAX AdsAvailAdsPrRow
	ACCESS not-accessible
	STATUS mandatory
	DESCRIPTION
		"&<caiAdsA2.429>The table entry."
	INDEX { adsAvailAdsPrName }
	::= { adsAvailAdsPrTable 1 }


AdsAvailAdsPrRow ::=
	SEQUENCE {
		adsAvailAdsPrName DisplayString,
		adsAvailAdsPrDescription DisplayString,
		adsAvailAdsPrAutoWatch INTEGER,
		adsAvailAdsPrExpression DisplayString,
		adsAvailAdsPrCounter0 INTEGER,
		adsAvailAdsPrCounter1 INTEGER,
		adsAvailAdsPrCounter2 INTEGER,
		adsAvailAdsPrCounter3 INTEGER,
		adsAvailAdsPrCounter4 INTEGER,
		adsAvailAdsPrCounter5 INTEGER,
		adsAvailAdsPrCounter6 INTEGER,
		adsAvailAdsPrCounter7 INTEGER,
		adsAvailAdsPrCounter8 INTEGER,
		adsAvailAdsPrCounter9 INTEGER,
		adsAvailAdsPrAggLag INTEGER,
		adsAvailAdsPrWarn DisplayString,
		adsAvailAdsPrCrit DisplayString,
		adsAvailAdsPrWcMonitor INTEGER,
		adsAvailAdsPrMin DisplayString,
		adsAvailAdsPrMax DisplayString,
		adsAvailAdsPrMmMonitor INTEGER
	}


adsAvailAdsPrName OBJECT-TYPE
	SYNTAX DisplayString
	ACCESS read-only
	STATUS mandatory
	DESCRIPTION
		"&<caiAdsA2.430>Name of the Active Directory Service Performance watcher. Important: This name is arbitrary but case insensitive."
	::= { adsAvailAdsPrEntry 1 }


adsAvailAdsPrDescription OBJECT-TYPE
	SYNTAX DisplayString
	ACCESS read-only
	STATUS mandatory
	DESCRIPTION
		"&<caiAdsA2.431>Any description for this watcher."
	::= { adsAvailAdsPrEntry 2 }


adsAvailAdsPrAutoWatch OBJECT-TYPE
	SYNTAX INTEGER {
		no(1),
		yes(2)
	}
	ACCESS read-only
	STATUS mandatory
	DESCRIPTION
		"&<caiAdsA2.432>If this value is 'yes' the agent automatically creates a watcher for this entry at startup. Otherwise the watcher must be created manually."
	::= { adsAvailAdsPrEntry 3 }


adsAvailAdsPrExpression OBJECT-TYPE
	SYNTAX DisplayString
	ACCESS read-only
	STATUS mandatory
	DESCRIPTION
		"&<caiAdsA2.433>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsAvailAdsPrEntry 4 }


adsAvailAdsPrCounter0 OBJECT-TYPE
	SYNTAX INTEGER
	ACCESS read-only
	STATUS mandatory
	DESCRIPTION
		"&<caiAdsA2.434>The definition of the counter with reference key C0 or L0."
	::= { adsAvailAdsPrEntry 5 }


adsAvailAdsPrCounter1 OBJECT-TYPE
	SYNTAX INTEGER
	ACCESS read-only
	STATUS mandatory
	DESCRIPTION
		"&<caiAdsA2.435>The definition of the counter with reference key C1 or L1."
	::= { adsAvailAdsPrEntry 6 }


adsAvailAdsPrCounter2 OBJECT-TYPE
	SYNTAX INTEGER
	ACCESS read-only
	STATUS mandatory
	DESCRIPTION
		"&<caiAdsA2.436>The definition of the counter with reference key C2 or L2."
	::= { adsAvailAdsPrEntry 7 }


adsAvailAdsPrCounter3 OBJECT-TYPE
	SYNTAX INTEGER
	ACCESS read-only
	STATUS mandatory
	DESCRIPTION
		"&<caiAdsA2.437>The definition of the counter with reference key C3 or L3."
	::= { adsAvailAdsPrEntry 8 }


adsAvailAdsPrCounter4 OBJECT-TYPE
	SYNTAX INTEGER
	ACCESS read-only
	STATUS mandatory
	DESCRIPTION
		"&<caiAdsA2.438>The definition of the counter with reference key C4 or L4."
	::= { adsAvailAdsPrEntry 9 }


adsAvailAdsPrCounter5 OBJECT-TYPE
	SYNTAX INTEGER
	ACCESS read-only
	STATUS mandatory
	DESCRIPTION
		"&<caiAdsA2.439>The definition of the counter with reference key C5 or L5."
	::= { adsAvailAdsPrEntry 10 }


adsAvailAdsPrCounter6 OBJECT-TYPE
	SYNTAX INTEGER
	ACCESS read-only
	STATUS mandatory
	DESCRIPTION
		"&<caiAdsA2.440>The definition of the counter with reference key C6 or L6."
	::= { adsAvailAdsPrEntry 11 }


adsAvailAdsPrCounter7 OBJECT-TYPE
	SYNTAX INTEGER
	ACCESS read-only
	STATUS mandatory
	DESCRIPTION
		"&<caiAdsA2.441>The definition of the counter with reference key C7 or L7."
	::= { adsAvailAdsPrEntry 12 }


adsAvailAdsPrCounter8 OBJECT-TYPE
	SYNTAX INTEGER
	ACCESS read-only
	STATUS mandatory
	DESCRIPTION
		"&<caiAdsA2.442>The definition of the counter with reference key C8 or L8."
	::= { adsAvailAdsPrEntry 13 }


adsAvailAdsPrCounter9 OBJECT-TYPE
	SYNTAX INTEGER
	ACCESS read-only
	STATUS mandatory
	DESCRIPTION
		"&<caiAdsA2.443>The definition of the counter with reference key C9 or L9."
	::= { adsAvailAdsPrEntry 14 }


adsAvailAdsPrAggLag OBJECT-TYPE
	SYNTAX INTEGER
	ACCESS read-only
	STATUS mandatory
	DESCRIPTION
		"&<caiAdsA2.444>The number of consecutive poll intervals on which any status is not in the Ok or Up state, before the aggregate status changes. Valid values are greater than 0."
	::= { adsAvailAdsPrEntry 15 }


adsAvailAdsPrWarn OBJECT-TYPE
	SYNTAX DisplayString
	ACCESS read-only
	STATUS mandatory
	DESCRIPTION
		"&<caiAdsA2.445>Warning threshold for the calculated value of the expression. Valid values are greater than 0.0 and smaller than or equal to the critical threshold."
	::= { adsAvailAdsPrEntry 16 }


adsAvailAdsPrCrit OBJECT-TYPE
	SYNTAX DisplayString
	ACCESS read-only
	STATUS mandatory
	DESCRIPTION
		"&<caiAdsA2.446>Critical threshold for the calculated value of the expression. Valid values are greater than 0.0 and greater than or equal to the warning threshold."
	::= { adsAvailAdsPrEntry 17 }


adsAvailAdsPrWcMonitor OBJECT-TYPE
	SYNTAX INTEGER {
		do-not-monitor(1),
		warning-only(2),
		critical-only(3),
		both(4)
	}
	ACCESS read-only
	STATUS mandatory
	DESCRIPTION
		"&<caiAdsA2.447>Flag indicating whether the programmed expression should be monitored against warning/critical thresholds and if so, which threshold should be compared with."
	::= { adsAvailAdsPrEntry 18 }


adsAvailAdsPrMin OBJECT-TYPE
	SYNTAX DisplayString
	ACCESS read-only
	STATUS mandatory
	DESCRIPTION
		"&<caiAdsA2.448>Minimum threshold for the calculated value of the expression. Valid values are greater than 0.0 or equal to -1.0 and smaller than or equal to the maximum threshold. Setting to -1.0 disables the monitoring of the minimum."
	::= { adsAvailAdsPrEntry 19 }


adsAvailAdsPrMax OBJECT-TYPE
	SYNTAX DisplayString
	ACCESS read-only
	STATUS mandatory
	DESCRIPTION
		"&<caiAdsA2.449>Maximum threshold for the calculated value of the expression. Valid values are greater than 0.0 or equal to -1.0 and greater than or equal to the minimum threshold. Setting to -1.0 disables the monitoring of the maximum."
	::= { adsAvailAdsPrEntry 20 }


adsAvailAdsPrMmMonitor OBJECT-TYPE
	SYNTAX INTEGER {
		do-not-monitor(1),
		down-warning(2),
		down-critical(3)
	}
	ACCESS read-only
	STATUS mandatory
	DESCRIPTION
		"&<caiAdsA2.450>Flag indicating whether the programmed expression should be monitored against minimum/maximum thresholds and if so, the level of alert to raise."
	::= { adsAvailAdsPrEntry 21 }




-- *****************************************************************************
-- File Replication Service Events Available Group
-- *****************************************************************************


adsAvailFrsEvRefresh OBJECT-TYPE
	SYNTAX INTEGER {
		none(1),
		refresh(2)
	}
	ACCESS read-write
	STATUS mandatory
	DESCRIPTION
		"&<caiAdsA2.451>Set this value to 'refresh' to let the agent check again for predefined File Replication Service Event Logs patterns. The user can not set the value to 'none'."
	::= { adsAvailFrsEvGroup 1 }


adsAvailFrsEvCount OBJECT-TYPE
	SYNTAX INTEGER
	ACCESS read-only
	STATUS mandatory
	DESCRIPTION
		"&<caiAdsA2.452>The number of currently predefined File Replication Service Event Logs patterns."
	::= { adsAvailFrsEvGroup 2 }


adsAvailFrsEvTable OBJECT-TYPE
	SYNTAX SEQUENCE OF AdsAvailFrsEvRow
	ACCESS not-accessible
	STATUS mandatory
	DESCRIPTION
		"&<caiAdsA2.453>A table containing the predefined File Replication Service Event Logs patterns available for monitoring. These entries are read from the file 'agents\config\caiAdsA2.ini'."
	::= { adsAvailFrsEvGroup 3 }


adsAvailFrsEvEntry OBJECT-TYPE
	SYNTAX AdsAvailFrsEvRow
	ACCESS not-accessible
	STATUS mandatory
	DESCRIPTION
		"&<caiAdsA2.454>The table entry."
	INDEX { adsAvailFrsEvName }
	::= { adsAvailFrsEvTable 1 }


AdsAvailFrsEvRow ::=
	SEQUENCE {
		adsAvailFrsEvName DisplayString,
		adsAvailFrsEvDescription DisplayString,
		adsAvailFrsEvAutoWatch INTEGER,
		adsAvailFrsEvPatterns DisplayString,
		adsAvailFrsEvMonitor INTEGER
	}


adsAvailFrsEvName OBJECT-TYPE
	SYNTAX DisplayString
	ACCESS read-only
	STATUS mandatory
	DESCRIPTION
		"&<caiAdsA2.455>Name of the watcher, monitoring File Replication Service Event Logs. Important: This name is arbitrary but case insensitive. When prefixed with the keyword '[OTHER]' then the watcher will not be applied on a new Event Log entry, if any other watcher not using this prefix already matches the entry during the same poll cycle."
	::= { adsAvailFrsEvEntry 1 }


adsAvailFrsEvDescription OBJECT-TYPE
	SYNTAX DisplayString
	ACCESS read-only
	STATUS mandatory
	DESCRIPTION
		"&<caiAdsA2.456>Any description for this watcher."
	::= { adsAvailFrsEvEntry 2 }


adsAvailFrsEvAutoWatch OBJECT-TYPE
	SYNTAX INTEGER {
		no(1),
		yes(2)
	}
	ACCESS read-only
	STATUS mandatory
	DESCRIPTION
		"&<caiAdsA2.457>If this value is 'yes' the agent automatically creates a watcher for this entry at startup. Otherwise the watcher must be created manually."
	::= { adsAvailFrsEvEntry 3 }


adsAvailFrsEvPatterns OBJECT-TYPE
	SYNTAX DisplayString
	ACCESS read-only
	STATUS mandatory
	DESCRIPTION
		"&<caiAdsA2.458>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsAvailFrsEvEntry 4 }


adsAvailFrsEvMonitor OBJECT-TYPE
	SYNTAX INTEGER {
		do-not-monitor(1),
		down-warning(2),
		down-critical(3)
	}
	ACCESS read-only
	STATUS mandatory
	DESCRIPTION
		"&<caiAdsA2.459>Flag indicating whether File Replication Service Event Logs should be monitored and if so, the level of alert to raise."
	::= { adsAvailFrsEvEntry 5 }




-- *****************************************************************************
-- File Replication Service Performance Available Group
-- *****************************************************************************


adsAvailFrsPrRefresh OBJECT-TYPE
	SYNTAX INTEGER {
		none(1),
		refresh(2)
	}
	ACCESS read-write
	STATUS mandatory
	DESCRIPTION
		"&<caiAdsA2.460>Set this value to 'refresh' to let the agent check again for predefined File Replication Service Performance expressions. The user can not set the value to 'none'."
	::= { adsAvailFrsPrGroup 1 }


adsAvailFrsPrCount OBJECT-TYPE
	SYNTAX INTEGER
	ACCESS read-only
	STATUS mandatory
	DESCRIPTION
		"&<caiAdsA2.461>The number of currently predefined File Replication Service Performance expressions."
	::= { adsAvailFrsPrGroup 2 }


adsAvailFrsPrTable OBJECT-TYPE
	SYNTAX SEQUENCE OF AdsAvailFrsPrRow
	ACCESS not-accessible
	STATUS mandatory
	DESCRIPTION
		"&<caiAdsA2.462>A table containing the predefined File Replication Service Performance expressions available for monitoring. These entries are read from the file 'agents\config\caiAdsA2.ini'. This table is only filled if the corresponding performance object 'FileReplicaSet' can be found on the machine. Otherwise the table will be empty."
	::= { adsAvailFrsPrGroup 3 }


adsAvailFrsPrEntry OBJECT-TYPE
	SYNTAX AdsAvailFrsPrRow
	ACCESS not-accessible
	STATUS mandatory
	DESCRIPTION
		"&<caiAdsA2.463>The table entry."
	INDEX { adsAvailFrsPrName }
	::= { adsAvailFrsPrTable 1 }


AdsAvailFrsPrRow ::=
	SEQUENCE {
		adsAvailFrsPrName DisplayString,
		adsAvailFrsPrDescription DisplayString,
		adsAvailFrsPrAutoWatch INTEGER,
		adsAvailFrsPrExpression DisplayString,
		adsAvailFrsPrCounter0 INTEGER,
		adsAvailFrsPrCounter1 INTEGER,
		adsAvailFrsPrCounter2 INTEGER,
		adsAvailFrsPrCounter3 INTEGER,
		adsAvailFrsPrCounter4 INTEGER,
		adsAvailFrsPrCounter5 INTEGER,
		adsAvailFrsPrCounter6 INTEGER,
		adsAvailFrsPrCounter7 INTEGER,
		adsAvailFrsPrCounter8 INTEGER,
		adsAvailFrsPrCounter9 INTEGER,
		adsAvailFrsPrAggLag INTEGER,
		adsAvailFrsPrWarn DisplayString,
		adsAvailFrsPrCrit DisplayString,
		adsAvailFrsPrWcMonitor INTEGER,
		adsAvailFrsPrMin DisplayString,
		adsAvailFrsPrMax DisplayString,
		adsAvailFrsPrMmMonitor INTEGER
	}


adsAvailFrsPrName OBJECT-TYPE
	SYNTAX DisplayString
	ACCESS read-only
	STATUS mandatory
	DESCRIPTION
		"&<caiAdsA2.464>Name of the Active Directory Service Performance watcher. Important: This name is arbitrary but case insensitive."
	::= { adsAvailFrsPrEntry 1 }


adsAvailFrsPrDescription OBJECT-TYPE
	SYNTAX DisplayString
	ACCESS read-only
	STATUS mandatory
	DESCRIPTION
		"&<caiAdsA2.465>Any description for this watcher."
	::= { adsAvailFrsPrEntry 2 }


adsAvailFrsPrAutoWatch OBJECT-TYPE
	SYNTAX INTEGER {
		no(1),
		yes(2)
	}
	ACCESS read-only
	STATUS mandatory
	DESCRIPTION
		"&<caiAdsA2.466>If this value is 'yes' the agent automatically creates a watcher for this entry at startup. Otherwise the watcher must be created manually."
	::= { adsAvailFrsPrEntry 3 }


adsAvailFrsPrExpression OBJECT-TYPE
	SYNTAX DisplayString
	ACCESS read-only
	STATUS mandatory
	DESCRIPTION
		"&<caiAdsA2.467>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsAvailFrsPrEntry 4 }


adsAvailFrsPrCounter0 OBJECT-TYPE
	SYNTAX INTEGER
	ACCESS read-only
	STATUS mandatory
	DESCRIPTION
		"&<caiAdsA2.468>The definition of the counter with reference key C0 or L0."
	::= { adsAvailFrsPrEntry 5 }


adsAvailFrsPrCounter1 OBJECT-TYPE
	SYNTAX INTEGER
	ACCESS read-only
	STATUS mandatory
	DESCRIPTION
		"&<caiAdsA2.469>The definition of the counter with reference key C1 or L1."
	::= { adsAvailFrsPrEntry 6 }


adsAvailFrsPrCounter2 OBJECT-TYPE
	SYNTAX INTEGER
	ACCESS read-only
	STATUS mandatory
	DESCRIPTION
		"&<caiAdsA2.470>The definition of the counter with reference key C2 or L2."
	::= { adsAvailFrsPrEntry 7 }


adsAvailFrsPrCounter3 OBJECT-TYPE
	SYNTAX INTEGER
	ACCESS read-only
	STATUS mandatory
	DESCRIPTION
		"&<caiAdsA2.471>The definition of the counter with reference key C3 or L3."
	::= { adsAvailFrsPrEntry 8 }


adsAvailFrsPrCounter4 OBJECT-TYPE
	SYNTAX INTEGER
	ACCESS read-only
	STATUS mandatory
	DESCRIPTION
		"&<caiAdsA2.472>The definition of the counter with reference key C4 or L4."
	::= { adsAvailFrsPrEntry 9 }


adsAvailFrsPrCounter5 OBJECT-TYPE
	SYNTAX INTEGER
	ACCESS read-only
	STATUS mandatory
	DESCRIPTION
		"&<caiAdsA2.473>The definition of the counter with reference key C5 or L5."
	::= { adsAvailFrsPrEntry 10 }


adsAvailFrsPrCounter6 OBJECT-TYPE
	SYNTAX INTEGER
	ACCESS read-only
	STATUS mandatory
	DESCRIPTION
		"&<caiAdsA2.474>The definition of the counter with reference key C6 or L6."
	::= { adsAvailFrsPrEntry 11 }


adsAvailFrsPrCounter7 OBJECT-TYPE
	SYNTAX INTEGER
	ACCESS read-only
	STATUS mandatory
	DESCRIPTION
		"&<caiAdsA2.475>The definition of the counter with reference key C7 or L7."
	::= { adsAvailFrsPrEntry 12 }


adsAvailFrsPrCounter8 OBJECT-TYPE
	SYNTAX INTEGER
	ACCESS read-only
	STATUS mandatory
	DESCRIPTION
		"&<caiAdsA2.476>The definition of the counter with reference key C8 or L8."
	::= { adsAvailFrsPrEntry 13 }


adsAvailFrsPrCounter9 OBJECT-TYPE
	SYNTAX INTEGER
	ACCESS read-only
	STATUS mandatory
	DESCRIPTION
		"&<caiAdsA2.477>The definition of the counter with reference key C9 or L9."
	::= { adsAvailFrsPrEntry 14 }


adsAvailFrsPrAggLag OBJECT-TYPE
	SYNTAX INTEGER
	ACCESS read-only
	STATUS mandatory
	DESCRIPTION
		"&<caiAdsA2.478>The number of consecutive poll intervals on which any status is not in the Ok or Up state, before the aggregate status changes. Valid values are greater than 0."
	::= { adsAvailFrsPrEntry 15 }


adsAvailFrsPrWarn OBJECT-TYPE
	SYNTAX DisplayString
	ACCESS read-only
	STATUS mandatory
	DESCRIPTION
		"&<caiAdsA2.479>Warning threshold for the calculated value of the expression. Valid values are greater than 0.0 and smaller than or equal to the critical threshold."
	::= { adsAvailFrsPrEntry 16 }


adsAvailFrsPrCrit OBJECT-TYPE
	SYNTAX DisplayString
	ACCESS read-only
	STATUS mandatory
	DESCRIPTION
		"&<caiAdsA2.480>Critical threshold for the calculated value of the expression. Valid values are greater than 0.0 and greater than or equal to the warning threshold."
	::= { adsAvailFrsPrEntry 17 }


adsAvailFrsPrWcMonitor OBJECT-TYPE
	SYNTAX INTEGER {
		do-not-monitor(1),
		warning-only(2),
		critical-only(3),
		both(4)
	}
	ACCESS read-only
	STATUS mandatory
	DESCRIPTION
		"&<caiAdsA2.481>Flag indicating whether the programmed expression should be monitored against warning/critical thresholds and if so, which threshold should be compared with."
	::= { adsAvailFrsPrEntry 18 }


adsAvailFrsPrMin OBJECT-TYPE
	SYNTAX DisplayString
	ACCESS read-only
	STATUS mandatory
	DESCRIPTION
		"&<caiAdsA2.482>Minimum threshold for the calculated value of the expression. Valid values are greater than 0.0 or equal to -1.0 and smaller than or equal to the maximum threshold. Setting to -1.0 disables the monitoring of the minimum."
	::= { adsAvailFrsPrEntry 19 }


adsAvailFrsPrMax OBJECT-TYPE
	SYNTAX DisplayString
	ACCESS read-only
	STATUS mandatory
	DESCRIPTION
		"&<caiAdsA2.483>Maximum threshold for the calculated value of the expression. Valid values are greater than 0.0 or equal to -1.0 and greater than or equal to the minimum threshold. Setting to -1.0 disables the monitoring of the maximum."
	::= { adsAvailFrsPrEntry 20 }


adsAvailFrsPrMmMonitor OBJECT-TYPE
	SYNTAX INTEGER {
		do-not-monitor(1),
		down-warning(2),
		down-critical(3)
	}
	ACCESS read-only
	STATUS mandatory
	DESCRIPTION
		"&<caiAdsA2.484>Flag indicating whether the programmed expression should be monitored against minimum/maximum thresholds and if so, the level of alert to raise."
	::= { adsAvailFrsPrEntry 21 }




-- *****************************************************************************
-- Domain Name Service Events Available Group
-- *****************************************************************************


adsAvailDnsEvRefresh OBJECT-TYPE
	SYNTAX INTEGER {
		none(1),
		refresh(2)
	}
	ACCESS read-write
	STATUS mandatory
	DESCRIPTION
		"&<caiAdsA2.485>Set this value to 'refresh' to let the agent check again for predefined Domain Name Service Event Logs patterns. The user can not set the value to 'none'."
	::= { adsAvailDnsEvGroup 1 }


adsAvailDnsEvCount OBJECT-TYPE
	SYNTAX INTEGER
	ACCESS read-only
	STATUS mandatory
	DESCRIPTION
		"&<caiAdsA2.486>The number of currently predefined Domain Name Service Event Logs patterns."
	::= { adsAvailDnsEvGroup 2 }


adsAvailDnsEvTable OBJECT-TYPE
	SYNTAX SEQUENCE OF AdsAvailDnsEvRow
	ACCESS not-accessible
	STATUS mandatory
	DESCRIPTION
		"&<caiAdsA2.487>A table containing the predefined Domain Name Service Event Logs patterns available for monitoring. These entries are read from the file 'agents\config\caiAdsA2.ini'."
	::= { adsAvailDnsEvGroup 3 }


adsAvailDnsEvEntry OBJECT-TYPE
	SYNTAX AdsAvailDnsEvRow
	ACCESS not-accessible
	STATUS mandatory
	DESCRIPTION
		"&<caiAdsA2.488>The table entry."
	INDEX { adsAvailDnsEvName }
	::= { adsAvailDnsEvTable 1 }


AdsAvailDnsEvRow ::=
	SEQUENCE {
		adsAvailDnsEvName DisplayString,
		adsAvailDnsEvDescription DisplayString,
		adsAvailDnsEvAutoWatch INTEGER,
		adsAvailDnsEvPatterns DisplayString,
		adsAvailDnsEvMonitor INTEGER
	}


adsAvailDnsEvName OBJECT-TYPE
	SYNTAX DisplayString
	ACCESS read-only
	STATUS mandatory
	DESCRIPTION
		"&<caiAdsA2.489>Name of the watcher, monitoring Domain Name Service Event Logs. Important: This name is arbitrary but case insensitive. When prefixed with the keyword '[OTHER]' then the watcher will not be applied on a new Event Log entry, if any other watcher not using this prefix already matches the entry during the same poll cycle."
	::= { adsAvailDnsEvEntry 1 }


adsAvailDnsEvDescription OBJECT-TYPE
	SYNTAX DisplayString
	ACCESS read-only
	STATUS mandatory
	DESCRIPTION
		"&<caiAdsA2.490>Any description for this watcher."
	::= { adsAvailDnsEvEntry 2 }


adsAvailDnsEvAutoWatch OBJECT-TYPE
	SYNTAX INTEGER {
		no(1),
		yes(2)
	}
	ACCESS read-only
	STATUS mandatory
	DESCRIPTION
		"&<caiAdsA2.491>If this value is 'yes' the agent automatically creates a watcher for this entry at startup. Otherwise the watcher must be created manually."
	::= { adsAvailDnsEvEntry 3 }


adsAvailDnsEvPatterns OBJECT-TYPE
	SYNTAX DisplayString
	ACCESS read-only
	STATUS mandatory
	DESCRIPTION
		"&<caiAdsA2.492>A list of patterns, each of which is compared to match an Event Log entry, that occurred since the last poll. The patterns must be separated by a pipe sign. A match is reported, if any of the patterns matches. The syntax of each pattern is Log/Source/Id/Type/Message. Each component in a pattern can be a regular expression. For example the pattern 'System/Unicenter/.*/Error/.*' matches all Error event log entries of the source Unicenter in the System Log. The missing of a regular expression is treated as any string (.*), for example 'System/Unicenter//Error/'. If a regular expression itself contains any of the two used delimiters (/ or |), each occurrence of this character must be put between [] in the regular expression."
	::= { adsAvailDnsEvEntry 4 }


adsAvailDnsEvMonitor OBJECT-TYPE
	SYNTAX INTEGER {
		do-not-monitor(1),
		down-warning(2),
		down-critical(3)
	}
	ACCESS read-only
	STATUS mandatory
	DESCRIPTION
		"&<caiAdsA2.493>Flag indicating whether Active Directory Service Event Logs should be monitored and if so, the level of alert to raise."
	::= { adsAvailDnsEvEntry 5 }




-- *****************************************************************************
-- Domain Name Service Performance Available Group
-- *****************************************************************************


adsAvailDnsPrRefresh OBJECT-TYPE
	SYNTAX INTEGER {
		none(1),
		refresh(2)
	}
	ACCESS read-write
	STATUS mandatory
	DESCRIPTION
		"&<caiAdsA2.494>Set this value to 'refresh' to let the agent check again for predefined Domain Name Service Performance expressions. The user can not set the value to 'none'."
	::= { adsAvailDnsPrGroup 1 }


adsAvailDnsPrCount OBJECT-TYPE
	SYNTAX INTEGER
	ACCESS read-only
	STATUS mandatory
	DESCRIPTION
		"&<caiAdsA2.495>The number of currently predefined Domain Name Service Performance expressions."
	::= { adsAvailDnsPrGroup 2 }


adsAvailDnsPrTable OBJECT-TYPE
	SYNTAX SEQUENCE OF AdsAvailDnsPrRow
	ACCESS not-accessible
	STATUS mandatory
	DESCRIPTION
		"&<caiAdsA2.496>A table containing the predefined Domain Name Service Performance expressions available for monitoring. These entries are read from the file 'agents\config\caiAdsA2.ini'. This table is only filled if the corresponding performance object 'DNS' can be found on the machine. Otherwise the table will be empty."
	::= { adsAvailDnsPrGroup 3 }


adsAvailDnsPrEntry OBJECT-TYPE
	SYNTAX AdsAvailDnsPrRow
	ACCESS not-accessible
	STATUS mandatory
	DESCRIPTION
		"&<caiAdsA2.497>The table entry."
	INDEX { adsAvailDnsPrName }
	::= { adsAvailDnsPrTable 1 }


AdsAvailDnsPrRow ::=
	SEQUENCE {
		adsAvailDnsPrName DisplayString,
		adsAvailDnsPrDescription DisplayString,
		adsAvailDnsPrAutoWatch INTEGER,
		adsAvailDnsPrExpression DisplayString,
		adsAvailDnsPrCounter0 INTEGER,
		adsAvailDnsPrCounter1 INTEGER,
		adsAvailDnsPrCounter2 INTEGER,
		adsAvailDnsPrCounter3 INTEGER,
		adsAvailDnsPrCounter4 INTEGER,
		adsAvailDnsPrCounter5 INTEGER,
		adsAvailDnsPrCounter6 INTEGER,
		adsAvailDnsPrCounter7 INTEGER,
		adsAvailDnsPrCounter8 INTEGER,
		adsAvailDnsPrCounter9 INTEGER,
		adsAvailDnsPrAggLag INTEGER,
		adsAvailDnsPrWarn DisplayString,
		adsAvailDnsPrCrit DisplayString,
		adsAvailDnsPrWcMonitor INTEGER,
		adsAvailDnsPrMin DisplayString,
		adsAvailDnsPrMax DisplayString,
		adsAvailDnsPrMmMonitor INTEGER
	}


adsAvailDnsPrName OBJECT-TYPE
	SYNTAX DisplayString
	ACCESS read-only
	STATUS mandatory
	DESCRIPTION
		"&<caiAdsA2.498>Name of the Active Directory Service Performance watcher. Important: This name is arbitrary but case insensitive."
	::= { adsAvailDnsPrEntry 1 }


adsAvailDnsPrDescription OBJECT-TYPE
	SYNTAX DisplayString
	ACCESS read-only
	STATUS mandatory
	DESCRIPTION
		"&<caiAdsA2.499>Any description for this watcher."
	::= { adsAvailDnsPrEntry 2 }


adsAvailDnsPrAutoWatch OBJECT-TYPE
	SYNTAX INTEGER {
		no(1),
		yes(2)
	}
	ACCESS read-only
	STATUS mandatory
	DESCRIPTION
		"&<caiAdsA2.500>If this value is 'yes' the agent automatically creates a watcher for this entry at startup. Otherwise the watcher must be created manually."
	::= { adsAvailDnsPrEntry 3 }


adsAvailDnsPrExpression OBJECT-TYPE
	SYNTAX DisplayString
	ACCESS read-only
	STATUS mandatory
	DESCRIPTION
		"&<caiAdsA2.501>The expression that should be calculated for this watcher. The following 3 types of variables can be used in the expression: Cn, Ln, and P. Cn refers to counter n and is replaced during calculation by its value determined at the current poll. Ln refers to counter n and is replaced during calculation by its value determined at the last poll. P is the last poll interval in seconds (if polled by query, P could be smaller than the actual definition of the PollInterval attribute). These variables, the operators + - * / ( ) and constants build the arithmetic syntax of the expression. Such an arithmetic expression can be defined solely or can be used as first argument A in one of the following four functions: MIN(A,N), MAX(A,N), AVG(A,N), and SUM(A,N). The second argument N denotes the number of poll intervals. If such a function is used in the expression, the value of the expression is the minimum, maximum, average or sum of the last N values calculated according to A at the last N polls. The maximum for N is 20000."
	::= { adsAvailDnsPrEntry 4 }


adsAvailDnsPrCounter0 OBJECT-TYPE
	SYNTAX INTEGER
	ACCESS read-only
	STATUS mandatory
	DESCRIPTION
		"&<caiAdsA2.502>The definition of the counter with reference key C0 or L0."
	::= { adsAvailDnsPrEntry 5 }


adsAvailDnsPrCounter1 OBJECT-TYPE
	SYNTAX INTEGER
	ACCESS read-only
	STATUS mandatory
	DESCRIPTION
		"&<caiAdsA2.503>The definition of the counter with reference key C1 or L1."
	::= { adsAvailDnsPrEntry 6 }


adsAvailDnsPrCounter2 OBJECT-TYPE
	SYNTAX INTEGER
	ACCESS read-only
	STATUS mandatory
	DESCRIPTION
		"&<caiAdsA2.504>The definition of the counter with reference key C2 or L2."
	::= { adsAvailDnsPrEntry 7 }


adsAvailDnsPrCounter3 OBJECT-TYPE
	SYNTAX INTEGER
	ACCESS read-only
	STATUS mandatory
	DESCRIPTION
		"&<caiAdsA2.505>The definition of the counter with reference key C3 or L3."
	::= { adsAvailDnsPrEntry 8 }


adsAvailDnsPrCounter4 OBJECT-TYPE
	SYNTAX INTEGER
	ACCESS read-only
	STATUS mandatory
	DESCRIPTION
		"&<caiAdsA2.506>The definition of the counter with reference key C4 or L4."
	::= { adsAvailDnsPrEntry 9 }


adsAvailDnsPrCounter5 OBJECT-TYPE
	SYNTAX INTEGER
	ACCESS read-only
	STATUS mandatory
	DESCRIPTION
		"&<caiAdsA2.507>The definition of the counter with reference key C5 or L5."
	::= { adsAvailDnsPrEntry 10 }


adsAvailDnsPrCounter6 OBJECT-TYPE
	SYNTAX INTEGER
	ACCESS read-only
	STATUS mandatory
	DESCRIPTION
		"&<caiAdsA2.508>The definition of the counter with reference key C6 or L6."
	::= { adsAvailDnsPrEntry 11 }


adsAvailDnsPrCounter7 OBJECT-TYPE
	SYNTAX INTEGER
	ACCESS read-only
	STATUS mandatory
	DESCRIPTION
		"&<caiAdsA2.509>The definition of the counter with reference key C7 or L7."
	::= { adsAvailDnsPrEntry 12 }


adsAvailDnsPrCounter8 OBJECT-TYPE
	SYNTAX INTEGER
	ACCESS read-only
	STATUS mandatory
	DESCRIPTION
		"&<caiAdsA2.510>The definition of the counter with reference key C8 or L8."
	::= { adsAvailDnsPrEntry 13 }


adsAvailDnsPrCounter9 OBJECT-TYPE
	SYNTAX INTEGER
	ACCESS read-only
	STATUS mandatory
	DESCRIPTION
		"&<caiAdsA2.511>The definition of the counter with reference key C9 or L9."
	::= { adsAvailDnsPrEntry 14 }


adsAvailDnsPrAggLag OBJECT-TYPE
	SYNTAX INTEGER
	ACCESS read-only
	STATUS mandatory
	DESCRIPTION
		"&<caiAdsA2.512>The number of consecutive poll intervals on which any status is not in the Ok or Up state, before the aggregate status changes. Valid values are greater than 0."
	::= { adsAvailDnsPrEntry 15 }


adsAvailDnsPrWarn OBJECT-TYPE
	SYNTAX DisplayString
	ACCESS read-only
	STATUS mandatory
	DESCRIPTION
		"&<caiAdsA2.513>Warning threshold for the calculated value of the expression. Valid values are greater than 0.0 and smaller than or equal to the critical threshold."
	::= { adsAvailDnsPrEntry 16 }


adsAvailDnsPrCrit OBJECT-TYPE
	SYNTAX DisplayString
	ACCESS read-only
	STATUS mandatory
	DESCRIPTION
		"&<caiAdsA2.514>Critical threshold for the calculated value of the expression. Valid values are greater than 0.0 and greater than or equal to the warning threshold."
	::= { adsAvailDnsPrEntry 17 }


adsAvailDnsPrWcMonitor OBJECT-TYPE
	SYNTAX INTEGER {
		do-not-monitor(1),
		warning-only(2),
		critical-only(3),
		both(4)
	}
	ACCESS read-only
	STATUS mandatory
	DESCRIPTION
		"&<caiAdsA2.515>Flag indicating whether the programmed expression should be monitored against warning/critical thresholds and if so, which threshold should be compared with."
	::= { adsAvailDnsPrEntry 18 }


adsAvailDnsPrMin OBJECT-TYPE
	SYNTAX DisplayString
	ACCESS read-only
	STATUS mandatory
	DESCRIPTION
		"&<caiAdsA2.516>Minimum threshold for the calculated value of the expression. Valid values are greater than 0.0 or equal to -1.0 and smaller than or equal to the maximum threshold. Setting to -1.0 disables the monitoring of the minimum."
	::= { adsAvailDnsPrEntry 19 }


adsAvailDnsPrMax OBJECT-TYPE
	SYNTAX DisplayString
	ACCESS read-only
	STATUS mandatory
	DESCRIPTION
		"&<caiAdsA2.517>Maximum threshold for the calculated value of the expression. Valid values are greater than 0.0 or equal to -1.0 and greater than or equal to the minimum threshold. Setting to -1.0 disables the monitoring of the maximum."
	::= { adsAvailDnsPrEntry 20 }


adsAvailDnsPrMmMonitor OBJECT-TYPE
	SYNTAX INTEGER {
		do-not-monitor(1),
		down-warning(2),
		down-critical(3)
	}
	ACCESS read-only
	STATUS mandatory
	DESCRIPTION
		"&<caiAdsA2.518>Flag indicating whether the programmed expression should be monitored against minimum/maximum thresholds and if so, the level of alert to raise."
	::= { adsAvailDnsPrEntry 21 }




-- *****************************************************************************
-- History Group
-- *****************************************************************************


adsHistoryDCtrlCollect OBJECT-TYPE
	SYNTAX INTEGER {
		no(1),
		yes(2)
	}
	ACCESS read-write
	STATUS mandatory
	DESCRIPTION
		"&<caiAdsA2.519>Set this value to 'yes' to let the agent collect traps of the Domain Controller group in the history table. If set to 'no' these traps are not stored in the history table."
	::= { adsHistoryGroup 1 }


adsHistoryDskSpCollect OBJECT-TYPE
	SYNTAX INTEGER {
		no(1),
		yes(2)
	}
	ACCESS read-write
	STATUS mandatory
	DESCRIPTION
		"&<caiAdsA2.520>Set this value to 'yes' to let the agent collect traps of the Disk Space group in the history table. If set to 'no' these traps are not stored in the history table."
	::= { adsHistoryGroup 2 }


adsHistoryAdsEvCollect OBJECT-TYPE
	SYNTAX INTEGER {
		no(1),
		yes(2)
	}
	ACCESS read-write
	STATUS mandatory
	DESCRIPTION
		"&<caiAdsA2.521>Set this value to 'yes' to let the agent collect traps of the Active Directory Service Events group in the history table. If set to 'no' these traps are not stored in the history table."
	::= { adsHistoryGroup 3 }


adsHistoryAdsPrCollect OBJECT-TYPE
	SYNTAX INTEGER {
		no(1),
		yes(2)
	}
	ACCESS read-write
	STATUS mandatory
	DESCRIPTION
		"&<caiAdsA2.522>Set this value to 'yes' to let the agent collect traps of the Programmable Active Directory Service group in the history table. If set to 'no' these traps are not stored in the history table."
	::= { adsHistoryGroup 4 }


adsHistoryFrsEvCollect OBJECT-TYPE
	SYNTAX INTEGER {
		no(1),
		yes(2)
	}
	ACCESS read-write
	STATUS mandatory
	DESCRIPTION
		"&<caiAdsA2.523>Set this value to 'yes' to let the agent collect traps of the File Replication Service Events group in the history table. If set to 'no' these traps are not stored in the history table."
	::= { adsHistoryGroup 5 }


adsHistoryFrsPrCollect OBJECT-TYPE
	SYNTAX INTEGER {
		no(1),
		yes(2)
	}
	ACCESS read-write
	STATUS mandatory
	DESCRIPTION
		"&<caiAdsA2.524>Set this value to 'yes' to let the agent collect traps of the Programmable File Replication Service group in the history table. If set to 'no' these traps are not stored in the history table."
	::= { adsHistoryGroup 6 }


adsHistoryDnsEvCollect OBJECT-TYPE
	SYNTAX INTEGER {
		no(1),
		yes(2)
	}
	ACCESS read-write
	STATUS mandatory
	DESCRIPTION
		"&<caiAdsA2.525>Set this value to 'yes' to let the agent collect traps of the Domain Name Service Events group in the history table. If set to 'no' these traps are not stored in the history table."
	::= { adsHistoryGroup 7 }


adsHistoryDnsPrCollect OBJECT-TYPE
	SYNTAX INTEGER {
		no(1),
		yes(2)
	}
	ACCESS read-write
	STATUS mandatory
	DESCRIPTION
		"&<caiAdsA2.526>Set this value to 'yes' to let the agent collect traps of the Programmable Domain Name Service group in the history table. If set to 'no' these traps are not stored in the history table."
	::= { adsHistoryGroup 8 }


adsHistoryButton OBJECT-TYPE
	SYNTAX INTEGER {
		none(1),
		clear(2)
	}
	ACCESS read-write
	STATUS mandatory
	DESCRIPTION
		"&<caiAdsA2.527>Set this value to 'clear' to let the agent empty the history table. The user can not set the value to 'none'."
	::= { adsHistoryGroup 9 }


adsHistoryMaxEntries OBJECT-TYPE
	SYNTAX INTEGER
	ACCESS read-write
	STATUS mandatory
	DESCRIPTION
		"&<caiAdsA2.528>The maximum number of entries to be stored in the history table. Valid values are 0 to 100. If set to 0 no history information of traps is stored."
	::= { adsHistoryGroup 10 }


adsHistoryCount OBJECT-TYPE
	SYNTAX INTEGER
	ACCESS read-only
	STATUS mandatory
	DESCRIPTION
		"&<caiAdsA2.529>The number of entries in the history table."
	::= { adsHistoryGroup 11 }


--adsHistoryTable OBJECT-TYPE
--	SYNTAX SEQUENCE OF AdsHistoryRow
--	ACCESS not-accessible
--	STATUS mandatory
--	DESCRIPTION
--		"&<caiAdsA2.530>A table containing the last enterprise specific traps the agent arised."
--	::= { adsHistoryGroup 12 }


--adsHistoryEntry OBJECT-TYPE
--	SYNTAX AdsHistoryRow
--	ACCESS not-accessible
--	STATUS mandatory
--	DESCRIPTION
--		"&<caiAdsA2.531>The table entry."
--	::= { adsHistoryTable 1 }


--AdsHistoryRow ::=
--	SEQUENCE {
--		adsHistoryTrapName DisplayString,
--		adsHistoryTrapNumber INTEGER,
--		adsHistoryTrapTime DisplayString,
--		adsHistoryTrapVarBind DisplayString
--	}


--adsHistoryTrapName OBJECT-TYPE
--	SYNTAX DisplayString
--	ACCESS read-only
--	STATUS mandatory
--	DESCRIPTION
--		"&<caiAdsA2.532>The name of the trap as defined in the MIB."
--	::= { adsHistoryEntry 1 }


--adsHistoryTrapNumber OBJECT-TYPE
--	SYNTAX INTEGER
--	ACCESS read-only
--	STATUS mandatory
--	DESCRIPTION
--		"&<caiAdsA2.533>The enterprise specific trap type number."
--	::= { adsHistoryEntry 2 }


--adsHistoryTrapTime OBJECT-TYPE
--	SYNTAX DisplayString
--	ACCESS read-only
--	STATUS mandatory
--	DESCRIPTION
--		"&<caiAdsA2.534>The date and time the trap was sent."
--	::= { adsHistoryEntry 3 }


--adsHistoryTrapVarBind OBJECT-TYPE
--	SYNTAX DisplayString
--	ACCESS read-only
--	STATUS mandatory
--	DESCRIPTION
--		"&<caiAdsA2.535>A comma separated list of the varbinds the agent sent with the trap. Each element has the form 'attribute=value'."
--	::= { adsHistoryEntry 4 }



















-- *****************************************************************************
-- Domain Controller Traps
-- *****************************************************************************


adsDCtrlUnknown TRAP-TYPE
	ENTERPRISE caiAdsA2
	DESCRIPTION
		"&<caiAdsA2.536>A watcher of the corresponding status group changed its status to 'unknown'. The varbind list contains the name of the involved resource."
	::= 10980


adsDCtrlOk TRAP-TYPE
	ENTERPRISE caiAdsA2
	DESCRIPTION
		"&<caiAdsA2.537>A watcher of the corresponding status group changed its status to 'ok'. The varbind list contains the name of the involved resource."
	::= 10981


adsDCtrlWarning TRAP-TYPE
	ENTERPRISE caiAdsA2
	DESCRIPTION
		"&<caiAdsA2.538>A watcher of the corresponding status group changed its status to 'warning'. The varbind list contains the name of the involved resource."
	::= 10982


adsDCtrlCritical TRAP-TYPE
	ENTERPRISE caiAdsA2
	DESCRIPTION
		"&<caiAdsA2.539>A watcher of the corresponding status group changed its status to 'critical'. The varbind list contains the name of the involved resource."
	::= 10983


adsDCtrlAdded TRAP-TYPE
	ENTERPRISE caiAdsA2
	DESCRIPTION
		"&<caiAdsA2.540>A watcher was added to the corresponding status group. The varbind list contains the name of the involved resource."
	::= 10986


adsDCtrlDeleted TRAP-TYPE
	ENTERPRISE caiAdsA2
	DESCRIPTION
		"&<caiAdsA2.541>A watcher was removed from the corresponding status group. The varbind list contains the name of the involved resource."
	::= 10987


adsDCtrlInfo TRAP-TYPE
	ENTERPRISE caiAdsA2
	DESCRIPTION
		"&<caiAdsA2.542>A watcher of the corresponding status group changed a substatus. The varbind list contains detailed information in one string."
	::= 10988


adsDCtrlModified TRAP-TYPE
	ENTERPRISE caiAdsA2
	DESCRIPTION
		"&<caiAdsA2.543>The configuration of a watcher of the corresponding status group changed. The varbind list contains the name of the involved resource, the changed attribute with its old value and with its new value."
	::= 10989




-- *****************************************************************************
-- Disk Space Traps
-- *****************************************************************************


adsDskSpUnknown TRAP-TYPE
	ENTERPRISE caiAdsA2
	DESCRIPTION
		"&<caiAdsA2.544>A watcher of the corresponding status group changed its status to 'unknown'. The varbind list contains the name of the involved resource."
	::= 11980


adsDskSpOk TRAP-TYPE
	ENTERPRISE caiAdsA2
	DESCRIPTION
		"&<caiAdsA2.545>A watcher of the corresponding status group changed its status to 'ok'. The varbind list contains the name of the involved resource."
	::= 11981


adsDskSpWarning TRAP-TYPE
	ENTERPRISE caiAdsA2
	DESCRIPTION
		"&<caiAdsA2.546>A watcher of the corresponding status group changed its status to 'warning'. The varbind list contains the name of the involved resource."
	::= 11982


adsDskSpCritical TRAP-TYPE
	ENTERPRISE caiAdsA2
	DESCRIPTION
		"&<caiAdsA2.547>A watcher of the corresponding status group changed its status to 'critical'. The varbind list contains the name of the involved resource."
	::= 11983


adsDskSpAdded TRAP-TYPE
	ENTERPRISE caiAdsA2
	DESCRIPTION
		"&<caiAdsA2.548>A watcher was added to the corresponding status group. The varbind list contains the name of the involved resource."
	::= 11986


adsDskSpDeleted TRAP-TYPE
	ENTERPRISE caiAdsA2
	DESCRIPTION
		"&<caiAdsA2.549>A watcher was removed from the corresponding status group. The varbind list contains the name of the involved resource."
	::= 11987


adsDskSpInfo TRAP-TYPE
	ENTERPRISE caiAdsA2
	DESCRIPTION
		"&<caiAdsA2.550>A watcher of the corresponding status group changed a substatus. The varbind list contains detailed information in one string."
	::= 11988


adsDskSpModified TRAP-TYPE
	ENTERPRISE caiAdsA2
	DESCRIPTION
		"&<caiAdsA2.551>The configuration of a watcher of the corresponding status group changed. The varbind list contains the name of the involved resource, the changed attribute with its old value and with its new value."
	::= 11989




-- *****************************************************************************
-- Active Directory Service Events Traps
-- *****************************************************************************


adsAdsEvUnknown TRAP-TYPE
	ENTERPRISE caiAdsA2
	DESCRIPTION
		"&<caiAdsA2.552>A watcher of the corresponding status group changed its status to 'unknown'. The varbind list contains the name of the involved resource."
	::= 12980


adsAdsEvOk TRAP-TYPE
	ENTERPRISE caiAdsA2
	DESCRIPTION
		"&<caiAdsA2.553>A watcher of the corresponding status group changed its status to 'ok'. The varbind list contains the name of the involved resource."
	::= 12981


adsAdsEvWarning TRAP-TYPE
	ENTERPRISE caiAdsA2
	DESCRIPTION
		"&<caiAdsA2.554>A watcher of the corresponding status group changed its status to 'warning'. The varbind list contains the name of the involved resource."
	::= 12982


adsAdsEvCritical TRAP-TYPE
	ENTERPRISE caiAdsA2
	DESCRIPTION
		"&<caiAdsA2.555>A watcher of the corresponding status group changed its status to 'critical'. The varbind list contains the name of the involved resource."
	::= 12983


adsAdsEvAdded TRAP-TYPE
	ENTERPRISE caiAdsA2
	DESCRIPTION
		"&<caiAdsA2.556>A watcher was added to the corresponding status group. The varbind list contains the name of the involved resource."
	::= 12986


adsAdsEvDeleted TRAP-TYPE
	ENTERPRISE caiAdsA2
	DESCRIPTION
		"&<caiAdsA2.557>A watcher was removed from the corresponding status group. The varbind list contains the name of the involved resource."
	::= 12987


adsAdsEvInfo TRAP-TYPE
	ENTERPRISE caiAdsA2
	DESCRIPTION
		"&<caiAdsA2.558>A watcher of the corresponding status group changed a substatus. The varbind list contains detailed information in one string."
	::= 12988


adsAdsEvModified TRAP-TYPE
	ENTERPRISE caiAdsA2
	DESCRIPTION
		"&<caiAdsA2.559>The configuration of a watcher of the corresponding status group changed. The varbind list contains the name of the involved resource, the changed attribute with its old value and with its new value."
	::= 12989




-- *****************************************************************************
-- Active Directory Service Performance Traps
-- *****************************************************************************


adsAdsPrUnknown TRAP-TYPE
	ENTERPRISE caiAdsA2
	DESCRIPTION
		"&<caiAdsA2.560>A watcher of the corresponding status group changed its status to 'unknown'. The varbind list contains the name of the involved resource."
	::= 13980


adsAdsPrOk TRAP-TYPE
	ENTERPRISE caiAdsA2
	DESCRIPTION
		"&<caiAdsA2.561>A watcher of the corresponding status group changed its status to 'ok'. The varbind list contains the name of the involved resource."
	::= 13981


adsAdsPrWarning TRAP-TYPE
	ENTERPRISE caiAdsA2
	DESCRIPTION
		"&<caiAdsA2.562>A watcher of the corresponding status group changed its status to 'warning'. The varbind list contains the name of the involved resource."
	::= 13982


adsAdsPrCritical TRAP-TYPE
	ENTERPRISE caiAdsA2
	DESCRIPTION
		"&<caiAdsA2.563>A watcher of the corresponding status group changed its status to 'critical'. The varbind list contains the name of the involved resource."
	::= 13983


adsAdsPrAdded TRAP-TYPE
	ENTERPRISE caiAdsA2
	DESCRIPTION
		"&<caiAdsA2.564>A watcher was added to the corresponding status group. The varbind list contains the name of the involved resource."
	::= 13986


adsAdsPrDeleted TRAP-TYPE
	ENTERPRISE caiAdsA2
	DESCRIPTION
		"&<caiAdsA2.565>A watcher was removed from the corresponding status group. The varbind list contains the name of the involved resource."
	::= 13987


adsAdsPrInfo TRAP-TYPE
	ENTERPRISE caiAdsA2
	DESCRIPTION
		"&<caiAdsA2.566>A watcher of the corresponding status group changed a substatus. The varbind list contains detailed information in one string."
	::= 13988


adsAdsPrModified TRAP-TYPE
	ENTERPRISE caiAdsA2
	DESCRIPTION
		"&<caiAdsA2.567>The configuration of a watcher of the corresponding status group changed. The varbind list contains the name of the involved resource, the changed attribute with its old value and with its new value."
	::= 13989




-- *****************************************************************************
-- File Replication Service Events Traps
-- *****************************************************************************


adsFrsEvUnknown TRAP-TYPE
	ENTERPRISE caiAdsA2
	DESCRIPTION
		"&<caiAdsA2.568>A watcher of the corresponding status group changed its status to 'unknown'. The varbind list contains the name of the involved resource."
	::= 14980


adsFrsEvOk TRAP-TYPE
	ENTERPRISE caiAdsA2
	DESCRIPTION
		"&<caiAdsA2.569>A watcher of the corresponding status group changed its status to 'ok'. The varbind list contains the name of the involved resource."
	::= 14981


adsFrsEvWarning TRAP-TYPE
	ENTERPRISE caiAdsA2
	DESCRIPTION
		"&<caiAdsA2.570>A watcher of the corresponding status group changed its status to 'warning'. The varbind list contains the name of the involved resource."
	::= 14982


adsFrsEvCritical TRAP-TYPE
	ENTERPRISE caiAdsA2
	DESCRIPTION
		"&<caiAdsA2.571>A watcher of the corresponding status group changed its status to 'critical'. The varbind list contains the name of the involved resource."
	::= 14983


adsFrsEvAdded TRAP-TYPE
	ENTERPRISE caiAdsA2
	DESCRIPTION
		"&<caiAdsA2.572>A watcher was added to the corresponding status group. The varbind list contains the name of the involved resource."
	::= 14986


adsFrsEvDeleted TRAP-TYPE
	ENTERPRISE caiAdsA2
	DESCRIPTION
		"&<caiAdsA2.573>A watcher was removed from the corresponding status group. The varbind list contains the name of the involved resource."
	::= 14987


adsFrsEvInfo TRAP-TYPE
	ENTERPRISE caiAdsA2
	DESCRIPTION
		"&<caiAdsA2.574>A watcher of the corresponding status group changed a substatus. The varbind list contains detailed information in one string."
	::= 14988


adsFrsEvModified TRAP-TYPE
	ENTERPRISE caiAdsA2
	DESCRIPTION
		"&<caiAdsA2.575>The configuration of a watcher of the corresponding status group changed. The varbind list contains the name of the involved resource, the changed attribute with its old value and with its new value."
	::= 14989




-- *****************************************************************************
-- File Replication Service Performance Traps
-- *****************************************************************************


adsFrsPrUnknown TRAP-TYPE
	ENTERPRISE caiAdsA2
	DESCRIPTION
		"&<caiAdsA2.576>A watcher of the corresponding status group changed its status to 'unknown'. The varbind list contains the name of the involved resource."
	::= 15980


adsFrsPrOk TRAP-TYPE
	ENTERPRISE caiAdsA2
	DESCRIPTION
		"&<caiAdsA2.577>A watcher of the corresponding status group changed its status to 'ok'. The varbind list contains the name of the involved resource."
	::= 15981


adsFrsPrWarning TRAP-TYPE
	ENTERPRISE caiAdsA2
	DESCRIPTION
		"&<caiAdsA2.578>A watcher of the corresponding status group changed its status to 'warning'. The varbind list contains the name of the involved resource."
	::= 15982


adsFrsPrCritical TRAP-TYPE
	ENTERPRISE caiAdsA2
	DESCRIPTION
		"&<caiAdsA2.579>A watcher of the corresponding status group changed its status to 'critical'. The varbind list contains the name of the involved resource."
	::= 15983


adsFrsPrAdded TRAP-TYPE
	ENTERPRISE caiAdsA2
	DESCRIPTION
		"&<caiAdsA2.580>A watcher was added to the corresponding status group. The varbind list contains the name of the involved resource."
	::= 15986


adsFrsPrDeleted TRAP-TYPE
	ENTERPRISE caiAdsA2
	DESCRIPTION
		"&<caiAdsA2.581>A watcher was removed from the corresponding status group. The varbind list contains the name of the involved resource."
	::= 15987


adsFrsPrInfo TRAP-TYPE
	ENTERPRISE caiAdsA2
	DESCRIPTION
		"&<caiAdsA2.582>A watcher of the corresponding status group changed a substatus. The varbind list contains detailed information in one string."
	::= 15988


adsFrsPrModified TRAP-TYPE
	ENTERPRISE caiAdsA2
	DESCRIPTION
		"&<caiAdsA2.583>The configuration of a watcher of the corresponding status group changed. The varbind list contains the name of the involved resource, the changed attribute with its old value and with its new value."
	::= 15989




-- *****************************************************************************
-- Domain Name Service Events Traps
-- *****************************************************************************


adsDnsEvUnknown TRAP-TYPE
	ENTERPRISE caiAdsA2
	DESCRIPTION
		"&<caiAdsA2.584>A watcher of the corresponding status group changed its status to 'unknown'. The varbind list contains the name of the involved resource."
	::= 16980


adsDnsEvOk TRAP-TYPE
	ENTERPRISE caiAdsA2
	DESCRIPTION
		"&<caiAdsA2.585>A watcher of the corresponding status group changed its status to 'ok'. The varbind list contains the name of the involved resource."
	::= 16981


adsDnsEvWarning TRAP-TYPE
	ENTERPRISE caiAdsA2
	DESCRIPTION
		"&<caiAdsA2.586>A watcher of the corresponding status group changed its status to 'warning'. The varbind list contains the name of the involved resource."
	::= 16982


adsDnsEvCritical TRAP-TYPE
	ENTERPRISE caiAdsA2
	DESCRIPTION
		"&<caiAdsA2.587>A watcher of the corresponding status group changed its status to 'critical'. The varbind list contains the name of the involved resource."
	::= 16983


adsDnsEvAdded TRAP-TYPE
	ENTERPRISE caiAdsA2
	DESCRIPTION
		"&<caiAdsA2.588>A watcher was added to the corresponding status group. The varbind list contains the name of the involved resource."
	::= 16986


adsDnsEvDeleted TRAP-TYPE
	ENTERPRISE caiAdsA2
	DESCRIPTION
		"&<caiAdsA2.589>A watcher was removed from the corresponding status group. The varbind list contains the name of the involved resource."
	::= 16987


adsDnsEvInfo TRAP-TYPE
	ENTERPRISE caiAdsA2
	DESCRIPTION
		"&<caiAdsA2.590>A watcher of the corresponding status group changed a substatus. The varbind list contains detailed information in one string."
	::= 16988


adsDnsEvModified TRAP-TYPE
	ENTERPRISE caiAdsA2
	DESCRIPTION
		"&<caiAdsA2.591>The configuration of a watcher of the corresponding status group changed. The varbind list contains the name of the involved resource, the changed attribute with its old value and with its new value."
	::= 16989




-- *****************************************************************************
-- Domain Name Service Performance Traps
-- *****************************************************************************


adsDnsPrUnknown TRAP-TYPE
	ENTERPRISE caiAdsA2
	DESCRIPTION
		"&<caiAdsA2.592>A watcher of the corresponding status group changed its status to 'unknown'. The varbind list contains the name of the involved resource."
	::= 17980


adsDnsPrOk TRAP-TYPE
	ENTERPRISE caiAdsA2
	DESCRIPTION
		"&<caiAdsA2.593>A watcher of the corresponding status group changed its status to 'ok'. The varbind list contains the name of the involved resource."
	::= 17981


adsDnsPrWarning TRAP-TYPE
	ENTERPRISE caiAdsA2
	DESCRIPTION
		"&<caiAdsA2.594>A watcher of the corresponding status group changed its status to 'warning'. The varbind list contains the name of the involved resource."
	::= 17982


adsDnsPrCritical TRAP-TYPE
	ENTERPRISE caiAdsA2
	DESCRIPTION
		"&<caiAdsA2.595>A watcher of the corresponding status group changed its status to 'critical'. The varbind list contains the name of the involved resource."
	::= 17983


adsDnsPrAdded TRAP-TYPE
	ENTERPRISE caiAdsA2
	DESCRIPTION
		"&<caiAdsA2.596>A watcher was added to the corresponding status group. The varbind list contains the name of the involved resource."
	::= 17986


adsDnsPrDeleted TRAP-TYPE
	ENTERPRISE caiAdsA2
	DESCRIPTION
		"&<caiAdsA2.597>A watcher was removed from the corresponding status group. The varbind list contains the name of the involved resource."
	::= 17987


adsDnsPrInfo TRAP-TYPE
	ENTERPRISE caiAdsA2
	DESCRIPTION
		"&<caiAdsA2.598>A watcher of the corresponding status group changed a substatus. The varbind list contains detailed information in one string."
	::= 17988


adsDnsPrModified TRAP-TYPE
	ENTERPRISE caiAdsA2
	DESCRIPTION
		"&<caiAdsA2.599>The configuration of a watcher of the corresponding status group changed. The varbind list contains the name of the involved resource, the changed attribute with its old value and with its new value."
	::= 17989


END
