-- ===========================================================
-- Copyright (C) 2009 by HUAWEI TECHNOLOGIES. All rights reserved.
--
-- Description: HUAWEI-CLOCK-MIB
-- Reference:     
-- Version: 1.0
-- History: 
-- ===========================================================

    HUAWEI-CLOCK-MIB DEFINITIONS ::= BEGIN
 
        IMPORTS
            hwDatacomm            
                FROM HUAWEI-MIB            
            InterfaceIndex            
                FROM IF-MIB
            PhysicalIndex
                FROM ENTITY-MIB            
            EnabledStatus            
                FROM P-BRIDGE-MIB            
            OBJECT-GROUP, MODULE-COMPLIANCE, NOTIFICATION-GROUP            
                FROM SNMPv2-CONF            
            Integer32, OBJECT-TYPE, MODULE-IDENTITY, NOTIFICATION-TYPE            
                FROM SNMPv2-SMI
            RowStatus            
                FROM SNMPv2-TC;
    
        hwClockMIB MODULE-IDENTITY 
            LAST-UPDATED "200902051608Z"
            ORGANIZATION 
                "Huawei Technologies Co., Ltd.
                "
            CONTACT-INFO 
                "
                NanJing Institute,Huawei Technologies Co.,Ltd.
                HuiHong Mansion,No.91 BaiXia Rd.
                NanJing, P.R. of China
                Zipcode:210001
                 
                Http://www.huawei.com                                       
                E-mail:support@huawei.com "
            DESCRIPTION 
                "The MIB contains objects of module clock management and 1588 interface."
            ::= { hwDatacomm 186 }

        
    
    
--
-- Node definitions
--
    
        hwClockManageObjects OBJECT IDENTIFIER ::= { hwClockMIB 1 }

        
        hwClockGlobalObjects OBJECT IDENTIFIER ::= { hwClockManageObjects 1 }

        
        hwClockSourceEthClkEnable OBJECT-TYPE
            SYNTAX EnabledStatus
            MAX-ACCESS read-write
            STATUS current
            DESCRIPTION
                "The flag indicates that the ethernet clock is globally enabled."
            ::= { hwClockGlobalObjects 1 }

        
        hwClockSourceSsmUnknown OBJECT-TYPE
            SYNTAX INTEGER
                {
                prc(2),
                ssua(4),
                ssub(8),
                sec(11),
                dnu(15)
                }
            MAX-ACCESS read-write
            STATUS current
            DESCRIPTION
                "The quality level of unknown SSM."     
            ::= { hwClockGlobalObjects 2 }

        
        hwClockSourceSysClkWorkMode OBJECT-TYPE
            SYNTAX INTEGER
                {
                trace(1),
                hold(2),
                freeoscillate(3)
                }
            MAX-ACCESS read-only
            STATUS current
            DESCRIPTION
                "The work mode of system clock."
            ::= { hwClockGlobalObjects 3 }

        
        hwClockSourceForceCloseEnableStatus OBJECT-TYPE
            SYNTAX EnabledStatus
            MAX-ACCESS read-write
            STATUS current
            DESCRIPTION
                "The enable status of export forced close."
            ::= { hwClockGlobalObjects 4 }

        
        hwClockSourceSsmControl OBJECT-TYPE
            SYNTAX INTEGER
                {
                on(1),
                off(2),
                extend(3)
                }
            MAX-ACCESS read-write
            STATUS current
            DESCRIPTION
                "The flag whether SSM is concerned with the clock source selection."
            ::= { hwClockGlobalObjects 5 }

        
        hwClockSourceHoldMode OBJECT-TYPE
            SYNTAX INTEGER
                {
                hold24Hours(1),
                holdForever(2)
                }
            MAX-ACCESS read-only
            STATUS current
            DESCRIPTION
                "The hold mode of clock source."
            ::= { hwClockGlobalObjects 6 }

        
        hwClockSourceFreqCheckEnable OBJECT-TYPE
            SYNTAX EnabledStatus
            MAX-ACCESS read-write
            STATUS current
            DESCRIPTION
                "The enable flag of frequency check."
            ::= { hwClockGlobalObjects 7 }

        
        hwClockSourceFreqCheckLeftRange OBJECT-TYPE
            SYNTAX Integer32 (50..1000)
            MAX-ACCESS read-write
            STATUS current
            DESCRIPTION
                "The left range of frequency check, unit in 0.01ppm."
            ::= { hwClockGlobalObjects 8 }

        
        hwClockSourceFreqCheckRightRange OBJECT-TYPE
            SYNTAX Integer32 (50..1000)
            MAX-ACCESS read-write
            STATUS current
            DESCRIPTION
                "The right range of frequency check, unit in 0.01ppm."
            ::= { hwClockGlobalObjects 9 }

        
        hwClockSourceRetrieveMode OBJECT-TYPE
            SYNTAX INTEGER
                {
                retrieve(1),
                noRetrieve(2)
                }
            MAX-ACCESS read-write
            STATUS current
            DESCRIPTION
                "The retrieve mode of clock source."
            ::= { hwClockGlobalObjects 10 }

        
        hwClockTimeUsedSource OBJECT-TYPE
            SYNTAX INTEGER
                {
                srcDclsTimeBit0(1),
                srcDclsTimeBit1(2),
                src1ppsTodBit0(3),
                src1ppsTodBit1(4),
                srcPtp(5),
                srcFreeRun(6)
                }
            MAX-ACCESS read-write
            STATUS current
            DESCRIPTION
                "The clock time used source."
            ::= { hwClockGlobalObjects 11 }

        
        hwClockExtTimeInputType OBJECT-TYPE
            SYNTAX INTEGER
                {
                typeDclsTime(1),
                type1ppsTodRs232(2),
                type1ppsTodGps(3),
                typeNone(4)
                }
            MAX-ACCESS read-write
            STATUS current
            DESCRIPTION
                "The input time type of clock extern time."
            ::= { hwClockGlobalObjects 12 }

        
        hwClockExtTimeOutputType OBJECT-TYPE
            SYNTAX INTEGER
                {
                typeDclsTime(1),
                type1ppsTodRs232(2),
                type1ppsTodGps(3),
                typeNone(4)
                }
            MAX-ACCESS read-write
            STATUS current
            DESCRIPTION
                "The output time type of clock extern time."
            ::= { hwClockGlobalObjects 13 }

        
        hwClockSourceSelTable OBJECT-TYPE
            SYNTAX SEQUENCE OF HwClockSourceSelEntry
            MAX-ACCESS not-accessible
            STATUS current
            DESCRIPTION
                "The system clock source selection table."
            ::= { hwClockManageObjects 2 }

        
        hwClockSourceSelEntry OBJECT-TYPE
            SYNTAX HwClockSourceSelEntry
            MAX-ACCESS not-accessible
            STATUS current
            DESCRIPTION
                "The entry of system clock source selection table."
            INDEX { hwClockSourceSelChassisIndex, hwClockSourceSelType }
            ::= { hwClockSourceSelTable 1 }

        
        HwClockSourceSelEntry ::=
            SEQUENCE { 
                hwClockSourceSelChassisIndex
                    PhysicalIndex,
                hwClockSourceSelType
                    Integer32,
                hwClockSourceSelMode
                    INTEGER,
                hwClockSourceSelSourceId
                    Integer32
             }

        hwClockSourceSelChassisIndex OBJECT-TYPE
            SYNTAX PhysicalIndex
            MAX-ACCESS not-accessible
            STATUS current
            DESCRIPTION
                "The chassis index."
            ::= { hwClockSourceSelEntry 1 }

        
        hwClockSourceSelType OBJECT-TYPE
            SYNTAX Integer32 (1..100)
            MAX-ACCESS not-accessible
            STATUS current
            DESCRIPTION
                "The select type."
            ::= { hwClockSourceSelEntry 2 }

        
        hwClockSourceSelMode OBJECT-TYPE
            SYNTAX INTEGER
                {
                auto(1),
                manual(2),
                force(3)
                }
            MAX-ACCESS read-create
            STATUS current
            DESCRIPTION
                "The mode of clock source selection."
            ::= { hwClockSourceSelEntry 3 }

        
        hwClockSourceSelSourceId OBJECT-TYPE
            SYNTAX Integer32
            MAX-ACCESS read-create
            STATUS current
            DESCRIPTION
                "The source ID of the clock traced."
            ::= { hwClockSourceSelEntry 4 }

        
        hwClockSourceCfgTable OBJECT-TYPE
            SYNTAX SEQUENCE OF HwClockSourceCfgEntry
            MAX-ACCESS not-accessible
            STATUS current
            DESCRIPTION
                "The clock source config table."
            ::= { hwClockManageObjects 3 }

        
        hwClockSourceCfgEntry OBJECT-TYPE
            SYNTAX HwClockSourceCfgEntry
            MAX-ACCESS not-accessible
            STATUS current
            DESCRIPTION
                "The entry of clock source config table."
            INDEX { hwClockCfgChassisIndex, hwClockCfgSourceIndex }
            ::= { hwClockSourceCfgTable 1 }

        
        HwClockSourceCfgEntry ::=
            SEQUENCE { 
                hwClockCfgChassisIndex
                    PhysicalIndex,
                hwClockCfgSourceIndex
                    Integer32,
                hwClockCfgSourceId
                    Integer32,
                hwClockCfgSourceDescr
                    OCTET STRING,
                hwClockCfgWtrTime
                    Integer32,
                hwClockCfgBadDetect
                    EnabledStatus,
                hwClockCfgSystemPriority
                    Integer32,
                hwClockCfgBits0Priority
                    Integer32,
                hwClockCfgBits1Priority
                    Integer32,
                hwClockCfgSystemLockOut
                    Integer32,
                hwClockCfgBits0LockOut
                    Integer32,
                hwClockCfgBits1LockOut
                    Integer32,
                hwClockCfgSourceSsm
                    INTEGER,
                hwClockCfgSourceSsmSetMode
                    INTEGER,
                hwClockCfgExportEnableStatus
                    EnabledStatus,
                hwClockCfgSwiEnableStatus
                    EnabledStatus,
                hwClockCfgSourceState
                    INTEGER,
                hwClockCfgSsmThreshold
                    INTEGER,
                hwClockCfgSourceS1Id
                    Integer32,
                hwClockCfgFreqCheckResult
                    Integer32,
                hwClockCfgHoldOffTime
                    Integer32,
                hwClockCfgPriRvtEnableStatus
                    EnabledStatus,
                hwClockCfgSwitchCondition
                    INTEGER,
                hwClockCfgClkSourceType
                    INTEGER
             }

        hwClockCfgChassisIndex OBJECT-TYPE
            SYNTAX PhysicalIndex
            MAX-ACCESS not-accessible
            STATUS current
            DESCRIPTION
                "The index of the chassis whitch the clock source belongs to."
            ::= { hwClockSourceCfgEntry 1 }

        
        hwClockCfgSourceIndex OBJECT-TYPE
            SYNTAX Integer32 (1..20)
            MAX-ACCESS not-accessible
            STATUS current
            DESCRIPTION
                "The clock source index."
            ::= { hwClockSourceCfgEntry 2 }

        
        hwClockCfgSourceId OBJECT-TYPE
            SYNTAX Integer32
            MAX-ACCESS read-only
            STATUS current
            DESCRIPTION
                "The clock source ID."
            ::= { hwClockSourceCfgEntry 3 }

        
        hwClockCfgSourceDescr OBJECT-TYPE
            SYNTAX OCTET STRING
            MAX-ACCESS read-only
            STATUS current
            DESCRIPTION
                "The clock source description."
            ::= { hwClockSourceCfgEntry 4 }

        
        hwClockCfgWtrTime OBJECT-TYPE
            SYNTAX Integer32 (0..12)
            MAX-ACCESS read-write
            STATUS current
            DESCRIPTION
                "The waiting for restore time of clock source."
            ::= { hwClockSourceCfgEntry 5 }

        
        hwClockCfgBadDetect OBJECT-TYPE
            SYNTAX EnabledStatus
            MAX-ACCESS read-write
            STATUS current
            DESCRIPTION
                "The enable status of clock source bad detecting."
            ::= { hwClockSourceCfgEntry 6 }

        
        hwClockCfgSystemPriority OBJECT-TYPE
            SYNTAX Integer32 (0..255)
            MAX-ACCESS read-write
            STATUS current
            DESCRIPTION
                "The priority of system clock source."
            ::= { hwClockSourceCfgEntry 7 }

        
        hwClockCfgBits0Priority OBJECT-TYPE
            SYNTAX Integer32 (0..255)
            MAX-ACCESS read-write
            STATUS current
            DESCRIPTION
                "The priority of BITS0 clock source."
            ::= { hwClockSourceCfgEntry 8 }

        
        hwClockCfgBits1Priority OBJECT-TYPE
            SYNTAX Integer32 (0..255)
            MAX-ACCESS read-write
            STATUS current
            DESCRIPTION
                "The priority of BITS1 clock source."
            ::= { hwClockSourceCfgEntry 9 }

        
        hwClockCfgSystemLockOut OBJECT-TYPE
            SYNTAX Integer32
            MAX-ACCESS read-write
            STATUS current
            DESCRIPTION
                "The lock out of system clock source."
            ::= { hwClockSourceCfgEntry 10 }

        
        hwClockCfgBits0LockOut OBJECT-TYPE
            SYNTAX Integer32
            MAX-ACCESS read-write
            STATUS current
            DESCRIPTION
                "The lock out of BITS0 clock source."
            ::= { hwClockSourceCfgEntry 11 }

        
        hwClockCfgBits1LockOut OBJECT-TYPE
            SYNTAX Integer32
            MAX-ACCESS read-write
            STATUS current
            DESCRIPTION
                "The lock out of BITS1 clock source."
            ::= { hwClockSourceCfgEntry 12 }

        
        hwClockCfgSourceSsm OBJECT-TYPE
            SYNTAX INTEGER
                {
                ssmPrc(1),
                ssmSsut(2),
                ssmSsul(3),
                ssmSec(4),
                ssmDnu(5),
                ssmUnknown(6)
                }
            MAX-ACCESS read-write
            STATUS current
            DESCRIPTION
                "The SSM quality of clock source."
            ::= { hwClockSourceCfgEntry 13 }

        
        hwClockCfgSourceSsmSetMode OBJECT-TYPE
            SYNTAX INTEGER
                {
                manual(1),
                auto(2)
                }
            MAX-ACCESS read-write
            STATUS current
            DESCRIPTION
                "The set mode of SSM."
            ::= { hwClockSourceCfgEntry 14 }

        
        hwClockCfgExportEnableStatus OBJECT-TYPE
            SYNTAX EnabledStatus
            MAX-ACCESS read-write
            STATUS current
            DESCRIPTION
                "The enable status of clock source export."
            ::= { hwClockSourceCfgEntry 15 }

        
        hwClockCfgSwiEnableStatus OBJECT-TYPE
            SYNTAX EnabledStatus
            MAX-ACCESS read-write
            STATUS current
            DESCRIPTION
                "he enable status of clock source switch."
            ::= { hwClockSourceCfgEntry 16 }

        
        hwClockCfgSourceState OBJECT-TYPE
            SYNTAX INTEGER
                {
                normal(1),
                abnormal(2)
                }
            MAX-ACCESS read-write
            STATUS current
            DESCRIPTION
                "The state of clock source."
            ::= { hwClockSourceCfgEntry 17 }

        
        hwClockCfgSsmThreshold OBJECT-TYPE
            SYNTAX INTEGER
                {
                qlDnu(1),
                qlSec(2),
                qlSsub(3),
                qlSsua(4),
                qlPrc(5)
                }
            MAX-ACCESS read-write
            STATUS current
            DESCRIPTION
                "The SSM quality level threshold of clock source."
            ::= { hwClockSourceCfgEntry 18 }

        
        hwClockCfgSourceS1Id OBJECT-TYPE
            SYNTAX Integer32 (0..255)
            MAX-ACCESS read-only
            STATUS current
            DESCRIPTION
                "The S1 byte of the clock."
            ::= { hwClockSourceCfgEntry 19 }

        
        hwClockCfgFreqCheckResult OBJECT-TYPE
            SYNTAX Integer32
            MAX-ACCESS read-write
            STATUS current
            DESCRIPTION
                "The result of frequency check, unit in 0.01ppm."
            ::= { hwClockSourceCfgEntry 20 }

        
        hwClockCfgHoldOffTime OBJECT-TYPE
            SYNTAX Integer32 (3..18)
            MAX-ACCESS read-write
            STATUS current
            DESCRIPTION
                "The hold off time of clock, unit in 100ms."
            ::= { hwClockSourceCfgEntry 21 }

        
        hwClockCfgPriRvtEnableStatus OBJECT-TYPE
            SYNTAX EnabledStatus
            MAX-ACCESS read-write
            STATUS current
            DESCRIPTION
                "The enable status of switch according priority."
            ::= { hwClockSourceCfgEntry 22 }

        
        hwClockCfgSwitchCondition OBJECT-TYPE
            SYNTAX INTEGER
                {
                noSwitch(1),
                switch(2)
                }
            MAX-ACCESS read-write
            STATUS current
            DESCRIPTION
                "The condition of clock switch."
            ::= { hwClockSourceCfgEntry 23 }

        
        hwClockCfgClkSourceType OBJECT-TYPE
            SYNTAX INTEGER
                {
                bits(1),
                line(2),
                inner(3),
                system(4)
                }
            MAX-ACCESS read-only
            STATUS current
            DESCRIPTION
                "The type of clock source."
            ::= { hwClockSourceCfgEntry 24 }

        
        hwClockBitsCfgTable OBJECT-TYPE
            SYNTAX SEQUENCE OF HwClockBitsCfgEntry
            MAX-ACCESS not-accessible
            STATUS current
            DESCRIPTION
                "The clock bits congfig table."
            ::= { hwClockManageObjects 4 }

        
        hwClockBitsCfgEntry OBJECT-TYPE
            SYNTAX HwClockBitsCfgEntry
            MAX-ACCESS not-accessible
            STATUS current
            DESCRIPTION
                "The entry of clock bits congfig table."
            INDEX { hwClockBitsCfgChassisIndex, hwClockBitsCfgBitsIndex }
            ::= { hwClockBitsCfgTable 1 }

        
        HwClockBitsCfgEntry ::=
            SEQUENCE { 
                hwClockBitsCfgChassisIndex
                    PhysicalIndex,
                hwClockBitsCfgBitsIndex
                    Integer32,
                hwClockBitsCfgName
                    OCTET STRING,
                hwClockBitsCfgBitsPortType
                    INTEGER,
                hwClockBitsCfgBitsType
                    INTEGER,
                hwClockBitsCfgDirection
                    INTEGER,
                hwClockBitsCfgRecvSaBit
                    INTEGER,
                hwClockBitsCfgSendSaBit
                    INTEGER,
                hwClockBitsCfgForceOutS1
                    INTEGER,
                hwClockBitsCfgSaBit
                    INTEGER,
                hwClockBitsCfgInputMode
                    INTEGER,
                hwClockBitsCfgOutputMode
                    INTEGER,
                hwClockBitsCfgInvalidCond
                    INTEGER,
                hwClockBitsCfgSourceId
                    Integer32,
                hwClockBitsCfgTodFormat
                    INTEGER
             }

        hwClockBitsCfgChassisIndex OBJECT-TYPE
            SYNTAX PhysicalIndex
            MAX-ACCESS not-accessible
            STATUS current
            DESCRIPTION
                "The index of the chassis whitch the clock source belongs to."
            ::= { hwClockBitsCfgEntry 1 }

        
        hwClockBitsCfgBitsIndex OBJECT-TYPE
            SYNTAX Integer32 (1..10)
            MAX-ACCESS not-accessible
            STATUS current
            DESCRIPTION
                "The index of BITS clock."
            ::= { hwClockBitsCfgEntry 2 }

        
        hwClockBitsCfgName OBJECT-TYPE
            SYNTAX OCTET STRING
            MAX-ACCESS read-only
            STATUS current
            DESCRIPTION
                "The name of clock."
            ::= { hwClockBitsCfgEntry 3 }

        
        hwClockBitsCfgBitsPortType OBJECT-TYPE
            SYNTAX INTEGER
                {
                portRj45(1),
                portSMB(2)
                }
            MAX-ACCESS read-only
            STATUS current
            DESCRIPTION
                "The BITS port type."
            ::= { hwClockBitsCfgEntry 4 }

        
        hwClockBitsCfgBitsType OBJECT-TYPE
            SYNTAX INTEGER
                {
                type2Mbps(0),
                type2Mhz(1),
                typeDclsTime(2),
                type1ppsTod(3),
                none(4)
                }
            MAX-ACCESS read-write
            STATUS current
            DESCRIPTION
                "The BITS type."
            ::= { hwClockBitsCfgEntry 5 }

        
        hwClockBitsCfgDirection OBJECT-TYPE
            SYNTAX INTEGER
                {
                in(1),
                out(2),
                inAndOut(3),
                none(4)
                }
            MAX-ACCESS read-write
            STATUS current
            DESCRIPTION
                "The direction of BITS."
            ::= { hwClockBitsCfgEntry 6 }

        
        hwClockBitsCfgRecvSaBit OBJECT-TYPE
            SYNTAX INTEGER
                {
                sa4(4),
                sa5(5),
                sa6(6),
                sa7(7),
                sa8(8)
                }
            MAX-ACCESS read-write
            STATUS current
            DESCRIPTION
                "The received SA bit."
            ::= { hwClockBitsCfgEntry 7 }

        
        hwClockBitsCfgSendSaBit OBJECT-TYPE
            SYNTAX INTEGER
                {
                sa4(4),
                sa5(5),
                sa6(6),
                sa7(7),
                sa8(8)
                }
            MAX-ACCESS read-write
            STATUS current
            DESCRIPTION
                "The sent SA bit."
            ::= { hwClockBitsCfgEntry 8 }

        
        hwClockBitsCfgForceOutS1 OBJECT-TYPE
            SYNTAX INTEGER
                {
                unk(0),
                prc(2),
                ssua(4),
                ssub(8),
                sec(11),
                dnu(15)
                }
            MAX-ACCESS read-write
            STATUS current
            DESCRIPTION
                "The S1 byte of forcing out."
            ::= { hwClockBitsCfgEntry 9 }

        
        hwClockBitsCfgSaBit OBJECT-TYPE
            SYNTAX INTEGER
                {
                sa4(4),
                sa5(5),
                sa6(6),
                sa7(7),
                sa8(8)
                }
            MAX-ACCESS read-write
            STATUS current
            DESCRIPTION
                "The SA bit of SSM information."
            ::= { hwClockBitsCfgEntry 10 }

        
        hwClockBitsCfgInputMode OBJECT-TYPE
            SYNTAX INTEGER
                {
                clk2MBits(0),
                clk2MHz(1),
                dclsTime(2)
                }
            MAX-ACCESS read-write
            STATUS current
            DESCRIPTION
                "The input mode of clock source."
            ::= { hwClockBitsCfgEntry 11 }

        
        hwClockBitsCfgOutputMode OBJECT-TYPE
            SYNTAX INTEGER
                {
                clk2MBits(0),
                clk2MHz(1),
                dclsTime(2)
                }
            MAX-ACCESS read-write
            STATUS current
            DESCRIPTION
                "The output mode of clock source."
            ::= { hwClockBitsCfgEntry 12 }

        
        hwClockBitsCfgInvalidCond OBJECT-TYPE
            SYNTAX INTEGER
                {
                no(1),
                ais(2),
                lof(3)
                }
            MAX-ACCESS read-write
            STATUS current
            DESCRIPTION
                "The invalid condition of clock source."
            ::= { hwClockBitsCfgEntry 13 }

        
        hwClockBitsCfgSourceId OBJECT-TYPE
            SYNTAX Integer32
            MAX-ACCESS read-only
            STATUS current
            DESCRIPTION
                "The clock source ID."
            ::= { hwClockBitsCfgEntry 14 }

        hwClockBitsCfgTodFormat OBJECT-TYPE
            SYNTAX INTEGER
                {
                nmea(1),
                ubx(2),
                none(3)
                }
            MAX-ACCESS read-write
            STATUS current
            DESCRIPTION
                "The tod signal of clock source."
            ::= { hwClockBitsCfgEntry 15 }
            
        hwClockPortCfgTable OBJECT-TYPE
            SYNTAX SEQUENCE OF HwClockPortCfgEntry
            MAX-ACCESS not-accessible
            STATUS current
            DESCRIPTION
                "The clock port config table."
            ::= { hwClockManageObjects 5 }

        
        hwClockPortCfgEntry OBJECT-TYPE
            SYNTAX HwClockPortCfgEntry
            MAX-ACCESS not-accessible
            STATUS current
            DESCRIPTION
                "The entry of clock port config table."
            INDEX { hwClockPortCfgIfIndex }
            ::= { hwClockPortCfgTable 1 }

        
        HwClockPortCfgEntry ::=
            SEQUENCE { 
                hwClockPortCfgIfIndex
                    InterfaceIndex,
                hwClockPortCfgLeftFramePri
                    Integer32,
                hwClockPortCfgRightFramePri
                    Integer32,
                hwClockPortCfgForceOutS1
                    Integer32
             }

        hwClockPortCfgIfIndex OBJECT-TYPE
            SYNTAX InterfaceIndex
            MAX-ACCESS not-accessible
            STATUS current
            DESCRIPTION
                "The interface index."
            ::= { hwClockPortCfgEntry 1 }

        
        hwClockPortCfgLeftFramePri OBJECT-TYPE
            SYNTAX Integer32 (0..255)
            MAX-ACCESS read-write
            STATUS current
            DESCRIPTION
                "The clock priority of left frame."
            ::= { hwClockPortCfgEntry 2 }

        
        hwClockPortCfgRightFramePri OBJECT-TYPE
            SYNTAX Integer32 (0..255)
            MAX-ACCESS read-write
            STATUS current
            DESCRIPTION
                "The clock priority of right frame."
            ::= { hwClockPortCfgEntry 3 }

        
        hwClockPortCfgForceOutS1 OBJECT-TYPE
            SYNTAX Integer32 (0..255)
            MAX-ACCESS read-write
            STATUS current
            DESCRIPTION
                "The S1 byte of forcing out."
            ::= { hwClockPortCfgEntry 4 }

        
        hwClockLineClkCfgTable OBJECT-TYPE
            SYNTAX SEQUENCE OF HwClockLineClkCfgEntry
            MAX-ACCESS not-accessible
            STATUS current
            DESCRIPTION
                "The line clock config table."
            ::= { hwClockManageObjects 6 }

        
        hwClockLineClkCfgEntry OBJECT-TYPE
            SYNTAX HwClockLineClkCfgEntry
            MAX-ACCESS not-accessible
            STATUS current
            DESCRIPTION
                "The entry of line clock config table."
            INDEX { hwClockLineClkCfgChassisIndex, hwClockLineClkCfgSlotIndex }
            ::= { hwClockLineClkCfgTable 1 }

        
        HwClockLineClkCfgEntry ::=
            SEQUENCE { 
                hwClockLineClkCfgChassisIndex
                    PhysicalIndex,
                hwClockLineClkCfgSlotIndex
                    Integer32,
                hwClockLineClkCfgCardId
                    Integer32,
                hwClockLineClkCfgPortId
                    Integer32,
                hwClockLineClkCfgRecvS1
                    Integer32,
                hwClockLineClkCfgSendS1
                    Integer32
             }

        hwClockLineClkCfgChassisIndex OBJECT-TYPE
            SYNTAX PhysicalIndex
            MAX-ACCESS not-accessible
            STATUS current
            DESCRIPTION
                "The chassis index."
            ::= { hwClockLineClkCfgEntry 1 }

        
        hwClockLineClkCfgSlotIndex OBJECT-TYPE
            SYNTAX Integer32 (1..200)
            MAX-ACCESS not-accessible
            STATUS current
            DESCRIPTION
                "The slot index of the line clock."
            ::= { hwClockLineClkCfgEntry 2 }

        
        hwClockLineClkCfgCardId OBJECT-TYPE
            SYNTAX Integer32
            MAX-ACCESS read-create
            STATUS current
            DESCRIPTION
                "The card index witch is seleced to provide line clock."
            ::= { hwClockLineClkCfgEntry 3 }

        
        hwClockLineClkCfgPortId OBJECT-TYPE
            SYNTAX Integer32
            MAX-ACCESS read-create
            STATUS current
            DESCRIPTION
                "The port index witch is seleced to provide line clock."
            ::= { hwClockLineClkCfgEntry 4 }

        
        hwClockLineClkCfgRecvS1 OBJECT-TYPE
            SYNTAX Integer32
            MAX-ACCESS read-only
            STATUS current
            DESCRIPTION
                "The S1 byte value received."
            ::= { hwClockLineClkCfgEntry 5 }

        
        hwClockLineClkCfgSendS1 OBJECT-TYPE
            SYNTAX Integer32
            MAX-ACCESS read-create
            STATUS current
            DESCRIPTION
                "The S1 byte value sent."
            ::= { hwClockLineClkCfgEntry 6 }

        
        hwClockTrapOid OBJECT IDENTIFIER ::= { hwClockManageObjects 7 }

        
        hwClockLastSourceName OBJECT-TYPE
            SYNTAX OCTET STRING
            MAX-ACCESS accessible-for-notify
            STATUS current
            DESCRIPTION
                "The last clock source name."
            ::= { hwClockTrapOid 1 }

        
        hwClockCurSourceName OBJECT-TYPE
            SYNTAX OCTET STRING
            MAX-ACCESS accessible-for-notify
            STATUS current
            DESCRIPTION
                "The current clock source name."
            ::= { hwClockTrapOid 2 }

        
        hwClockSourceOldLockMode OBJECT-TYPE
            SYNTAX INTEGER
                {
                freeRun(0),
                fastLock(1),
                lock(2),
                hold(3),
                freeRunJudge(16),
                holdJudge(19)
                }
            MAX-ACCESS accessible-for-notify
            STATUS current
            DESCRIPTION
                "The old lock mode of clock source."
            ::= { hwClockTrapOid 3 }

        
        hwClockChassisId OBJECT-TYPE
            SYNTAX Integer32
            MAX-ACCESS accessible-for-notify
            STATUS current
            DESCRIPTION
                "The chassis ID."
            ::= { hwClockTrapOid 4 }

        
        hwClockOldSourceState OBJECT-TYPE
            SYNTAX INTEGER
                {
                 initial(0), 
                 normal(1), 
                 abnormal(2), 
                 wtr(3),
                 holdoff(4)
                }
            MAX-ACCESS accessible-for-notify
            STATUS current
            DESCRIPTION
                "The old state of clock source."
            ::= { hwClockTrapOid 5 }
                    
                    
        hwClockPllId OBJECT-TYPE
            SYNTAX INTEGER
                {
                system(1),
                sync2M-1(2),
                sync2M-2(3)
                }
            MAX-ACCESS accessible-for-notify
            STATUS current
            DESCRIPTION
                "The id of pll."
            ::= { hwClockTrapOid 6 }
                     
        hwClockAttributeOutValue OBJECT-TYPE
            SYNTAX INTEGER
                {
                unk(0),
                prc(2),
                ssua(4),
                ssub(8),
                sec(11),
                dnu(15)
                }

            MAX-ACCESS accessible-for-notify
            STATUS current
            DESCRIPTION
                "The current output value."
            ::= { hwClockTrapOid 7 }
                 
        hwClockNotifications OBJECT IDENTIFIER ::= { hwClockManageObjects 8 }

        
        hwClockSourceSwitch NOTIFICATION-TYPE
            OBJECTS {hwClockChassisId, hwClockPllId, hwClockLastSourceName, hwClockCurSourceName, hwClockSrcSelMode }
            STATUS current
            DESCRIPTION 
                "Clock source switch notification."
            ::= { hwClockNotifications 1 }

        
        hwClockSourceSysClkLockModeChange NOTIFICATION-TYPE
            OBJECTS { hwClockChassisId, hwClockSourceOldLockMode, hwClockAttributeSysClkLockMode }
            STATUS current
            DESCRIPTION 
                "The lock mode of system clock source change notification."
            ::= { hwClockNotifications 2 }

        
        hwClockSourceStateChange NOTIFICATION-TYPE
            OBJECTS { hwClockChassisId, hwClockCurSourceName, hwClockOldSourceState, hwClockSrcCfgSourceState }
            STATUS current
            DESCRIPTION 
                "The state of clock source change notification."
            ::= { hwClockNotifications 3 }

        
        -- 1.3.6.1.4.1.2011.5.25.186.1.8.4
        hwClockSourceStateResume NOTIFICATION-TYPE
            OBJECTS { hwClockChassisId, hwClockCurSourceName, hwClockOldSourceState, hwClockSrcCfgSourceState }
            STATUS current
            DESCRIPTION 
                "The state of clock source resume notification."
            ::= { hwClockNotifications 4 }

        
        -- 1.3.6.1.4.1.2011.5.25.186.1.8.5
        hwClockSourceFreqCheck NOTIFICATION-TYPE
            OBJECTS { hwClockChassisId, hwClockSrcCfgSourceDescr, hwClockSrcCfgFreqCheckResult }
            STATUS current
            DESCRIPTION 
                "The result of clock source frequnce check abnormal notification."
            ::= { hwClockNotifications 5 }

        
        -- 1.3.6.1.4.1.2011.5.25.186.1.8.6
        hwClockSourceOutputBelowThreshold NOTIFICATION-TYPE
            OBJECTS { hwClockChassisId, hwClockPllId, hwClockAttributeOutThreshold, hwClockAttributeOutValue }
            STATUS current
            DESCRIPTION 
                "The SSM of output below threshold notification."
            ::= { hwClockNotifications 6 }

        
        -- 1.3.6.1.4.1.2011.5.25.186.1.9
        hwClockAttributeTable OBJECT-TYPE
            SYNTAX SEQUENCE OF HwClockAttributeEntry
            MAX-ACCESS not-accessible
            STATUS current
            DESCRIPTION
                "The clock Attribute table."
            ::= { hwClockManageObjects 9 }

        
        -- 1.3.6.1.4.1.2011.5.25.186.1.9.1
        hwClockAttributeEntry OBJECT-TYPE
            SYNTAX HwClockAttributeEntry
            MAX-ACCESS not-accessible
            STATUS current
            DESCRIPTION
                "The entry of clock Attribute table."
            INDEX { hwClockAttributeChassisIndex }
            ::= { hwClockAttributeTable 1 }

        
        HwClockAttributeEntry ::=
            SEQUENCE { 
                hwClockAttributeChassisIndex
                    PhysicalIndex,
                hwClockAttributeSysClkRunMode
                    INTEGER,
                hwClockAttributeSsmControl
                    INTEGER,
                hwClockAttributeFreqCheckEnable
                    EnabledStatus,
                hwClockAttributeRetrieveMode
                    INTEGER,
                hwClockAttributeWtrTime
                    Integer32,
                hwClockAttributeHoldOffTime
                    Integer32,
                hwClockAttributeOutThreshold
                    INTEGER, 
                hwClockAttributeSysMaxOutSsm
                    INTEGER, 
                hwClockAttribute2M1MaxOutSsm
                    INTEGER,
                hwClockAttribute2M2MaxOutSsm
                    INTEGER,
                hwClockAttributeSysClkLockMode
                    INTEGER
             }

        -- 1.3.6.1.4.1.2011.5.25.186.1.9.1.1
        hwClockAttributeChassisIndex OBJECT-TYPE
            SYNTAX PhysicalIndex
            MAX-ACCESS not-accessible
            STATUS current
            DESCRIPTION
                "The chassis index."
            ::= { hwClockAttributeEntry 1 }

        
        -- 1.3.6.1.4.1.2011.5.25.186.1.9.1.2
        hwClockAttributeSysClkRunMode OBJECT-TYPE
            SYNTAX INTEGER
                {
                normal(0),
                freeRun(1),
                hold(2)
                }
            MAX-ACCESS read-write
            STATUS current
            DESCRIPTION
                "The run mode of system clock."
            ::= { hwClockAttributeEntry 2 }

        
        -- 1.3.6.1.4.1.2011.5.25.186.1.9.1.3
        hwClockAttributeSsmControl OBJECT-TYPE
            SYNTAX INTEGER
                {
                on(0),
                off(1)
                }
            MAX-ACCESS read-write
            STATUS current
            DESCRIPTION
                "The flag whether SSM is concerned with the clock source selection."
            ::= { hwClockAttributeEntry 3 }

        
        -- 1.3.6.1.4.1.2011.5.25.186.1.9.1.4
        hwClockAttributeFreqCheckEnable OBJECT-TYPE
            SYNTAX EnabledStatus
            MAX-ACCESS read-write
            STATUS current
            DESCRIPTION
                "The enable flag of frequency check."
            ::= { hwClockAttributeEntry 4 }

        
        -- 1.3.6.1.4.1.2011.5.25.186.1.9.1.5
        hwClockAttributeRetrieveMode OBJECT-TYPE
            SYNTAX INTEGER
                {
                retrieve(0),
                noRetrieve(1)
                }
            MAX-ACCESS read-write
            STATUS current
            DESCRIPTION
                "The retrieve mode of system clock." 
            DEFVAL { retrieve }    
            ::= { hwClockAttributeEntry 5 }

        
        -- 1.3.6.1.4.1.2011.5.25.186.1.9.1.6
        hwClockAttributeWtrTime OBJECT-TYPE
            SYNTAX Integer32 (0..12)
            MAX-ACCESS read-write
            STATUS current
            DESCRIPTION
                "The time waiting for retrieve." 
            DEFVAL { 5 }
            ::= { hwClockAttributeEntry 6 }

        
        -- 1.3.6.1.4.1.2011.5.25.186.1.9.1.7
        hwClockAttributeHoldOffTime OBJECT-TYPE
            SYNTAX Integer32 (300..1800)
            MAX-ACCESS read-write
            STATUS current
            DESCRIPTION
                "The holdoff-time when the system source is lost." 
            DEFVAL { 1000 }
            ::= { hwClockAttributeEntry 7 }

        
        -- 1.3.6.1.4.1.2011.5.25.186.1.9.1.8
        hwClockAttributeOutThreshold OBJECT-TYPE
            SYNTAX INTEGER
                {
                prc(2),
                ssua(4),
                ssub(8),
                sec(11),
                dnu(15)
                }
            MAX-ACCESS read-write
            STATUS current
            DESCRIPTION
                "The Threshold of out put."
            ::= { hwClockAttributeEntry 8 }
             
        -- 1.3.6.1.4.1.2011.5.25.186.1.9.1.9
        hwClockAttributeSysMaxOutSsm OBJECT-TYPE
            SYNTAX INTEGER
                {
                unk(0),
                prc(2),
                ssua(4),
                ssub(8),
                sec(11)
                }
            MAX-ACCESS read-write
            STATUS current
            DESCRIPTION
                "The max ssm of system out put."
            ::= { hwClockAttributeEntry 9 }


        -- 1.3.6.1.4.1.2011.5.25.186.1.9.1.10
        hwClockAttribute2M1MaxOutSsm OBJECT-TYPE
            SYNTAX INTEGER
                { 
                unk(0),
                prc(2),
                ssua(4),
                ssub(8),
                sec(11)
                }
            MAX-ACCESS read-write
            STATUS current
            DESCRIPTION
                "The max ssm of 2msync-1 out put."
            ::= { hwClockAttributeEntry 10 }


        
        -- 1.3.6.1.4.1.2011.5.25.186.1.9.1.11
        hwClockAttribute2M2MaxOutSsm OBJECT-TYPE
            SYNTAX INTEGER
                { 
                unk(0),
                prc(2),
                ssua(4),
                ssub(8),
                sec(11)
                }
            MAX-ACCESS read-write
            STATUS current
            DESCRIPTION
                "The max ssm of 2msync-2 out put."
            ::= { hwClockAttributeEntry 11 }


        
        -- 1.3.6.1.4.1.2011.5.25.186.1.9.1.12
        hwClockAttributeSysClkLockMode OBJECT-TYPE
            SYNTAX INTEGER
                {
                freeRun(0),
                fastLock(1),
                lock(2),
                hold(3),
                freeRunJudge(16),
                holdJudge(19)
                }
            MAX-ACCESS read-only
            STATUS current
            DESCRIPTION
                "The Lock mode of system clock."
            ::= { hwClockAttributeEntry 12 }

        
        -- 1.3.6.1.4.1.2011.5.25.186.1.10
        hwClockSrcSelTable OBJECT-TYPE
            SYNTAX SEQUENCE OF HwClockSrcSelEntry
            MAX-ACCESS not-accessible
            STATUS current
            DESCRIPTION
                "The system clock source selection table."
            ::= { hwClockManageObjects 10 }

        
        -- 1.3.6.1.4.1.2011.5.25.186.1.10.1
        hwClockSrcSelEntry OBJECT-TYPE
            SYNTAX HwClockSrcSelEntry
            MAX-ACCESS not-accessible
            STATUS current
            DESCRIPTION
                "The entry of system clock source selection table."
            INDEX { hwClockSrcSelChassisIndex, hwClockSrcSelType }
            ::= { hwClockSrcSelTable 1 }

        
        HwClockSrcSelEntry ::=
            SEQUENCE { 
                hwClockSrcSelChassisIndex
                    PhysicalIndex,
                hwClockSrcSelType
                    INTEGER,
                hwClockSrcSelMode
                    INTEGER,
                hwClockSrcSelSrcName
                    OCTET STRING,
                hwClockSrcTraceSrcName
                    OCTET STRING
             }

        -- 1.3.6.1.4.1.2011.5.25.186.1.10.1.1
        hwClockSrcSelChassisIndex OBJECT-TYPE
            SYNTAX PhysicalIndex
            MAX-ACCESS not-accessible
            STATUS current
            DESCRIPTION
                "The chassis index."
            ::= { hwClockSrcSelEntry 1 }

        
        -- 1.3.6.1.4.1.2011.5.25.186.1.10.1.2
        hwClockSrcSelType OBJECT-TYPE
            SYNTAX INTEGER
                {
                system(1),
                sync2M-1(2),
                sync2M-2(3)
                }
            MAX-ACCESS not-accessible
            STATUS current
            DESCRIPTION
                "The PLL Id."
            ::= { hwClockSrcSelEntry 2 }

        
        -- 1.3.6.1.4.1.2011.5.25.186.1.10.1.3
        hwClockSrcSelMode OBJECT-TYPE
            SYNTAX INTEGER
                {
                auto(0),
                manual(1),
                force(2)
                }
            MAX-ACCESS read-write
            STATUS current
            DESCRIPTION
                "The mode of clock source selection."
            ::= { hwClockSrcSelEntry 3 }

        
        -- 1.3.6.1.4.1.2011.5.25.186.1.10.1.4
        hwClockSrcSelSrcName OBJECT-TYPE
            SYNTAX OCTET STRING
            MAX-ACCESS read-write
            STATUS current
            DESCRIPTION
                "The name of clock source for selection."
            ::= { hwClockSrcSelEntry 4 }


        -- 1.3.6.1.4.1.2011.5.25.186.1.10.1.5
        hwClockSrcTraceSrcName OBJECT-TYPE
            SYNTAX OCTET STRING
            MAX-ACCESS read-only
            STATUS current
            DESCRIPTION
                "The name of trace source."
            ::= { hwClockSrcSelEntry 5 }
            
            
        -- 1.3.6.1.4.1.2011.5.25.186.1.11
        hwClockSrcCfgTable OBJECT-TYPE
            SYNTAX SEQUENCE OF HwClockSrcCfgEntry
            MAX-ACCESS not-accessible
            STATUS current
            DESCRIPTION
                "The clock source config table."
            ::= { hwClockManageObjects 11 }

        
        -- 1.3.6.1.4.1.2011.5.25.186.1.11.1
        hwClockSrcCfgEntry OBJECT-TYPE
            SYNTAX HwClockSrcCfgEntry
            MAX-ACCESS not-accessible
            STATUS current
            DESCRIPTION
                "The entry of clock source config table."
            INDEX { hwClockSrcCfgChassisIndex, hwClockSrcCfgSourceTypeIndex, hwClockSrcCfgSourceIndex }
            ::= { hwClockSrcCfgTable 1 }


        
        HwClockSrcCfgEntry ::=
            SEQUENCE { 
                hwClockSrcCfgChassisIndex
                    PhysicalIndex,
                hwClockSrcCfgSourceTypeIndex
                    INTEGER,
                hwClockSrcCfgSourceIndex
                    Integer32,
                hwClockSrcCfgSourceDescr
                    OCTET STRING,
                hwClockSrcCfgClkEnable
                    EnabledStatus,
                hwClockSrcCfgSystemPriority
                    Integer32,
                hwClockSrcCfg2M1Priority
                    Integer32,
                hwClockSrcCfg2M2Priority
                    Integer32,
                hwClockSrcCfgSourceSsm
                    INTEGER,
                hwClockSrcCfgSsmSetMode
                    INTEGER,
                hwClockSrcCfgSourceState
                    INTEGER,
                hwClockSrcCfgFreqCheckResult
                    INTEGER,
                hwClockSrcCfgRowStatus
                    RowStatus
             }

        -- 1.3.6.1.4.1.2011.5.25.186.1.11.1.1
        hwClockSrcCfgChassisIndex OBJECT-TYPE
            SYNTAX PhysicalIndex
            MAX-ACCESS not-accessible
            STATUS current
            DESCRIPTION
                "The chassis index."
            ::= { hwClockSrcCfgEntry 1 }

        
        -- 1.3.6.1.4.1.2011.5.25.186.1.11.1.2
        hwClockSrcCfgSourceTypeIndex OBJECT-TYPE
            SYNTAX INTEGER
                {
                bits(1),
                ptp(2),
                interface(3)
                }
            MAX-ACCESS accessible-for-notify
            STATUS current
            DESCRIPTION
                "The type of clock source."
            ::= { hwClockSrcCfgEntry 2 }

        
        -- 1.3.6.1.4.1.2011.5.25.186.1.11.1.3
        hwClockSrcCfgSourceIndex OBJECT-TYPE
            SYNTAX Integer32
            MAX-ACCESS not-accessible
            STATUS current
            DESCRIPTION
                "The index of clock source."
            ::= { hwClockSrcCfgEntry 3 }

        
        -- 1.3.6.1.4.1.2011.5.25.186.1.11.1.4
        hwClockSrcCfgSourceDescr OBJECT-TYPE
            SYNTAX OCTET STRING
            MAX-ACCESS read-only
            STATUS current
            DESCRIPTION
                "The description of clock source."
            ::= { hwClockSrcCfgEntry 4 }

        
        -- 1.3.6.1.4.1.2011.5.25.186.1.11.1.5
        hwClockSrcCfgClkEnable OBJECT-TYPE
            SYNTAX EnabledStatus
            MAX-ACCESS read-create
            STATUS current
            DESCRIPTION
                "The enable flag of clock source."
            ::= { hwClockSrcCfgEntry 5 }

        
        -- 1.3.6.1.4.1.2011.5.25.186.1.11.1.6
        hwClockSrcCfgSystemPriority OBJECT-TYPE
            SYNTAX Integer32 (0..255)
            MAX-ACCESS read-create
            STATUS current
            DESCRIPTION
                "The priority of system clock source."   
            DEFVAL { 0 }
            ::= { hwClockSrcCfgEntry 6 }

        
        -- 1.3.6.1.4.1.2011.5.25.186.1.11.1.7
        hwClockSrcCfg2M1Priority OBJECT-TYPE
            SYNTAX Integer32 (0..255)
            MAX-ACCESS read-create
            STATUS current
            DESCRIPTION
                "The priority of 2msync-1 clock source."
            DEFVAL { 0 }
            ::= { hwClockSrcCfgEntry 7 }

        
        -- 1.3.6.1.4.1.2011.5.25.186.1.11.1.8
        hwClockSrcCfg2M2Priority OBJECT-TYPE
            SYNTAX Integer32 (0..255)
            MAX-ACCESS read-create
            STATUS current
            DESCRIPTION
                "The priority of 2msync-2 clock source."
            DEFVAL { 0 }
            ::= { hwClockSrcCfgEntry 8 }

        
        -- 1.3.6.1.4.1.2011.5.25.186.1.11.1.9
        hwClockSrcCfgSourceSsm OBJECT-TYPE
            SYNTAX INTEGER
                {
                unk(0),
                prc(2),
                ssua(4),
                ssub(8),
                sec(11),
                dnu(15),
                unknown(16)
                }
            MAX-ACCESS read-create
            STATUS current
            DESCRIPTION
                "The SSM quality of clock source."
            ::= { hwClockSrcCfgEntry 9 }

        
        -- 1.3.6.1.4.1.2011.5.25.186.1.11.1.10
        hwClockSrcCfgSsmSetMode OBJECT-TYPE
            SYNTAX INTEGER
                {
                manual(1),
                auto(2)
                }
            MAX-ACCESS read-only
            STATUS current
            DESCRIPTION
                "The set mode of SSM."
            ::= { hwClockSrcCfgEntry 10 }

        
        -- 1.3.6.1.4.1.2011.5.25.186.1.11.1.11
        hwClockSrcCfgSourceState OBJECT-TYPE
            SYNTAX INTEGER
                {
                initial(0),
                normal(1),
                abnormal(2),
                waitwtr(3),
                holdoff(4)
                }
            MAX-ACCESS read-only
            STATUS current
            DESCRIPTION
                "The state of clock source."
            ::= { hwClockSrcCfgEntry 11 }

        
        -- 1.3.6.1.4.1.2011.5.25.186.1.11.1.12
        hwClockSrcCfgFreqCheckResult OBJECT-TYPE
            SYNTAX INTEGER
                {
                abnormal(0),
                normal(1)
                }
            MAX-ACCESS read-only
            STATUS current
            DESCRIPTION
                "The result of frequency check."
            ::= { hwClockSrcCfgEntry 12 }      
            
        -- 1.3.6.1.4.1.2011.5.25.186.1.11.1.20
        hwClockSrcCfgRowStatus OBJECT-TYPE
            SYNTAX RowStatus
            MAX-ACCESS read-create
            STATUS current
            DESCRIPTION
                "The row status."
            ::= { hwClockSrcCfgEntry 20 }
            
                    
        hwClockConformance OBJECT IDENTIFIER ::= { hwClockMIB 10 }

        
        hwClockSourceCompliances OBJECT IDENTIFIER ::= { hwClockConformance 1 }

        
        hwClockSourceCompliance MODULE-COMPLIANCE
            STATUS current
            DESCRIPTION 
                "The compliance of clock MIB."
            MODULE -- this module
                MANDATORY-GROUPS { hwClockManageSysGroup, hwClockSourceCfgGroup, hwClockPortCfgGroup, hwClockBitsCfgGroup, hwClockNotificationsGroup, 
                    hwClockSysSelGroup, hwClockTrapOidGroup, hwClockLineCfgGroup }
            ::= { hwClockSourceCompliances 1 }

        
        hwClockSourceGroups OBJECT IDENTIFIER ::= { hwClockConformance 2 }

        
        hwClockManageSysGroup OBJECT-GROUP
            OBJECTS { hwClockSourceSysClkWorkMode, hwClockSourceFreqCheckEnable, hwClockSourceHoldMode, hwClockSourceSsmControl, hwClockSourceFreqCheckRightRange, 
                hwClockSourceFreqCheckLeftRange, hwClockSourceRetrieveMode, hwClockSourceForceCloseEnableStatus, hwClockSourceSsmUnknown, hwClockExtTimeOutputType, 
                hwClockExtTimeInputType, hwClockTimeUsedSource, hwClockSourceEthClkEnable }
            STATUS current
            DESCRIPTION 
                "The manage group."
            ::= { hwClockSourceGroups 8 }

        
        hwClockSysSelGroup OBJECT-GROUP
            OBJECTS { hwClockSourceSelMode, hwClockSourceSelSourceId }
            STATUS current
            DESCRIPTION 
                "The system selection group."
            ::= { hwClockSourceGroups 9 }

        
        hwClockSourceCfgGroup OBJECT-GROUP
            OBJECTS { hwClockCfgSourceId, hwClockCfgPriRvtEnableStatus, hwClockCfgSwitchCondition, hwClockCfgWtrTime, hwClockCfgBadDetect, 
                hwClockCfgSourceSsm, hwClockCfgExportEnableStatus, hwClockCfgSwiEnableStatus, hwClockCfgSourceState, hwClockCfgSourceDescr, 
                hwClockCfgFreqCheckResult, hwClockCfgHoldOffTime, hwClockCfgBits0Priority, hwClockCfgBits1Priority, hwClockCfgSystemPriority, 
                hwClockCfgSourceSsmSetMode, hwClockCfgSourceS1Id, hwClockCfgClkSourceType, hwClockCfgSsmThreshold, hwClockCfgSystemLockOut, 
                hwClockCfgBits0LockOut, hwClockCfgBits1LockOut,hwClockBitsCfgTodFormat }
            STATUS current
            DESCRIPTION 
                "The clock source group."
            ::= { hwClockSourceGroups 10 }

        
        hwClockPortCfgGroup OBJECT-GROUP
            OBJECTS { hwClockPortCfgLeftFramePri, hwClockPortCfgRightFramePri, hwClockPortCfgForceOutS1 }
            STATUS current
            DESCRIPTION 
                "The port config of clock source group."
            ::= { hwClockSourceGroups 13 }

        
        hwClockBitsCfgGroup OBJECT-GROUP
            OBJECTS { hwClockBitsCfgRecvSaBit, hwClockBitsCfgSendSaBit, hwClockBitsCfgForceOutS1, hwClockBitsCfgName, hwClockBitsCfgBitsType, 
                hwClockBitsCfgDirection, hwClockBitsCfgSaBit, hwClockBitsCfgInputMode, hwClockBitsCfgOutputMode, hwClockBitsCfgSourceId, 
                hwClockBitsCfgInvalidCond, hwClockBitsCfgBitsPortType }
            STATUS current
            DESCRIPTION 
                "The BITS clock source group."
            ::= { hwClockSourceGroups 14 }

        
        hwClockTrapOidGroup OBJECT-GROUP
			OBJECTS { hwClockLastSourceName, hwClockCurSourceName, hwClockSourceOldLockMode, hwClockChassisId, hwClockOldSourceState
                 }
            STATUS current
            DESCRIPTION 
                "The clock trap group."
            ::= { hwClockSourceGroups 15 }

        
        hwClockNotificationsGroup NOTIFICATION-GROUP
			NOTIFICATIONS { hwClockSourceSwitch, hwClockSourceSysClkLockModeChange, hwClockSourceStateChange }
            STATUS current
            DESCRIPTION 
                "This is the group of clock notification."
            ::= { hwClockSourceGroups 16 }

        
        hwClockLineCfgGroup OBJECT-GROUP
            OBJECTS { hwClockLineClkCfgRecvS1, hwClockLineClkCfgSendS1, hwClockLineClkCfgCardId, hwClockLineClkCfgPortId }
            STATUS current
            DESCRIPTION 
                "The line clock group.."
            ::= { hwClockSourceGroups 17 }

        
    
    END

--
-- HUAWEI-CLOCK-MIB.mib
--
