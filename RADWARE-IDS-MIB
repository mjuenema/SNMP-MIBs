IDS-MIB DEFINITIONS ::= BEGIN

-- Title:      RADWARE
--             This Private MIB supports the Vgate
-- Version:    2.9
-- Date:       9 Apr 2000
-- By:         RMA (Radware MIB Authority)
-- E-mail:     US:            support@radware.com
--             International: support_int@radware.com
--
IMPORTS
       NetworkAddress,
       IpAddress,
       Counter,
       Gauge,
       enterprises
              FROM RFC1155-SMI
       OBJECT-TYPE
              FROM RFC-1212
       DisplayString,
       PhysAddress,
       ipAddrEntry
              FROM RFC1213-MIB
       TRAP-TYPE
                    FROM RFC-1215
       rsIDS
                    FROM RADWARE-MIB;

    TruthValue ::= INTEGER {
         true (1),
         false (2)
        }
    RowStatus ::= INTEGER {
        active(1),
        notInService(2),
        notReady(3),
        createAndGo(4),
        createAndWait(5),
        destroy(6)
        }
    NetNumber ::=  OCTET STRING (SIZE(4))

-- Some MIB compilers require that the following 7 lines which define the path
-- to RND MIB are commented out:

-- mib            OBJECT IDENTIFIER ::= { mgmt 1  }
-- directory      OBJECT IDENTIFIER ::= { internet 1  }
-- experimental   OBJECT IDENTIFIER ::= { internet 3  }
-- private        OBJECT IDENTIFIER ::= { internet 4  }
-- enterprises    OBJECT IDENTIFIER ::= { private 1  }



 rsIDSTrackingTable OBJECT-TYPE
    SYNTAX SEQUENCE OF RsIDSTrackingEntry
    ACCESS not-accessible
    STATUS  mandatory
    DESCRIPTION
      "Table containing the parameters that are needed to detect intrusions"
    ::=  {rsIDS 1}


rsIDStrackingEntry OBJECT-TYPE
    SYNTAX RsIDSTrackingEntry
    ACCESS not-accessible
    STATUS  mandatory
    DESCRIPTION
       "The row definition for this table."
    INDEX { rsIDSFilterGroupName }
    ::=  { rsIDSTrackingTable 1 }

RsIDSTrackingEntry ::= SEQUENCE {
    rsIDSFilterGroupName DisplayString,
    rsIDSTrackingTime INTEGER,
    rsIDSThreshold INTEGER,
    rsIDSFilterGroupType INTEGER,
    rsIDSTrackingType INTEGER,
    rsIDSStatus    RowStatus,
    rsIDSReportMode INTEGER,
	rsIDSPacketReport INTEGER,
    rsIDSRisk INTEGER
}

rsIDSFilterGroupName OBJECT-TYPE
    SYNTAX DisplayString (SIZE(0..30))
    ACCESS  read-only
    STATUS  mandatory
    DESCRIPTION
      "The Name for the filter/group must be unique.
       that name should be the same as the name of the
       appropriate filter/group"
    ::=  {rsIDStrackingEntry 1}

rsIDSTrackingTime OBJECT-TYPE
    SYNTAX INTEGER
    ACCESS  read-write
    STATUS  mandatory
    DESCRIPTION
       "This variable indicates the time interval, in miliseconds,
        to track a detection"
    DEFVAL  { 1000 }
    ::=  { rsIDStrackingEntry 2 }

rsIDSThreshold OBJECT-TYPE
    SYNTAX INTEGER
    ACCESS  read-write
    STATUS  mandatory
    DESCRIPTION
       "This variable indicates the threshold "
    DEFVAL  { 50 }
    ::=  { rsIDStrackingEntry 3 }

rsIDSFilterGroupType OBJECT-TYPE
    SYNTAX INTEGER {
              filter(1),
              advanced-filter(2) }
    ACCESS  read-write
    STATUS  mandatory
    DESCRIPTION
       "This variable indicates the object type- whether it is a filter or group  "
    ::=  { rsIDStrackingEntry 4}

rsIDSTrackingType OBJECT-TYPE
    SYNTAX INTEGER {
    drop(0),
--    reset(1),
    ncps(2),
    ncpd(3),
    ncpsd(4),
--    ncpf(5),
--    winnuke(6),
    landattack(7),
--    synattackack(8),
--    tcpsyn(9),
--    tcpack(10),
--    tcpsynack(11),
--    tcprst(12),
--    tcpfin(13),
--    tcpelse(14),
      fragments(15),
      ncpsdscan(16),
	  dhcp(17)
    }
    ACCESS  read-write
    STATUS  mandatory
    DESCRIPTION
       "This variable indicates how to count  "
    ::=  { rsIDStrackingEntry 5}

rsIDSStatus OBJECT-TYPE
    SYNTAX RowStatus
    ACCESS  read-write
    STATUS  mandatory
    DESCRIPTION
       "This variable indicates the administrative status of this entry.
        Used to delete an entry of this table."
    ::=  { rsIDStrackingEntry 6 }


rsIDSReportMode OBJECT-TYPE
    SYNTAX INTEGER {
			drop(1),
			forward(2),
			rst-src(3),
     	    rst-dst(4),
    	    rst-bi(5),
			default(6)}
    ACCESS  read-write
    STATUS  mandatory
    DESCRIPTION
       "This variable indicates the attack report mode"
    ::=  { rsIDStrackingEntry 7}

rsIDSPacketReport OBJECT-TYPE
    SYNTAX INTEGER {
			enable(1),
			disable(2)}
    ACCESS  read-write
    STATUS  mandatory
    DESCRIPTION
       "This variable indicates the per-attack packet report"
	DEFVAL  {disable}
    ::=  { rsIDStrackingEntry 8}

rsIDSRisk OBJECT-TYPE
    SYNTAX INTEGER {
		  n-a(1),
		  low(2),
       	  medium(3),
		  high(4)}
    ACCESS  read-write
    STATUS  mandatory
    DESCRIPTION
       "This variable indicates the risk of the attack"
    ::=  {rsIDStrackingEntry 9}

rsIDSMechanismStatus OBJECT-TYPE
 SYNTAX INTEGER {
      enable(1),
      disable(2)
   }
    ACCESS read-write
    STATUS mandatory
    DESCRIPTION
      "the Application Security trigger"
   DEFVAL  {disable}
    ::= {rsIDS 2}

rsIDSTCPAgingTimeFreq OBJECT-TYPE
 SYNTAX INTEGER
    ACCESS read-write
    STATUS mandatory
    DESCRIPTION
      "the TCP table aging time frequency"
    ::= {rsIDS 3}

rsIDSNCPsAgingTimeFreq OBJECT-TYPE
 SYNTAX INTEGER
    ACCESS read-write
    STATUS mandatory
    DESCRIPTION
      "the NCP's tables aging time frequency"
    ::= {rsIDS 4}

rsIDSStatsAgingTimeFreq OBJECT-TYPE
 SYNTAX INTEGER
    ACCESS read-write
    STATUS mandatory
    DESCRIPTION
      "the statistics table aging time frequency"
    ::= {rsIDS 5}

rsIDSNCPSTableSize OBJECT-TYPE
SYNTAX INTEGER
    ACCESS read-write
    STATUS mandatory
    DESCRIPTION
      "the NCPS table size"
    ::= {rsIDS 6}

rsIDSNCPDTableSize OBJECT-TYPE
 SYNTAX INTEGER
    ACCESS read-write
    STATUS mandatory
    DESCRIPTION
      "the NCPD table size"
    ::= {rsIDS 7}

rsIDSNCPSDTableSize OBJECT-TYPE
 SYNTAX INTEGER
    ACCESS read-write
    STATUS mandatory
    DESCRIPTION
      "the NCPSD table size"
    ::= {rsIDS 8}

rsIDSTCPTableSize OBJECT-TYPE
 SYNTAX INTEGER
    ACCESS read-write
    STATUS mandatory
    DESCRIPTION
      "the TCP table size"
    ::= {rsIDS 9}

rsIDSSTATSTableSize OBJECT-TYPE
 SYNTAX INTEGER
    ACCESS read-write
    STATUS mandatory
    DESCRIPTION
      "the statistics table size"
    ::= {rsIDS 10}

rsIDSBasic OBJECT-TYPE
 SYNTAX INTEGER {
      enable(1),
      disable(2)
   }
    ACCESS read-write
    STATUS mandatory
    DESCRIPTION
      "the basic protection rule trigger"
   DEFVAL  {disable}
    ::= {rsIDS 11}

rsIDSAllServers OBJECT-TYPE
 SYNTAX INTEGER {
      enable(1),
      disable(2)
   }
    ACCESS read-write
    STATUS mandatory
    DESCRIPTION
      "the All servers rule trigger"
   DEFVAL  {disable}
    ::= {rsIDS 12}


rsIDSUNIXServers OBJECT-TYPE
 SYNTAX INTEGER {
      enable(1),
      disable(2)
   }
    ACCESS read-write
    STATUS mandatory
    DESCRIPTION
      "the unix servers rule trigger"
   DEFVAL  {disable}
    ::= {rsIDS 13}

rsIDSLotusServers OBJECT-TYPE
 SYNTAX INTEGER {
      enable(1),
      disable(2)
   }
    ACCESS read-write
    STATUS mandatory
    DESCRIPTION
      "the Lotus servers rule trigger"
   DEFVAL  {disable}
    ::= {rsIDS 14}

rsIDSMSIISServers OBJECT-TYPE
 SYNTAX INTEGER {
      enable(1),
      disable(2)
   }
    ACCESS read-write
    STATUS mandatory
    DESCRIPTION
      "the MS_IIS servers rule trigger"
   DEFVAL  {disable}
    ::= {rsIDS 15}

rsIDSMSFrontPageServers OBJECT-TYPE
 SYNTAX INTEGER {
      enable(1),
      disable(2)
   }
    ACCESS read-write
    STATUS mandatory
    DESCRIPTION
      "the MS front page servers rule trigger"
   DEFVAL  {disable}
    ::= {rsIDS 16}

rsIDSApacheServers OBJECT-TYPE
 SYNTAX INTEGER {
      enable(1),
      disable(2)
   }
    ACCESS read-write
    STATUS mandatory
    DESCRIPTION
      "the Apache servers rule trigger"
   DEFVAL  {disable}
    ::= {rsIDS 17}

rsIDSNetscapeWebServers OBJECT-TYPE
 SYNTAX INTEGER {
      enable(1),
      disable(2)
   }
    ACCESS read-write
    STATUS mandatory
    DESCRIPTION
      "the Netscape_Web servers rule trigger"
   DEFVAL  {disable}
    ::= {rsIDS 18}

rsIDSNovellServers OBJECT-TYPE
 SYNTAX INTEGER {
      enable(1),
      disable(2)
   }
    ACCESS read-write
    STATUS mandatory
    DESCRIPTION
      "the Novell servers rule trigger"
   DEFVAL  {disable}
    ::= {rsIDS 19}

rsIDSOracleServers OBJECT-TYPE
 SYNTAX INTEGER {
      enable(1),
      disable(2)
   }
    ACCESS read-write
    STATUS mandatory
    DESCRIPTION
      "the Oracle servers rule trigger"
   DEFVAL  {disable}
    ::= {rsIDS 20}

rsIDSOmniHTTPDServers OBJECT-TYPE
 SYNTAX INTEGER {
      enable(1),
      disable(2)
   }
    ACCESS read-write
    STATUS mandatory
    DESCRIPTION
      "the OmniHTTPD servers rule trigger"
   DEFVAL  {disable}
    ::= {rsIDS 21}

rsIDSWebSiteServers OBJECT-TYPE
 SYNTAX INTEGER {
      enable(1),
      disable(2)
   }
    ACCESS read-write
    STATUS mandatory
    DESCRIPTION
      "the WebSite_WebSitePro servers rule trigger"
   DEFVAL  {disable}
    ::= {rsIDS 22}

rsIDSColdfusionServers OBJECT-TYPE
 SYNTAX INTEGER {
      enable(1),
      disable(2)
   }
    ACCESS read-write
    STATUS mandatory
    DESCRIPTION
      "the Allaire_Coldfusion servers rule trigger"
   DEFVAL  {disable}
    ::= {rsIDS 23}

rsIDSIRIXServers OBJECT-TYPE
 SYNTAX INTEGER {
      enable(1),
      disable(2)
   }
    ACCESS read-write
    STATUS mandatory
    DESCRIPTION
      "the IRIX servers rule trigger"
   DEFVAL  {disable}
    ::= {rsIDS 24}

rsIDSNCSAServers OBJECT-TYPE
 SYNTAX INTEGER {
      enable(1),
      disable(2)
   }
    ACCESS read-write
    STATUS mandatory
    DESCRIPTION
      "the NCSA servers rule trigger"
   DEFVAL  {disable}
    ::= {rsIDS 25}

rsIDSCompaqServers OBJECT-TYPE
 SYNTAX INTEGER {
      enable(1),
      disable(2)
   }
    ACCESS read-write
    STATUS mandatory
    DESCRIPTION
      "the Compaq_Web_Servers servers rule trigger"
   DEFVAL  {disable}
    ::= {rsIDS 26}

rsIDSbackdoors OBJECT-TYPE
 SYNTAX INTEGER {
      enable(1),
      disable(2)
   }
    ACCESS read-write
    STATUS mandatory
    DESCRIPTION
      "the backdoors rule trigger"
   DEFVAL  {disable}
    ::= {rsIDS 27}

rsIDSTraps OBJECT-TYPE
 SYNTAX INTEGER {
      enable(1),
      disable(2)
   }
    ACCESS read-write
    STATUS mandatory
    DESCRIPTION
      "the traps sending mechanism trigger"
   DEFVAL  {enable}
    ::= {rsIDS 28}

rsIDSStatsTable OBJECT-TYPE
    SYNTAX SEQUENCE OF RsIDSStatsEntry
    ACCESS not-accessible
    STATUS  mandatory
    DESCRIPTION
      "Table containing the intrusion detection statistics"
    ::=  {rsIDS 29}

rsIDSStatsEntry OBJECT-TYPE
    SYNTAX RsIDSStatsEntry
    ACCESS not-accessible
    STATUS  mandatory
    DESCRIPTION
       "The row definition for this table."
    INDEX { rsIDSAttackIndex }
    ::=  { rsIDSStatsTable 1 }

RsIDSStatsEntry ::= SEQUENCE {
    rsIDSAttackIndex   INTEGER,
    rsIDSAttackName    DisplayString,
    rsIDSAttackSrcAddr IpAddress,
    rsIDSAttackDstAddr IpAddress,
    rsIDSAttackStatus  INTEGER,
    rsIDSAttacktime    DisplayString,
    rsIDSStatsStatus   RowStatus,
    rsIDSStatsContext  INTEGER,
    rsIDSStatsSrcPort  INTEGER,
    rsIDSStatsDstPort  INTEGER,
    rsIDSStatsProtocol INTEGER,
    rsIDSStatsPhyPort  INTEGER,
    rsIDSStatsRID      INTEGER,
    rsIDSStatsService  INTEGER,
    rsIDSPolicyName    DisplayString,
    rsIDSStatsPktCount INTEGER,
    rsIDSStatsByteCount INTEGER,
    rsIDSStatsReportMode INTEGER,
    rsIDSStatsRisk INTEGER
}

rsIDSAttackIndex OBJECT-TYPE
    SYNTAX  INTEGER
    ACCESS  read-only
    STATUS  mandatory
    DESCRIPTION
      "The index of the attack that was detected"
    ::=  {rsIDSStatsEntry 1}

rsIDSAttackName OBJECT-TYPE
    SYNTAX DisplayString (SIZE(0..80))
    ACCESS  read-only
    STATUS  mandatory
    DESCRIPTION
      "The Name for the attack"
    ::=  {rsIDSStatsEntry 2}

rsIDSAttackSrcAddr OBJECT-TYPE
    SYNTAX  IpAddress
    ACCESS  read-only
    STATUS  mandatory
    DESCRIPTION
      "The src address of the attack"
    ::=  {rsIDSStatsEntry 3}

rsIDSAttackDstAddr OBJECT-TYPE
    SYNTAX  IpAddress
    ACCESS  read-only
    STATUS  mandatory
    DESCRIPTION
      "The dest address of the attack"
    ::=  {rsIDSStatsEntry 4}

rsIDSAttackStatus OBJECT-TYPE
    SYNTAX INTEGER {
      started(1),
      terminated(2),
      occured(3),
      ongoing(4),
      started-ssl(5),
      terminated-ssl(6),
      occured-ssl(7),
      appsec(8),
      alert-sent(9),
      activated(10),
      blocking(11),
      deactivation-alert(12),
      deactivated(13),
	  ongoing-slt(14),
	  started-term(15),
	  started-term-ssl(16),
	  active-deactive(17)
   }
    ACCESS  read-only
    STATUS  mandatory
    DESCRIPTION
      "The status of the attack(started/terminated/occured...)"
    ::=  {rsIDSStatsEntry 5}

rsIDSAttacktime OBJECT-TYPE
    SYNTAX DisplayString (SIZE(0..32))
    ACCESS  read-only
    STATUS  mandatory
    DESCRIPTION
      "The time of the attack"
    ::=  {rsIDSStatsEntry 6}

rsIDSStatsStatus OBJECT-TYPE
    SYNTAX RowStatus
    ACCESS  read-write
    STATUS  mandatory
    DESCRIPTION
       "This variable indicates the administrative status of this entry.
        Used to delete an entry of this table."
    ::=  { rsIDSStatsEntry 7 }

rsIDSStatsContext  OBJECT-TYPE
    SYNTAX INTEGER {
    	regular(1),
    	ssl(2)
    }
    ACCESS  read-only
    STATUS  mandatory
    DESCRIPTION
      "The context of the attack"
    ::=  {rsIDSStatsEntry 8}
    
    
rsIDSStatsSrcPort  OBJECT-TYPE
    SYNTAX INTEGER 
    ACCESS  read-only
    STATUS  mandatory
    DESCRIPTION
      "The src address of the attack"
    ::=  {rsIDSStatsEntry 9}
    
rsIDSStatsDstPort  OBJECT-TYPE
    SYNTAX INTEGER 
    ACCESS  read-only
    STATUS  mandatory
    DESCRIPTION
      "The dst address of the attack"
    ::=  {rsIDSStatsEntry 10}
    
rsIDSStatsProtocol OBJECT-TYPE
    SYNTAX INTEGER {
    	ip(1),
    	tcp(2),
    	udp(3),
    	icmp(4)
    }
    ACCESS  read-only
    STATUS  mandatory
    DESCRIPTION
      "The protocol of the attack"
    ::=  {rsIDSStatsEntry 11}

rsIDSStatsPhyPort OBJECT-TYPE
    SYNTAX INTEGER 
    ACCESS  read-only
    STATUS  mandatory
    DESCRIPTION
      "The phy address of the attack"
    ::=  {rsIDSStatsEntry 12}

rsIDSStatsRID OBJECT-TYPE
    SYNTAX INTEGER 
    ACCESS  read-only
    STATUS  mandatory
    DESCRIPTION
      "The Radware ID of the attack"
    ::=  {rsIDSStatsEntry 13}

rsIDSStatsService OBJECT-TYPE
    SYNTAX INTEGER {
      unassigned(1),
      intrusion(2),
      dos(3),
	  anomalies(4),
	  scanning(5)
   }    
    ACCESS  read-only
    STATUS  mandatory
    DESCRIPTION
      "The Service/Category related to the event"
    ::=  {rsIDSStatsEntry 14}

rsIDSPolicyName OBJECT-TYPE
    SYNTAX DisplayString (SIZE(0..80))
    ACCESS  read-only
    STATUS  mandatory
    DESCRIPTION
      "The Name for the policy"
    ::=  {rsIDSStatsEntry 15}

rsIDSStatsPktCount OBJECT-TYPE
    SYNTAX INTEGER 
    ACCESS  read-only
    STATUS  mandatory
    DESCRIPTION
      "The # of packets that match the attack filter"
    ::=  {rsIDSStatsEntry 16}

rsIDSStatsByteCount OBJECT-TYPE
    SYNTAX INTEGER 
    ACCESS  read-only
    STATUS  mandatory
    DESCRIPTION
      "The # of packets that match the attack filter"
    ::=  {rsIDSStatsEntry 17}

rsIDSStatsReportMode OBJECT-TYPE
    SYNTAX INTEGER {
		  drop(1),
		  forward(2),
       	  rst-src(3),
   	      rst-dst(4),
   	      rst-bi(5)}
    ACCESS  read-only
    STATUS  mandatory
    DESCRIPTION
       "This variable indicates the action performed on the attack"
    ::=  {rsIDSStatsEntry 18}

rsIDSStatsRisk OBJECT-TYPE
    SYNTAX INTEGER {
		  n-a(1),
		  low(2),
       	  medium(3),
		  high(4)}
    ACCESS  read-only
    STATUS  mandatory
    DESCRIPTION
       "This variable indicates the risk of the attack"
    ::=  {rsIDSStatsEntry 19}


rsIDSNCPDTableSizeAfterReset OBJECT-TYPE
    SYNTAX INTEGER
    ACCESS read-write
    STATUS mandatory
    DESCRIPTION
      "the NCPD after-reset table size"
    ::= {rsIDS 30}

rsIDSNCPSDTableSizeAfterReset OBJECT-TYPE
    SYNTAX INTEGER
    ACCESS read-write
    STATUS mandatory
    DESCRIPTION
      "the NCPS after-reset table size"
    ::= {rsIDS 31}

rsIDSTCPTableSizeAfterReset OBJECT-TYPE
    SYNTAX INTEGER
    ACCESS read-write
    STATUS mandatory
    DESCRIPTION
      "the NCPS after-reset table size"
    ::= {rsIDS 32}

 rsIDSSTATSTableSizeAfterReset OBJECT-TYPE
    SYNTAX INTEGER
    ACCESS read-write
    STATUS mandatory
    DESCRIPTION
      "the NCPS after-reset table size"
    ::= {rsIDS 33}

 rsIDSLogfileAgingTimeFreq OBJECT-TYPE
 SYNTAX INTEGER
    ACCESS read-write
    STATUS mandatory
    DESCRIPTION
      "the log file polling time frequency"
    ::= {rsIDS 34}

 rsIDSSendLogFile OBJECT-TYPE
    SYNTAX DisplayString
    ACCESS  read-write
    STATUS  mandatory
    DESCRIPTION
        "The file name include path where the device will put the
         log file. The default destination address will be the sender
         address."
    ::= { rsIDS 35 }

rsIDSUtils OBJECT-TYPE
 SYNTAX INTEGER {
      clrstats(1),
      clrlog(2)
   }
    ACCESS read-write
    STATUS mandatory
    DESCRIPTION
      "IDS miscellaneous utilities"
    ::= { rsIDS 36 }

rsIDSVersion OBJECT-TYPE
    SYNTAX DisplayString
    ACCESS  read-only
    STATUS  mandatory
    DESCRIPTION
        "The current IDS software version."
    ::= { rsIDS 37 }

 rsIDSSLTTrackingTable OBJECT-TYPE
    SYNTAX SEQUENCE OF RsIDSSLTTrackingEntry
    ACCESS not-accessible
    STATUS  mandatory
    DESCRIPTION
      "TempTable containing the temp parameters that are needed to detect
      intrusions"
    ::=  {rsIDS 38}


rsIDSSLTtrackingEntry OBJECT-TYPE
    SYNTAX RsIDSSLTTrackingEntry
    ACCESS not-accessible
    STATUS  mandatory
    DESCRIPTION
       "The row definition for this table."
    INDEX { rsIDSSLTFilterGroupName }
    ::=  { rsIDSSLTTrackingTable 1 }

RsIDSSLTTrackingEntry ::= SEQUENCE {
    rsIDSSLTFilterGroupName DisplayString,
    rsIDSSLTAlertThreshold INTEGER,
    rsIDSSLTActiveThreshold INTEGER,
    rsIDSSLTDropThreshold INTEGER,
    rsIDSSLTTermAlertThreshold INTEGER,
    rsIDSSLTTermThreshold INTEGER,
    rsIDSSLTAgingPeriod INTEGER,
    rsIDSSLTObjectID INTEGER,
    rsIDSSLTAttackState INTEGER,
    rsIDSSLTMsg DisplayString,
    rsIDSSLTStatus    RowStatus,
    rsIDSSLTReportMode INTEGER,
    rsIDSSLTRisk INTEGER
}

rsIDSSLTFilterGroupName OBJECT-TYPE
    SYNTAX DisplayString (SIZE(0..30))
    ACCESS  read-only
    STATUS  mandatory
    DESCRIPTION
      "The Name for the filter/group must be unique.
       that name should be the same as the name of the
       appropriate filter/group"
    ::=  {rsIDSSLTtrackingEntry 1}

rsIDSSLTAlertThreshold OBJECT-TYPE
    SYNTAX INTEGER
    ACCESS  read-write
    STATUS  mandatory
    DESCRIPTION
       "This variable indicates the attack alerting threshold "
    DEFVAL  { 30 }
    ::=  { rsIDSSLTtrackingEntry 2 }

rsIDSSLTActiveThreshold OBJECT-TYPE
    SYNTAX INTEGER
    ACCESS  read-write
    STATUS  mandatory
    DESCRIPTION
       "This variable indicates the activating threshold "
    DEFVAL  { 50 }
    ::=  { rsIDSSLTtrackingEntry 3 }

rsIDSSLTDropThreshold OBJECT-TYPE
    SYNTAX INTEGER
    ACCESS  read-write
    STATUS  mandatory
    DESCRIPTION
       "This variable indicates the dropping threshold "
    DEFVAL  { 50 }
    ::=  { rsIDSSLTtrackingEntry 4 }

rsIDSSLTTermAlertThreshold OBJECT-TYPE
    SYNTAX INTEGER
    ACCESS  read-write
    STATUS  mandatory
    DESCRIPTION
       "This variable indicates the termination alert threshold "
    DEFVAL  { 50 }
    ::=  { rsIDSSLTtrackingEntry 5 }

rsIDSSLTTermThreshold OBJECT-TYPE
    SYNTAX INTEGER
    ACCESS  read-write
    STATUS  mandatory
    DESCRIPTION
       "This variable indicates the termination threshold "
    DEFVAL  { 30 }
    ::=  { rsIDSSLTtrackingEntry 6 }

rsIDSSLTAgingPeriod OBJECT-TYPE
    SYNTAX INTEGER
    ACCESS  read-write
    STATUS  mandatory
    DESCRIPTION
       "This variable indicates the the number of periods before an attack is
       removed "
    DEFVAL  { 5 }
    ::=  { rsIDSSLTtrackingEntry 7 }

rsIDSSLTObjectID OBJECT-TYPE
    SYNTAX INTEGER
    ACCESS  read-write
    STATUS  mandatory
    DESCRIPTION
       "This variable indicates the the index of the object in the temp tracking
       table "
    ::=  { rsIDSSLTtrackingEntry 8 }

rsIDSSLTAttackState OBJECT-TYPE
    SYNTAX INTEGER {
    disable(0),
    sampling(1),
    active(2),
	panic(3) }
    ACCESS  read-write
    STATUS  mandatory
    DESCRIPTION
       "This variable indicates the attack state "
    ::=  { rsIDSSLTtrackingEntry 9}

rsIDSSLTMsg OBJECT-TYPE
    SYNTAX DisplayString (SIZE(0..80))
    ACCESS  read-write
    STATUS  mandatory
    DESCRIPTION
      "The alert that pops up in the terminal when
      there is an attack"
    ::=  {rsIDSSLTtrackingEntry 10}


rsIDSSLTStatus OBJECT-TYPE
    SYNTAX RowStatus
    ACCESS  read-write
    STATUS  mandatory
    DESCRIPTION
       "This variable indicates the administrative status of this entry.
        Used to delete an entry of this table."
    ::=  { rsIDSSLTtrackingEntry 11 }


rsIDSSLTReportMode OBJECT-TYPE
    SYNTAX INTEGER {
			drop(1),
			forward(2),
--       	  rst-src(3),
--     	      rst-dst(4),
--     	      rst-bi(5),
			  default(6)}
    ACCESS  read-write
    STATUS  mandatory
    DESCRIPTION
       "This variable indicates the dos attack report mode"
    ::=  { rsIDSSLTtrackingEntry 12}

rsIDSSLTRisk OBJECT-TYPE
    SYNTAX INTEGER {
		  n-a(1),
		  low(2),
       	  medium(3),
		  high(4)}
    ACCESS  read-write
    STATUS  mandatory
    DESCRIPTION
       "This variable indicates the risk of the dos attack"
    ::=  {rsIDSSLTtrackingEntry 13}

rsIDSSLTACTTrackingTable OBJECT-TYPE
    SYNTAX SEQUENCE OF RsIDSSLTACTTrackingEntry
    ACCESS not-accessible
    STATUS  mandatory
    DESCRIPTION
      "The table containing the actual parameters that are needed to detect
      intrusions"
    ::=  {rsIDS 39}


rsIDSSLTACTtrackingEntry OBJECT-TYPE
    SYNTAX RsIDSSLTACTTrackingEntry
    ACCESS not-accessible
    STATUS  mandatory
    DESCRIPTION
       "The row definition for this table."
    INDEX { rsIDSSLTACTFilterGroupName }
    ::=  { rsIDSSLTACTTrackingTable 1 }

RsIDSSLTACTTrackingEntry ::= SEQUENCE {
    rsIDSSLTACTFilterGroupName DisplayString,
    rsIDSSLTACTAlertThreshold INTEGER,
    rsIDSSLTACTActiveThreshold INTEGER,
    rsIDSSLTACTDropThreshold INTEGER,
    rsIDSSLTACTTermAlertThreshold INTEGER,
    rsIDSSLTACTTermThreshold INTEGER,
    rsIDSSLTACTAgingPeriod INTEGER,
    rsIDSSLTACTObjectID INTEGER,
    rsIDSSLTACTAttackState INTEGER,
    rsIDSSLTACTMsg      DisplayString,
    rsIDSSLTACTStatus    RowStatus,
    rsIDSSLTACTReportMode INTEGER,
    rsIDSSLTACTRisk INTEGER
}

rsIDSSLTACTFilterGroupName OBJECT-TYPE
    SYNTAX DisplayString (SIZE(0..30))
    ACCESS  read-only
    STATUS  mandatory
    DESCRIPTION
      "The Name for the filter/group must be unique.
       that name should be the same as the name of the
       appropriate filter/group"
    ::=  {rsIDSSLTACTtrackingEntry 1}

rsIDSSLTACTAlertThreshold OBJECT-TYPE
    SYNTAX INTEGER
    ACCESS  read-only
    STATUS  mandatory
    DESCRIPTION
       "This variable indicates the attack alerting threshold "
    ::=  { rsIDSSLTACTtrackingEntry 2 }

rsIDSSLTACTActiveThreshold OBJECT-TYPE
    SYNTAX INTEGER
    ACCESS  read-only
    STATUS  mandatory
    DESCRIPTION
       "This variable indicates the activating threshold "
    DEFVAL  { 50 }
    ::=  { rsIDSSLTACTtrackingEntry 3 }

rsIDSSLTACTDropThreshold OBJECT-TYPE
    SYNTAX INTEGER
    ACCESS  read-only
    STATUS  mandatory
    DESCRIPTION
       "This variable indicates the dropping threshold "
    ::=  { rsIDSSLTACTtrackingEntry 4 }

rsIDSSLTACTTermAlertThreshold OBJECT-TYPE
    SYNTAX INTEGER
    ACCESS  read-only
    STATUS  mandatory
    DESCRIPTION
       "This variable indicates the termination alert threshold "
    ::=  { rsIDSSLTACTtrackingEntry 5 }

rsIDSSLTACTTermThreshold OBJECT-TYPE
    SYNTAX INTEGER
    ACCESS  read-only
    STATUS  mandatory
    DESCRIPTION
       "This variable indicates the termination threshold "
    ::=  { rsIDSSLTACTtrackingEntry 6 }

rsIDSSLTACTAgingPeriod OBJECT-TYPE
    SYNTAX INTEGER
    ACCESS  read-only
    STATUS  mandatory
    DESCRIPTION
       "This variable indicates the the number of periods before an attack is
       removed "
    ::=  { rsIDSSLTACTtrackingEntry 7 }

rsIDSSLTACTObjectID OBJECT-TYPE
    SYNTAX INTEGER
    ACCESS  read-only
    STATUS  mandatory
    DESCRIPTION
       "This variable indicates the the index of the object in the act tracking
       table "
    ::=  { rsIDSSLTACTtrackingEntry 8 }

rsIDSSLTACTAttackState OBJECT-TYPE
    SYNTAX INTEGER {
    disable(0),
    sampling(1),
    active(2),
	panic(3) }
    ACCESS  read-only
    STATUS  mandatory
    DESCRIPTION
       "This variable indicates the attack state "
    ::=  { rsIDSSLTACTtrackingEntry 9}

rsIDSSLTACTMsg OBJECT-TYPE
    SYNTAX DisplayString (SIZE(0..80))
    ACCESS  read-only
    STATUS  mandatory
    DESCRIPTION
      "The alert that pops up in the terminal when
      there is an attack"
    ::=  {rsIDSSLTACTtrackingEntry 10}


rsIDSSLTACTStatus OBJECT-TYPE
    SYNTAX RowStatus
    ACCESS  read-write
    STATUS  mandatory
    DESCRIPTION
       "This variable indicates the administrative status of this entry.
        Used to delete an entry of this table."
    ::=  { rsIDSSLTACTtrackingEntry 11 }

rsIDSSLTACTReportMode OBJECT-TYPE
    SYNTAX INTEGER {
			  drop(1),
			  forward(2),
--       	  rst-src(3),
--     	      rst-dst(4),
--     	      rst-bi(5),
			  default(6)}
    ACCESS  read-write
    STATUS  mandatory
    DESCRIPTION
       "This variable indicates the dos act attack report mode"
    ::=  { rsIDSSLTACTtrackingEntry 12}

rsIDSSLTACTRisk OBJECT-TYPE
    SYNTAX INTEGER {
		  n-a(1),
		  low(2),
       	  medium(3),
		  high(4)}
    ACCESS  read-write
    STATUS  mandatory
    DESCRIPTION
       "This variable indicates the risk of the dos act attack"
    ::=  {rsIDSSLTACTtrackingEntry 13}

rsIDSSLTNCPFTable OBJECT-TYPE
    SYNTAX SEQUENCE OF RsIDSSLTNCPFEntry
    ACCESS not-accessible
    STATUS  mandatory
    DESCRIPTION
      "The table containing the SLT params"
    ::=  {rsIDS 40}


rsIDSSLTNCPFEntry OBJECT-TYPE
    SYNTAX RsIDSSLTNCPFEntry
    ACCESS not-accessible
    STATUS  mandatory
    DESCRIPTION
       "The row definition for this table."
    INDEX { rsIDSSLTNCPFObjectID, rsIDSSLTNCPFRuleName }
    ::=  { rsIDSSLTNCPFTable 1 }


RsIDSSLTNCPFEntry ::= SEQUENCE {
    rsIDSSLTNCPFObjectID INTEGER,
    rsIDSSLTNCPFRuleName DisplayString,
    rsIDSSLTNCPFSamplingCNT INTEGER,
    rsIDSSLTNCPFActiveCNT INTEGER,
    rsIDSSLTNCPFAlertState INTEGER,
    rsIDSSLTNCPFAttackState INTEGER,
    rsIDSSLTNCPFTermAlertCNT INTEGER,
    rsIDSSLTNCPFTermCNT INTEGER,
    rsIDSSLTAttackTime DisplayString,
    rsIDSSLTAttackDate DisplayString,
    rsIDSSLTAttackTermTime DisplayString,
    rsIDSSLTAttackTermDate DisplayString,
    rsIDSSLTNCPFStatus    RowStatus,
    rsIDSSLTAttackMsg DisplayString,
    rsIDSSLTNCPFPeakCNT INTEGER
}

rsIDSSLTNCPFObjectID OBJECT-TYPE
    SYNTAX INTEGER
    ACCESS  read-only
    STATUS  mandatory
    DESCRIPTION
       "This variable indicates attack's object id "
    ::=  { rsIDSSLTNCPFEntry 1 }

rsIDSSLTNCPFRuleName OBJECT-TYPE
    SYNTAX DisplayString (SIZE(0..20))
    ACCESS  read-only
    STATUS  mandatory
    DESCRIPTION
      "The name of the policy which caught the attack"
    ::=  {rsIDSSLTNCPFEntry 2}

rsIDSSLTNCPFSamplingCNT OBJECT-TYPE
    SYNTAX INTEGER
    ACCESS  read-only
    STATUS  mandatory
    DESCRIPTION
       "This variable indicates the sampling counter"
    ::=  { rsIDSSLTNCPFEntry 3 }

rsIDSSLTNCPFActiveCNT OBJECT-TYPE
    SYNTAX INTEGER
    ACCESS  read-only
    STATUS  mandatory
    DESCRIPTION
       "This variable indicates the active counter"
    ::=  { rsIDSSLTNCPFEntry 4 }

rsIDSSLTNCPFAlertState OBJECT-TYPE
    SYNTAX INTEGER {
              dont(0),
              not(1),
              sent(2),
              act(3),
              drop(4) }
    ACCESS  read-only
    STATUS  mandatory
    DESCRIPTION
       "This variable indicates the attack alerting state "
    ::=  { rsIDSSLTNCPFEntry 5 }

rsIDSSLTNCPFAttackState OBJECT-TYPE
    SYNTAX INTEGER {
              sampling(1),
              active(2) }
    ACCESS  read-only
    STATUS  mandatory
    DESCRIPTION
       "This variable indicates the attack state "
    ::=  { rsIDSSLTNCPFEntry 6 }

rsIDSSLTNCPFTermAlertCNT OBJECT-TYPE
    SYNTAX INTEGER
    ACCESS  read-only
    STATUS  mandatory
    DESCRIPTION
       "This variable indicates the attack termination alert counter "
    ::=  { rsIDSSLTNCPFEntry 7 }

rsIDSSLTNCPFTermCNT OBJECT-TYPE
    SYNTAX INTEGER
    ACCESS  read-only
    STATUS  mandatory
    DESCRIPTION
       "This variable indicates the attack termination counter"
    ::=  { rsIDSSLTNCPFEntry 8 }

rsIDSSLTAttackTime OBJECT-TYPE
    SYNTAX DisplayString (SIZE(0..9))
    ACCESS  read-only
    STATUS  mandatory
    DESCRIPTION
      "The last time the attack took place"
    ::=  {rsIDSSLTNCPFEntry 9}

rsIDSSLTAttackDate OBJECT-TYPE
    SYNTAX DisplayString (SIZE(0..11))
    ACCESS  read-only
    STATUS  mandatory
    DESCRIPTION
      "The last date the attack took place"
    ::=  {rsIDSSLTNCPFEntry 10}

rsIDSSLTAttackTermTime OBJECT-TYPE
    SYNTAX DisplayString (SIZE(0..9))
    ACCESS  read-only
    STATUS  mandatory
    DESCRIPTION
      "The last time the attack terminated"
    ::=  {rsIDSSLTNCPFEntry 11}

rsIDSSLTAttackTermDate OBJECT-TYPE
    SYNTAX DisplayString (SIZE(0..11))
    ACCESS  read-only
    STATUS  mandatory
    DESCRIPTION
      "The last date the attack terminated"
    ::=  {rsIDSSLTNCPFEntry 12}

rsIDSSLTNCPFStatus OBJECT-TYPE
    SYNTAX RowStatus
    ACCESS  read-write
    STATUS  mandatory
    DESCRIPTION
       "This variable indicates the administrative status of this entry.
        Used to delete an entry of this table."
    ::=  { rsIDSSLTNCPFEntry 13 }

rsIDSSLTAttackMsg OBJECT-TYPE
    SYNTAX DisplayString (SIZE(0..80))
    ACCESS  read-only
    STATUS  mandatory
    DESCRIPTION
      "The attack message"
    ::=  {rsIDSSLTNCPFEntry 14}

rsIDSSLTNCPFPeakCNT OBJECT-TYPE
    SYNTAX INTEGER
    ACCESS  read-only
    STATUS  mandatory
    DESCRIPTION
       "This variable indicates the peak counter"
    ::=  { rsIDSSLTNCPFEntry 15 }

rsIDSEmail OBJECT-TYPE
 SYNTAX INTEGER {
      enable(1),
      disable(2)
   }
    ACCESS read-write
    STATUS mandatory
    DESCRIPTION
      "the email sending mechanism trigger"
   DEFVAL  {enable}
    ::= {rsIDS 41}

rsIDSLogging OBJECT-TYPE
 SYNTAX INTEGER {
      enable(1),
      disable(2)
   }
    ACCESS read-write
    STATUS mandatory
    DESCRIPTION
      "the logging mechanism trigger"
   DEFVAL  {enable}
    ::= {rsIDS 42}

rsIDSSLTSamplingTimeFreq OBJECT-TYPE
 SYNTAX INTEGER
 ACCESS read-write
 STATUS mandatory
 DESCRIPTION
   "the SLT sampling time frequency"
   ::= {rsIDS 43}

rsIDSSLTMechStatus OBJECT-TYPE
 SYNTAX INTEGER {
      enable(1),
      disable(2)
   }
    ACCESS read-write
    STATUS mandatory
    DESCRIPTION
      "the DoS Shield trigger"
   DEFVAL  {disable}
    ::= {rsIDS 44}

rsIDSReportStatus OBJECT-TYPE
 SYNTAX INTEGER {
		drop(1),
		forward(2),
       	  rst-src(3),
     	      rst-dst(4),
     	      rst-bi(5)
   }
    ACCESS read-write
    STATUS mandatory
    DESCRIPTION
      "the Application Security reporting mode"
   DEFVAL  {drop}
    ::= {rsIDS 45}

rsIDSSLTReportStatus OBJECT-TYPE
 SYNTAX INTEGER {
		drop(1),
		forward(2)
--       	  rst-src(3),
--     	      rst-dst(4),
--     	      rst-bi(5)
   }
    ACCESS read-write
    STATUS mandatory
    DESCRIPTION
      "the DoS Shield reporting mode"
   DEFVAL  {drop}
    ::= {rsIDS 46}

rsIDSRulesTable OBJECT-TYPE
    SYNTAX SEQUENCE OF RsIDSRulesEntry
    ACCESS not-accessible
    STATUS  mandatory
    DESCRIPTION
      "Table containing the list of rules params for the ids"
    ::=  {rsIDS 47}

rsIDSRulesEntry OBJECT-TYPE
    SYNTAX RsIDSRulesEntry
    ACCESS not-accessible
    STATUS  mandatory
    DESCRIPTION
       "The row definition for this table."
    INDEX { rsIDSRulesIndex }
    ::=  { rsIDSRulesTable 1 }

RsIDSRulesEntry ::= SEQUENCE {
    rsIDSRulesIndex INTEGER,
    rsIDSRulesName DisplayString,
    rsIDSRulesSource DisplayString,
    rsIDSRulesDestination DisplayString,
    rsIDSRulesDirection INTEGER,
    rsIDSRulesPortmask DisplayString,
    rsIDSRulesStatus  RowStatus
}

rsIDSRulesIndex OBJECT-TYPE
    SYNTAX INTEGER
    ACCESS  read-only
    STATUS  mandatory
    DESCRIPTION
       "This variable indicates the administrative index of a line it
       determines the order of the rules."
    ::=  { rsIDSRulesEntry 1 }

rsIDSRulesName OBJECT-TYPE
    SYNTAX DisplayString (SIZE(0..20))
    ACCESS  read-only
    STATUS  mandatory
    DESCRIPTION
      "The Name for the Rule."
    ::=  {rsIDSRulesEntry 2}

rsIDSRulesSource OBJECT-TYPE
    SYNTAX DisplayString (SIZE(0..20))
    ACCESS  read-write
    STATUS  mandatory
    DESCRIPTION
      "The source address / range of address for the packet, the name is
      defined in the Objects table or can be an IP address."
    ::=  {rsIDSRulesEntry 3}

rsIDSRulesDestination OBJECT-TYPE
    SYNTAX DisplayString (SIZE(0..20))
    ACCESS  read-write
    STATUS  mandatory
    DESCRIPTION
      "The destination address / range of address for the packet, the name is
      defined in the Objects table or can be an IP address."
    ::=  {rsIDSRulesEntry 4}

rsIDSRulesDirection OBJECT-TYPE
    SYNTAX INTEGER {
              oneway(1),
              twoway(2) }
    ACCESS  read-write
    STATUS  mandatory
    DESCRIPTION
       "This variable indicates the direction of the incoming packet."
    DEFVAL { 1 }
    ::=  { rsIDSRulesEntry 5 }


rsIDSRulesPortmask OBJECT-TYPE
    SYNTAX DisplayString (SIZE(0..80))
    ACCESS  read-write
    STATUS  mandatory
    DESCRIPTION
       "The mask of the ports, should be in the format
       of 1,2,3,2"
    ::=  { rsIDSRulesEntry 6 }

rsIDSRulesStatus OBJECT-TYPE
    SYNTAX RowStatus
    ACCESS  read-write
    STATUS  mandatory
    DESCRIPTION
       "This variable indicates the administrative status of this entry.
        Used to delete an entry of this table."
    ::=  { rsIDSRulesEntry 7 }

rsIDSRestore OBJECT-TYPE
 SYNTAX INTEGER {
      dflsecgroups(1)
   }
    ACCESS read-write
    STATUS mandatory
    DESCRIPTION
      "Restore Default Configuration"
    ::= { rsIDS 48 }

rsIDSMaxURILength OBJECT-TYPE
    SYNTAX INTEGER (1..65535)
    ACCESS read-write
    STATUS mandatory
    DESCRIPTION
      "Max URI Length"
    DEFVAL  { 500 }
    ::=  { rsIDS 49 }

rsIDSMinFragmentSize OBJECT-TYPE
    SYNTAX INTEGER (0..65535)
    ACCESS read-write
    STATUS mandatory
    DESCRIPTION
      "Min fragmented packet size"
    DEFVAL  { 100 }
    ::=  { rsIDS 50 }

rsIDSMinUrlPktSize OBJECT-TYPE
    SYNTAX INTEGER (0..65535)
    ACCESS read-write
    STATUS mandatory
    DESCRIPTION
      "Min HTTP GET/HEAD/POST fargmented
      packet Length"
    DEFVAL  { 50 }
    ::=  { rsIDS 51 }

rsIDSNewRulesTable OBJECT-TYPE
    SYNTAX SEQUENCE OF RsIDSNewRulesEntry
    ACCESS not-accessible
    STATUS  mandatory
    DESCRIPTION
      "Table containing the list of rules params for the ids"
    ::=  {rsIDS 52}

rsIDSNewRulesEntry OBJECT-TYPE
    SYNTAX RsIDSNewRulesEntry
    ACCESS not-accessible
    STATUS  mandatory
    DESCRIPTION
       "The row definition for this table."
    INDEX { rsIDSNewRulesName }
    ::=  { rsIDSNewRulesTable 1 }

RsIDSNewRulesEntry ::= SEQUENCE {
    rsIDSNewRulesName DisplayString,
    rsIDSServiceName DisplayString,
    rsIDSNewRulesSource DisplayString,
    rsIDSNewRulesDestination DisplayString,
    rsIDSNewRulesDirection INTEGER,
    rsIDSNewRulesPortmask DisplayString,
    rsIDSNewRulesState INTEGER,
    rsIDSNewRulesStatus  RowStatus,
	rsIDSNewRulesVlanTagGroup DisplayString
}

rsIDSNewRulesName OBJECT-TYPE
    SYNTAX DisplayString (SIZE(0..20))
    ACCESS  read-write
    STATUS  mandatory
    DESCRIPTION
      "The Name for the Rule."
    ::=  {rsIDSNewRulesEntry 1}

rsIDSServiceName OBJECT-TYPE
    SYNTAX DisplayString (SIZE(0..30))
    ACCESS  read-write
    STATUS  mandatory
    DESCRIPTION
      "The Name for the Service."
    ::=  {rsIDSNewRulesEntry 2}

rsIDSNewRulesSource OBJECT-TYPE
    SYNTAX DisplayString (SIZE(0..20))
    ACCESS  read-write
    STATUS  mandatory
    DESCRIPTION
      "The source address / range of address for the packet, the name is
      defined in the Objects table or can be an IP address."
    ::=  {rsIDSNewRulesEntry 3}

rsIDSNewRulesDestination OBJECT-TYPE
    SYNTAX DisplayString (SIZE(0..20))
    ACCESS  read-write
    STATUS  mandatory
    DESCRIPTION
      "The destination address / range of address for the packet, the name is
      defined in the Objects table or can be an IP address."
    ::=  {rsIDSNewRulesEntry 4}

rsIDSNewRulesDirection OBJECT-TYPE
    SYNTAX INTEGER {
              oneway(1),
              twoway(2) }
    ACCESS  read-write
    STATUS  mandatory
    DESCRIPTION
       "This variable indicates the direction of the incoming packet."
    DEFVAL { 1 }
    ::=  { rsIDSNewRulesEntry 5 }


rsIDSNewRulesPortmask OBJECT-TYPE
    SYNTAX DisplayString (SIZE(0..80))
    ACCESS  read-write
    STATUS  mandatory
    DESCRIPTION
       "The Port Group"
    ::=  { rsIDSNewRulesEntry 6 }

 rsIDSNewRulesState OBJECT-TYPE
    SYNTAX INTEGER {
              active(1),
              inactive(2) }
    ACCESS  read-write
    STATUS  mandatory
    DESCRIPTION
       "This variable indicates the state of the rule."
    DEFVAL { 1 }
    ::=  { rsIDSNewRulesEntry 7 }

rsIDSNewRulesStatus OBJECT-TYPE
    SYNTAX RowStatus
    ACCESS  read-write
    STATUS  mandatory
    DESCRIPTION
       "This variable indicates the administrative status of this entry.
        Used to delete an entry of this table."
    ::=  { rsIDSNewRulesEntry 8 }

rsIDSNewRulesVlanTagGroup OBJECT-TYPE
    SYNTAX DisplayString (SIZE(0..80))
    ACCESS  read-write
    STATUS  mandatory
    DESCRIPTION
       "The VLAN tag Group"
    ::=  { rsIDSNewRulesEntry 9 }


rsIDSRestoreGroup OBJECT-TYPE
    SYNTAX DisplayString
    ACCESS read-write
    STATUS mandatory
    DESCRIPTION
      "Restore Default Group Configuration"
    ::= { rsIDS 53 }

rsIDSStaticGroupTable OBJECT-TYPE
    SYNTAX SEQUENCE OF RsIDSStaticGroupEntry
    ACCESS not-accessible
    STATUS  mandatory
    DESCRIPTION
      "Table containing the parameters that are needed to detect intrusions"
    ::=  {rsIDS 54}


rsIDSStaticGroupEntry OBJECT-TYPE
    SYNTAX RsIDSStaticGroupEntry
    ACCESS not-accessible
    STATUS  mandatory
    DESCRIPTION
       "The row definition for this table."
    INDEX { rsIDSStaticGroupName }
    ::=  { rsIDSStaticGroupTable 1 }

RsIDSStaticGroupEntry ::= SEQUENCE {
    rsIDSStaticGroupName DisplayString
}

rsIDSStaticGroupName OBJECT-TYPE
    SYNTAX DisplayString (SIZE(0..30))
    ACCESS  read-only
    STATUS  mandatory
    DESCRIPTION
      "The Name for the filter/group must be unique.
       that name should be the same as the name of the
       appropriate filter/group"
    ::=  {rsIDSStaticGroupEntry 1}


rsIDSPanicMode OBJECT-TYPE
 SYNTAX INTEGER {
     enable(1),
     disable(2)
   }
    ACCESS read-write
    STATUS mandatory
    DESCRIPTION
      "the Panic Mode status"
   DEFVAL  {disable}
    ::= {rsIDS 55}


rsIDSAttackDBSend OBJECT-TYPE
    SYNTAX DisplayString
    ACCESS  read-write
    STATUS  mandatory
    DESCRIPTION
        "The file name include path where the attack database located."
    ::=  {rsIDS 56}

rsIDSAttackDBVersion OBJECT-TYPE
    SYNTAX DisplayString (SIZE(0..30))
    ACCESS  read-only
    STATUS  mandatory
    DESCRIPTION
      "The version of the Attack database file"
    ::=  {rsIDS 57}

rsIDSAttackDBUpdateRes OBJECT-TYPE
 SYNTAX INTEGER {
     succeeded(1),
     failed(2),
     processing(3)
   }
    ACCESS read-write
    STATUS mandatory
    DESCRIPTION
      "The attack db file update result"
   DEFVAL  {succeeded}
    ::= {rsIDS 58}


rsIDSDHCPTableSize OBJECT-TYPE
 SYNTAX INTEGER
    ACCESS read-write
    STATUS mandatory
    DESCRIPTION
      "the DHCP table size"
    ::= {rsIDS 59}

rsIDSDHCPTableSizeAfterReset OBJECT-TYPE
    SYNTAX INTEGER
    ACCESS read-write
    STATUS mandatory
    DESCRIPTION
      "the DHCP after-reset table size"
    ::= {rsIDS 60}


rsIDSLogDisplay OBJECT-TYPE
    SYNTAX SEQUENCE OF RsIDSLogEntry
    ACCESS not-accessible
    STATUS  mandatory
    DESCRIPTION
      "A table-like display containing security logfile entries"
    ::=  {rsIDS 61}

rsIDSLogEntry OBJECT-TYPE
    SYNTAX RsIDSLogEntry
    ACCESS not-accessible
    STATUS  mandatory
    DESCRIPTION
       "The row definition for the Security logfile."
    INDEX { rsIDSLogIndex }
    ::=  { rsIDSLogDisplay 1 }

RsIDSLogEntry ::= SEQUENCE {
    rsIDSLogIndex		INTEGER,
    rsIDSLogAttackName	DisplayString,
    rsIDSLogSrcAddr		IpAddress,
    rsIDSLogDstAddr		IpAddress,
    rsIDSLogAttackStatus INTEGER,
    rsIDSLogtime		DisplayString,
	rsIDSLogStatus		RowStatus,
    rsIDSLogContext		INTEGER,
    rsIDSLogSrcPort		INTEGER,
    rsIDSLogDstPort		INTEGER,
    rsIDSLogProtocol	INTEGER,
    rsIDSLogPhyPort		INTEGER,
    rsIDSLogRID			INTEGER,
    rsIDSLogService		INTEGER,
    rsIDSLogPolicyName	DisplayString,
    rsIDSLogPktCount	INTEGER,
    rsIDSLogByteCount	INTEGER,
	rsIDSLogReportMode	INTEGER,
	rsIDSLogRisk	INTEGER
}

rsIDSLogIndex OBJECT-TYPE
    SYNTAX  INTEGER
    ACCESS  read-only
    STATUS  mandatory
    DESCRIPTION
      "The index of the attack that was detected"
    ::=  {rsIDSLogEntry 1}

rsIDSLogAttackName OBJECT-TYPE
    SYNTAX DisplayString (SIZE(0..80))
    ACCESS  read-only
    STATUS  mandatory
    DESCRIPTION
      "The Name for the attack"
    ::=  {rsIDSLogEntry 2}

rsIDSLogSrcAddr OBJECT-TYPE
    SYNTAX  IpAddress
    ACCESS  read-only
    STATUS  mandatory
    DESCRIPTION
      "The src address of the attack"
    ::=  {rsIDSLogEntry 3}

rsIDSLogDstAddr OBJECT-TYPE
    SYNTAX  IpAddress
    ACCESS  read-only
    STATUS  mandatory
    DESCRIPTION
      "The dest address of the attack"
    ::=  {rsIDSLogEntry 4}

rsIDSLogAttackStatus OBJECT-TYPE
    SYNTAX INTEGER {
      started(1),
      terminated(2),
      occured(3),
      ongoing(4),
      started-ssl(5),
      terminated-ssl(6),
      occured-ssl(7),
      appsec(8),
      alert-sent(9),
      activated(10),
      blocking(11),
      deactivation-alert(12),
      deactivated(13),
	  ongoing-slt(14),
	  started-term(15),
	  started-term-ssl(16),
	  active-deactive(17)
   }
    ACCESS  read-only
    STATUS  mandatory
    DESCRIPTION
      "The status of the attack(started/terminated/occured...)"
    ::=  {rsIDSLogEntry 5}

rsIDSLogtime OBJECT-TYPE
    SYNTAX DisplayString (SIZE(0..32))
    ACCESS  read-only
    STATUS  mandatory
    DESCRIPTION
      "The time of the attack"
    ::=  {rsIDSLogEntry 6}

rsIDSLogStatus OBJECT-TYPE
    SYNTAX RowStatus
    ACCESS  read-write
    STATUS  mandatory
    DESCRIPTION
       "This variable indicates the administrative status of this entry.
        Used to delete an entry of this table."
    ::=  { rsIDSLogEntry 7 }

rsIDSLogContext  OBJECT-TYPE
    SYNTAX INTEGER {
    	regular(1),
    	ssl(2)
    }
    ACCESS  read-only
    STATUS  mandatory
    DESCRIPTION
      "The context of the attack"
    ::=  {rsIDSLogEntry 8}
    
    
rsIDSLogSrcPort  OBJECT-TYPE
    SYNTAX INTEGER 
    ACCESS  read-only
    STATUS  mandatory
    DESCRIPTION
      "The src address of the attack"
    ::=  {rsIDSLogEntry 9}
    
rsIDSLogDstPort  OBJECT-TYPE
    SYNTAX INTEGER 
    ACCESS  read-only
    STATUS  mandatory
    DESCRIPTION
      "The dst address of the attack"
    ::=  {rsIDSLogEntry 10}
    
rsIDSLogProtocol OBJECT-TYPE
    SYNTAX INTEGER {
    	ip(1),
    	tcp(2),
    	udp(3),
    	icmp(4)
    }
    ACCESS  read-only
    STATUS  mandatory
    DESCRIPTION
      "The protocol of the attack"
    ::=  {rsIDSLogEntry 11}

rsIDSLogPhyPort OBJECT-TYPE
    SYNTAX INTEGER 
    ACCESS  read-only
    STATUS  mandatory
    DESCRIPTION
      "The phy address of the attack"
    ::=  {rsIDSLogEntry 12}

rsIDSLogRID OBJECT-TYPE
    SYNTAX INTEGER 
    ACCESS  read-only
    STATUS  mandatory
    DESCRIPTION
      "The Radware ID of the attack"
    ::=  {rsIDSLogEntry 13}

rsIDSLogService OBJECT-TYPE
    SYNTAX INTEGER {
      unassigned(1),
      intrusion(2),
      dos(3),
	  anomalies(4),
	  scanning(5)
   }    
    ACCESS  read-only
    STATUS  mandatory
    DESCRIPTION
      "The Service related to the event"
    ::=  {rsIDSLogEntry 14}

rsIDSLogPolicyName OBJECT-TYPE
    SYNTAX DisplayString (SIZE(0..80))
    ACCESS  read-only
    STATUS  mandatory
    DESCRIPTION
      "The Name for the policy"
    ::=  {rsIDSLogEntry 15}

rsIDSLogPktCount OBJECT-TYPE
    SYNTAX INTEGER 
    ACCESS  read-only
    STATUS  mandatory
    DESCRIPTION
      "The # of packets that match the attack filter"
    ::=  {rsIDSLogEntry 16}

rsIDSLogByteCount OBJECT-TYPE
    SYNTAX INTEGER 
    ACCESS  read-only
    STATUS  mandatory
    DESCRIPTION
      "The # of packets that match the attack filter"
    ::=  {rsIDSLogEntry 17}

rsIDSLogReportMode OBJECT-TYPE
    SYNTAX INTEGER {
		  drop(1),
		  forward(2),
       	  rst-src(3),
   	      rst-dst(4),
   	      rst-bi(5)}
    ACCESS  read-only
    STATUS  mandatory
    DESCRIPTION
       "This variable indicates the action performed on the attack"
    ::=  {rsIDSLogEntry 18}

rsIDSLogRisk OBJECT-TYPE
    SYNTAX INTEGER {
		  n-a(1),
		  low(2),
       	  medium(3),
		  high(4)}
    ACCESS  read-only
    STATUS  mandatory
    DESCRIPTION
       "This variable indicates the risk of the attack"
    ::=  {rsIDSLogEntry 19}

rsIDSGlobalPacketReport OBJECT-TYPE
 SYNTAX INTEGER {
      enable(1),
      disable(2)
   }
    ACCESS read-write
    STATUS mandatory
    DESCRIPTION
      "The Application Security global packet-reporting configuration"
   DEFVAL  {disable}
    ::= {rsIDS 62}

rsIDSGroupCategoryTable OBJECT-TYPE
    SYNTAX SEQUENCE OF RsIDSGroupCategoryEntry
    ACCESS not-accessible
    STATUS  mandatory
    DESCRIPTION
      "Table group list and categories."
    ::= { rsIDS 63 }

rsIDSGroupCategoryEntry OBJECT-TYPE
    SYNTAX RsIDSGroupCategoryEntry 
    ACCESS not-accessible
    STATUS mandatory
    DESCRIPTION
       "The row definition for this table."
    INDEX {rsIDSGroupCategory, rsIDSGroupCatName }
    ::=  { rsIDSGroupCategoryTable 1 }

RsIDSGroupCategoryEntry ::= SEQUENCE {
    rsIDSGroupCategory INTEGER,
    rsIDSGroupCatName DisplayString
}

rsIDSGroupCategory OBJECT-TYPE
    SYNTAX INTEGER {
        unassigned(1),
        intrusions(2),
        dos(3),
        anomalies(4),
        anti-scanning(5)
    }
    ACCESS read-only
    STATUS mandatory
    DESCRIPTION
      "The group category."
    ::=  { rsIDSGroupCategoryEntry 1 }

rsIDSGroupCatName OBJECT-TYPE
    SYNTAX DisplayString(SIZE(0..30))
    ACCESS read-write
    STATUS mandatory
    DESCRIPTION
      "The name of the group."
    ::=  { rsIDSGroupCategoryEntry 2 }

rsIDSReportingInterval OBJECT-TYPE
    SYNTAX INTEGER (1..65535)
    ACCESS read-write
    STATUS mandatory
    DESCRIPTION
      "Reporting Interval"
    DEFVAL  { 5 }
    ::=  { rsIDS 64 }

rsIDSMaxAlertPerReport OBJECT-TYPE
    SYNTAX INTEGER (1..65535)
    ACCESS read-write
    STATUS mandatory
    DESCRIPTION
      "Maximum Alerts per Report"
    DEFVAL  { 1000 }
    ::=  { rsIDS 65 }

rsIDSProfilesTable OBJECT-TYPE
    SYNTAX SEQUENCE OF RsIDSProfilesEntry
    ACCESS not-accessible
    STATUS  mandatory
    DESCRIPTION
      "Table containing the list of rules params for the ids"
    ::=  {rsIDS 66}

rsIDSProfilesEntry OBJECT-TYPE
    SYNTAX RsIDSProfilesEntry
    ACCESS not-accessible
    STATUS  mandatory
    DESCRIPTION
       "The row definition for this table."
    INDEX { rsIDSProfilesName, rsIDSProfileServiceName }
    ::=  { rsIDSProfilesTable 1 }

RsIDSProfilesEntry ::= SEQUENCE {
    rsIDSProfilesName DisplayString,
    rsIDSProfileServiceName DisplayString,
	rsIDSProfileCategory INTEGER,
    rsIDSProfilesStatus RowStatus
}

rsIDSProfilesName OBJECT-TYPE
    SYNTAX DisplayString (SIZE(0..30))
    ACCESS  read-write
    STATUS  mandatory
    DESCRIPTION
      "The Name for the Profile."
    ::=  {rsIDSProfilesEntry 1}

rsIDSProfileServiceName OBJECT-TYPE
    SYNTAX DisplayString (SIZE(0..30))
    ACCESS  read-write
    STATUS  mandatory
    DESCRIPTION
      "The Name for the Service."
    ::=  {rsIDSProfilesEntry 2}

rsIDSProfileCategory OBJECT-TYPE
    SYNTAX INTEGER {
        intrusions(2),
        dos(3),
        anomalies(4),
        anti-scanning(5)
    }
    ACCESS read-write
    STATUS mandatory
    DESCRIPTION
      "The profile category."
    ::=  { rsIDSProfilesEntry 3 }

rsIDSProfilesStatus OBJECT-TYPE
    SYNTAX RowStatus
    ACCESS  read-write
    STATUS  mandatory
    DESCRIPTION
       "This variable indicates the administrative status of this entry.
        Used to delete an entry of this table."
    ::=  { rsIDSProfilesEntry 4 }

rsIDSNCPSTableSizeAfterReset OBJECT-TYPE
    SYNTAX INTEGER
    ACCESS read-write
    STATUS mandatory
    DESCRIPTION
      "the NCPS after-reset table size"
    ::= {rsIDS 67}

rsIDSSLTProfilesTable OBJECT-TYPE
    SYNTAX SEQUENCE OF RsIDSSLTProfilesEntry
    ACCESS not-accessible
    STATUS  mandatory
    DESCRIPTION
      "Table containing the list of SLT rules params for the ids"
    ::=  {rsIDS 68}

rsIDSSLTProfilesEntry OBJECT-TYPE
    SYNTAX RsIDSSLTProfilesEntry
    ACCESS not-accessible
    STATUS  mandatory
    DESCRIPTION
       "The row definition for this table."
    INDEX { rsIDSSLTProfilesName, rsIDSSLTProfileServiceName }
    ::=  { rsIDSSLTProfilesTable 1 }

RsIDSSLTProfilesEntry ::= SEQUENCE {
    rsIDSSLTProfilesName DisplayString,
    rsIDSSLTProfileServiceName DisplayString,
	rsIDSSLTProfileCategory INTEGER,
    rsIDSSLTProfilesStatus RowStatus
}

rsIDSSLTProfilesName OBJECT-TYPE
    SYNTAX DisplayString (SIZE(0..30))
    ACCESS  read-write
    STATUS  mandatory
    DESCRIPTION
      "The Name for the Profile."
    ::=  {rsIDSSLTProfilesEntry 1}

rsIDSSLTProfileServiceName OBJECT-TYPE
    SYNTAX DisplayString (SIZE(0..30))
    ACCESS  read-write
    STATUS  mandatory
    DESCRIPTION
      "The Name for the Service."
    ::=  {rsIDSSLTProfilesEntry 2}

rsIDSSLTProfileCategory OBJECT-TYPE
    SYNTAX INTEGER {
        dos(3)
    }
    ACCESS read-write
    STATUS mandatory
    DESCRIPTION
      "The profile category."
    ::=  { rsIDSSLTProfilesEntry 3 }

rsIDSSLTProfilesStatus OBJECT-TYPE
    SYNTAX RowStatus
    ACCESS  read-write
    STATUS  mandatory
    DESCRIPTION
       "This variable indicates the administrative status of this entry.
        Used to delete an entry of this table."
    ::=  { rsIDSSLTProfilesEntry 4 }

rsIDSSLTNewRulesTable OBJECT-TYPE
    SYNTAX SEQUENCE OF RsIDSSLTNewRulesEntry
    ACCESS not-accessible
    STATUS  mandatory
    DESCRIPTION
      "Table containing the list of rules params for the ids"
    ::=  {rsIDS 69}

rsIDSSLTNewRulesEntry OBJECT-TYPE
    SYNTAX RsIDSSLTNewRulesEntry
    ACCESS not-accessible
    STATUS  mandatory
    DESCRIPTION
       "The row definition for this table."
    INDEX { rsIDSSLTNewRulesName }
    ::=  { rsIDSSLTNewRulesTable 1 }

RsIDSSLTNewRulesEntry ::= SEQUENCE {
    rsIDSSLTNewRulesName DisplayString,
    rsIDSSLTServiceName DisplayString,
    rsIDSSLTNewRulesSource DisplayString,
    rsIDSSLTNewRulesDestination DisplayString,
    rsIDSSLTNewRulesDirection INTEGER,
    rsIDSSLTNewRulesPortmask DisplayString,
    rsIDSSLTNewRulesState INTEGER,
    rsIDSSLTNewRulesStatus  RowStatus,
	rsIDSSLTNewRulesVlanTagGroup DisplayString
}

rsIDSSLTNewRulesName OBJECT-TYPE
    SYNTAX DisplayString (SIZE(0..20))
    ACCESS  read-write
    STATUS  mandatory
    DESCRIPTION
      "The Name for the Rule."
    ::=  {rsIDSSLTNewRulesEntry 1}

rsIDSSLTServiceName OBJECT-TYPE
    SYNTAX DisplayString (SIZE(0..30))
    ACCESS  read-write
    STATUS  mandatory
    DESCRIPTION
      "The Name for the Service."
    ::=  {rsIDSSLTNewRulesEntry 2}

rsIDSSLTNewRulesSource OBJECT-TYPE
    SYNTAX DisplayString (SIZE(0..20))
    ACCESS  read-write
    STATUS  mandatory
    DESCRIPTION
      "The source address / range of address for the packet, the name is
      defined in the Objects table or can be an IP address."
    ::=  {rsIDSSLTNewRulesEntry 3}

rsIDSSLTNewRulesDestination OBJECT-TYPE
    SYNTAX DisplayString (SIZE(0..20))
    ACCESS  read-write
    STATUS  mandatory
    DESCRIPTION
      "The destination address / range of address for the packet, the name is
      defined in the Objects table or can be an IP address."
    ::=  {rsIDSSLTNewRulesEntry 4}

rsIDSSLTNewRulesDirection OBJECT-TYPE
    SYNTAX INTEGER {
              oneway(1),
              twoway(2) }
    ACCESS  read-write
    STATUS  mandatory
    DESCRIPTION
       "This variable indicates the direction of the incoming packet."
    DEFVAL { 1 }
    ::=  { rsIDSSLTNewRulesEntry 5 }


rsIDSSLTNewRulesPortmask OBJECT-TYPE
    SYNTAX DisplayString (SIZE(0..80))
    ACCESS  read-write
    STATUS  mandatory
    DESCRIPTION
       "The Port Group"
    ::=  { rsIDSSLTNewRulesEntry 6 }

 rsIDSSLTNewRulesState OBJECT-TYPE
    SYNTAX INTEGER {
              active(1),
              inactive(2) }
    ACCESS  read-write
    STATUS  mandatory
    DESCRIPTION
       "This variable indicates the state of the rule."
    DEFVAL { 1 }
    ::=  { rsIDSSLTNewRulesEntry 7 }

rsIDSSLTNewRulesStatus OBJECT-TYPE
    SYNTAX RowStatus
    ACCESS  read-write
    STATUS  mandatory
    DESCRIPTION
       "This variable indicates the administrative status of this entry.
        Used to delete an entry of this table."
    ::=  { rsIDSSLTNewRulesEntry 8 }

rsIDSSLTNewRulesVlanTagGroup OBJECT-TYPE
    SYNTAX DisplayString (SIZE(0..80))
    ACCESS  read-write
    STATUS  mandatory
    DESCRIPTION
       "The VLAN tag Group"
    ::=  { rsIDSSLTNewRulesEntry 9 }


rsIDSReportTerminalStatus OBJECT-TYPE
 SYNTAX INTEGER {
      enable(1),
      disable(2)
   }
    ACCESS read-write
    STATUS mandatory
    DESCRIPTION
      "configures the terminal echo on security event"
   DEFVAL  {enable}
    ::= {rsIDS 70}

rsIDSReportSysLogStatus OBJECT-TYPE
 SYNTAX INTEGER {
      enable(1),
      disable(2)
   }
    ACCESS read-write
    STATUS mandatory
    DESCRIPTION
      "configures syslog sending status on security event"
   DEFVAL  {enable}
    ::= {rsIDS 71}

rsIDSPacketReportLimit OBJECT-TYPE
    SYNTAX INTEGER
    ACCESS read-write
    STATUS mandatory
    DESCRIPTION
      "the maximum number of reported packets per-report interval"
	DEFVAL  { 10000 }
    ::= {rsIDS 72}

rsIDSPacketReportAttackLimit OBJECT-TYPE
    SYNTAX INTEGER
    ACCESS read-write
    STATUS mandatory
    DESCRIPTION
      "the maximum number of reported packets per-attack per-report interval"
	DEFVAL  { 10 }
    ::= {rsIDS 73}

rsIDSReportAggregationTrheshold OBJECT-TYPE
    SYNTAX INTEGER
    ACCESS read-write
    STATUS mandatory
    DESCRIPTION
      "the maximum number of reported packets per-report interval"
	DEFVAL  { 10 }
    ::= {rsIDS 74}

   END
