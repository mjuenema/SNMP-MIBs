-- file automatically created


TELDAT-TRAP-G703-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


g703TrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the G703 event subsystem."
    REVISION "201401200930Z"
    DESCRIPTION "Initial implementation"
        ::= { telEventTraps 161 }


g703EventsGroup	OBJECT IDENTIFIER	::= { g703TrapsMIB 1 }

g703Notifications	OBJECT IDENTIFIER	::= { g703TrapsMIB 2 }
g703NotificationsPrefix	OBJECT IDENTIFIER	::= { g703Notifications 0 }

g703EventObjects1 OBJECT-IDENTITY
    STATUS current
    DESCRIPTION
        "Event G703.1
        Loss of Signal Alarm Set."
    ::= { g703EventsGroup 1 }

g7031_ifc_name OBJECT-TYPE
    SYNTAX DisplayString
    MAX-ACCESS accessible-for-notify
    STATUS current
    DESCRIPTION
        "Parameter 'ifc_name' in event G703.1"
    ::= { g703EventObjects1 1 }

g703EventObjects2 OBJECT-IDENTITY
    STATUS current
    DESCRIPTION
        "Event G703.2
        Loss of Signal Alarm Clear."
    ::= { g703EventsGroup 2 }

g7032_ifc_name OBJECT-TYPE
    SYNTAX DisplayString
    MAX-ACCESS accessible-for-notify
    STATUS current
    DESCRIPTION
        "Parameter 'ifc_name' in event G703.2"
    ::= { g703EventObjects2 1 }

g703EventObjects3 OBJECT-IDENTITY
    STATUS current
    DESCRIPTION
        "Event G703.3
        Out Of Frame Alarm Set."
    ::= { g703EventsGroup 3 }

g7033_ifc_name OBJECT-TYPE
    SYNTAX DisplayString
    MAX-ACCESS accessible-for-notify
    STATUS current
    DESCRIPTION
        "Parameter 'ifc_name' in event G703.3"
    ::= { g703EventObjects3 1 }

g703EventObjects4 OBJECT-IDENTITY
    STATUS current
    DESCRIPTION
        "Event G703.4
        Out Of Frame Alarm Clear."
    ::= { g703EventsGroup 4 }

g7034_ifc_name OBJECT-TYPE
    SYNTAX DisplayString
    MAX-ACCESS accessible-for-notify
    STATUS current
    DESCRIPTION
        "Parameter 'ifc_name' in event G703.4"
    ::= { g703EventObjects4 1 }

g703EventObjects5 OBJECT-IDENTITY
    STATUS current
    DESCRIPTION
        "Event G703.5
        Ramote Alarm Indication Set."
    ::= { g703EventsGroup 5 }

g7035_ifc_name OBJECT-TYPE
    SYNTAX DisplayString
    MAX-ACCESS accessible-for-notify
    STATUS current
    DESCRIPTION
        "Parameter 'ifc_name' in event G703.5"
    ::= { g703EventObjects5 1 }

g703EventObjects6 OBJECT-IDENTITY
    STATUS current
    DESCRIPTION
        "Event G703.6
        Ramote Alarm Indication Clear."
    ::= { g703EventsGroup 6 }

g7036_ifc_name OBJECT-TYPE
    SYNTAX DisplayString
    MAX-ACCESS accessible-for-notify
    STATUS current
    DESCRIPTION
        "Parameter 'ifc_name' in event G703.6"
    ::= { g703EventObjects6 1 }

g703EventObjects7 OBJECT-IDENTITY
    STATUS current
    DESCRIPTION
        "Event G703.7
        Alarm Indication Signal Set."
    ::= { g703EventsGroup 7 }

g7037_ifc_name OBJECT-TYPE
    SYNTAX DisplayString
    MAX-ACCESS accessible-for-notify
    STATUS current
    DESCRIPTION
        "Parameter 'ifc_name' in event G703.7"
    ::= { g703EventObjects7 1 }

g703EventObjects8 OBJECT-IDENTITY
    STATUS current
    DESCRIPTION
        "Event G703.8
        Alarm Indication Signal Clear."
    ::= { g703EventsGroup 8 }

g7038_ifc_name OBJECT-TYPE
    SYNTAX DisplayString
    MAX-ACCESS accessible-for-notify
    STATUS current
    DESCRIPTION
        "Parameter 'ifc_name' in event G703.8"
    ::= { g703EventObjects8 1 }

g703EventObjects9 OBJECT-IDENTITY
    STATUS current
    DESCRIPTION
        "Event G703.9
        Open Fail."
    ::= { g703EventsGroup 9 }

g7039_index OBJECT-TYPE
    SYNTAX Integer32
    MAX-ACCESS accessible-for-notify
    STATUS current
    DESCRIPTION
        "Parameter 'index' in event G703.9"
    ::= { g703EventObjects9 1 }

g7039_list OBJECT-TYPE
    SYNTAX Integer32
    MAX-ACCESS accessible-for-notify
    STATUS current
    DESCRIPTION
        "Parameter 'list' in event G703.9"
    ::= { g703EventObjects9 2 }

g7039_ifc_name OBJECT-TYPE
    SYNTAX DisplayString
    MAX-ACCESS accessible-for-notify
    STATUS current
    DESCRIPTION
        "Parameter 'ifc_name' in event G703.9"
    ::= { g703EventObjects9 3 }

g703EventObjects10 OBJECT-IDENTITY
    STATUS current
    DESCRIPTION
        "Event G703.10
        Open Success."
    ::= { g703EventsGroup 10 }

g70310_index OBJECT-TYPE
    SYNTAX Integer32
    MAX-ACCESS accessible-for-notify
    STATUS current
    DESCRIPTION
        "Parameter 'index' in event G703.10"
    ::= { g703EventObjects10 1 }

g70310_list OBJECT-TYPE
    SYNTAX Integer32
    MAX-ACCESS accessible-for-notify
    STATUS current
    DESCRIPTION
        "Parameter 'list' in event G703.10"
    ::= { g703EventObjects10 2 }

g70310_ifc_name OBJECT-TYPE
    SYNTAX DisplayString
    MAX-ACCESS accessible-for-notify
    STATUS current
    DESCRIPTION
        "Parameter 'ifc_name' in event G703.10"
    ::= { g703EventObjects10 3 }

g703EventObjects11 OBJECT-IDENTITY
    STATUS current
    DESCRIPTION
        "Event G703.11
        Close Fail."
    ::= { g703EventsGroup 11 }

g70311_index OBJECT-TYPE
    SYNTAX Integer32
    MAX-ACCESS accessible-for-notify
    STATUS current
    DESCRIPTION
        "Parameter 'index' in event G703.11"
    ::= { g703EventObjects11 1 }

g70311_list OBJECT-TYPE
    SYNTAX Integer32
    MAX-ACCESS accessible-for-notify
    STATUS current
    DESCRIPTION
        "Parameter 'list' in event G703.11"
    ::= { g703EventObjects11 2 }

g70311_ifc_name OBJECT-TYPE
    SYNTAX DisplayString
    MAX-ACCESS accessible-for-notify
    STATUS current
    DESCRIPTION
        "Parameter 'ifc_name' in event G703.11"
    ::= { g703EventObjects11 3 }

g703EventObjects12 OBJECT-IDENTITY
    STATUS current
    DESCRIPTION
        "Event G703.12
        Close Success."
    ::= { g703EventsGroup 12 }

g70312_index OBJECT-TYPE
    SYNTAX Integer32
    MAX-ACCESS accessible-for-notify
    STATUS current
    DESCRIPTION
        "Parameter 'index' in event G703.12"
    ::= { g703EventObjects12 1 }

g70312_list OBJECT-TYPE
    SYNTAX Integer32
    MAX-ACCESS accessible-for-notify
    STATUS current
    DESCRIPTION
        "Parameter 'list' in event G703.12"
    ::= { g703EventObjects12 2 }

g70312_ifc_name OBJECT-TYPE
    SYNTAX DisplayString
    MAX-ACCESS accessible-for-notify
    STATUS current
    DESCRIPTION
        "Parameter 'ifc_name' in event G703.12"
    ::= { g703EventObjects12 3 }

g703EventObjects13 OBJECT-IDENTITY
    STATUS current
    DESCRIPTION
        "Event G703.13
        A frame was transmitted."
    ::= { g703EventsGroup 13 }

g70313_index OBJECT-TYPE
    SYNTAX Integer32
    MAX-ACCESS accessible-for-notify
    STATUS current
    DESCRIPTION
        "Parameter 'index' in event G703.13"
    ::= { g703EventObjects13 1 }

g70313_value OBJECT-TYPE
    SYNTAX Integer32
    MAX-ACCESS accessible-for-notify
    STATUS current
    DESCRIPTION
        "Parameter 'value' in event G703.13"
    ::= { g703EventObjects13 2 }

g70313_ifc_name OBJECT-TYPE
    SYNTAX DisplayString
    MAX-ACCESS accessible-for-notify
    STATUS current
    DESCRIPTION
        "Parameter 'ifc_name' in event G703.13"
    ::= { g703EventObjects13 3 }

g703EventObjects14 OBJECT-IDENTITY
    STATUS current
    DESCRIPTION
        "Event G703.14
        A frame was transmitted with error."
    ::= { g703EventsGroup 14 }

g70314_index OBJECT-TYPE
    SYNTAX Integer32
    MAX-ACCESS accessible-for-notify
    STATUS current
    DESCRIPTION
        "Parameter 'index' in event G703.14"
    ::= { g703EventObjects14 1 }

g70314_ifc_name OBJECT-TYPE
    SYNTAX DisplayString
    MAX-ACCESS accessible-for-notify
    STATUS current
    DESCRIPTION
        "Parameter 'ifc_name' in event G703.14"
    ::= { g703EventObjects14 2 }

g703EventObjects15 OBJECT-IDENTITY
    STATUS current
    DESCRIPTION
        "Event G703.15
        A frame in the transmit path was dropped."
    ::= { g703EventsGroup 15 }

g70315_index OBJECT-TYPE
    SYNTAX Integer32
    MAX-ACCESS accessible-for-notify
    STATUS current
    DESCRIPTION
        "Parameter 'index' in event G703.15"
    ::= { g703EventObjects15 1 }

g70315_value OBJECT-TYPE
    SYNTAX Integer32
    MAX-ACCESS accessible-for-notify
    STATUS current
    DESCRIPTION
        "Parameter 'value' in event G703.15"
    ::= { g703EventObjects15 2 }

g70315_ifc_name OBJECT-TYPE
    SYNTAX DisplayString
    MAX-ACCESS accessible-for-notify
    STATUS current
    DESCRIPTION
        "Parameter 'ifc_name' in event G703.15"
    ::= { g703EventObjects15 3 }

g703EventObjects16 OBJECT-IDENTITY
    STATUS current
    DESCRIPTION
        "Event G703.16
        A frame was received."
    ::= { g703EventsGroup 16 }

g70316_index OBJECT-TYPE
    SYNTAX Integer32
    MAX-ACCESS accessible-for-notify
    STATUS current
    DESCRIPTION
        "Parameter 'index' in event G703.16"
    ::= { g703EventObjects16 1 }

g70316_value OBJECT-TYPE
    SYNTAX Integer32
    MAX-ACCESS accessible-for-notify
    STATUS current
    DESCRIPTION
        "Parameter 'value' in event G703.16"
    ::= { g703EventObjects16 2 }

g70316_ifc_name OBJECT-TYPE
    SYNTAX DisplayString
    MAX-ACCESS accessible-for-notify
    STATUS current
    DESCRIPTION
        "Parameter 'ifc_name' in event G703.16"
    ::= { g703EventObjects16 3 }

g703EventObjects17 OBJECT-IDENTITY
    STATUS current
    DESCRIPTION
        "Event G703.17
        A short frame was received."
    ::= { g703EventsGroup 17 }

g70317_index OBJECT-TYPE
    SYNTAX Integer32
    MAX-ACCESS accessible-for-notify
    STATUS current
    DESCRIPTION
        "Parameter 'index' in event G703.17"
    ::= { g703EventObjects17 1 }

g70317_value OBJECT-TYPE
    SYNTAX Integer32
    MAX-ACCESS accessible-for-notify
    STATUS current
    DESCRIPTION
        "Parameter 'value' in event G703.17"
    ::= { g703EventObjects17 2 }

g70317_ifc_name OBJECT-TYPE
    SYNTAX DisplayString
    MAX-ACCESS accessible-for-notify
    STATUS current
    DESCRIPTION
        "Parameter 'ifc_name' in event G703.17"
    ::= { g703EventObjects17 3 }

g703EventObjects18 OBJECT-IDENTITY
    STATUS current
    DESCRIPTION
        "Event G703.18
        A frame was received with CRC error."
    ::= { g703EventsGroup 18 }

g70318_index OBJECT-TYPE
    SYNTAX Integer32
    MAX-ACCESS accessible-for-notify
    STATUS current
    DESCRIPTION
        "Parameter 'index' in event G703.18"
    ::= { g703EventObjects18 1 }

g70318_value OBJECT-TYPE
    SYNTAX Integer32
    MAX-ACCESS accessible-for-notify
    STATUS current
    DESCRIPTION
        "Parameter 'value' in event G703.18"
    ::= { g703EventObjects18 2 }

g70318_ifc_name OBJECT-TYPE
    SYNTAX DisplayString
    MAX-ACCESS accessible-for-notify
    STATUS current
    DESCRIPTION
        "Parameter 'ifc_name' in event G703.18"
    ::= { g703EventObjects18 3 }

g703EventObjects19 OBJECT-IDENTITY
    STATUS current
    DESCRIPTION
        "Event G703.19
        A incomplete frame was received."
    ::= { g703EventsGroup 19 }

g70319_index OBJECT-TYPE
    SYNTAX Integer32
    MAX-ACCESS accessible-for-notify
    STATUS current
    DESCRIPTION
        "Parameter 'index' in event G703.19"
    ::= { g703EventObjects19 1 }

g70319_value OBJECT-TYPE
    SYNTAX Integer32
    MAX-ACCESS accessible-for-notify
    STATUS current
    DESCRIPTION
        "Parameter 'value' in event G703.19"
    ::= { g703EventObjects19 2 }

g70319_ifc_name OBJECT-TYPE
    SYNTAX DisplayString
    MAX-ACCESS accessible-for-notify
    STATUS current
    DESCRIPTION
        "Parameter 'ifc_name' in event G703.19"
    ::= { g703EventObjects19 3 }

g703EventObjects20 OBJECT-IDENTITY
    STATUS current
    DESCRIPTION
        "Event G703.20
        A long frame was received. Check interface MTU."
    ::= { g703EventsGroup 20 }

g70320_index OBJECT-TYPE
    SYNTAX Integer32
    MAX-ACCESS accessible-for-notify
    STATUS current
    DESCRIPTION
        "Parameter 'index' in event G703.20"
    ::= { g703EventObjects20 1 }

g70320_value OBJECT-TYPE
    SYNTAX Integer32
    MAX-ACCESS accessible-for-notify
    STATUS current
    DESCRIPTION
        "Parameter 'value' in event G703.20"
    ::= { g703EventObjects20 2 }

g70320_ifc_name OBJECT-TYPE
    SYNTAX DisplayString
    MAX-ACCESS accessible-for-notify
    STATUS current
    DESCRIPTION
        "Parameter 'ifc_name' in event G703.20"
    ::= { g703EventObjects20 3 }

g703EventObjects21 OBJECT-IDENTITY
    STATUS current
    DESCRIPTION
        "Event G703.21
        An aborted frame was received."
    ::= { g703EventsGroup 21 }

g70321_index OBJECT-TYPE
    SYNTAX Integer32
    MAX-ACCESS accessible-for-notify
    STATUS current
    DESCRIPTION
        "Parameter 'index' in event G703.21"
    ::= { g703EventObjects21 1 }

g70321_value OBJECT-TYPE
    SYNTAX Integer32
    MAX-ACCESS accessible-for-notify
    STATUS current
    DESCRIPTION
        "Parameter 'value' in event G703.21"
    ::= { g703EventObjects21 2 }

g70321_ifc_name OBJECT-TYPE
    SYNTAX DisplayString
    MAX-ACCESS accessible-for-notify
    STATUS current
    DESCRIPTION
        "Parameter 'ifc_name' in event G703.21"
    ::= { g703EventObjects21 3 }

g703EventObjects22 OBJECT-IDENTITY
    STATUS current
    DESCRIPTION
        "Event G703.22
        Overflow on reception path."
    ::= { g703EventsGroup 22 }

g70322_index OBJECT-TYPE
    SYNTAX Integer32
    MAX-ACCESS accessible-for-notify
    STATUS current
    DESCRIPTION
        "Parameter 'index' in event G703.22"
    ::= { g703EventObjects22 1 }

g70322_ifc_name OBJECT-TYPE
    SYNTAX DisplayString
    MAX-ACCESS accessible-for-notify
    STATUS current
    DESCRIPTION
        "Parameter 'ifc_name' in event G703.22"
    ::= { g703EventObjects22 2 }

g703EventObjects23 OBJECT-IDENTITY
    STATUS current
    DESCRIPTION
        "Event G703.23
        A frame received was dropped."
    ::= { g703EventsGroup 23 }

g70323_index OBJECT-TYPE
    SYNTAX Integer32
    MAX-ACCESS accessible-for-notify
    STATUS current
    DESCRIPTION
        "Parameter 'index' in event G703.23"
    ::= { g703EventObjects23 1 }

g70323_value OBJECT-TYPE
    SYNTAX Integer32
    MAX-ACCESS accessible-for-notify
    STATUS current
    DESCRIPTION
        "Parameter 'value' in event G703.23"
    ::= { g703EventObjects23 2 }

g70323_ifc_name OBJECT-TYPE
    SYNTAX DisplayString
    MAX-ACCESS accessible-for-notify
    STATUS current
    DESCRIPTION
        "Parameter 'ifc_name' in event G703.23"
    ::= { g703EventObjects23 3 }

g703EventObjects24 OBJECT-IDENTITY
    STATUS current
    DESCRIPTION
        "Event G703.24
        A connection was created."
    ::= { g703EventsGroup 24 }

g70324_address OBJECT-TYPE
    SYNTAX Integer32
    MAX-ACCESS accessible-for-notify
    STATUS current
    DESCRIPTION
        "Parameter 'address' in event G703.24"
    ::= { g703EventObjects24 1 }

g70324_owner OBJECT-TYPE
    SYNTAX Integer32
    MAX-ACCESS accessible-for-notify
    STATUS current
    DESCRIPTION
        "Parameter 'owner' in event G703.24"
    ::= { g703EventObjects24 2 }

g70324_ifc_name OBJECT-TYPE
    SYNTAX DisplayString
    MAX-ACCESS accessible-for-notify
    STATUS current
    DESCRIPTION
        "Parameter 'ifc_name' in event G703.24"
    ::= { g703EventObjects24 3 }

g703EventObjects25 OBJECT-IDENTITY
    STATUS current
    DESCRIPTION
        "Event G703.25
        A connection was released."
    ::= { g703EventsGroup 25 }

g70325_address OBJECT-TYPE
    SYNTAX Integer32
    MAX-ACCESS accessible-for-notify
    STATUS current
    DESCRIPTION
        "Parameter 'address' in event G703.25"
    ::= { g703EventObjects25 1 }

g70325_owner OBJECT-TYPE
    SYNTAX Integer32
    MAX-ACCESS accessible-for-notify
    STATUS current
    DESCRIPTION
        "Parameter 'owner' in event G703.25"
    ::= { g703EventObjects25 2 }

g70325_ifc_name OBJECT-TYPE
    SYNTAX DisplayString
    MAX-ACCESS accessible-for-notify
    STATUS current
    DESCRIPTION
        "Parameter 'ifc_name' in event G703.25"
    ::= { g703EventObjects25 3 }

g703EventObjects26 OBJECT-IDENTITY
    STATUS current
    DESCRIPTION
        "Event G703.26
        Dynamic change on a group."
    ::= { g703EventsGroup 26 }

g70326_channel OBJECT-TYPE
    SYNTAX Integer32
    MAX-ACCESS accessible-for-notify
    STATUS current
    DESCRIPTION
        "Parameter 'channel' in event G703.26"
    ::= { g703EventObjects26 1 }

g70326_group OBJECT-TYPE
    SYNTAX Integer32
    MAX-ACCESS accessible-for-notify
    STATUS current
    DESCRIPTION
        "Parameter 'group' in event G703.26"
    ::= { g703EventObjects26 2 }

g70326_base_channel OBJECT-TYPE
    SYNTAX Integer32
    MAX-ACCESS accessible-for-notify
    STATUS current
    DESCRIPTION
        "Parameter 'base_channel' in event G703.26"
    ::= { g703EventObjects26 3 }

g70326_ifc_name OBJECT-TYPE
    SYNTAX DisplayString
    MAX-ACCESS accessible-for-notify
    STATUS current
    DESCRIPTION
        "Parameter 'ifc_name' in event G703.26"
    ::= { g703EventObjects26 4 }

g703EventObjects27 OBJECT-IDENTITY
    STATUS current
    DESCRIPTION
        "Event G703.27
        Not enough buffers."
    ::= { g703EventsGroup 27 }

g70327_index OBJECT-TYPE
    SYNTAX Integer32
    MAX-ACCESS accessible-for-notify
    STATUS current
    DESCRIPTION
        "Parameter 'index' in event G703.27"
    ::= { g703EventObjects27 1 }

g70327_ifc_name OBJECT-TYPE
    SYNTAX DisplayString
    MAX-ACCESS accessible-for-notify
    STATUS current
    DESCRIPTION
        "Parameter 'ifc_name' in event G703.27"
    ::= { g703EventObjects27 2 }


g703Notification1 NOTIFICATION-TYPE
    OBJECTS { 
              g7031_ifc_name 
            }
    STATUS current
    DESCRIPTION
        "Notification of Event G703.1

        Message: 'Loss of Signal (Red Alarm) Set on interface $1'

        Parameters list:
              $1: g7031_ifc_name

        Loss of Signal Alarm Set."
    ::= { g703NotificationsPrefix 1 }

g703Notification2 NOTIFICATION-TYPE
    OBJECTS { 
              g7032_ifc_name 
            }
    STATUS current
    DESCRIPTION
        "Notification of Event G703.2

        Message: 'Loss of Signal (Red Alarm) Clear on interface $1'

        Parameters list:
              $1: g7032_ifc_name

        Loss of Signal Alarm Clear."
    ::= { g703NotificationsPrefix 2 }

g703Notification3 NOTIFICATION-TYPE
    OBJECTS { 
              g7033_ifc_name 
            }
    STATUS current
    DESCRIPTION
        "Notification of Event G703.3

        Message: 'Out Of Frame Alarm Set on interface $1'

        Parameters list:
              $1: g7033_ifc_name

        Out Of Frame Alarm Set."
    ::= { g703NotificationsPrefix 3 }

g703Notification4 NOTIFICATION-TYPE
    OBJECTS { 
              g7034_ifc_name 
            }
    STATUS current
    DESCRIPTION
        "Notification of Event G703.4

        Message: 'Out Of Frame Alarm Clear on interface $1'

        Parameters list:
              $1: g7034_ifc_name

        Out Of Frame Alarm Clear."
    ::= { g703NotificationsPrefix 4 }

g703Notification5 NOTIFICATION-TYPE
    OBJECTS { 
              g7035_ifc_name 
            }
    STATUS current
    DESCRIPTION
        "Notification of Event G703.5

        Message: 'Ramote Alarm Indication (Yellow Alarm) Set on interface $1'

        Parameters list:
              $1: g7035_ifc_name

        Ramote Alarm Indication Set."
    ::= { g703NotificationsPrefix 5 }

g703Notification6 NOTIFICATION-TYPE
    OBJECTS { 
              g7036_ifc_name 
            }
    STATUS current
    DESCRIPTION
        "Notification of Event G703.6

        Message: 'Ramote Alarm Indication (Yellow Alarm) Clear on interface $1'

        Parameters list:
              $1: g7036_ifc_name

        Ramote Alarm Indication Clear."
    ::= { g703NotificationsPrefix 6 }

g703Notification7 NOTIFICATION-TYPE
    OBJECTS { 
              g7037_ifc_name 
            }
    STATUS current
    DESCRIPTION
        "Notification of Event G703.7

        Message: 'Alarm Indication Signal (Blue Alarm) Set on interface $1'

        Parameters list:
              $1: g7037_ifc_name

        Alarm Indication Signal Set."
    ::= { g703NotificationsPrefix 7 }

g703Notification8 NOTIFICATION-TYPE
    OBJECTS { 
              g7038_ifc_name 
            }
    STATUS current
    DESCRIPTION
        "Notification of Event G703.8

        Message: 'Alarm Indication Signal(Blue Alarm) Clear on interface $1'

        Parameters list:
              $1: g7038_ifc_name

        Alarm Indication Signal Clear."
    ::= { g703NotificationsPrefix 8 }

g703Notification9 NOTIFICATION-TYPE
    OBJECTS { 
              g7039_index, 
              g7039_list,
              g7039_ifc_name 
            }
    STATUS current
    DESCRIPTION
        "Notification of Event G703.9

        Message: 'Open Fail for channel $1 with time slot map $2 on interface $3'

        Parameters list:
              $1: g7039_index
              $2: g7039_list
              $3: g7039_ifc_name

        Open Fail."
    ::= { g703NotificationsPrefix 9 }

g703Notification10 NOTIFICATION-TYPE
    OBJECTS { 
              g70310_index, 
              g70310_list,
              g70310_ifc_name 
            }
    STATUS current
    DESCRIPTION
        "Notification of Event G703.10

        Message: 'Open Success for channel $1 with time slot map $2 on interface $3'

        Parameters list:
              $1: g70310_index
              $2: g70310_list
              $3: g70310_ifc_name

        Open Success."
    ::= { g703NotificationsPrefix 10 }

g703Notification11 NOTIFICATION-TYPE
    OBJECTS { 
              g70311_index, 
              g70311_list,
              g70311_ifc_name 
            }
    STATUS current
    DESCRIPTION
        "Notification of Event G703.11

        Message: 'Close Fail for channel $1 with time slot map $2 on interface $3'

        Parameters list:
              $1: g70311_index
              $2: g70311_list
              $3: g70311_ifc_name

        Close Fail."
    ::= { g703NotificationsPrefix 11 }

g703Notification12 NOTIFICATION-TYPE
    OBJECTS { 
              g70312_index, 
              g70312_list,
              g70312_ifc_name 
            }
    STATUS current
    DESCRIPTION
        "Notification of Event G703.12

        Message: 'Close Success for channel $1 with time slot map $2 on interface $3'

        Parameters list:
              $1: g70312_index
              $2: g70312_list
              $3: g70312_ifc_name

        Close Success."
    ::= { g703NotificationsPrefix 12 }

g703Notification13 NOTIFICATION-TYPE
    OBJECTS { 
              g70313_index, 
              g70313_value,
              g70313_ifc_name 
            }
    STATUS current
    DESCRIPTION
        "Notification of Event G703.13

        Message: 'Frame transmitted channel $1 length $2 on interface $3'

        Parameters list:
              $1: g70313_index
              $2: g70313_value
              $3: g70313_ifc_name

        A frame was transmitted."
    ::= { g703NotificationsPrefix 13 }

g703Notification14 NOTIFICATION-TYPE
    OBJECTS { 
              g70314_index, 
              g70314_ifc_name 
            }
    STATUS current
    DESCRIPTION
        "Notification of Event G703.14

        Message: 'Frame transmitted with error channel $1 on interface $2'

        Parameters list:
              $1: g70314_index
              $2: g70314_ifc_name

        A frame was transmitted with error."
    ::= { g703NotificationsPrefix 14 }

g703Notification15 NOTIFICATION-TYPE
    OBJECTS { 
              g70315_index, 
              g70315_value,
              g70315_ifc_name 
            }
    STATUS current
    DESCRIPTION
        "Notification of Event G703.15

        Message: 'Frame transmitted dropped channel $1 length $2 on interface $3'

        Parameters list:
              $1: g70315_index
              $2: g70315_value
              $3: g70315_ifc_name

        A frame in the transmit path was dropped."
    ::= { g703NotificationsPrefix 15 }

g703Notification16 NOTIFICATION-TYPE
    OBJECTS { 
              g70316_index, 
              g70316_value,
              g70316_ifc_name 
            }
    STATUS current
    DESCRIPTION
        "Notification of Event G703.16

        Message: 'Frame received channel $1 length $2 on interface $3'

        Parameters list:
              $1: g70316_index
              $2: g70316_value
              $3: g70316_ifc_name

        A frame was received."
    ::= { g703NotificationsPrefix 16 }

g703Notification17 NOTIFICATION-TYPE
    OBJECTS { 
              g70317_index, 
              g70317_value,
              g70317_ifc_name 
            }
    STATUS current
    DESCRIPTION
        "Notification of Event G703.17

        Message: 'Frame received short channel $1 length $2 on interface $3'

        Parameters list:
              $1: g70317_index
              $2: g70317_value
              $3: g70317_ifc_name

        A short frame was received."
    ::= { g703NotificationsPrefix 17 }

g703Notification18 NOTIFICATION-TYPE
    OBJECTS { 
              g70318_index, 
              g70318_value,
              g70318_ifc_name 
            }
    STATUS current
    DESCRIPTION
        "Notification of Event G703.18

        Message: 'Frame received with crc error channel $1 length $2 on interface $3'

        Parameters list:
              $1: g70318_index
              $2: g70318_value
              $3: g70318_ifc_name

        A frame was received with CRC error."
    ::= { g703NotificationsPrefix 18 }

g703Notification19 NOTIFICATION-TYPE
    OBJECTS { 
              g70319_index, 
              g70319_value,
              g70319_ifc_name 
            }
    STATUS current
    DESCRIPTION
        "Notification of Event G703.19

        Message: 'Incomplete frame received channel $1 length $2 on interface $3'

        Parameters list:
              $1: g70319_index
              $2: g70319_value
              $3: g70319_ifc_name

        A incomplete frame was received."
    ::= { g703NotificationsPrefix 19 }

g703Notification20 NOTIFICATION-TYPE
    OBJECTS { 
              g70320_index, 
              g70320_value,
              g70320_ifc_name 
            }
    STATUS current
    DESCRIPTION
        "Notification of Event G703.20

        Message: 'Long frame received channel $1 length $2 on interface $3'

        Parameters list:
              $1: g70320_index
              $2: g70320_value
              $3: g70320_ifc_name

        A long frame was received. Check interface MTU."
    ::= { g703NotificationsPrefix 20 }

g703Notification21 NOTIFICATION-TYPE
    OBJECTS { 
              g70321_index, 
              g70321_value,
              g70321_ifc_name 
            }
    STATUS current
    DESCRIPTION
        "Notification of Event G703.21

        Message: 'Aborted frame received channel $1 length $2 on interface $3'

        Parameters list:
              $1: g70321_index
              $2: g70321_value
              $3: g70321_ifc_name

        An aborted frame was received."
    ::= { g703NotificationsPrefix 21 }

g703Notification22 NOTIFICATION-TYPE
    OBJECTS { 
              g70322_index, 
              g70322_ifc_name 
            }
    STATUS current
    DESCRIPTION
        "Notification of Event G703.22

        Message: 'Reception overlow channel $1 on interface $2'

        Parameters list:
              $1: g70322_index
              $2: g70322_ifc_name

        Overflow on reception path."
    ::= { g703NotificationsPrefix 22 }

g703Notification23 NOTIFICATION-TYPE
    OBJECTS { 
              g70323_index, 
              g70323_value,
              g70323_ifc_name 
            }
    STATUS current
    DESCRIPTION
        "Notification of Event G703.23

        Message: 'Drop frame received channel $1 length $2 on interface $3'

        Parameters list:
              $1: g70323_index
              $2: g70323_value
              $3: g70323_ifc_name

        A frame received was dropped."
    ::= { g703NotificationsPrefix 23 }

g703Notification24 NOTIFICATION-TYPE
    OBJECTS { 
              g70324_address, 
              g70324_owner,
              g70324_ifc_name 
            }
    STATUS current
    DESCRIPTION
        "Notification of Event G703.24

        Message: 'Create connection at $1 for $2 on interface $3'

        Parameters list:
              $1: g70324_address
              $2: g70324_owner
              $3: g70324_ifc_name

        A connection was created."
    ::= { g703NotificationsPrefix 24 }

g703Notification25 NOTIFICATION-TYPE
    OBJECTS { 
              g70325_address, 
              g70325_owner,
              g70325_ifc_name 
            }
    STATUS current
    DESCRIPTION
        "Notification of Event G703.25

        Message: 'Release connection at $1 for $2 on interface $3'

        Parameters list:
              $1: g70325_address
              $2: g70325_owner
              $3: g70325_ifc_name

        A connection was released."
    ::= { g703NotificationsPrefix 25 }

g703Notification26 NOTIFICATION-TYPE
    OBJECTS { 
              g70326_channel, 
              g70326_group,
              g70326_base_channel,
              g70326_ifc_name 
            }
    STATUS current
    DESCRIPTION
        "Notification of Event G703.26

        Message: 'Dynamic remove channel $1 from group $2 base channel $3 on interface $4'

        Parameters list:
              $1: g70326_channel
              $2: g70326_group
              $3: g70326_base_channel
              $4: g70326_ifc_name

        Dynamic change on a group."
    ::= { g703NotificationsPrefix 26 }

g703Notification27 NOTIFICATION-TYPE
    OBJECTS { 
              g70327_index, 
              g70327_ifc_name 
            }
    STATUS current
    DESCRIPTION
        "Notification of Event G703.27

        Message: 'Reception error not enough buffer for channel $1 on interface $2'

        Parameters list:
              $1: g70327_index
              $2: g70327_ifc_name

        Not enough buffers."
    ::= { g703NotificationsPrefix 27 }


END
