-- file automatically created


TELDAT-TRAP-P3OE-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


p3oeTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the P3OE event subsystem."
    REVISION "201401200930Z"
    DESCRIPTION "Initial implementation"
        ::= { telEventTraps 148 }


p3oeEventsGroup	OBJECT IDENTIFIER	::= { p3oeTrapsMIB 1 }

p3oeNotifications	OBJECT IDENTIFIER	::= { p3oeTrapsMIB 2 }
p3oeNotificationsPrefix	OBJECT IDENTIFIER	::= { p3oeNotifications 0 }

p3oeEventObjects1 OBJECT-IDENTITY
    STATUS current
    DESCRIPTION
        "Event P3OE.1
        An incoming packet is discarded because a PADT was previously received."
    ::= { p3oeEventsGroup 1 }

p3oe1_interface OBJECT-TYPE
    SYNTAX DisplayString
    MAX-ACCESS accessible-for-notify
    STATUS current
    DESCRIPTION
        "Parameter 'interface' in event P3OE.1"
    ::= { p3oeEventObjects1 1 }

p3oeEventObjects2 OBJECT-IDENTITY
    STATUS current
    DESCRIPTION
        "Event P3OE.2
        An incoming packet is discarded because of an unexpected tag length."
    ::= { p3oeEventsGroup 2 }

p3oe2_base_interface OBJECT-TYPE
    SYNTAX DisplayString
    MAX-ACCESS accessible-for-notify
    STATUS current
    DESCRIPTION
        "Parameter 'base_interface' in event P3OE.2"
    ::= { p3oeEventObjects2 1 }

p3oeEventObjects3 OBJECT-IDENTITY
    STATUS current
    DESCRIPTION
        "Event P3OE.3
        An incoming packet is discarded because of an incorrect Service-Name."
    ::= { p3oeEventsGroup 3 }

p3oe3_service_name OBJECT-TYPE
    SYNTAX DisplayString
    MAX-ACCESS accessible-for-notify
    STATUS current
    DESCRIPTION
        "Parameter 'service_name' in event P3OE.3"
    ::= { p3oeEventObjects3 1 }

p3oe3_interface OBJECT-TYPE
    SYNTAX DisplayString
    MAX-ACCESS accessible-for-notify
    STATUS current
    DESCRIPTION
        "Parameter 'interface' in event P3OE.3"
    ::= { p3oeEventObjects3 2 }

p3oeEventObjects4 OBJECT-IDENTITY
    STATUS current
    DESCRIPTION
        "Event P3OE.4
        An incoming packet is discarded because of an incorrect Ac-Name."
    ::= { p3oeEventsGroup 4 }

p3oe4_service_name OBJECT-TYPE
    SYNTAX DisplayString
    MAX-ACCESS accessible-for-notify
    STATUS current
    DESCRIPTION
        "Parameter 'service_name' in event P3OE.4"
    ::= { p3oeEventObjects4 1 }

p3oe4_interface OBJECT-TYPE
    SYNTAX DisplayString
    MAX-ACCESS accessible-for-notify
    STATUS current
    DESCRIPTION
        "Parameter 'interface' in event P3OE.4"
    ::= { p3oeEventObjects4 2 }

p3oeEventObjects5 OBJECT-IDENTITY
    STATUS current
    DESCRIPTION
        "Event P3OE.5
        An incoming packet is discarded because of an incorrect Host-Uniq."
    ::= { p3oeEventsGroup 5 }

p3oe5_host_uniq OBJECT-TYPE
    SYNTAX DisplayString
    MAX-ACCESS accessible-for-notify
    STATUS current
    DESCRIPTION
        "Parameter 'host_uniq' in event P3OE.5"
    ::= { p3oeEventObjects5 1 }

p3oe5_interface OBJECT-TYPE
    SYNTAX DisplayString
    MAX-ACCESS accessible-for-notify
    STATUS current
    DESCRIPTION
        "Parameter 'interface' in event P3OE.5"
    ::= { p3oeEventObjects5 2 }

p3oeEventObjects6 OBJECT-IDENTITY
    STATUS current
    DESCRIPTION
        "Event P3OE.6
        A packet with a tag indicating an error was received."
    ::= { p3oeEventsGroup 6 }

p3oe6_tag_type OBJECT-TYPE
    SYNTAX Integer32
    MAX-ACCESS accessible-for-notify
    STATUS current
    DESCRIPTION
        "Parameter 'tag_type' in event P3OE.6"
    ::= { p3oeEventObjects6 1 }

p3oe6_tag_value OBJECT-TYPE
    SYNTAX DisplayString
    MAX-ACCESS accessible-for-notify
    STATUS current
    DESCRIPTION
        "Parameter 'tag_value' in event P3OE.6"
    ::= { p3oeEventObjects6 2 }

p3oe6_interface OBJECT-TYPE
    SYNTAX DisplayString
    MAX-ACCESS accessible-for-notify
    STATUS current
    DESCRIPTION
        "Parameter 'interface' in event P3OE.6"
    ::= { p3oeEventObjects6 3 }

p3oeEventObjects7 OBJECT-IDENTITY
    STATUS current
    DESCRIPTION
        "Event P3OE.7
        An incoming packet is discarded due to a wrong destination MAC address."
    ::= { p3oeEventsGroup 7 }

p3oe7_mac OBJECT-TYPE
    SYNTAX DisplayString
    MAX-ACCESS accessible-for-notify
    STATUS current
    DESCRIPTION
        "Parameter 'mac' in event P3OE.7"
    ::= { p3oeEventObjects7 1 }

p3oe7_interface OBJECT-TYPE
    SYNTAX DisplayString
    MAX-ACCESS accessible-for-notify
    STATUS current
    DESCRIPTION
        "Parameter 'interface' in event P3OE.7"
    ::= { p3oeEventObjects7 2 }

p3oeEventObjects8 OBJECT-IDENTITY
    STATUS current
    DESCRIPTION
        "Event P3OE.8
        An incoming packet is discarded due to a wrong ethernet type."
    ::= { p3oeEventsGroup 8 }

p3oe8_eth_type OBJECT-TYPE
    SYNTAX Integer32
    MAX-ACCESS accessible-for-notify
    STATUS current
    DESCRIPTION
        "Parameter 'eth_type' in event P3OE.8"
    ::= { p3oeEventObjects8 1 }

p3oe8_interface OBJECT-TYPE
    SYNTAX DisplayString
    MAX-ACCESS accessible-for-notify
    STATUS current
    DESCRIPTION
        "Parameter 'interface' in event P3OE.8"
    ::= { p3oeEventObjects8 2 }

p3oeEventObjects9 OBJECT-IDENTITY
    STATUS current
    DESCRIPTION
        "Event P3OE.9
        An incoming packet is discarded due to a wrong version field."
    ::= { p3oeEventsGroup 9 }

p3oe9_version OBJECT-TYPE
    SYNTAX Integer32
    MAX-ACCESS accessible-for-notify
    STATUS current
    DESCRIPTION
        "Parameter 'version' in event P3OE.9"
    ::= { p3oeEventObjects9 1 }

p3oe9_interface OBJECT-TYPE
    SYNTAX DisplayString
    MAX-ACCESS accessible-for-notify
    STATUS current
    DESCRIPTION
        "Parameter 'interface' in event P3OE.9"
    ::= { p3oeEventObjects9 2 }

p3oeEventObjects10 OBJECT-IDENTITY
    STATUS current
    DESCRIPTION
        "Event P3OE.10
        An incoming packet is discarded due to a wrong type field."
    ::= { p3oeEventsGroup 10 }

p3oe10_type OBJECT-TYPE
    SYNTAX Integer32
    MAX-ACCESS accessible-for-notify
    STATUS current
    DESCRIPTION
        "Parameter 'type' in event P3OE.10"
    ::= { p3oeEventObjects10 1 }

p3oe10_interface OBJECT-TYPE
    SYNTAX DisplayString
    MAX-ACCESS accessible-for-notify
    STATUS current
    DESCRIPTION
        "Parameter 'interface' in event P3OE.10"
    ::= { p3oeEventObjects10 2 }

p3oeEventObjects11 OBJECT-IDENTITY
    STATUS current
    DESCRIPTION
        "Event P3OE.11
        An incoming packet is discarded due to a wrong code field."
    ::= { p3oeEventsGroup 11 }

p3oe11_code OBJECT-TYPE
    SYNTAX Integer32
    MAX-ACCESS accessible-for-notify
    STATUS current
    DESCRIPTION
        "Parameter 'code' in event P3OE.11"
    ::= { p3oeEventObjects11 1 }

p3oe11_session_id OBJECT-TYPE
    SYNTAX Integer32
    MAX-ACCESS accessible-for-notify
    STATUS current
    DESCRIPTION
        "Parameter 'session_id' in event P3OE.11"
    ::= { p3oeEventObjects11 2 }

p3oe11_interface OBJECT-TYPE
    SYNTAX DisplayString
    MAX-ACCESS accessible-for-notify
    STATUS current
    DESCRIPTION
        "Parameter 'interface' in event P3OE.11"
    ::= { p3oeEventObjects11 3 }

p3oeEventObjects12 OBJECT-IDENTITY
    STATUS current
    DESCRIPTION
        "Event P3OE.12
        An incoming packet is discarded due to a missing tag field."
    ::= { p3oeEventsGroup 12 }

p3oe12_tag OBJECT-TYPE
    SYNTAX DisplayString
    MAX-ACCESS accessible-for-notify
    STATUS current
    DESCRIPTION
        "Parameter 'tag' in event P3OE.12"
    ::= { p3oeEventObjects12 1 }

p3oe12_interface OBJECT-TYPE
    SYNTAX DisplayString
    MAX-ACCESS accessible-for-notify
    STATUS current
    DESCRIPTION
        "Parameter 'interface' in event P3OE.12"
    ::= { p3oeEventObjects12 2 }

p3oeEventObjects13 OBJECT-IDENTITY
    STATUS current
    DESCRIPTION
        "Event P3OE.13
        An incoming packet is discarded due to a wrong session identifier field."
    ::= { p3oeEventsGroup 13 }

p3oe13_session_id OBJECT-TYPE
    SYNTAX Integer32
    MAX-ACCESS accessible-for-notify
    STATUS current
    DESCRIPTION
        "Parameter 'session_id' in event P3OE.13"
    ::= { p3oeEventObjects13 1 }

p3oe13_interface OBJECT-TYPE
    SYNTAX DisplayString
    MAX-ACCESS accessible-for-notify
    STATUS current
    DESCRIPTION
        "Parameter 'interface' in event P3OE.13"
    ::= { p3oeEventObjects13 2 }

p3oeEventObjects14 OBJECT-IDENTITY
    STATUS current
    DESCRIPTION
        "Event P3OE.14
        An outgoing packet is discarded due to an excessive length to be carried
        over Ethernet."
    ::= { p3oeEventsGroup 14 }

p3oe14_length OBJECT-TYPE
    SYNTAX Integer32
    MAX-ACCESS accessible-for-notify
    STATUS current
    DESCRIPTION
        "Parameter 'length' in event P3OE.14"
    ::= { p3oeEventObjects14 1 }

p3oe14_interface OBJECT-TYPE
    SYNTAX DisplayString
    MAX-ACCESS accessible-for-notify
    STATUS current
    DESCRIPTION
        "Parameter 'interface' in event P3OE.14"
    ::= { p3oeEventObjects14 2 }

p3oeEventObjects15 OBJECT-IDENTITY
    STATUS current
    DESCRIPTION
        "Event P3OE.15
        There are memory limitations when trying to store a received tag."
    ::= { p3oeEventsGroup 15 }

p3oe15_interface OBJECT-TYPE
    SYNTAX DisplayString
    MAX-ACCESS accessible-for-notify
    STATUS current
    DESCRIPTION
        "Parameter 'interface' in event P3OE.15"
    ::= { p3oeEventObjects15 1 }

p3oeEventObjects16 OBJECT-IDENTITY
    STATUS current
    DESCRIPTION
        "Event P3OE.16
        Maximum number of retries for a sending PPPoE packet has been reached.
        The connection will be closed."
    ::= { p3oeEventsGroup 16 }

p3oe16_packet_name OBJECT-TYPE
    SYNTAX DisplayString
    MAX-ACCESS accessible-for-notify
    STATUS current
    DESCRIPTION
        "Parameter 'packet_name' in event P3OE.16"
    ::= { p3oeEventObjects16 1 }

p3oe16_interface OBJECT-TYPE
    SYNTAX DisplayString
    MAX-ACCESS accessible-for-notify
    STATUS current
    DESCRIPTION
        "Parameter 'interface' in event P3OE.16"
    ::= { p3oeEventObjects16 2 }

p3oeEventObjects17 OBJECT-IDENTITY
    STATUS current
    DESCRIPTION
        "Event P3OE.17
        A timeout has produced when waiting for a given PPPoE packet.
        The connection will be closed."
    ::= { p3oeEventsGroup 17 }

p3oe17_packet_name OBJECT-TYPE
    SYNTAX DisplayString
    MAX-ACCESS accessible-for-notify
    STATUS current
    DESCRIPTION
        "Parameter 'packet_name' in event P3OE.17"
    ::= { p3oeEventObjects17 1 }

p3oe17_interface OBJECT-TYPE
    SYNTAX DisplayString
    MAX-ACCESS accessible-for-notify
    STATUS current
    DESCRIPTION
        "Parameter 'interface' in event P3OE.17"
    ::= { p3oeEventObjects17 2 }

p3oeEventObjects18 OBJECT-IDENTITY
    STATUS current
    DESCRIPTION
        "Event P3OE.18
        A PPPoE packet has been sent."
    ::= { p3oeEventsGroup 18 }

p3oe18_packet_name OBJECT-TYPE
    SYNTAX DisplayString
    MAX-ACCESS accessible-for-notify
    STATUS current
    DESCRIPTION
        "Parameter 'packet_name' in event P3OE.18"
    ::= { p3oeEventObjects18 1 }

p3oe18_session_id OBJECT-TYPE
    SYNTAX Integer32
    MAX-ACCESS accessible-for-notify
    STATUS current
    DESCRIPTION
        "Parameter 'session_id' in event P3OE.18"
    ::= { p3oeEventObjects18 2 }

p3oe18_interface OBJECT-TYPE
    SYNTAX DisplayString
    MAX-ACCESS accessible-for-notify
    STATUS current
    DESCRIPTION
        "Parameter 'interface' in event P3OE.18"
    ::= { p3oeEventObjects18 3 }

p3oeEventObjects19 OBJECT-IDENTITY
    STATUS current
    DESCRIPTION
        "Event P3OE.19
        A PPPoE packet has been received."
    ::= { p3oeEventsGroup 19 }

p3oe19_packet_name OBJECT-TYPE
    SYNTAX DisplayString
    MAX-ACCESS accessible-for-notify
    STATUS current
    DESCRIPTION
        "Parameter 'packet_name' in event P3OE.19"
    ::= { p3oeEventObjects19 1 }

p3oe19_session_id OBJECT-TYPE
    SYNTAX Integer32
    MAX-ACCESS accessible-for-notify
    STATUS current
    DESCRIPTION
        "Parameter 'session_id' in event P3OE.19"
    ::= { p3oeEventObjects19 2 }

p3oe19_interface OBJECT-TYPE
    SYNTAX DisplayString
    MAX-ACCESS accessible-for-notify
    STATUS current
    DESCRIPTION
        "Parameter 'interface' in event P3OE.19"
    ::= { p3oeEventObjects19 3 }

p3oeEventObjects20 OBJECT-IDENTITY
    STATUS current
    DESCRIPTION
        "Event P3OE.20
        There are memory limitations. The PPPoE may not work properly."
    ::= { p3oeEventsGroup 20 }

p3oe20_string OBJECT-TYPE
    SYNTAX DisplayString
    MAX-ACCESS accessible-for-notify
    STATUS current
    DESCRIPTION
        "Parameter 'string' in event P3OE.20"
    ::= { p3oeEventObjects20 1 }

p3oe20_interface OBJECT-TYPE
    SYNTAX DisplayString
    MAX-ACCESS accessible-for-notify
    STATUS current
    DESCRIPTION
        "Parameter 'interface' in event P3OE.20"
    ::= { p3oeEventObjects20 2 }

p3oeEventObjects21 OBJECT-IDENTITY
    STATUS current
    DESCRIPTION
        "Event P3OE.21
        A PPPoE packet could not be sent. There may be problems in a
        lower layer."
    ::= { p3oeEventsGroup 21 }

p3oe21_packet_name OBJECT-TYPE
    SYNTAX DisplayString
    MAX-ACCESS accessible-for-notify
    STATUS current
    DESCRIPTION
        "Parameter 'packet_name' in event P3OE.21"
    ::= { p3oeEventObjects21 1 }

p3oe21_interface OBJECT-TYPE
    SYNTAX DisplayString
    MAX-ACCESS accessible-for-notify
    STATUS current
    DESCRIPTION
        "Parameter 'interface' in event P3OE.21"
    ::= { p3oeEventObjects21 2 }

p3oeEventObjects22 OBJECT-IDENTITY
    STATUS current
    DESCRIPTION
        "Event P3OE.22
        A PPPoE packet for a MAC that is not the MAC of the Ethernet interface
        has been received. The packet will be sent to the bridge layer."
    ::= { p3oeEventsGroup 22 }

p3oe22_mac_address OBJECT-TYPE
    SYNTAX DisplayString
    MAX-ACCESS accessible-for-notify
    STATUS current
    DESCRIPTION
        "Parameter 'mac_address' in event P3OE.22"
    ::= { p3oeEventObjects22 1 }

p3oe22_base_interface OBJECT-TYPE
    SYNTAX DisplayString
    MAX-ACCESS accessible-for-notify
    STATUS current
    DESCRIPTION
        "Parameter 'base_interface' in event P3OE.22"
    ::= { p3oeEventObjects22 2 }

p3oeEventObjects23 OBJECT-IDENTITY
    STATUS current
    DESCRIPTION
        "Event P3OE.23
        A PPPoE packet for an unknown session has been received. The packet
        is discarded."
    ::= { p3oeEventsGroup 23 }

p3oe23_code OBJECT-TYPE
    SYNTAX Integer32
    MAX-ACCESS accessible-for-notify
    STATUS current
    DESCRIPTION
        "Parameter 'code' in event P3OE.23"
    ::= { p3oeEventObjects23 1 }

p3oe23_session_id OBJECT-TYPE
    SYNTAX Integer32
    MAX-ACCESS accessible-for-notify
    STATUS current
    DESCRIPTION
        "Parameter 'session_id' in event P3OE.23"
    ::= { p3oeEventObjects23 2 }

p3oe23_base_interface OBJECT-TYPE
    SYNTAX DisplayString
    MAX-ACCESS accessible-for-notify
    STATUS current
    DESCRIPTION
        "Parameter 'base_interface' in event P3OE.23"
    ::= { p3oeEventObjects23 3 }


p3oeNotification1 NOTIFICATION-TYPE
    OBJECTS { 
              p3oe1_interface 
            }
    STATUS current
    DESCRIPTION
        "Notification of Event P3OE.1

        Message: 'packet discarded, previous PADT received on interface $1'

        Parameters list:
              $1: p3oe1_interface

        An incoming packet is discarded because a PADT was previously received."
    ::= { p3oeNotificationsPrefix 1 }

p3oeNotification2 NOTIFICATION-TYPE
    OBJECTS { 
              p3oe2_base_interface 
            }
    STATUS current
    DESCRIPTION
        "Notification of Event P3OE.2

        Message: 'packet discarded, tag length error, on base interface $1'

        Parameters list:
              $1: p3oe2_base_interface

        An incoming packet is discarded because of an unexpected tag length."
    ::= { p3oeNotificationsPrefix 2 }

p3oeNotification3 NOTIFICATION-TYPE
    OBJECTS { 
              p3oe3_service_name, 
              p3oe3_interface 
            }
    STATUS current
    DESCRIPTION
        "Notification of Event P3OE.3

        Message: 'packet discarded, Service-Name error, received $1 on interface $2'

        Parameters list:
              $1: p3oe3_service_name
              $2: p3oe3_interface

        An incoming packet is discarded because of an incorrect Service-Name."
    ::= { p3oeNotificationsPrefix 3 }

p3oeNotification4 NOTIFICATION-TYPE
    OBJECTS { 
              p3oe4_service_name, 
              p3oe4_interface 
            }
    STATUS current
    DESCRIPTION
        "Notification of Event P3OE.4

        Message: 'packet discarded, Ac-Name error, received $1 on interface $2'

        Parameters list:
              $1: p3oe4_service_name
              $2: p3oe4_interface

        An incoming packet is discarded because of an incorrect Ac-Name."
    ::= { p3oeNotificationsPrefix 4 }

p3oeNotification5 NOTIFICATION-TYPE
    OBJECTS { 
              p3oe5_host_uniq, 
              p3oe5_interface 
            }
    STATUS current
    DESCRIPTION
        "Notification of Event P3OE.5

        Message: 'packet discarded, Host-Uniq error, received $1 on interface $2'

        Parameters list:
              $1: p3oe5_host_uniq
              $2: p3oe5_interface

        An incoming packet is discarded because of an incorrect Host-Uniq."
    ::= { p3oeNotificationsPrefix 5 }

p3oeNotification6 NOTIFICATION-TYPE
    OBJECTS { 
              p3oe6_tag_type, 
              p3oe6_tag_value,
              p3oe6_interface 
            }
    STATUS current
    DESCRIPTION
        "Notification of Event P3OE.6

        Message: 'received tag error, type=0x$1 ($2) on interface $3'

        Parameters list:
              $1: p3oe6_tag_type
              $2: p3oe6_tag_value
              $3: p3oe6_interface

        A packet with a tag indicating an error was received."
    ::= { p3oeNotificationsPrefix 6 }

p3oeNotification7 NOTIFICATION-TYPE
    OBJECTS { 
              p3oe7_mac, 
              p3oe7_interface 
            }
    STATUS current
    DESCRIPTION
        "Notification of Event P3OE.7

        Message: 'packet discarded, mac error, mac=$1 on interface $2'

        Parameters list:
              $1: p3oe7_mac
              $2: p3oe7_interface

        An incoming packet is discarded due to a wrong destination MAC address."
    ::= { p3oeNotificationsPrefix 7 }

p3oeNotification8 NOTIFICATION-TYPE
    OBJECTS { 
              p3oe8_eth_type, 
              p3oe8_interface 
            }
    STATUS current
    DESCRIPTION
        "Notification of Event P3OE.8

        Message: 'received packet error, eth_type=0x$1 on interface $2'

        Parameters list:
              $1: p3oe8_eth_type
              $2: p3oe8_interface

        An incoming packet is discarded due to a wrong ethernet type."
    ::= { p3oeNotificationsPrefix 8 }

p3oeNotification9 NOTIFICATION-TYPE
    OBJECTS { 
              p3oe9_version, 
              p3oe9_interface 
            }
    STATUS current
    DESCRIPTION
        "Notification of Event P3OE.9

        Message: 'received packet error, version=0x$1 on interface $2'

        Parameters list:
              $1: p3oe9_version
              $2: p3oe9_interface

        An incoming packet is discarded due to a wrong version field."
    ::= { p3oeNotificationsPrefix 9 }

p3oeNotification10 NOTIFICATION-TYPE
    OBJECTS { 
              p3oe10_type, 
              p3oe10_interface 
            }
    STATUS current
    DESCRIPTION
        "Notification of Event P3OE.10

        Message: 'received packet error, type=0x$1 on interface $2'

        Parameters list:
              $1: p3oe10_type
              $2: p3oe10_interface

        An incoming packet is discarded due to a wrong type field."
    ::= { p3oeNotificationsPrefix 10 }

p3oeNotification11 NOTIFICATION-TYPE
    OBJECTS { 
              p3oe11_code, 
              p3oe11_session_id,
              p3oe11_interface 
            }
    STATUS current
    DESCRIPTION
        "Notification of Event P3OE.11

        Message: 'received packet error, code=0x$1 session_id=0x$2 on interface $3'

        Parameters list:
              $1: p3oe11_code
              $2: p3oe11_session_id
              $3: p3oe11_interface

        An incoming packet is discarded due to a wrong code field."
    ::= { p3oeNotificationsPrefix 11 }

p3oeNotification12 NOTIFICATION-TYPE
    OBJECTS { 
              p3oe12_tag, 
              p3oe12_interface 
            }
    STATUS current
    DESCRIPTION
        "Notification of Event P3OE.12

        Message: 'received packet error, tag $1 missing on interface $2'

        Parameters list:
              $1: p3oe12_tag
              $2: p3oe12_interface

        An incoming packet is discarded due to a missing tag field."
    ::= { p3oeNotificationsPrefix 12 }

p3oeNotification13 NOTIFICATION-TYPE
    OBJECTS { 
              p3oe13_session_id, 
              p3oe13_interface 
            }
    STATUS current
    DESCRIPTION
        "Notification of Event P3OE.13

        Message: 'received packet error, session=0x$1 on interface $2'

        Parameters list:
              $1: p3oe13_session_id
              $2: p3oe13_interface

        An incoming packet is discarded due to a wrong session identifier field."
    ::= { p3oeNotificationsPrefix 13 }

p3oeNotification14 NOTIFICATION-TYPE
    OBJECTS { 
              p3oe14_length, 
              p3oe14_interface 
            }
    STATUS current
    DESCRIPTION
        "Notification of Event P3OE.14

        Message: 'transmit packet error, excessive length=$1 on interface $2'

        Parameters list:
              $1: p3oe14_length
              $2: p3oe14_interface

        An outgoing packet is discarded due to an excessive length to be carried
        over Ethernet."
    ::= { p3oeNotificationsPrefix 14 }

p3oeNotification15 NOTIFICATION-TYPE
    OBJECTS { 
              p3oe15_interface 
            }
    STATUS current
    DESCRIPTION
        "Notification of Event P3OE.15

        Message: 'no memory to store tag on interface $1'

        Parameters list:
              $1: p3oe15_interface

        There are memory limitations when trying to store a received tag."
    ::= { p3oeNotificationsPrefix 15 }

p3oeNotification16 NOTIFICATION-TYPE
    OBJECTS { 
              p3oe16_packet_name, 
              p3oe16_interface 
            }
    STATUS current
    DESCRIPTION
        "Notification of Event P3OE.16

        Message: 'maximum number of retries reached for $1 on interface $2'

        Parameters list:
              $1: p3oe16_packet_name
              $2: p3oe16_interface

        Maximum number of retries for a sending PPPoE packet has been reached.
        The connection will be closed."
    ::= { p3oeNotificationsPrefix 16 }

p3oeNotification17 NOTIFICATION-TYPE
    OBJECTS { 
              p3oe17_packet_name, 
              p3oe17_interface 
            }
    STATUS current
    DESCRIPTION
        "Notification of Event P3OE.17

        Message: 'timeout waiting for $1 on interface $2'

        Parameters list:
              $1: p3oe17_packet_name
              $2: p3oe17_interface

        A timeout has produced when waiting for a given PPPoE packet.
        The connection will be closed."
    ::= { p3oeNotificationsPrefix 17 }

p3oeNotification18 NOTIFICATION-TYPE
    OBJECTS { 
              p3oe18_packet_name, 
              p3oe18_session_id,
              p3oe18_interface 
            }
    STATUS current
    DESCRIPTION
        "Notification of Event P3OE.18

        Message: 'sending packet $1 session_id 0x$2 on interface $3'

        Parameters list:
              $1: p3oe18_packet_name
              $2: p3oe18_session_id
              $3: p3oe18_interface

        A PPPoE packet has been sent."
    ::= { p3oeNotificationsPrefix 18 }

p3oeNotification19 NOTIFICATION-TYPE
    OBJECTS { 
              p3oe19_packet_name, 
              p3oe19_session_id,
              p3oe19_interface 
            }
    STATUS current
    DESCRIPTION
        "Notification of Event P3OE.19

        Message: 'received packet $1 session_id 0x$2 on interface $3'

        Parameters list:
              $1: p3oe19_packet_name
              $2: p3oe19_session_id
              $3: p3oe19_interface

        A PPPoE packet has been received."
    ::= { p3oeNotificationsPrefix 19 }

p3oeNotification20 NOTIFICATION-TYPE
    OBJECTS { 
              p3oe20_string, 
              p3oe20_interface 
            }
    STATUS current
    DESCRIPTION
        "Notification of Event P3OE.20

        Message: 'no memory for $1 on interface $2'

        Parameters list:
              $1: p3oe20_string
              $2: p3oe20_interface

        There are memory limitations. The PPPoE may not work properly."
    ::= { p3oeNotificationsPrefix 20 }

p3oeNotification21 NOTIFICATION-TYPE
    OBJECTS { 
              p3oe21_packet_name, 
              p3oe21_interface 
            }
    STATUS current
    DESCRIPTION
        "Notification of Event P3OE.21

        Message: 'send packet $1 error on interface $2'

        Parameters list:
              $1: p3oe21_packet_name
              $2: p3oe21_interface

        A PPPoE packet could not be sent. There may be problems in a
        lower layer."
    ::= { p3oeNotificationsPrefix 21 }

p3oeNotification22 NOTIFICATION-TYPE
    OBJECTS { 
              p3oe22_mac_address, 
              p3oe22_base_interface 
            }
    STATUS current
    DESCRIPTION
        "Notification of Event P3OE.22

        Message: 'received packet for MAC $1 on base interface $2, trying to bridge'

        Parameters list:
              $1: p3oe22_mac_address
              $2: p3oe22_base_interface

        A PPPoE packet for a MAC that is not the MAC of the Ethernet interface
        has been received. The packet will be sent to the bridge layer."
    ::= { p3oeNotificationsPrefix 22 }

p3oeNotification23 NOTIFICATION-TYPE
    OBJECTS { 
              p3oe23_code, 
              p3oe23_session_id,
              p3oe23_base_interface 
            }
    STATUS current
    DESCRIPTION
        "Notification of Event P3OE.23

        Message: 'received packet for unknown pppoe with code=0x$1, session_id=0x$2 on base interface $3'

        Parameters list:
              $1: p3oe23_code
              $2: p3oe23_session_id
              $3: p3oe23_base_interface

        A PPPoE packet for an unknown session has been received. The packet
        is discarded."
    ::= { p3oeNotificationsPrefix 23 }


END
