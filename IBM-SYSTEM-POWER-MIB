IBM-SYSTEM-POWER-MIB DEFINITIONS ::= BEGIN

IMPORTS
   OBJECT-TYPE
        FROM RFC-1212

   TRAP-TYPE
        FROM RFC-1215

   ibmSystemPower,
   Boolean, Uint8, Sint8, Uint16, Sint16, Uint32,
   Sint32, Uint64, Sint64, Real32, Real64, String, Datetime
      FROM IBM-SYSTEM-MIB;
      

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING

ibmSystemPowerSupplyTable OBJECT-TYPE
   SYNTAX         SEQUENCE OF IbmSystemPowerSupplyEntry
   ACCESS         not-accessible
   STATUS         mandatory
   DESCRIPTION    "The IBMPSG_PowerSupply class represents an IBM managed Power Supply"
   REFERENCE      "IBMPSG_PowerSupply"
::= { ibmSystemPower 1 }

ibmSystemPowerSupplyEntry OBJECT-TYPE
   SYNTAX         IbmSystemPowerSupplyEntry
   ACCESS         not-accessible
   STATUS         mandatory
   DESCRIPTION     "This class defines an entry for each IBMPSG_PowerSupply
                    instance. Each instance of the IBMPSG_PowerSupply class 
                    contains status and descriptive information for each power 
                    supply recognized by the operating system."
   INDEX          { ibmSystemPowerSupplyKeyIndex }
::= { ibmSystemPowerSupplyTable 1 }

IbmSystemPowerSupplyEntry ::= SEQUENCE
{
   ibmSystemPowerSupplyKeyIndex String,   
   ibmSystemPowerSupplyDescription String,
   ibmSystemPowerSupplyPNPDeviceID String,
   ibmSystemPowerSupplyStatusInfo Uint16,
   ibmSystemPowerSupplySystemCreationClassName String,
   ibmSystemPowerSupplyEventsEnabled Boolean,
   ibmSystemPowerSupplyPollingInterval Uint64,
   ibmSystemPowerSupplyEventAutoClearEnabled Boolean,
   ibmSystemPowerSupplyStatus String
}

ibmSystemPowerSupplyKeyIndex OBJECT-TYPE
   SYNTAX         String
   ACCESS         read-write
   STATUS         mandatory
   DESCRIPTION    ""
   REFERENCE      "IBMPSG_PowerSupply.KeyIndex"
::= { ibmSystemPowerSupplyEntry 1 }

ibmSystemPowerSupplyDescription OBJECT-TYPE
   SYNTAX         String
   ACCESS         read-write
   STATUS         mandatory
   DESCRIPTION    ""
   REFERENCE      "IBMPSG_PowerSupply.Description"
::= { ibmSystemPowerSupplyEntry 2 }

ibmSystemPowerSupplyPNPDeviceID OBJECT-TYPE
   SYNTAX         String
   ACCESS         read-write
   STATUS         mandatory
   DESCRIPTION    ""
   REFERENCE      "IBMPSG_PowerSupply.PNPDeviceID"
::= { ibmSystemPowerSupplyEntry 3 }

ibmSystemPowerSupplyStatusInfo OBJECT-TYPE
   SYNTAX         Uint16
   ACCESS         read-write
   STATUS         mandatory
   DESCRIPTION    ""
   REFERENCE      "IBMPSG_PowerSupply.StatusInfo"
::= { ibmSystemPowerSupplyEntry 4 }

ibmSystemPowerSupplySystemCreationClassName OBJECT-TYPE
   SYNTAX         String
   ACCESS         read-write
   STATUS         mandatory
   DESCRIPTION    ""
   REFERENCE      "IBMPSG_PowerSupply.SystemCreationClassName"
::= { ibmSystemPowerSupplyEntry 5 }

ibmSystemPowerSupplyEventsEnabled OBJECT-TYPE
   SYNTAX         Boolean
   ACCESS         read-write
   STATUS         mandatory
   DESCRIPTION    ""
   REFERENCE      "IBMPSG_PowerSupply.EventsEnabled"
::= { ibmSystemPowerSupplyEntry 6 }

ibmSystemPowerSupplyPollingInterval OBJECT-TYPE
   SYNTAX         Uint64
   ACCESS         read-write
   STATUS         mandatory
   DESCRIPTION    ""
   REFERENCE      "IBMPSG_PowerSupply.PollingInterval"
::= { ibmSystemPowerSupplyEntry 7 }

ibmSystemPowerSupplyEventAutoClearEnabled OBJECT-TYPE
   SYNTAX         Boolean
   ACCESS         read-write
   STATUS         mandatory
   DESCRIPTION    ""
   REFERENCE      "IBMPSG_PowerSupply.EventAutoClearEnabled"
::= { ibmSystemPowerSupplyEntry 8 }

ibmSystemPowerSupplyStatus OBJECT-TYPE
   SYNTAX         String
   ACCESS         read-write
   STATUS         mandatory
   DESCRIPTION    ""
   REFERENCE      "IBMPSG_PowerSupply.Status"
::= { ibmSystemPowerSupplyEntry 9 }

END
