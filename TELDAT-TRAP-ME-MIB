-- file automatically created


TELDAT-TRAP-ME-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


meTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ME event subsystem."
    REVISION "201401200930Z"
    DESCRIPTION "Initial implementation"
        ::= { telEventTraps 201 }


meEventsGroup	OBJECT IDENTIFIER	::= { meTrapsMIB 1 }

meNotifications	OBJECT IDENTIFIER	::= { meTrapsMIB 2 }
meNotificationsPrefix	OBJECT IDENTIFIER	::= { meNotifications 0 }

meEventObjects1 OBJECT-IDENTITY
    STATUS current
    DESCRIPTION
        "Event ME.1
        Data has been received from Serial Terminal."
    ::= { meEventsGroup 1 }

me1_bytes_number OBJECT-TYPE
    SYNTAX Integer32
    MAX-ACCESS accessible-for-notify
    STATUS current
    DESCRIPTION
        "Parameter 'bytes_number' in event ME.1"
    ::= { meEventObjects1 1 }

me1_interface OBJECT-TYPE
    SYNTAX DisplayString
    MAX-ACCESS accessible-for-notify
    STATUS current
    DESCRIPTION
        "Parameter 'interface' in event ME.1"
    ::= { meEventObjects1 2 }

meEventObjects2 OBJECT-IDENTITY
    STATUS current
    DESCRIPTION
        "Event ME.2
        One AT command message has been received from Serial Terminal."
    ::= { meEventsGroup 2 }

me2_coment OBJECT-TYPE
    SYNTAX DisplayString
    MAX-ACCESS accessible-for-notify
    STATUS current
    DESCRIPTION
        "Parameter 'coment' in event ME.2"
    ::= { meEventObjects2 1 }

me2_atCommand OBJECT-TYPE
    SYNTAX DisplayString
    MAX-ACCESS accessible-for-notify
    STATUS current
    DESCRIPTION
        "Parameter 'atCommand' in event ME.2"
    ::= { meEventObjects2 2 }

me2_interface OBJECT-TYPE
    SYNTAX DisplayString
    MAX-ACCESS accessible-for-notify
    STATUS current
    DESCRIPTION
        "Parameter 'interface' in event ME.2"
    ::= { meEventObjects2 3 }

me2_state OBJECT-TYPE
    SYNTAX Integer32
    MAX-ACCESS accessible-for-notify
    STATUS current
    DESCRIPTION
        "Parameter 'state' in event ME.2"
    ::= { meEventObjects2 4 }

meEventObjects3 OBJECT-IDENTITY
    STATUS current
    DESCRIPTION
        "Event ME.3
        A Message with bad address has been received from Serial Terminal."
    ::= { meEventsGroup 3 }

me3_bad_addr OBJECT-TYPE
    SYNTAX Integer32
    MAX-ACCESS accessible-for-notify
    STATUS current
    DESCRIPTION
        "Parameter 'bad_addr' in event ME.3"
    ::= { meEventObjects3 1 }

me3_interface OBJECT-TYPE
    SYNTAX DisplayString
    MAX-ACCESS accessible-for-notify
    STATUS current
    DESCRIPTION
        "Parameter 'interface' in event ME.3"
    ::= { meEventObjects3 2 }

meEventObjects4 OBJECT-IDENTITY
    STATUS current
    DESCRIPTION
        "Event ME.4
        One Bad Message has been received from Serial Terminal."
    ::= { meEventsGroup 4 }

me4_cause OBJECT-TYPE
    SYNTAX DisplayString
    MAX-ACCESS accessible-for-notify
    STATUS current
    DESCRIPTION
        "Parameter 'cause' in event ME.4"
    ::= { meEventObjects4 1 }

me4_interface OBJECT-TYPE
    SYNTAX DisplayString
    MAX-ACCESS accessible-for-notify
    STATUS current
    DESCRIPTION
        "Parameter 'interface' in event ME.4"
    ::= { meEventObjects4 2 }

me4_state OBJECT-TYPE
    SYNTAX Integer32
    MAX-ACCESS accessible-for-notify
    STATUS current
    DESCRIPTION
        "Parameter 'state' in event ME.4"
    ::= { meEventObjects4 3 }

meEventObjects5 OBJECT-IDENTITY
    STATUS current
    DESCRIPTION
        "Event ME.5
        A message with LRC/CRC error has been received from Serial Terminal."
    ::= { meEventsGroup 5 }

me5_interface OBJECT-TYPE
    SYNTAX DisplayString
    MAX-ACCESS accessible-for-notify
    STATUS current
    DESCRIPTION
        "Parameter 'interface' in event ME.5"
    ::= { meEventObjects5 1 }

me5_state OBJECT-TYPE
    SYNTAX Integer32
    MAX-ACCESS accessible-for-notify
    STATUS current
    DESCRIPTION
        "Parameter 'state' in event ME.5"
    ::= { meEventObjects5 2 }

meEventObjects6 OBJECT-IDENTITY
    STATUS current
    DESCRIPTION
        "Event ME.6
        A message with error has been received from Remote."
    ::= { meEventsGroup 6 }

me6_error_type OBJECT-TYPE
    SYNTAX DisplayString
    MAX-ACCESS accessible-for-notify
    STATUS current
    DESCRIPTION
        "Parameter 'error_type' in event ME.6"
    ::= { meEventObjects6 1 }

me6_interface OBJECT-TYPE
    SYNTAX DisplayString
    MAX-ACCESS accessible-for-notify
    STATUS current
    DESCRIPTION
        "Parameter 'interface' in event ME.6"
    ::= { meEventObjects6 2 }

me6_state OBJECT-TYPE
    SYNTAX Integer32
    MAX-ACCESS accessible-for-notify
    STATUS current
    DESCRIPTION
        "Parameter 'state' in event ME.6"
    ::= { meEventObjects6 3 }

meEventObjects7 OBJECT-IDENTITY
    STATUS current
    DESCRIPTION
        "Event ME.7
        Addres received from Serial Terminal is not included in configuration
        registers list."
    ::= { meEventsGroup 7 }

me7_serial_address OBJECT-TYPE
    SYNTAX Integer32
    MAX-ACCESS accessible-for-notify
    STATUS current
    DESCRIPTION
        "Parameter 'serial_address' in event ME.7"
    ::= { meEventObjects7 1 }

me7_interface OBJECT-TYPE
    SYNTAX DisplayString
    MAX-ACCESS accessible-for-notify
    STATUS current
    DESCRIPTION
        "Parameter 'interface' in event ME.7"
    ::= { meEventObjects7 2 }

meEventObjects8 OBJECT-IDENTITY
    STATUS current
    DESCRIPTION
        "Event ME.8
        Processed a basic AT command"
    ::= { meEventsGroup 8 }

me8_atCommand OBJECT-TYPE
    SYNTAX DisplayString
    MAX-ACCESS accessible-for-notify
    STATUS current
    DESCRIPTION
        "Parameter 'atCommand' in event ME.8"
    ::= { meEventObjects8 1 }

me8_value OBJECT-TYPE
    SYNTAX Integer32
    MAX-ACCESS accessible-for-notify
    STATUS current
    DESCRIPTION
        "Parameter 'value' in event ME.8"
    ::= { meEventObjects8 2 }

meEventObjects9 OBJECT-IDENTITY
    STATUS current
    DESCRIPTION
        "Event ME.9
        The Transfer has been completed successfully."
    ::= { meEventsGroup 9 }

me9_interface OBJECT-TYPE
    SYNTAX DisplayString
    MAX-ACCESS accessible-for-notify
    STATUS current
    DESCRIPTION
        "Parameter 'interface' in event ME.9"
    ::= { meEventObjects9 1 }

meEventObjects10 OBJECT-IDENTITY
    STATUS current
    DESCRIPTION
        "Event ME.10
        Processed an extended AT command"
    ::= { meEventsGroup 10 }

me10_atCommand OBJECT-TYPE
    SYNTAX DisplayString
    MAX-ACCESS accessible-for-notify
    STATUS current
    DESCRIPTION
        "Parameter 'atCommand' in event ME.10"
    ::= { meEventObjects10 1 }

me10_value OBJECT-TYPE
    SYNTAX Integer32
    MAX-ACCESS accessible-for-notify
    STATUS current
    DESCRIPTION
        "Parameter 'value' in event ME.10"
    ::= { meEventObjects10 2 }

meEventObjects11 OBJECT-IDENTITY
    STATUS current
    DESCRIPTION
        "Event ME.11
        Processed an extended AT command"
    ::= { meEventsGroup 11 }

me11_atCommand OBJECT-TYPE
    SYNTAX DisplayString
    MAX-ACCESS accessible-for-notify
    STATUS current
    DESCRIPTION
        "Parameter 'atCommand' in event ME.11"
    ::= { meEventObjects11 1 }

me11_value OBJECT-TYPE
    SYNTAX Integer32
    MAX-ACCESS accessible-for-notify
    STATUS current
    DESCRIPTION
        "Parameter 'value' in event ME.11"
    ::= { meEventObjects11 2 }

meEventObjects12 OBJECT-IDENTITY
    STATUS current
    DESCRIPTION
        "Event ME.12
        Processed a basic AT command Sn=x"
    ::= { meEventsGroup 12 }

me12_atCommand OBJECT-TYPE
    SYNTAX DisplayString
    MAX-ACCESS accessible-for-notify
    STATUS current
    DESCRIPTION
        "Parameter 'atCommand' in event ME.12"
    ::= { meEventObjects12 1 }

me12_sReg OBJECT-TYPE
    SYNTAX Integer32
    MAX-ACCESS accessible-for-notify
    STATUS current
    DESCRIPTION
        "Parameter 'sReg' in event ME.12"
    ::= { meEventObjects12 2 }

me12_value OBJECT-TYPE
    SYNTAX Integer32
    MAX-ACCESS accessible-for-notify
    STATUS current
    DESCRIPTION
        "Parameter 'value' in event ME.12"
    ::= { meEventObjects12 3 }

meEventObjects13 OBJECT-IDENTITY
    STATUS current
    DESCRIPTION
        "Event ME.13
        The TCP session has been closed."
    ::= { meEventsGroup 13 }

me13_foreign_host OBJECT-TYPE
    SYNTAX IpAddress
    MAX-ACCESS accessible-for-notify
    STATUS current
    DESCRIPTION
        "Parameter 'foreign_host' in event ME.13"
    ::= { meEventObjects13 1 }

me13_remote_port OBJECT-TYPE
    SYNTAX Integer32
    MAX-ACCESS accessible-for-notify
    STATUS current
    DESCRIPTION
        "Parameter 'remote_port' in event ME.13"
    ::= { meEventObjects13 2 }

meEventObjects14 OBJECT-IDENTITY
    STATUS current
    DESCRIPTION
        "Event ME.14
        The TCP session has been closed by the Remote end."
    ::= { meEventsGroup 14 }

me14_foreign_host OBJECT-TYPE
    SYNTAX IpAddress
    MAX-ACCESS accessible-for-notify
    STATUS current
    DESCRIPTION
        "Parameter 'foreign_host' in event ME.14"
    ::= { meEventObjects14 1 }

me14_remote_port OBJECT-TYPE
    SYNTAX Integer32
    MAX-ACCESS accessible-for-notify
    STATUS current
    DESCRIPTION
        "Parameter 'remote_port' in event ME.14"
    ::= { meEventObjects14 2 }

meEventObjects15 OBJECT-IDENTITY
    STATUS current
    DESCRIPTION
        "Event ME.15
        The TCP session has been opened by the Remote end."
    ::= { meEventsGroup 15 }

me15_remote_ip OBJECT-TYPE
    SYNTAX IpAddress
    MAX-ACCESS accessible-for-notify
    STATUS current
    DESCRIPTION
        "Parameter 'remote_ip' in event ME.15"
    ::= { meEventObjects15 1 }

me15_remote_port OBJECT-TYPE
    SYNTAX Integer32
    MAX-ACCESS accessible-for-notify
    STATUS current
    DESCRIPTION
        "Parameter 'remote_port' in event ME.15"
    ::= { meEventObjects15 2 }

meEventObjects16 OBJECT-IDENTITY
    STATUS current
    DESCRIPTION
        "Event ME.16
        An AT response message has been transmited to Serial Terminal."
    ::= { meEventsGroup 16 }

me16_atResponse OBJECT-TYPE
    SYNTAX DisplayString
    MAX-ACCESS accessible-for-notify
    STATUS current
    DESCRIPTION
        "Parameter 'atResponse' in event ME.16"
    ::= { meEventObjects16 1 }

me16_interface OBJECT-TYPE
    SYNTAX DisplayString
    MAX-ACCESS accessible-for-notify
    STATUS current
    DESCRIPTION
        "Parameter 'interface' in event ME.16"
    ::= { meEventObjects16 2 }

me16_state OBJECT-TYPE
    SYNTAX Integer32
    MAX-ACCESS accessible-for-notify
    STATUS current
    DESCRIPTION
        "Parameter 'state' in event ME.16"
    ::= { meEventObjects16 3 }

meEventObjects17 OBJECT-IDENTITY
    STATUS current
    DESCRIPTION
        "Event ME.17
        A change ON/OFF has been detected in Serial Control Signal Input."
    ::= { meEventsGroup 17 }

me17_message_type OBJECT-TYPE
    SYNTAX DisplayString
    MAX-ACCESS accessible-for-notify
    STATUS current
    DESCRIPTION
        "Parameter 'message_type' in event ME.17"
    ::= { meEventObjects17 1 }

me17_interface OBJECT-TYPE
    SYNTAX DisplayString
    MAX-ACCESS accessible-for-notify
    STATUS current
    DESCRIPTION
        "Parameter 'interface' in event ME.17"
    ::= { meEventObjects17 2 }

me17_state OBJECT-TYPE
    SYNTAX Integer32
    MAX-ACCESS accessible-for-notify
    STATUS current
    DESCRIPTION
        "Parameter 'state' in event ME.17"
    ::= { meEventObjects17 3 }

meEventObjects18 OBJECT-IDENTITY
    STATUS current
    DESCRIPTION
        "Event ME.18
        Timeout has occur waiting data."
    ::= { meEventsGroup 18 }

me18_site OBJECT-TYPE
    SYNTAX DisplayString
    MAX-ACCESS accessible-for-notify
    STATUS current
    DESCRIPTION
        "Parameter 'site' in event ME.18"
    ::= { meEventObjects18 1 }

me18_interface OBJECT-TYPE
    SYNTAX DisplayString
    MAX-ACCESS accessible-for-notify
    STATUS current
    DESCRIPTION
        "Parameter 'interface' in event ME.18"
    ::= { meEventObjects18 2 }

me18_state OBJECT-TYPE
    SYNTAX Integer32
    MAX-ACCESS accessible-for-notify
    STATUS current
    DESCRIPTION
        "Parameter 'state' in event ME.18"
    ::= { meEventObjects18 3 }

meEventObjects19 OBJECT-IDENTITY
    STATUS current
    DESCRIPTION
        "Event ME.19
        A packet was lost, due TCP Tx overrun error."
    ::= { meEventsGroup 19 }

me19_interface OBJECT-TYPE
    SYNTAX DisplayString
    MAX-ACCESS accessible-for-notify
    STATUS current
    DESCRIPTION
        "Parameter 'interface' in event ME.19"
    ::= { meEventObjects19 1 }

me19_state OBJECT-TYPE
    SYNTAX Integer32
    MAX-ACCESS accessible-for-notify
    STATUS current
    DESCRIPTION
        "Parameter 'state' in event ME.19"
    ::= { meEventObjects19 2 }

meEventObjects20 OBJECT-IDENTITY
    STATUS current
    DESCRIPTION
        "Event ME.20
        A packet was lost, due TCP is closed."
    ::= { meEventsGroup 20 }

me20_interface OBJECT-TYPE
    SYNTAX DisplayString
    MAX-ACCESS accessible-for-notify
    STATUS current
    DESCRIPTION
        "Parameter 'interface' in event ME.20"
    ::= { meEventObjects20 1 }

me20_state OBJECT-TYPE
    SYNTAX Integer32
    MAX-ACCESS accessible-for-notify
    STATUS current
    DESCRIPTION
        "Parameter 'state' in event ME.20"
    ::= { meEventObjects20 2 }

meEventObjects21 OBJECT-IDENTITY
    STATUS current
    DESCRIPTION
        "Event ME.21
        The transfer has been wrong against specified NA and IP addr."
    ::= { meEventsGroup 21 }

me21_na OBJECT-TYPE
    SYNTAX Integer32
    MAX-ACCESS accessible-for-notify
    STATUS current
    DESCRIPTION
        "Parameter 'na' in event ME.21"
    ::= { meEventObjects21 1 }

me21_ip_host_address OBJECT-TYPE
    SYNTAX IpAddress
    MAX-ACCESS accessible-for-notify
    STATUS current
    DESCRIPTION
        "Parameter 'ip_host_address' in event ME.21"
    ::= { meEventObjects21 2 }

me21_cause OBJECT-TYPE
    SYNTAX Integer32
    MAX-ACCESS accessible-for-notify
    STATUS current
    DESCRIPTION
        "Parameter 'cause' in event ME.21"
    ::= { meEventObjects21 3 }

me21_interface OBJECT-TYPE
    SYNTAX DisplayString
    MAX-ACCESS accessible-for-notify
    STATUS current
    DESCRIPTION
        "Parameter 'interface' in event ME.21"
    ::= { meEventObjects21 4 }

meEventObjects22 OBJECT-IDENTITY
    STATUS current
    DESCRIPTION
        "Event ME.22
        TCP generic event was occurred."
    ::= { meEventsGroup 22 }

me22_event OBJECT-TYPE
    SYNTAX DisplayString
    MAX-ACCESS accessible-for-notify
    STATUS current
    DESCRIPTION
        "Parameter 'event' in event ME.22"
    ::= { meEventObjects22 1 }

me22_ip OBJECT-TYPE
    SYNTAX IpAddress
    MAX-ACCESS accessible-for-notify
    STATUS current
    DESCRIPTION
        "Parameter 'ip' in event ME.22"
    ::= { meEventObjects22 2 }

me22_port OBJECT-TYPE
    SYNTAX Integer32
    MAX-ACCESS accessible-for-notify
    STATUS current
    DESCRIPTION
        "Parameter 'port' in event ME.22"
    ::= { meEventObjects22 3 }

meEventObjects23 OBJECT-IDENTITY
    STATUS current
    DESCRIPTION
        "Event ME.23
        A change ON/OFF has been make in Serial Control Signal Input."
    ::= { meEventsGroup 23 }

me23_message_type OBJECT-TYPE
    SYNTAX DisplayString
    MAX-ACCESS accessible-for-notify
    STATUS current
    DESCRIPTION
        "Parameter 'message_type' in event ME.23"
    ::= { meEventObjects23 1 }

me23_interface OBJECT-TYPE
    SYNTAX DisplayString
    MAX-ACCESS accessible-for-notify
    STATUS current
    DESCRIPTION
        "Parameter 'interface' in event ME.23"
    ::= { meEventObjects23 2 }

me23_state OBJECT-TYPE
    SYNTAX Integer32
    MAX-ACCESS accessible-for-notify
    STATUS current
    DESCRIPTION
        "Parameter 'state' in event ME.23"
    ::= { meEventObjects23 3 }

meEventObjects24 OBJECT-IDENTITY
    STATUS current
    DESCRIPTION
        "Event ME.24
        Data error from Serial Terminal has been received."
    ::= { meEventsGroup 24 }

me24_message_type OBJECT-TYPE
    SYNTAX DisplayString
    MAX-ACCESS accessible-for-notify
    STATUS current
    DESCRIPTION
        "Parameter 'message_type' in event ME.24"
    ::= { meEventObjects24 1 }

me24_interface OBJECT-TYPE
    SYNTAX DisplayString
    MAX-ACCESS accessible-for-notify
    STATUS current
    DESCRIPTION
        "Parameter 'interface' in event ME.24"
    ::= { meEventObjects24 2 }

me24_state OBJECT-TYPE
    SYNTAX Integer32
    MAX-ACCESS accessible-for-notify
    STATUS current
    DESCRIPTION
        "Parameter 'state' in event ME.24"
    ::= { meEventObjects24 3 }

meEventObjects25 OBJECT-IDENTITY
    STATUS current
    DESCRIPTION
        "Event ME.25
        TCP Listen has been closed, due max session number has been reached."
    ::= { meEventsGroup 25 }

me25_port OBJECT-TYPE
    SYNTAX Integer32
    MAX-ACCESS accessible-for-notify
    STATUS current
    DESCRIPTION
        "Parameter 'port' in event ME.25"
    ::= { meEventObjects25 1 }

meEventObjects26 OBJECT-IDENTITY
    STATUS current
    DESCRIPTION
        "Event ME.26
        An input TCP session has been rejet."
    ::= { meEventsGroup 26 }

me26_event OBJECT-TYPE
    SYNTAX DisplayString
    MAX-ACCESS accessible-for-notify
    STATUS current
    DESCRIPTION
        "Parameter 'event' in event ME.26"
    ::= { meEventObjects26 1 }

me26_ip OBJECT-TYPE
    SYNTAX IpAddress
    MAX-ACCESS accessible-for-notify
    STATUS current
    DESCRIPTION
        "Parameter 'ip' in event ME.26"
    ::= { meEventObjects26 2 }

me26_port OBJECT-TYPE
    SYNTAX Integer32
    MAX-ACCESS accessible-for-notify
    STATUS current
    DESCRIPTION
        "Parameter 'port' in event ME.26"
    ::= { meEventObjects26 3 }

meEventObjects27 OBJECT-IDENTITY
    STATUS current
    DESCRIPTION
        "Event ME.27
        Detailed Data send to serial interface."
    ::= { meEventsGroup 27 }

me27_interface OBJECT-TYPE
    SYNTAX DisplayString
    MAX-ACCESS accessible-for-notify
    STATUS current
    DESCRIPTION
        "Parameter 'interface' in event ME.27"
    ::= { meEventObjects27 1 }

me27_serial_address OBJECT-TYPE
    SYNTAX Integer32
    MAX-ACCESS accessible-for-notify
    STATUS current
    DESCRIPTION
        "Parameter 'serial_address' in event ME.27"
    ::= { meEventObjects27 2 }

me27_lenght OBJECT-TYPE
    SYNTAX Integer32
    MAX-ACCESS accessible-for-notify
    STATUS current
    DESCRIPTION
        "Parameter 'lenght' in event ME.27"
    ::= { meEventObjects27 3 }

me27_hex_data OBJECT-TYPE
    SYNTAX DisplayString
    MAX-ACCESS accessible-for-notify
    STATUS current
    DESCRIPTION
        "Parameter 'hex_data' in event ME.27"
    ::= { meEventObjects27 4 }

meEventObjects28 OBJECT-IDENTITY
    STATUS current
    DESCRIPTION
        "Event ME.28
        Detailed Data received from serial interface."
    ::= { meEventsGroup 28 }

me28_interface OBJECT-TYPE
    SYNTAX DisplayString
    MAX-ACCESS accessible-for-notify
    STATUS current
    DESCRIPTION
        "Parameter 'interface' in event ME.28"
    ::= { meEventObjects28 1 }

me28_serial_address OBJECT-TYPE
    SYNTAX Integer32
    MAX-ACCESS accessible-for-notify
    STATUS current
    DESCRIPTION
        "Parameter 'serial_address' in event ME.28"
    ::= { meEventObjects28 2 }

me28_lenght OBJECT-TYPE
    SYNTAX Integer32
    MAX-ACCESS accessible-for-notify
    STATUS current
    DESCRIPTION
        "Parameter 'lenght' in event ME.28"
    ::= { meEventObjects28 3 }

me28_hex_data OBJECT-TYPE
    SYNTAX DisplayString
    MAX-ACCESS accessible-for-notify
    STATUS current
    DESCRIPTION
        "Parameter 'hex_data' in event ME.28"
    ::= { meEventObjects28 4 }

meEventObjects29 OBJECT-IDENTITY
    STATUS current
    DESCRIPTION
        "Event ME.29
        Change in the speed of the Serial Terminal."
    ::= { meEventsGroup 29 }

me29_speed OBJECT-TYPE
    SYNTAX Integer32
    MAX-ACCESS accessible-for-notify
    STATUS current
    DESCRIPTION
        "Parameter 'speed' in event ME.29"
    ::= { meEventObjects29 1 }

me29_interface OBJECT-TYPE
    SYNTAX DisplayString
    MAX-ACCESS accessible-for-notify
    STATUS current
    DESCRIPTION
        "Parameter 'interface' in event ME.29"
    ::= { meEventObjects29 2 }

meEventObjects30 OBJECT-IDENTITY
    STATUS current
    DESCRIPTION
        "Event ME.30
        Change in the speed of the Serial Terminal."
    ::= { meEventsGroup 30 }

me30_interface OBJECT-TYPE
    SYNTAX DisplayString
    MAX-ACCESS accessible-for-notify
    STATUS current
    DESCRIPTION
        "Parameter 'interface' in event ME.30"
    ::= { meEventObjects30 1 }


meNotification1 NOTIFICATION-TYPE
    OBJECTS { 
              me1_bytes_number, 
              me1_interface 
            }
    STATUS current
    DESCRIPTION
        "Notification of Event ME.1

        Message: 'Rx Data from Serial Terminal $1 bytes, interface $2'

        Parameters list:
              $1: me1_bytes_number
              $2: me1_interface

        Data has been received from Serial Terminal."
    ::= { meNotificationsPrefix 1 }

meNotification2 NOTIFICATION-TYPE
    OBJECTS { 
              me2_coment, 
              me2_atCommand,
              me2_interface,
              me2_state 
            }
    STATUS current
    DESCRIPTION
        "Notification of Event ME.2

        Message: 'Rx $1 from Serial Terminal: AT$2, interface $3 state $4'

        Parameters list:
              $1: me2_coment
              $2: me2_atCommand
              $3: me2_interface
              $4: me2_state

        One AT command message has been received from Serial Terminal."
    ::= { meNotificationsPrefix 2 }

meNotification3 NOTIFICATION-TYPE
    OBJECTS { 
              me3_bad_addr, 
              me3_interface 
            }
    STATUS current
    DESCRIPTION
        "Notification of Event ME.3

        Message: 'Rx Address error from Serial Terminal $1 bytes, interface $2'

        Parameters list:
              $1: me3_bad_addr
              $2: me3_interface

        A Message with bad address has been received from Serial Terminal."
    ::= { meNotificationsPrefix 3 }

meNotification4 NOTIFICATION-TYPE
    OBJECTS { 
              me4_cause, 
              me4_interface,
              me4_state 
            }
    STATUS current
    DESCRIPTION
        "Notification of Event ME.4

        Message: 'Rx Bad Message from Serial Terminal ($1), interface $2 state $3'

        Parameters list:
              $1: me4_cause
              $2: me4_interface
              $3: me4_state

        One Bad Message has been received from Serial Terminal."
    ::= { meNotificationsPrefix 4 }

meNotification5 NOTIFICATION-TYPE
    OBJECTS { 
              me5_interface, 
              me5_state 
            }
    STATUS current
    DESCRIPTION
        "Notification of Event ME.5

        Message: 'A block with LRC/CRC error has been received from Serial Terminal, interface $1 state $2'

        Parameters list:
              $1: me5_interface
              $2: me5_state

        A message with LRC/CRC error has been received from Serial Terminal."
    ::= { meNotificationsPrefix 5 }

meNotification6 NOTIFICATION-TYPE
    OBJECTS { 
              me6_error_type, 
              me6_interface,
              me6_state 
            }
    STATUS current
    DESCRIPTION
        "Notification of Event ME.6

        Message: 'A block with $1 error has been received from Serial Terminal, interface $2 state $3'

        Parameters list:
              $1: me6_error_type
              $2: me6_interface
              $3: me6_state

        A message with error has been received from Remote."
    ::= { meNotificationsPrefix 6 }

meNotification7 NOTIFICATION-TYPE
    OBJECTS { 
              me7_serial_address, 
              me7_interface 
            }
    STATUS current
    DESCRIPTION
        "Notification of Event ME.7

        Message: 'Address $1 received from Serial Terminal is not included in configuration regiters. Interface $2'

        Parameters list:
              $1: me7_serial_address
              $2: me7_interface

        Addres received from Serial Terminal is not included in configuration
        registers list."
    ::= { meNotificationsPrefix 7 }

meNotification8 NOTIFICATION-TYPE
    OBJECTS { 
              me8_atCommand, 
              me8_value 
            }
    STATUS current
    DESCRIPTION
        "Notification of Event ME.8

        Message: 'Basic AT Command: AT$1$2'

        Parameters list:
              $1: me8_atCommand
              $2: me8_value

        Processed a basic AT command"
    ::= { meNotificationsPrefix 8 }

meNotification9 NOTIFICATION-TYPE
    OBJECTS { 
              me9_interface 
            }
    STATUS current
    DESCRIPTION
        "Notification of Event ME.9

        Message: 'The Transfer has been completed successfully. Interface $1'

        Parameters list:
              $1: me9_interface

        The Transfer has been completed successfully."
    ::= { meNotificationsPrefix 9 }

meNotification10 NOTIFICATION-TYPE
    OBJECTS { 
              me10_atCommand, 
              me10_value 
            }
    STATUS current
    DESCRIPTION
        "Notification of Event ME.10

        Message: 'Extended AT Command: AT&$1$2'

        Parameters list:
              $1: me10_atCommand
              $2: me10_value

        Processed an extended AT command"
    ::= { meNotificationsPrefix 10 }

meNotification11 NOTIFICATION-TYPE
    OBJECTS { 
              me11_atCommand, 
              me11_value 
            }
    STATUS current
    DESCRIPTION
        "Notification of Event ME.11

        Message: 'Propietary AT Command: AT$1$2'

        Parameters list:
              $1: me11_atCommand
              $2: me11_value

        Processed an extended AT command"
    ::= { meNotificationsPrefix 11 }

meNotification12 NOTIFICATION-TYPE
    OBJECTS { 
              me12_atCommand, 
              me12_sReg,
              me12_value 
            }
    STATUS current
    DESCRIPTION
        "Notification of Event ME.12

        Message: 'Basic AT Command: AT$1$2=$3'

        Parameters list:
              $1: me12_atCommand
              $2: me12_sReg
              $3: me12_value

        Processed a basic AT command Sn=x"
    ::= { meNotificationsPrefix 12 }

meNotification13 NOTIFICATION-TYPE
    OBJECTS { 
              me13_foreign_host, 
              me13_remote_port 
            }
    STATUS current
    DESCRIPTION
        "Notification of Event ME.13

        Message: 'The TCP session has been closed. rem. IP: $1, Port: $2'

        Parameters list:
              $1: me13_foreign_host
              $2: me13_remote_port

        The TCP session has been closed."
    ::= { meNotificationsPrefix 13 }

meNotification14 NOTIFICATION-TYPE
    OBJECTS { 
              me14_foreign_host, 
              me14_remote_port 
            }
    STATUS current
    DESCRIPTION
        "Notification of Event ME.14

        Message: 'The TCP session has been closed by the Remote end. rem. IP: $1, Port: $2'

        Parameters list:
              $1: me14_foreign_host
              $2: me14_remote_port

        The TCP session has been closed by the Remote end."
    ::= { meNotificationsPrefix 14 }

meNotification15 NOTIFICATION-TYPE
    OBJECTS { 
              me15_remote_ip, 
              me15_remote_port 
            }
    STATUS current
    DESCRIPTION
        "Notification of Event ME.15

        Message: 'The TCP session has been opened by the Remote end. Remote IP:$1 , Port: $2'

        Parameters list:
              $1: me15_remote_ip
              $2: me15_remote_port

        The TCP session has been opened by the Remote end."
    ::= { meNotificationsPrefix 15 }

meNotification16 NOTIFICATION-TYPE
    OBJECTS { 
              me16_atResponse, 
              me16_interface,
              me16_state 
            }
    STATUS current
    DESCRIPTION
        "Notification of Event ME.16

        Message: 'Tx Message to Serial Terminal, $1, interface $2 state $3'

        Parameters list:
              $1: me16_atResponse
              $2: me16_interface
              $3: me16_state

        An AT response message has been transmited to Serial Terminal."
    ::= { meNotificationsPrefix 16 }

meNotification17 NOTIFICATION-TYPE
    OBJECTS { 
              me17_message_type, 
              me17_interface,
              me17_state 
            }
    STATUS current
    DESCRIPTION
        "Notification of Event ME.17

        Message: 'Serial Control Signal Input change to $1, interface $2 state $3'

        Parameters list:
              $1: me17_message_type
              $2: me17_interface
              $3: me17_state

        A change ON/OFF has been detected in Serial Control Signal Input."
    ::= { meNotificationsPrefix 17 }

meNotification18 NOTIFICATION-TYPE
    OBJECTS { 
              me18_site, 
              me18_interface,
              me18_state 
            }
    STATUS current
    DESCRIPTION
        "Notification of Event ME.18

        Message: 'Timeout waiting data from $1, interface $2 state $3'

        Parameters list:
              $1: me18_site
              $2: me18_interface
              $3: me18_state

        Timeout has occur waiting data."
    ::= { meNotificationsPrefix 18 }

meNotification19 NOTIFICATION-TYPE
    OBJECTS { 
              me19_interface, 
              me19_state 
            }
    STATUS current
    DESCRIPTION
        "Notification of Event ME.19

        Message: 'Packet lost due TCP Tx overrun error. Interface $1 state $2'

        Parameters list:
              $1: me19_interface
              $2: me19_state

        A packet was lost, due TCP Tx overrun error."
    ::= { meNotificationsPrefix 19 }

meNotification20 NOTIFICATION-TYPE
    OBJECTS { 
              me20_interface, 
              me20_state 
            }
    STATUS current
    DESCRIPTION
        "Notification of Event ME.20

        Message: 'Packet lost due TCP session is closes. Interface $1 state $2'

        Parameters list:
              $1: me20_interface
              $2: me20_state

        A packet was lost, due TCP is closed."
    ::= { meNotificationsPrefix 20 }

meNotification21 NOTIFICATION-TYPE
    OBJECTS { 
              me21_na, 
              me21_ip_host_address,
              me21_cause,
              me21_interface 
            }
    STATUS current
    DESCRIPTION
        "Notification of Event ME.21

        Message: 'The transfer has been wrong, against address $1, IP $2, Cause $3, interface $4'

        Parameters list:
              $1: me21_na
              $2: me21_ip_host_address
              $3: me21_cause
              $4: me21_interface

        The transfer has been wrong against specified NA and IP addr."
    ::= { meNotificationsPrefix 21 }

meNotification22 NOTIFICATION-TYPE
    OBJECTS { 
              me22_event, 
              me22_ip,
              me22_port 
            }
    STATUS current
    DESCRIPTION
        "Notification of Event ME.22

        Message: 'The TCP event: $1 . Rem. IP: $2, rem. Port: $3'

        Parameters list:
              $1: me22_event
              $2: me22_ip
              $3: me22_port

        TCP generic event was occurred."
    ::= { meNotificationsPrefix 22 }

meNotification23 NOTIFICATION-TYPE
    OBJECTS { 
              me23_message_type, 
              me23_interface,
              me23_state 
            }
    STATUS current
    DESCRIPTION
        "Notification of Event ME.23

        Message: 'Serial Control Signal Output change to $1, interface $2 state $3'

        Parameters list:
              $1: me23_message_type
              $2: me23_interface
              $3: me23_state

        A change ON/OFF has been make in Serial Control Signal Input."
    ::= { meNotificationsPrefix 23 }

meNotification24 NOTIFICATION-TYPE
    OBJECTS { 
              me24_message_type, 
              me24_interface,
              me24_state 
            }
    STATUS current
    DESCRIPTION
        "Notification of Event ME.24

        Message: 'Data ERROR from Serial Terminal has been received type: $1. Interface $2 state $3'

        Parameters list:
              $1: me24_message_type
              $2: me24_interface
              $3: me24_state

        Data error from Serial Terminal has been received."
    ::= { meNotificationsPrefix 24 }

meNotification25 NOTIFICATION-TYPE
    OBJECTS { 
              me25_port 
            }
    STATUS current
    DESCRIPTION
        "Notification of Event ME.25

        Message: 'Max sessions number has been reached, port $1'

        Parameters list:
              $1: me25_port

        TCP Listen has been closed, due max session number has been reached."
    ::= { meNotificationsPrefix 25 }

meNotification26 NOTIFICATION-TYPE
    OBJECTS { 
              me26_event, 
              me26_ip,
              me26_port 
            }
    STATUS current
    DESCRIPTION
        "Notification of Event ME.26

        Message: 'TCP inout session rejet: $1 . Rem. IP: $2, rem. Port: $3'

        Parameters list:
              $1: me26_event
              $2: me26_ip
              $3: me26_port

        An input TCP session has been rejet."
    ::= { meNotificationsPrefix 26 }

meNotification27 NOTIFICATION-TYPE
    OBJECTS { 
              me27_interface, 
              me27_serial_address,
              me27_lenght,
              me27_hex_data 
            }
    STATUS current
    DESCRIPTION
        "Notification of Event ME.27

        Message: 'Data transmitted to serial interface $1 (addr:$2,$3 bytes):$4'

        Parameters list:
              $1: me27_interface
              $2: me27_serial_address
              $3: me27_lenght
              $4: me27_hex_data

        Detailed Data send to serial interface."
    ::= { meNotificationsPrefix 27 }

meNotification28 NOTIFICATION-TYPE
    OBJECTS { 
              me28_interface, 
              me28_serial_address,
              me28_lenght,
              me28_hex_data 
            }
    STATUS current
    DESCRIPTION
        "Notification of Event ME.28

        Message: 'Data received from serial interface $1 (addr:$2,$3 bytes):$4'

        Parameters list:
              $1: me28_interface
              $2: me28_serial_address
              $3: me28_lenght
              $4: me28_hex_data

        Detailed Data received from serial interface."
    ::= { meNotificationsPrefix 28 }

meNotification29 NOTIFICATION-TYPE
    OBJECTS { 
              me29_speed, 
              me29_interface 
            }
    STATUS current
    DESCRIPTION
        "Notification of Event ME.29

        Message: 'Change the speed of Serial Terminal to $1 in interface $2'

        Parameters list:
              $1: me29_speed
              $2: me29_interface

        Change in the speed of the Serial Terminal."
    ::= { meNotificationsPrefix 29 }

meNotification30 NOTIFICATION-TYPE
    OBJECTS { 
              me30_interface 
            }
    STATUS current
    DESCRIPTION
        "Notification of Event ME.30

        Message: 'Received the escape char through interface $1'

        Parameters list:
              $1: me30_interface

        Change in the speed of the Serial Terminal."
    ::= { meNotificationsPrefix 30 }


END
