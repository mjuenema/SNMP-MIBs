-- file automatically created


TELDAT-TRAP-IPHC-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


iphcTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the IPHC event subsystem."
    REVISION "201401200930Z"
    DESCRIPTION "Initial implementation"
        ::= { telEventTraps 181 }


iphcEventsGroup	OBJECT IDENTIFIER	::= { iphcTrapsMIB 1 }

iphcNotifications	OBJECT IDENTIFIER	::= { iphcTrapsMIB 2 }
iphcNotificationsPrefix	OBJECT IDENTIFIER	::= { iphcNotifications 0 }

iphcEventObjects1 OBJECT-IDENTITY
    STATUS current
    DESCRIPTION
        "Event IPHC.1
        ."
    ::= { iphcEventsGroup 1 }

iphc1_interface OBJECT-TYPE
    SYNTAX DisplayString
    MAX-ACCESS accessible-for-notify
    STATUS current
    DESCRIPTION
        "Parameter 'interface' in event IPHC.1"
    ::= { iphcEventObjects1 1 }

iphc1_cid OBJECT-TYPE
    SYNTAX Integer32
    MAX-ACCESS accessible-for-notify
    STATUS current
    DESCRIPTION
        "Parameter 'cid' in event IPHC.1"
    ::= { iphcEventObjects1 2 }

iphc1_cause OBJECT-TYPE
    SYNTAX DisplayString
    MAX-ACCESS accessible-for-notify
    STATUS current
    DESCRIPTION
        "Parameter 'cause' in event IPHC.1"
    ::= { iphcEventObjects1 3 }

iphc1_pkt_counter OBJECT-TYPE
    SYNTAX Integer32
    MAX-ACCESS accessible-for-notify
    STATUS current
    DESCRIPTION
        "Parameter 'pkt_counter' in event IPHC.1"
    ::= { iphcEventObjects1 4 }

iphcEventObjects2 OBJECT-IDENTITY
    STATUS current
    DESCRIPTION
        "Event IPHC.2
        ."
    ::= { iphcEventsGroup 2 }

iphc2_interface OBJECT-TYPE
    SYNTAX DisplayString
    MAX-ACCESS accessible-for-notify
    STATUS current
    DESCRIPTION
        "Parameter 'interface' in event IPHC.2"
    ::= { iphcEventObjects2 1 }

iphc2_cid OBJECT-TYPE
    SYNTAX Integer32
    MAX-ACCESS accessible-for-notify
    STATUS current
    DESCRIPTION
        "Parameter 'cid' in event IPHC.2"
    ::= { iphcEventObjects2 2 }

iphc2_pkt_counter OBJECT-TYPE
    SYNTAX Integer32
    MAX-ACCESS accessible-for-notify
    STATUS current
    DESCRIPTION
        "Parameter 'pkt_counter' in event IPHC.2"
    ::= { iphcEventObjects2 3 }

iphcEventObjects3 OBJECT-IDENTITY
    STATUS current
    DESCRIPTION
        "Event IPHC.3
        ."
    ::= { iphcEventsGroup 3 }

iphc3_interface OBJECT-TYPE
    SYNTAX DisplayString
    MAX-ACCESS accessible-for-notify
    STATUS current
    DESCRIPTION
        "Parameter 'interface' in event IPHC.3"
    ::= { iphcEventObjects3 1 }

iphc3_cid OBJECT-TYPE
    SYNTAX Integer32
    MAX-ACCESS accessible-for-notify
    STATUS current
    DESCRIPTION
        "Parameter 'cid' in event IPHC.3"
    ::= { iphcEventObjects3 2 }

iphc3_generation OBJECT-TYPE
    SYNTAX Integer32
    MAX-ACCESS accessible-for-notify
    STATUS current
    DESCRIPTION
        "Parameter 'generation' in event IPHC.3"
    ::= { iphcEventObjects3 3 }

iphc3_flag_D OBJECT-TYPE
    SYNTAX DisplayString
    MAX-ACCESS accessible-for-notify
    STATUS current
    DESCRIPTION
        "Parameter 'flag_D' in event IPHC.3"
    ::= { iphcEventObjects3 4 }

iphc3_link_sequence OBJECT-TYPE
    SYNTAX Integer32
    MAX-ACCESS accessible-for-notify
    STATUS current
    DESCRIPTION
        "Parameter 'link_sequence' in event IPHC.3"
    ::= { iphcEventObjects3 5 }

iphc3_ip_id OBJECT-TYPE
    SYNTAX Integer32
    MAX-ACCESS accessible-for-notify
    STATUS current
    DESCRIPTION
        "Parameter 'ip_id' in event IPHC.3"
    ::= { iphcEventObjects3 6 }

iphc3_pkt_counter OBJECT-TYPE
    SYNTAX Integer32
    MAX-ACCESS accessible-for-notify
    STATUS current
    DESCRIPTION
        "Parameter 'pkt_counter' in event IPHC.3"
    ::= { iphcEventObjects3 7 }

iphcEventObjects4 OBJECT-IDENTITY
    STATUS current
    DESCRIPTION
        "Event IPHC.4
        ."
    ::= { iphcEventsGroup 4 }

iphc4_interface OBJECT-TYPE
    SYNTAX DisplayString
    MAX-ACCESS accessible-for-notify
    STATUS current
    DESCRIPTION
        "Parameter 'interface' in event IPHC.4"
    ::= { iphcEventObjects4 1 }

iphc4_cid OBJECT-TYPE
    SYNTAX Integer32
    MAX-ACCESS accessible-for-notify
    STATUS current
    DESCRIPTION
        "Parameter 'cid' in event IPHC.4"
    ::= { iphcEventObjects4 2 }

iphc4_generation OBJECT-TYPE
    SYNTAX Integer32
    MAX-ACCESS accessible-for-notify
    STATUS current
    DESCRIPTION
        "Parameter 'generation' in event IPHC.4"
    ::= { iphcEventObjects4 3 }

iphc4_flag_D OBJECT-TYPE
    SYNTAX DisplayString
    MAX-ACCESS accessible-for-notify
    STATUS current
    DESCRIPTION
        "Parameter 'flag_D' in event IPHC.4"
    ::= { iphcEventObjects4 4 }

iphc4_link_sequence OBJECT-TYPE
    SYNTAX Integer32
    MAX-ACCESS accessible-for-notify
    STATUS current
    DESCRIPTION
        "Parameter 'link_sequence' in event IPHC.4"
    ::= { iphcEventObjects4 5 }

iphc4_ip_id OBJECT-TYPE
    SYNTAX Integer32
    MAX-ACCESS accessible-for-notify
    STATUS current
    DESCRIPTION
        "Parameter 'ip_id' in event IPHC.4"
    ::= { iphcEventObjects4 6 }

iphc4_pkt_counter OBJECT-TYPE
    SYNTAX Integer32
    MAX-ACCESS accessible-for-notify
    STATUS current
    DESCRIPTION
        "Parameter 'pkt_counter' in event IPHC.4"
    ::= { iphcEventObjects4 7 }

iphcEventObjects5 OBJECT-IDENTITY
    STATUS current
    DESCRIPTION
        "Event IPHC.5
        ."
    ::= { iphcEventsGroup 5 }

iphc5_interface OBJECT-TYPE
    SYNTAX DisplayString
    MAX-ACCESS accessible-for-notify
    STATUS current
    DESCRIPTION
        "Parameter 'interface' in event IPHC.5"
    ::= { iphcEventObjects5 1 }

iphc5_cid OBJECT-TYPE
    SYNTAX Integer32
    MAX-ACCESS accessible-for-notify
    STATUS current
    DESCRIPTION
        "Parameter 'cid' in event IPHC.5"
    ::= { iphcEventObjects5 2 }

iphc5_flags OBJECT-TYPE
    SYNTAX DisplayString
    MAX-ACCESS accessible-for-notify
    STATUS current
    DESCRIPTION
        "Parameter 'flags' in event IPHC.5"
    ::= { iphcEventObjects5 3 }

iphc5_sequence_number OBJECT-TYPE
    SYNTAX Integer32
    MAX-ACCESS accessible-for-notify
    STATUS current
    DESCRIPTION
        "Parameter 'sequence_number' in event IPHC.5"
    ::= { iphcEventObjects5 4 }

iphc5_ack_number OBJECT-TYPE
    SYNTAX Integer32
    MAX-ACCESS accessible-for-notify
    STATUS current
    DESCRIPTION
        "Parameter 'ack_number' in event IPHC.5"
    ::= { iphcEventObjects5 5 }

iphc5_window_size OBJECT-TYPE
    SYNTAX Integer32
    MAX-ACCESS accessible-for-notify
    STATUS current
    DESCRIPTION
        "Parameter 'window_size' in event IPHC.5"
    ::= { iphcEventObjects5 6 }

iphc5_checksum OBJECT-TYPE
    SYNTAX Integer32
    MAX-ACCESS accessible-for-notify
    STATUS current
    DESCRIPTION
        "Parameter 'checksum' in event IPHC.5"
    ::= { iphcEventObjects5 7 }

iphc5_ip_id OBJECT-TYPE
    SYNTAX Integer32
    MAX-ACCESS accessible-for-notify
    STATUS current
    DESCRIPTION
        "Parameter 'ip_id' in event IPHC.5"
    ::= { iphcEventObjects5 8 }

iphc5_pkt_counter OBJECT-TYPE
    SYNTAX Integer32
    MAX-ACCESS accessible-for-notify
    STATUS current
    DESCRIPTION
        "Parameter 'pkt_counter' in event IPHC.5"
    ::= { iphcEventObjects5 9 }

iphcEventObjects6 OBJECT-IDENTITY
    STATUS current
    DESCRIPTION
        "Event IPHC.6
        ."
    ::= { iphcEventsGroup 6 }

iphc6_interface OBJECT-TYPE
    SYNTAX DisplayString
    MAX-ACCESS accessible-for-notify
    STATUS current
    DESCRIPTION
        "Parameter 'interface' in event IPHC.6"
    ::= { iphcEventObjects6 1 }

iphc6_cid OBJECT-TYPE
    SYNTAX Integer32
    MAX-ACCESS accessible-for-notify
    STATUS current
    DESCRIPTION
        "Parameter 'cid' in event IPHC.6"
    ::= { iphcEventObjects6 2 }

iphc6_flags OBJECT-TYPE
    SYNTAX DisplayString
    MAX-ACCESS accessible-for-notify
    STATUS current
    DESCRIPTION
        "Parameter 'flags' in event IPHC.6"
    ::= { iphcEventObjects6 3 }

iphc6_sequence_number OBJECT-TYPE
    SYNTAX Integer32
    MAX-ACCESS accessible-for-notify
    STATUS current
    DESCRIPTION
        "Parameter 'sequence_number' in event IPHC.6"
    ::= { iphcEventObjects6 4 }

iphc6_ack_number OBJECT-TYPE
    SYNTAX Integer32
    MAX-ACCESS accessible-for-notify
    STATUS current
    DESCRIPTION
        "Parameter 'ack_number' in event IPHC.6"
    ::= { iphcEventObjects6 5 }

iphc6_window_size OBJECT-TYPE
    SYNTAX Integer32
    MAX-ACCESS accessible-for-notify
    STATUS current
    DESCRIPTION
        "Parameter 'window_size' in event IPHC.6"
    ::= { iphcEventObjects6 6 }

iphc6_checksum OBJECT-TYPE
    SYNTAX Integer32
    MAX-ACCESS accessible-for-notify
    STATUS current
    DESCRIPTION
        "Parameter 'checksum' in event IPHC.6"
    ::= { iphcEventObjects6 7 }

iphc6_ip_id OBJECT-TYPE
    SYNTAX Integer32
    MAX-ACCESS accessible-for-notify
    STATUS current
    DESCRIPTION
        "Parameter 'ip_id' in event IPHC.6"
    ::= { iphcEventObjects6 8 }

iphc6_pkt_counter OBJECT-TYPE
    SYNTAX Integer32
    MAX-ACCESS accessible-for-notify
    STATUS current
    DESCRIPTION
        "Parameter 'pkt_counter' in event IPHC.6"
    ::= { iphcEventObjects6 9 }

iphcEventObjects7 OBJECT-IDENTITY
    STATUS current
    DESCRIPTION
        "Event IPHC.7
        ."
    ::= { iphcEventsGroup 7 }

iphc7_interface OBJECT-TYPE
    SYNTAX DisplayString
    MAX-ACCESS accessible-for-notify
    STATUS current
    DESCRIPTION
        "Parameter 'interface' in event IPHC.7"
    ::= { iphcEventObjects7 1 }

iphc7_cid OBJECT-TYPE
    SYNTAX Integer32
    MAX-ACCESS accessible-for-notify
    STATUS current
    DESCRIPTION
        "Parameter 'cid' in event IPHC.7"
    ::= { iphcEventObjects7 2 }

iphcEventObjects8 OBJECT-IDENTITY
    STATUS current
    DESCRIPTION
        "Event IPHC.8
        ."
    ::= { iphcEventsGroup 8 }

iphc8_interface OBJECT-TYPE
    SYNTAX DisplayString
    MAX-ACCESS accessible-for-notify
    STATUS current
    DESCRIPTION
        "Parameter 'interface' in event IPHC.8"
    ::= { iphcEventObjects8 1 }

iphc8_cid OBJECT-TYPE
    SYNTAX Integer32
    MAX-ACCESS accessible-for-notify
    STATUS current
    DESCRIPTION
        "Parameter 'cid' in event IPHC.8"
    ::= { iphcEventObjects8 2 }

iphcEventObjects9 OBJECT-IDENTITY
    STATUS current
    DESCRIPTION
        "Event IPHC.9
        ."
    ::= { iphcEventsGroup 9 }

iphc9_interface OBJECT-TYPE
    SYNTAX DisplayString
    MAX-ACCESS accessible-for-notify
    STATUS current
    DESCRIPTION
        "Parameter 'interface' in event IPHC.9"
    ::= { iphcEventObjects9 1 }

iphc9_cid OBJECT-TYPE
    SYNTAX Integer32
    MAX-ACCESS accessible-for-notify
    STATUS current
    DESCRIPTION
        "Parameter 'cid' in event IPHC.9"
    ::= { iphcEventObjects9 2 }

iphc9_flags OBJECT-TYPE
    SYNTAX DisplayString
    MAX-ACCESS accessible-for-notify
    STATUS current
    DESCRIPTION
        "Parameter 'flags' in event IPHC.9"
    ::= { iphcEventObjects9 3 }

iphc9_link_sequence OBJECT-TYPE
    SYNTAX Integer32
    MAX-ACCESS accessible-for-notify
    STATUS current
    DESCRIPTION
        "Parameter 'link_sequence' in event IPHC.9"
    ::= { iphcEventObjects9 4 }

iphc9_ip_id OBJECT-TYPE
    SYNTAX Integer32
    MAX-ACCESS accessible-for-notify
    STATUS current
    DESCRIPTION
        "Parameter 'ip_id' in event IPHC.9"
    ::= { iphcEventObjects9 5 }

iphc9_pkt_counter OBJECT-TYPE
    SYNTAX Integer32
    MAX-ACCESS accessible-for-notify
    STATUS current
    DESCRIPTION
        "Parameter 'pkt_counter' in event IPHC.9"
    ::= { iphcEventObjects9 6 }

iphcEventObjects10 OBJECT-IDENTITY
    STATUS current
    DESCRIPTION
        "Event IPHC.10
        ."
    ::= { iphcEventsGroup 10 }

iphc10_interface OBJECT-TYPE
    SYNTAX DisplayString
    MAX-ACCESS accessible-for-notify
    STATUS current
    DESCRIPTION
        "Parameter 'interface' in event IPHC.10"
    ::= { iphcEventObjects10 1 }

iphc10_cid OBJECT-TYPE
    SYNTAX Integer32
    MAX-ACCESS accessible-for-notify
    STATUS current
    DESCRIPTION
        "Parameter 'cid' in event IPHC.10"
    ::= { iphcEventObjects10 2 }

iphc10_flags OBJECT-TYPE
    SYNTAX DisplayString
    MAX-ACCESS accessible-for-notify
    STATUS current
    DESCRIPTION
        "Parameter 'flags' in event IPHC.10"
    ::= { iphcEventObjects10 3 }

iphc10_link_sequence OBJECT-TYPE
    SYNTAX Integer32
    MAX-ACCESS accessible-for-notify
    STATUS current
    DESCRIPTION
        "Parameter 'link_sequence' in event IPHC.10"
    ::= { iphcEventObjects10 4 }

iphc10_ip_id OBJECT-TYPE
    SYNTAX Integer32
    MAX-ACCESS accessible-for-notify
    STATUS current
    DESCRIPTION
        "Parameter 'ip_id' in event IPHC.10"
    ::= { iphcEventObjects10 5 }

iphc10_pkt_counter OBJECT-TYPE
    SYNTAX Integer32
    MAX-ACCESS accessible-for-notify
    STATUS current
    DESCRIPTION
        "Parameter 'pkt_counter' in event IPHC.10"
    ::= { iphcEventObjects10 6 }

iphcEventObjects11 OBJECT-IDENTITY
    STATUS current
    DESCRIPTION
        "Event IPHC.11
        ."
    ::= { iphcEventsGroup 11 }

iphc11_interface OBJECT-TYPE
    SYNTAX DisplayString
    MAX-ACCESS accessible-for-notify
    STATUS current
    DESCRIPTION
        "Parameter 'interface' in event IPHC.11"
    ::= { iphcEventObjects11 1 }

iphc11_cid OBJECT-TYPE
    SYNTAX Integer32
    MAX-ACCESS accessible-for-notify
    STATUS current
    DESCRIPTION
        "Parameter 'cid' in event IPHC.11"
    ::= { iphcEventObjects11 2 }

iphc11_flags OBJECT-TYPE
    SYNTAX DisplayString
    MAX-ACCESS accessible-for-notify
    STATUS current
    DESCRIPTION
        "Parameter 'flags' in event IPHC.11"
    ::= { iphcEventObjects11 3 }

iphc11_link_sequence OBJECT-TYPE
    SYNTAX Integer32
    MAX-ACCESS accessible-for-notify
    STATUS current
    DESCRIPTION
        "Parameter 'link_sequence' in event IPHC.11"
    ::= { iphcEventObjects11 4 }

iphc11_pkt_counter OBJECT-TYPE
    SYNTAX Integer32
    MAX-ACCESS accessible-for-notify
    STATUS current
    DESCRIPTION
        "Parameter 'pkt_counter' in event IPHC.11"
    ::= { iphcEventObjects11 5 }

iphcEventObjects12 OBJECT-IDENTITY
    STATUS current
    DESCRIPTION
        "Event IPHC.12
        ."
    ::= { iphcEventsGroup 12 }

iphc12_interface OBJECT-TYPE
    SYNTAX DisplayString
    MAX-ACCESS accessible-for-notify
    STATUS current
    DESCRIPTION
        "Parameter 'interface' in event IPHC.12"
    ::= { iphcEventObjects12 1 }

iphc12_cid OBJECT-TYPE
    SYNTAX Integer32
    MAX-ACCESS accessible-for-notify
    STATUS current
    DESCRIPTION
        "Parameter 'cid' in event IPHC.12"
    ::= { iphcEventObjects12 2 }

iphc12_flags OBJECT-TYPE
    SYNTAX DisplayString
    MAX-ACCESS accessible-for-notify
    STATUS current
    DESCRIPTION
        "Parameter 'flags' in event IPHC.12"
    ::= { iphcEventObjects12 3 }

iphc12_link_sequence OBJECT-TYPE
    SYNTAX Integer32
    MAX-ACCESS accessible-for-notify
    STATUS current
    DESCRIPTION
        "Parameter 'link_sequence' in event IPHC.12"
    ::= { iphcEventObjects12 4 }

iphc12_ip_id OBJECT-TYPE
    SYNTAX Integer32
    MAX-ACCESS accessible-for-notify
    STATUS current
    DESCRIPTION
        "Parameter 'ip_id' in event IPHC.12"
    ::= { iphcEventObjects12 5 }

iphc12_pkt_counter OBJECT-TYPE
    SYNTAX Integer32
    MAX-ACCESS accessible-for-notify
    STATUS current
    DESCRIPTION
        "Parameter 'pkt_counter' in event IPHC.12"
    ::= { iphcEventObjects12 6 }

iphcEventObjects13 OBJECT-IDENTITY
    STATUS current
    DESCRIPTION
        "Event IPHC.13
        ."
    ::= { iphcEventsGroup 13 }

iphc13_interface OBJECT-TYPE
    SYNTAX DisplayString
    MAX-ACCESS accessible-for-notify
    STATUS current
    DESCRIPTION
        "Parameter 'interface' in event IPHC.13"
    ::= { iphcEventObjects13 1 }

iphc13_cid OBJECT-TYPE
    SYNTAX Integer32
    MAX-ACCESS accessible-for-notify
    STATUS current
    DESCRIPTION
        "Parameter 'cid' in event IPHC.13"
    ::= { iphcEventObjects13 2 }

iphcEventObjects14 OBJECT-IDENTITY
    STATUS current
    DESCRIPTION
        "Event IPHC.14
        ."
    ::= { iphcEventsGroup 14 }

iphc14_interface OBJECT-TYPE
    SYNTAX DisplayString
    MAX-ACCESS accessible-for-notify
    STATUS current
    DESCRIPTION
        "Parameter 'interface' in event IPHC.14"
    ::= { iphcEventObjects14 1 }

iphc14_cid OBJECT-TYPE
    SYNTAX Integer32
    MAX-ACCESS accessible-for-notify
    STATUS current
    DESCRIPTION
        "Parameter 'cid' in event IPHC.14"
    ::= { iphcEventObjects14 2 }

iphc14_flags OBJECT-TYPE
    SYNTAX DisplayString
    MAX-ACCESS accessible-for-notify
    STATUS current
    DESCRIPTION
        "Parameter 'flags' in event IPHC.14"
    ::= { iphcEventObjects14 3 }

iphc14_link_sequence OBJECT-TYPE
    SYNTAX Integer32
    MAX-ACCESS accessible-for-notify
    STATUS current
    DESCRIPTION
        "Parameter 'link_sequence' in event IPHC.14"
    ::= { iphcEventObjects14 4 }

iphc14_ip_id OBJECT-TYPE
    SYNTAX Integer32
    MAX-ACCESS accessible-for-notify
    STATUS current
    DESCRIPTION
        "Parameter 'ip_id' in event IPHC.14"
    ::= { iphcEventObjects14 5 }

iphc14_pkt_counter OBJECT-TYPE
    SYNTAX Integer32
    MAX-ACCESS accessible-for-notify
    STATUS current
    DESCRIPTION
        "Parameter 'pkt_counter' in event IPHC.14"
    ::= { iphcEventObjects14 6 }

iphcEventObjects15 OBJECT-IDENTITY
    STATUS current
    DESCRIPTION
        "Event IPHC.15
        ."
    ::= { iphcEventsGroup 15 }

iphc15_interface OBJECT-TYPE
    SYNTAX DisplayString
    MAX-ACCESS accessible-for-notify
    STATUS current
    DESCRIPTION
        "Parameter 'interface' in event IPHC.15"
    ::= { iphcEventObjects15 1 }

iphc15_cid OBJECT-TYPE
    SYNTAX Integer32
    MAX-ACCESS accessible-for-notify
    STATUS current
    DESCRIPTION
        "Parameter 'cid' in event IPHC.15"
    ::= { iphcEventObjects15 2 }

iphcEventObjects16 OBJECT-IDENTITY
    STATUS current
    DESCRIPTION
        "Event IPHC.16
        ."
    ::= { iphcEventsGroup 16 }

iphc16_interface OBJECT-TYPE
    SYNTAX DisplayString
    MAX-ACCESS accessible-for-notify
    STATUS current
    DESCRIPTION
        "Parameter 'interface' in event IPHC.16"
    ::= { iphcEventObjects16 1 }

iphc16_cid OBJECT-TYPE
    SYNTAX Integer32
    MAX-ACCESS accessible-for-notify
    STATUS current
    DESCRIPTION
        "Parameter 'cid' in event IPHC.16"
    ::= { iphcEventObjects16 2 }

iphc16_flags OBJECT-TYPE
    SYNTAX DisplayString
    MAX-ACCESS accessible-for-notify
    STATUS current
    DESCRIPTION
        "Parameter 'flags' in event IPHC.16"
    ::= { iphcEventObjects16 3 }

iphc16_link_sequence OBJECT-TYPE
    SYNTAX Integer32
    MAX-ACCESS accessible-for-notify
    STATUS current
    DESCRIPTION
        "Parameter 'link_sequence' in event IPHC.16"
    ::= { iphcEventObjects16 4 }

iphc16_ip_id OBJECT-TYPE
    SYNTAX Integer32
    MAX-ACCESS accessible-for-notify
    STATUS current
    DESCRIPTION
        "Parameter 'ip_id' in event IPHC.16"
    ::= { iphcEventObjects16 5 }

iphc16_pkt_counter OBJECT-TYPE
    SYNTAX Integer32
    MAX-ACCESS accessible-for-notify
    STATUS current
    DESCRIPTION
        "Parameter 'pkt_counter' in event IPHC.16"
    ::= { iphcEventObjects16 6 }

iphcEventObjects17 OBJECT-IDENTITY
    STATUS current
    DESCRIPTION
        "Event IPHC.17
        ."
    ::= { iphcEventsGroup 17 }

iphc17_interface OBJECT-TYPE
    SYNTAX DisplayString
    MAX-ACCESS accessible-for-notify
    STATUS current
    DESCRIPTION
        "Parameter 'interface' in event IPHC.17"
    ::= { iphcEventObjects17 1 }

iphc17_cid OBJECT-TYPE
    SYNTAX Integer32
    MAX-ACCESS accessible-for-notify
    STATUS current
    DESCRIPTION
        "Parameter 'cid' in event IPHC.17"
    ::= { iphcEventObjects17 2 }

iphcEventObjects18 OBJECT-IDENTITY
    STATUS current
    DESCRIPTION
        "Event IPHC.18
        ."
    ::= { iphcEventsGroup 18 }

iphc18_interface OBJECT-TYPE
    SYNTAX DisplayString
    MAX-ACCESS accessible-for-notify
    STATUS current
    DESCRIPTION
        "Parameter 'interface' in event IPHC.18"
    ::= { iphcEventObjects18 1 }

iphc18_cid OBJECT-TYPE
    SYNTAX Integer32
    MAX-ACCESS accessible-for-notify
    STATUS current
    DESCRIPTION
        "Parameter 'cid' in event IPHC.18"
    ::= { iphcEventObjects18 2 }

iphc18_generation OBJECT-TYPE
    SYNTAX Integer32
    MAX-ACCESS accessible-for-notify
    STATUS current
    DESCRIPTION
        "Parameter 'generation' in event IPHC.18"
    ::= { iphcEventObjects18 3 }

iphc18_current_generation OBJECT-TYPE
    SYNTAX Integer32
    MAX-ACCESS accessible-for-notify
    STATUS current
    DESCRIPTION
        "Parameter 'current_generation' in event IPHC.18"
    ::= { iphcEventObjects18 4 }

iphc18_flag_I OBJECT-TYPE
    SYNTAX DisplayString
    MAX-ACCESS accessible-for-notify
    STATUS current
    DESCRIPTION
        "Parameter 'flag_I' in event IPHC.18"
    ::= { iphcEventObjects18 5 }

iphc18_link_sequence OBJECT-TYPE
    SYNTAX Integer32
    MAX-ACCESS accessible-for-notify
    STATUS current
    DESCRIPTION
        "Parameter 'link_sequence' in event IPHC.18"
    ::= { iphcEventObjects18 6 }

iphc18_current_link_sequence OBJECT-TYPE
    SYNTAX Integer32
    MAX-ACCESS accessible-for-notify
    STATUS current
    DESCRIPTION
        "Parameter 'current_link_sequence' in event IPHC.18"
    ::= { iphcEventObjects18 7 }

iphc18_pkt_counter OBJECT-TYPE
    SYNTAX Integer32
    MAX-ACCESS accessible-for-notify
    STATUS current
    DESCRIPTION
        "Parameter 'pkt_counter' in event IPHC.18"
    ::= { iphcEventObjects18 8 }

iphcEventObjects19 OBJECT-IDENTITY
    STATUS current
    DESCRIPTION
        "Event IPHC.19
        ."
    ::= { iphcEventsGroup 19 }

iphc19_interface OBJECT-TYPE
    SYNTAX DisplayString
    MAX-ACCESS accessible-for-notify
    STATUS current
    DESCRIPTION
        "Parameter 'interface' in event IPHC.19"
    ::= { iphcEventObjects19 1 }

iphc19_checksum OBJECT-TYPE
    SYNTAX Integer32
    MAX-ACCESS accessible-for-notify
    STATUS current
    DESCRIPTION
        "Parameter 'checksum' in event IPHC.19"
    ::= { iphcEventObjects19 2 }

iphc19_expected_checksum OBJECT-TYPE
    SYNTAX Integer32
    MAX-ACCESS accessible-for-notify
    STATUS current
    DESCRIPTION
        "Parameter 'expected_checksum' in event IPHC.19"
    ::= { iphcEventObjects19 3 }

iphc19_cid OBJECT-TYPE
    SYNTAX Integer32
    MAX-ACCESS accessible-for-notify
    STATUS current
    DESCRIPTION
        "Parameter 'cid' in event IPHC.19"
    ::= { iphcEventObjects19 4 }

iphcEventObjects20 OBJECT-IDENTITY
    STATUS current
    DESCRIPTION
        "Event IPHC.20
        ."
    ::= { iphcEventsGroup 20 }

iphc20_interface OBJECT-TYPE
    SYNTAX DisplayString
    MAX-ACCESS accessible-for-notify
    STATUS current
    DESCRIPTION
        "Parameter 'interface' in event IPHC.20"
    ::= { iphcEventObjects20 1 }

iphc20_cid OBJECT-TYPE
    SYNTAX Integer32
    MAX-ACCESS accessible-for-notify
    STATUS current
    DESCRIPTION
        "Parameter 'cid' in event IPHC.20"
    ::= { iphcEventObjects20 2 }

iphc20_max_cid OBJECT-TYPE
    SYNTAX Integer32
    MAX-ACCESS accessible-for-notify
    STATUS current
    DESCRIPTION
        "Parameter 'max_cid' in event IPHC.20"
    ::= { iphcEventObjects20 3 }

iphcEventObjects21 OBJECT-IDENTITY
    STATUS current
    DESCRIPTION
        "Event IPHC.21
        ."
    ::= { iphcEventsGroup 21 }

iphc21_interface OBJECT-TYPE
    SYNTAX DisplayString
    MAX-ACCESS accessible-for-notify
    STATUS current
    DESCRIPTION
        "Parameter 'interface' in event IPHC.21"
    ::= { iphcEventObjects21 1 }

iphc21_cid OBJECT-TYPE
    SYNTAX Integer32
    MAX-ACCESS accessible-for-notify
    STATUS current
    DESCRIPTION
        "Parameter 'cid' in event IPHC.21"
    ::= { iphcEventObjects21 2 }

iphcEventObjects22 OBJECT-IDENTITY
    STATUS current
    DESCRIPTION
        "Event IPHC.22
        ."
    ::= { iphcEventsGroup 22 }

iphc22_interface OBJECT-TYPE
    SYNTAX DisplayString
    MAX-ACCESS accessible-for-notify
    STATUS current
    DESCRIPTION
        "Parameter 'interface' in event IPHC.22"
    ::= { iphcEventObjects22 1 }

iphc22_cid OBJECT-TYPE
    SYNTAX Integer32
    MAX-ACCESS accessible-for-notify
    STATUS current
    DESCRIPTION
        "Parameter 'cid' in event IPHC.22"
    ::= { iphcEventObjects22 2 }

iphc22_ip_id OBJECT-TYPE
    SYNTAX Integer32
    MAX-ACCESS accessible-for-notify
    STATUS current
    DESCRIPTION
        "Parameter 'ip_id' in event IPHC.22"
    ::= { iphcEventObjects22 3 }

iphc22_src_ipaddr OBJECT-TYPE
    SYNTAX IpAddress
    MAX-ACCESS accessible-for-notify
    STATUS current
    DESCRIPTION
        "Parameter 'src_ipaddr' in event IPHC.22"
    ::= { iphcEventObjects22 4 }

iphc22_src_port OBJECT-TYPE
    SYNTAX Integer32
    MAX-ACCESS accessible-for-notify
    STATUS current
    DESCRIPTION
        "Parameter 'src_port' in event IPHC.22"
    ::= { iphcEventObjects22 5 }

iphc22_dst_ipaddr OBJECT-TYPE
    SYNTAX IpAddress
    MAX-ACCESS accessible-for-notify
    STATUS current
    DESCRIPTION
        "Parameter 'dst_ipaddr' in event IPHC.22"
    ::= { iphcEventObjects22 6 }

iphc22_dst_port OBJECT-TYPE
    SYNTAX Integer32
    MAX-ACCESS accessible-for-notify
    STATUS current
    DESCRIPTION
        "Parameter 'dst_port' in event IPHC.22"
    ::= { iphcEventObjects22 7 }

iphc22_generation OBJECT-TYPE
    SYNTAX Integer32
    MAX-ACCESS accessible-for-notify
    STATUS current
    DESCRIPTION
        "Parameter 'generation' in event IPHC.22"
    ::= { iphcEventObjects22 8 }

iphc22_cksum OBJECT-TYPE
    SYNTAX Integer32
    MAX-ACCESS accessible-for-notify
    STATUS current
    DESCRIPTION
        "Parameter 'cksum' in event IPHC.22"
    ::= { iphcEventObjects22 9 }

iphc22_flag OBJECT-TYPE
    SYNTAX DisplayString
    MAX-ACCESS accessible-for-notify
    STATUS current
    DESCRIPTION
        "Parameter 'flag' in event IPHC.22"
    ::= { iphcEventObjects22 10 }

iphc22_link_sequence OBJECT-TYPE
    SYNTAX Integer32
    MAX-ACCESS accessible-for-notify
    STATUS current
    DESCRIPTION
        "Parameter 'link_sequence' in event IPHC.22"
    ::= { iphcEventObjects22 11 }

iphcEventObjects23 OBJECT-IDENTITY
    STATUS current
    DESCRIPTION
        "Event IPHC.23
        ."
    ::= { iphcEventsGroup 23 }

iphc23_interface OBJECT-TYPE
    SYNTAX DisplayString
    MAX-ACCESS accessible-for-notify
    STATUS current
    DESCRIPTION
        "Parameter 'interface' in event IPHC.23"
    ::= { iphcEventObjects23 1 }

iphc23_cid OBJECT-TYPE
    SYNTAX Integer32
    MAX-ACCESS accessible-for-notify
    STATUS current
    DESCRIPTION
        "Parameter 'cid' in event IPHC.23"
    ::= { iphcEventObjects23 2 }

iphc23_cause OBJECT-TYPE
    SYNTAX DisplayString
    MAX-ACCESS accessible-for-notify
    STATUS current
    DESCRIPTION
        "Parameter 'cause' in event IPHC.23"
    ::= { iphcEventObjects23 3 }

iphc23_pkt_counter OBJECT-TYPE
    SYNTAX Integer32
    MAX-ACCESS accessible-for-notify
    STATUS current
    DESCRIPTION
        "Parameter 'pkt_counter' in event IPHC.23"
    ::= { iphcEventObjects23 4 }

iphcEventObjects24 OBJECT-IDENTITY
    STATUS current
    DESCRIPTION
        "Event IPHC.24
        ."
    ::= { iphcEventsGroup 24 }

iphc24_interface OBJECT-TYPE
    SYNTAX DisplayString
    MAX-ACCESS accessible-for-notify
    STATUS current
    DESCRIPTION
        "Parameter 'interface' in event IPHC.24"
    ::= { iphcEventObjects24 1 }

iphc24_cid OBJECT-TYPE
    SYNTAX Integer32
    MAX-ACCESS accessible-for-notify
    STATUS current
    DESCRIPTION
        "Parameter 'cid' in event IPHC.24"
    ::= { iphcEventObjects24 2 }

iphc24_pkt_counter OBJECT-TYPE
    SYNTAX Integer32
    MAX-ACCESS accessible-for-notify
    STATUS current
    DESCRIPTION
        "Parameter 'pkt_counter' in event IPHC.24"
    ::= { iphcEventObjects24 3 }

iphcEventObjects25 OBJECT-IDENTITY
    STATUS current
    DESCRIPTION
        "Event IPHC.25
        ."
    ::= { iphcEventsGroup 25 }

iphc25_interface OBJECT-TYPE
    SYNTAX DisplayString
    MAX-ACCESS accessible-for-notify
    STATUS current
    DESCRIPTION
        "Parameter 'interface' in event IPHC.25"
    ::= { iphcEventObjects25 1 }

iphc25_cid OBJECT-TYPE
    SYNTAX Integer32
    MAX-ACCESS accessible-for-notify
    STATUS current
    DESCRIPTION
        "Parameter 'cid' in event IPHC.25"
    ::= { iphcEventObjects25 2 }

iphc25_ip_id OBJECT-TYPE
    SYNTAX Integer32
    MAX-ACCESS accessible-for-notify
    STATUS current
    DESCRIPTION
        "Parameter 'ip_id' in event IPHC.25"
    ::= { iphcEventObjects25 3 }

iphc25_src_ipaddr OBJECT-TYPE
    SYNTAX IpAddress
    MAX-ACCESS accessible-for-notify
    STATUS current
    DESCRIPTION
        "Parameter 'src_ipaddr' in event IPHC.25"
    ::= { iphcEventObjects25 4 }

iphc25_src_port OBJECT-TYPE
    SYNTAX Integer32
    MAX-ACCESS accessible-for-notify
    STATUS current
    DESCRIPTION
        "Parameter 'src_port' in event IPHC.25"
    ::= { iphcEventObjects25 5 }

iphc25_dst_ipaddr OBJECT-TYPE
    SYNTAX IpAddress
    MAX-ACCESS accessible-for-notify
    STATUS current
    DESCRIPTION
        "Parameter 'dst_ipaddr' in event IPHC.25"
    ::= { iphcEventObjects25 6 }

iphc25_dst_port OBJECT-TYPE
    SYNTAX Integer32
    MAX-ACCESS accessible-for-notify
    STATUS current
    DESCRIPTION
        "Parameter 'dst_port' in event IPHC.25"
    ::= { iphcEventObjects25 7 }

iphc25_cksum OBJECT-TYPE
    SYNTAX Integer32
    MAX-ACCESS accessible-for-notify
    STATUS current
    DESCRIPTION
        "Parameter 'cksum' in event IPHC.25"
    ::= { iphcEventObjects25 8 }

iphcEventObjects26 OBJECT-IDENTITY
    STATUS current
    DESCRIPTION
        "Event IPHC.26
        ."
    ::= { iphcEventsGroup 26 }

iphc26_interface OBJECT-TYPE
    SYNTAX DisplayString
    MAX-ACCESS accessible-for-notify
    STATUS current
    DESCRIPTION
        "Parameter 'interface' in event IPHC.26"
    ::= { iphcEventObjects26 1 }

iphc26_cid OBJECT-TYPE
    SYNTAX Integer32
    MAX-ACCESS accessible-for-notify
    STATUS current
    DESCRIPTION
        "Parameter 'cid' in event IPHC.26"
    ::= { iphcEventObjects26 2 }

iphc26_hlen OBJECT-TYPE
    SYNTAX Integer32
    MAX-ACCESS accessible-for-notify
    STATUS current
    DESCRIPTION
        "Parameter 'hlen' in event IPHC.26"
    ::= { iphcEventObjects26 3 }

iphc26_max_hlen OBJECT-TYPE
    SYNTAX Integer32
    MAX-ACCESS accessible-for-notify
    STATUS current
    DESCRIPTION
        "Parameter 'max_hlen' in event IPHC.26"
    ::= { iphcEventObjects26 4 }

iphcEventObjects27 OBJECT-IDENTITY
    STATUS current
    DESCRIPTION
        "Event IPHC.27
        ."
    ::= { iphcEventsGroup 27 }

iphc27_interface OBJECT-TYPE
    SYNTAX DisplayString
    MAX-ACCESS accessible-for-notify
    STATUS current
    DESCRIPTION
        "Parameter 'interface' in event IPHC.27"
    ::= { iphcEventObjects27 1 }

iphc27_cid OBJECT-TYPE
    SYNTAX Integer32
    MAX-ACCESS accessible-for-notify
    STATUS current
    DESCRIPTION
        "Parameter 'cid' in event IPHC.27"
    ::= { iphcEventObjects27 2 }

iphc27_generation OBJECT-TYPE
    SYNTAX Integer32
    MAX-ACCESS accessible-for-notify
    STATUS current
    DESCRIPTION
        "Parameter 'generation' in event IPHC.27"
    ::= { iphcEventObjects27 3 }

iphc27_expected_generation OBJECT-TYPE
    SYNTAX Integer32
    MAX-ACCESS accessible-for-notify
    STATUS current
    DESCRIPTION
        "Parameter 'expected_generation' in event IPHC.27"
    ::= { iphcEventObjects27 4 }

iphcEventObjects29 OBJECT-IDENTITY
    STATUS current
    DESCRIPTION
        "Event IPHC.29
        This message is generated when an packet has an invalid sequence.
        The received sequence, together with the correct sequence,
        are displayed."
    ::= { iphcEventsGroup 29 }

iphc29_interface OBJECT-TYPE
    SYNTAX DisplayString
    MAX-ACCESS accessible-for-notify
    STATUS current
    DESCRIPTION
        "Parameter 'interface' in event IPHC.29"
    ::= { iphcEventObjects29 1 }

iphc29_link_sequence OBJECT-TYPE
    SYNTAX Integer32
    MAX-ACCESS accessible-for-notify
    STATUS current
    DESCRIPTION
        "Parameter 'link_sequence' in event IPHC.29"
    ::= { iphcEventObjects29 2 }

iphc29_expected_link_sequence OBJECT-TYPE
    SYNTAX Integer32
    MAX-ACCESS accessible-for-notify
    STATUS current
    DESCRIPTION
        "Parameter 'expected_link_sequence' in event IPHC.29"
    ::= { iphcEventObjects29 3 }

iphc29_cid OBJECT-TYPE
    SYNTAX Integer32
    MAX-ACCESS accessible-for-notify
    STATUS current
    DESCRIPTION
        "Parameter 'cid' in event IPHC.29"
    ::= { iphcEventObjects29 4 }

iphcEventObjects30 OBJECT-IDENTITY
    STATUS current
    DESCRIPTION
        "Event IPHC.30
        ."
    ::= { iphcEventsGroup 30 }

iphc30_interface OBJECT-TYPE
    SYNTAX DisplayString
    MAX-ACCESS accessible-for-notify
    STATUS current
    DESCRIPTION
        "Parameter 'interface' in event IPHC.30"
    ::= { iphcEventObjects30 1 }

iphc30_cid OBJECT-TYPE
    SYNTAX Integer32
    MAX-ACCESS accessible-for-notify
    STATUS current
    DESCRIPTION
        "Parameter 'cid' in event IPHC.30"
    ::= { iphcEventObjects30 2 }

iphc30_ip_id OBJECT-TYPE
    SYNTAX Integer32
    MAX-ACCESS accessible-for-notify
    STATUS current
    DESCRIPTION
        "Parameter 'ip_id' in event IPHC.30"
    ::= { iphcEventObjects30 3 }

iphc30_src_ipaddr OBJECT-TYPE
    SYNTAX IpAddress
    MAX-ACCESS accessible-for-notify
    STATUS current
    DESCRIPTION
        "Parameter 'src_ipaddr' in event IPHC.30"
    ::= { iphcEventObjects30 4 }

iphc30_src_port OBJECT-TYPE
    SYNTAX Integer32
    MAX-ACCESS accessible-for-notify
    STATUS current
    DESCRIPTION
        "Parameter 'src_port' in event IPHC.30"
    ::= { iphcEventObjects30 5 }

iphc30_dst_ipaddr OBJECT-TYPE
    SYNTAX IpAddress
    MAX-ACCESS accessible-for-notify
    STATUS current
    DESCRIPTION
        "Parameter 'dst_ipaddr' in event IPHC.30"
    ::= { iphcEventObjects30 6 }

iphc30_dst_port OBJECT-TYPE
    SYNTAX Integer32
    MAX-ACCESS accessible-for-notify
    STATUS current
    DESCRIPTION
        "Parameter 'dst_port' in event IPHC.30"
    ::= { iphcEventObjects30 7 }

iphc30_generation OBJECT-TYPE
    SYNTAX Integer32
    MAX-ACCESS accessible-for-notify
    STATUS current
    DESCRIPTION
        "Parameter 'generation' in event IPHC.30"
    ::= { iphcEventObjects30 8 }

iphc30_cksum OBJECT-TYPE
    SYNTAX Integer32
    MAX-ACCESS accessible-for-notify
    STATUS current
    DESCRIPTION
        "Parameter 'cksum' in event IPHC.30"
    ::= { iphcEventObjects30 9 }

iphc30_flag OBJECT-TYPE
    SYNTAX DisplayString
    MAX-ACCESS accessible-for-notify
    STATUS current
    DESCRIPTION
        "Parameter 'flag' in event IPHC.30"
    ::= { iphcEventObjects30 10 }

iphc30_link_sequence OBJECT-TYPE
    SYNTAX Integer32
    MAX-ACCESS accessible-for-notify
    STATUS current
    DESCRIPTION
        "Parameter 'link_sequence' in event IPHC.30"
    ::= { iphcEventObjects30 11 }

iphcEventObjects31 OBJECT-IDENTITY
    STATUS current
    DESCRIPTION
        "Event IPHC.31
        ."
    ::= { iphcEventsGroup 31 }

iphc31_interface OBJECT-TYPE
    SYNTAX DisplayString
    MAX-ACCESS accessible-for-notify
    STATUS current
    DESCRIPTION
        "Parameter 'interface' in event IPHC.31"
    ::= { iphcEventObjects31 1 }

iphc31_cid OBJECT-TYPE
    SYNTAX Integer32
    MAX-ACCESS accessible-for-notify
    STATUS current
    DESCRIPTION
        "Parameter 'cid' in event IPHC.31"
    ::= { iphcEventObjects31 2 }

iphc31_chksum OBJECT-TYPE
    SYNTAX Integer32
    MAX-ACCESS accessible-for-notify
    STATUS current
    DESCRIPTION
        "Parameter 'chksum' in event IPHC.31"
    ::= { iphcEventObjects31 3 }

iphc31_chksumexp OBJECT-TYPE
    SYNTAX Integer32
    MAX-ACCESS accessible-for-notify
    STATUS current
    DESCRIPTION
        "Parameter 'chksumexp' in event IPHC.31"
    ::= { iphcEventObjects31 4 }

iphcEventObjects32 OBJECT-IDENTITY
    STATUS current
    DESCRIPTION
        "Event IPHC.32
        ."
    ::= { iphcEventsGroup 32 }

iphc32_interface OBJECT-TYPE
    SYNTAX DisplayString
    MAX-ACCESS accessible-for-notify
    STATUS current
    DESCRIPTION
        "Parameter 'interface' in event IPHC.32"
    ::= { iphcEventObjects32 1 }

iphc32_cid OBJECT-TYPE
    SYNTAX Integer32
    MAX-ACCESS accessible-for-notify
    STATUS current
    DESCRIPTION
        "Parameter 'cid' in event IPHC.32"
    ::= { iphcEventObjects32 2 }

iphc32_pkt_counter OBJECT-TYPE
    SYNTAX Integer32
    MAX-ACCESS accessible-for-notify
    STATUS current
    DESCRIPTION
        "Parameter 'pkt_counter' in event IPHC.32"
    ::= { iphcEventObjects32 3 }

iphcEventObjects33 OBJECT-IDENTITY
    STATUS current
    DESCRIPTION
        "Event IPHC.33
        ."
    ::= { iphcEventsGroup 33 }

iphc33_interface OBJECT-TYPE
    SYNTAX DisplayString
    MAX-ACCESS accessible-for-notify
    STATUS current
    DESCRIPTION
        "Parameter 'interface' in event IPHC.33"
    ::= { iphcEventObjects33 1 }

iphc33_cid OBJECT-TYPE
    SYNTAX Integer32
    MAX-ACCESS accessible-for-notify
    STATUS current
    DESCRIPTION
        "Parameter 'cid' in event IPHC.33"
    ::= { iphcEventObjects33 2 }

iphc33_pkt_counter OBJECT-TYPE
    SYNTAX Integer32
    MAX-ACCESS accessible-for-notify
    STATUS current
    DESCRIPTION
        "Parameter 'pkt_counter' in event IPHC.33"
    ::= { iphcEventObjects33 3 }

iphcEventObjects34 OBJECT-IDENTITY
    STATUS current
    DESCRIPTION
        "Event IPHC.34
        ."
    ::= { iphcEventsGroup 34 }

iphc34_interface OBJECT-TYPE
    SYNTAX DisplayString
    MAX-ACCESS accessible-for-notify
    STATUS current
    DESCRIPTION
        "Parameter 'interface' in event IPHC.34"
    ::= { iphcEventObjects34 1 }

iphc34_cid OBJECT-TYPE
    SYNTAX Integer32
    MAX-ACCESS accessible-for-notify
    STATUS current
    DESCRIPTION
        "Parameter 'cid' in event IPHC.34"
    ::= { iphcEventObjects34 2 }

iphc34_pkt_counter OBJECT-TYPE
    SYNTAX Integer32
    MAX-ACCESS accessible-for-notify
    STATUS current
    DESCRIPTION
        "Parameter 'pkt_counter' in event IPHC.34"
    ::= { iphcEventObjects34 3 }

iphcEventObjects35 OBJECT-IDENTITY
    STATUS current
    DESCRIPTION
        "Event IPHC.35
        ."
    ::= { iphcEventsGroup 35 }

iphc35_interface OBJECT-TYPE
    SYNTAX DisplayString
    MAX-ACCESS accessible-for-notify
    STATUS current
    DESCRIPTION
        "Parameter 'interface' in event IPHC.35"
    ::= { iphcEventObjects35 1 }

iphc35_rx_tx OBJECT-TYPE
    SYNTAX DisplayString
    MAX-ACCESS accessible-for-notify
    STATUS current
    DESCRIPTION
        "Parameter 'rx/tx' in event IPHC.35"
    ::= { iphcEventObjects35 2 }

iphc35_ietf_compat OBJECT-TYPE
    SYNTAX DisplayString
    MAX-ACCESS accessible-for-notify
    STATUS current
    DESCRIPTION
        "Parameter 'ietf/compat' in event IPHC.35"
    ::= { iphcEventObjects35 3 }

iphc35_tcp_space OBJECT-TYPE
    SYNTAX Integer32
    MAX-ACCESS accessible-for-notify
    STATUS current
    DESCRIPTION
        "Parameter 'tcp_space' in event IPHC.35"
    ::= { iphcEventObjects35 4 }

iphc35_nontcp_space OBJECT-TYPE
    SYNTAX Integer32
    MAX-ACCESS accessible-for-notify
    STATUS current
    DESCRIPTION
        "Parameter 'nontcp_space' in event IPHC.35"
    ::= { iphcEventObjects35 5 }

iphc35_maxheader OBJECT-TYPE
    SYNTAX Integer32
    MAX-ACCESS accessible-for-notify
    STATUS current
    DESCRIPTION
        "Parameter 'maxheader' in event IPHC.35"
    ::= { iphcEventObjects35 6 }

iphc35_maxperiod OBJECT-TYPE
    SYNTAX Integer32
    MAX-ACCESS accessible-for-notify
    STATUS current
    DESCRIPTION
        "Parameter 'maxperiod' in event IPHC.35"
    ::= { iphcEventObjects35 7 }

iphc35_maxtime OBJECT-TYPE
    SYNTAX Integer32
    MAX-ACCESS accessible-for-notify
    STATUS current
    DESCRIPTION
        "Parameter 'maxtime' in event IPHC.35"
    ::= { iphcEventObjects35 8 }

iphcEventObjects36 OBJECT-IDENTITY
    STATUS current
    DESCRIPTION
        "Event IPHC.36
        ."
    ::= { iphcEventsGroup 36 }

iphc36_interface OBJECT-TYPE
    SYNTAX DisplayString
    MAX-ACCESS accessible-for-notify
    STATUS current
    DESCRIPTION
        "Parameter 'interface' in event IPHC.36"
    ::= { iphcEventObjects36 1 }

iphcEventObjects37 OBJECT-IDENTITY
    STATUS current
    DESCRIPTION
        "Event IPHC.37
        ."
    ::= { iphcEventsGroup 37 }

iphc37_interface OBJECT-TYPE
    SYNTAX DisplayString
    MAX-ACCESS accessible-for-notify
    STATUS current
    DESCRIPTION
        "Parameter 'interface' in event IPHC.37"
    ::= { iphcEventObjects37 1 }

iphc37_protocol OBJECT-TYPE
    SYNTAX DisplayString
    MAX-ACCESS accessible-for-notify
    STATUS current
    DESCRIPTION
        "Parameter 'protocol' in event IPHC.37"
    ::= { iphcEventObjects37 2 }

iphc37_cid OBJECT-TYPE
    SYNTAX Integer32
    MAX-ACCESS accessible-for-notify
    STATUS current
    DESCRIPTION
        "Parameter 'cid' in event IPHC.37"
    ::= { iphcEventObjects37 3 }

iphcEventObjects38 OBJECT-IDENTITY
    STATUS current
    DESCRIPTION
        "Event IPHC.38
        ."
    ::= { iphcEventsGroup 38 }

iphc38_interface OBJECT-TYPE
    SYNTAX DisplayString
    MAX-ACCESS accessible-for-notify
    STATUS current
    DESCRIPTION
        "Parameter 'interface' in event IPHC.38"
    ::= { iphcEventObjects38 1 }

iphc38_cid OBJECT-TYPE
    SYNTAX Integer32
    MAX-ACCESS accessible-for-notify
    STATUS current
    DESCRIPTION
        "Parameter 'cid' in event IPHC.38"
    ::= { iphcEventObjects38 2 }

iphc38_ip_id OBJECT-TYPE
    SYNTAX Integer32
    MAX-ACCESS accessible-for-notify
    STATUS current
    DESCRIPTION
        "Parameter 'ip_id' in event IPHC.38"
    ::= { iphcEventObjects38 3 }

iphc38_src_ipaddr OBJECT-TYPE
    SYNTAX IpAddress
    MAX-ACCESS accessible-for-notify
    STATUS current
    DESCRIPTION
        "Parameter 'src_ipaddr' in event IPHC.38"
    ::= { iphcEventObjects38 4 }

iphc38_src_port OBJECT-TYPE
    SYNTAX Integer32
    MAX-ACCESS accessible-for-notify
    STATUS current
    DESCRIPTION
        "Parameter 'src_port' in event IPHC.38"
    ::= { iphcEventObjects38 5 }

iphc38_dst_ipaddr OBJECT-TYPE
    SYNTAX IpAddress
    MAX-ACCESS accessible-for-notify
    STATUS current
    DESCRIPTION
        "Parameter 'dst_ipaddr' in event IPHC.38"
    ::= { iphcEventObjects38 6 }

iphc38_dst_port OBJECT-TYPE
    SYNTAX Integer32
    MAX-ACCESS accessible-for-notify
    STATUS current
    DESCRIPTION
        "Parameter 'dst_port' in event IPHC.38"
    ::= { iphcEventObjects38 7 }

iphc38_cksum OBJECT-TYPE
    SYNTAX Integer32
    MAX-ACCESS accessible-for-notify
    STATUS current
    DESCRIPTION
        "Parameter 'cksum' in event IPHC.38"
    ::= { iphcEventObjects38 8 }

iphcEventObjects39 OBJECT-IDENTITY
    STATUS current
    DESCRIPTION
        "Event IPHC.39
        ."
    ::= { iphcEventsGroup 39 }

iphc39_interface OBJECT-TYPE
    SYNTAX DisplayString
    MAX-ACCESS accessible-for-notify
    STATUS current
    DESCRIPTION
        "Parameter 'interface' in event IPHC.39"
    ::= { iphcEventObjects39 1 }

iphc39_cid OBJECT-TYPE
    SYNTAX Integer32
    MAX-ACCESS accessible-for-notify
    STATUS current
    DESCRIPTION
        "Parameter 'cid' in event IPHC.39"
    ::= { iphcEventObjects39 2 }

iphc39_chksum OBJECT-TYPE
    SYNTAX Integer32
    MAX-ACCESS accessible-for-notify
    STATUS current
    DESCRIPTION
        "Parameter 'chksum' in event IPHC.39"
    ::= { iphcEventObjects39 3 }

iphc39_chksumexp OBJECT-TYPE
    SYNTAX Integer32
    MAX-ACCESS accessible-for-notify
    STATUS current
    DESCRIPTION
        "Parameter 'chksumexp' in event IPHC.39"
    ::= { iphcEventObjects39 4 }

iphcEventObjects40 OBJECT-IDENTITY
    STATUS current
    DESCRIPTION
        "Event IPHC.40
        ."
    ::= { iphcEventsGroup 40 }

iphc40_interface OBJECT-TYPE
    SYNTAX DisplayString
    MAX-ACCESS accessible-for-notify
    STATUS current
    DESCRIPTION
        "Parameter 'interface' in event IPHC.40"
    ::= { iphcEventObjects40 1 }

iphc40_cid OBJECT-TYPE
    SYNTAX Integer32
    MAX-ACCESS accessible-for-notify
    STATUS current
    DESCRIPTION
        "Parameter 'cid' in event IPHC.40"
    ::= { iphcEventObjects40 2 }

iphc40_chksum OBJECT-TYPE
    SYNTAX Integer32
    MAX-ACCESS accessible-for-notify
    STATUS current
    DESCRIPTION
        "Parameter 'chksum' in event IPHC.40"
    ::= { iphcEventObjects40 3 }

iphc40_chksumexp OBJECT-TYPE
    SYNTAX Integer32
    MAX-ACCESS accessible-for-notify
    STATUS current
    DESCRIPTION
        "Parameter 'chksumexp' in event IPHC.40"
    ::= { iphcEventObjects40 4 }

iphcEventObjects41 OBJECT-IDENTITY
    STATUS current
    DESCRIPTION
        "Event IPHC.41
        ."
    ::= { iphcEventsGroup 41 }

iphc41_interface OBJECT-TYPE
    SYNTAX DisplayString
    MAX-ACCESS accessible-for-notify
    STATUS current
    DESCRIPTION
        "Parameter 'interface' in event IPHC.41"
    ::= { iphcEventObjects41 1 }

iphc41_cid OBJECT-TYPE
    SYNTAX Integer32
    MAX-ACCESS accessible-for-notify
    STATUS current
    DESCRIPTION
        "Parameter 'cid' in event IPHC.41"
    ::= { iphcEventObjects41 2 }

iphc41_chksum OBJECT-TYPE
    SYNTAX Integer32
    MAX-ACCESS accessible-for-notify
    STATUS current
    DESCRIPTION
        "Parameter 'chksum' in event IPHC.41"
    ::= { iphcEventObjects41 3 }

iphc41_chksumexp OBJECT-TYPE
    SYNTAX Integer32
    MAX-ACCESS accessible-for-notify
    STATUS current
    DESCRIPTION
        "Parameter 'chksumexp' in event IPHC.41"
    ::= { iphcEventObjects41 4 }

iphcEventObjects42 OBJECT-IDENTITY
    STATUS current
    DESCRIPTION
        "Event IPHC.42
        ."
    ::= { iphcEventsGroup 42 }

iphc42_interface OBJECT-TYPE
    SYNTAX DisplayString
    MAX-ACCESS accessible-for-notify
    STATUS current
    DESCRIPTION
        "Parameter 'interface' in event IPHC.42"
    ::= { iphcEventObjects42 1 }

iphc42_cause OBJECT-TYPE
    SYNTAX DisplayString
    MAX-ACCESS accessible-for-notify
    STATUS current
    DESCRIPTION
        "Parameter 'cause' in event IPHC.42"
    ::= { iphcEventObjects42 2 }

iphcEventObjects43 OBJECT-IDENTITY
    STATUS current
    DESCRIPTION
        "Event IPHC.43
        ."
    ::= { iphcEventsGroup 43 }

iphc43_interface OBJECT-TYPE
    SYNTAX DisplayString
    MAX-ACCESS accessible-for-notify
    STATUS current
    DESCRIPTION
        "Parameter 'interface' in event IPHC.43"
    ::= { iphcEventObjects43 1 }

iphc43_cid OBJECT-TYPE
    SYNTAX Integer32
    MAX-ACCESS accessible-for-notify
    STATUS current
    DESCRIPTION
        "Parameter 'cid' in event IPHC.43"
    ::= { iphcEventObjects43 2 }

iphc43_pps OBJECT-TYPE
    SYNTAX Integer32
    MAX-ACCESS accessible-for-notify
    STATUS current
    DESCRIPTION
        "Parameter 'pps' in event IPHC.43"
    ::= { iphcEventObjects43 3 }

iphcEventObjects44 OBJECT-IDENTITY
    STATUS current
    DESCRIPTION
        "Event IPHC.44
        ."
    ::= { iphcEventsGroup 44 }

iphc44_interface OBJECT-TYPE
    SYNTAX DisplayString
    MAX-ACCESS accessible-for-notify
    STATUS current
    DESCRIPTION
        "Parameter 'interface' in event IPHC.44"
    ::= { iphcEventObjects44 1 }

iphc44_cid OBJECT-TYPE
    SYNTAX Integer32
    MAX-ACCESS accessible-for-notify
    STATUS current
    DESCRIPTION
        "Parameter 'cid' in event IPHC.44"
    ::= { iphcEventObjects44 2 }

iphc44_pps OBJECT-TYPE
    SYNTAX Integer32
    MAX-ACCESS accessible-for-notify
    STATUS current
    DESCRIPTION
        "Parameter 'pps' in event IPHC.44"
    ::= { iphcEventObjects44 3 }

iphcEventObjects45 OBJECT-IDENTITY
    STATUS current
    DESCRIPTION
        "Event IPHC.45
        ."
    ::= { iphcEventsGroup 45 }

iphc45_interface OBJECT-TYPE
    SYNTAX DisplayString
    MAX-ACCESS accessible-for-notify
    STATUS current
    DESCRIPTION
        "Parameter 'interface' in event IPHC.45"
    ::= { iphcEventObjects45 1 }

iphc45_cause OBJECT-TYPE
    SYNTAX DisplayString
    MAX-ACCESS accessible-for-notify
    STATUS current
    DESCRIPTION
        "Parameter 'cause' in event IPHC.45"
    ::= { iphcEventObjects45 2 }

iphcEventObjects46 OBJECT-IDENTITY
    STATUS current
    DESCRIPTION
        "Event IPHC.46
        ."
    ::= { iphcEventsGroup 46 }

iphc46_interface OBJECT-TYPE
    SYNTAX DisplayString
    MAX-ACCESS accessible-for-notify
    STATUS current
    DESCRIPTION
        "Parameter 'interface' in event IPHC.46"
    ::= { iphcEventObjects46 1 }

iphc46_cid OBJECT-TYPE
    SYNTAX Integer32
    MAX-ACCESS accessible-for-notify
    STATUS current
    DESCRIPTION
        "Parameter 'cid' in event IPHC.46"
    ::= { iphcEventObjects46 2 }

iphc46_link_sequence OBJECT-TYPE
    SYNTAX Integer32
    MAX-ACCESS accessible-for-notify
    STATUS current
    DESCRIPTION
        "Parameter 'link_sequence' in event IPHC.46"
    ::= { iphcEventObjects46 3 }


iphcNotification1 NOTIFICATION-TYPE
    OBJECTS { 
              iphc1_interface, 
              iphc1_cid,
              iphc1_cause,
              iphc1_pkt_counter 
            }
    STATUS current
    DESCRIPTION
        "Notification of Event IPHC.1

        Message: '[$1] Encoded FULL_HEADER cid $2, prot NON_TCP, Cause: $3,#$4'

        Parameters list:
              $1: iphc1_interface
              $2: iphc1_cid
              $3: iphc1_cause
              $4: iphc1_pkt_counter

        ."
    ::= { iphcNotificationsPrefix 1 }

iphcNotification2 NOTIFICATION-TYPE
    OBJECTS { 
              iphc2_interface, 
              iphc2_cid,
              iphc2_pkt_counter 
            }
    STATUS current
    DESCRIPTION
        "Notification of Event IPHC.2

        Message: '[$1] Decoded FULL_HEADER cid $2, prot NON_TCP, #$3'

        Parameters list:
              $1: iphc2_interface
              $2: iphc2_cid
              $3: iphc2_pkt_counter

        ."
    ::= { iphcNotificationsPrefix 2 }

iphcNotification3 NOTIFICATION-TYPE
    OBJECTS { 
              iphc3_interface, 
              iphc3_cid,
              iphc3_generation,
              iphc3_flag_D,
              iphc3_link_sequence,
              iphc3_ip_id,
              iphc3_pkt_counter 
            }
    STATUS current
    DESCRIPTION
        "Notification of Event IPHC.3

        Message: '[$1] Encoded COMPRESS_NON_TCP cid $2, generation $3, ($4), link_seq 0x$5, ip_id 0x$6,#$7'

        Parameters list:
              $1: iphc3_interface
              $2: iphc3_cid
              $3: iphc3_generation
              $4: iphc3_flag_D
              $5: iphc3_link_sequence
              $6: iphc3_ip_id
              $7: iphc3_pkt_counter

        ."
    ::= { iphcNotificationsPrefix 3 }

iphcNotification4 NOTIFICATION-TYPE
    OBJECTS { 
              iphc4_interface, 
              iphc4_cid,
              iphc4_generation,
              iphc4_flag_D,
              iphc4_link_sequence,
              iphc4_ip_id,
              iphc4_pkt_counter 
            }
    STATUS current
    DESCRIPTION
        "Notification of Event IPHC.4

        Message: '[$1] Decoded COMPRESS_NON_TCP cid $2, generation $3, ($4), link_seq 0x$5, ip_id 0x$6,#$7'

        Parameters list:
              $1: iphc4_interface
              $2: iphc4_cid
              $3: iphc4_generation
              $4: iphc4_flag_D
              $5: iphc4_link_sequence
              $6: iphc4_ip_id
              $7: iphc4_pkt_counter

        ."
    ::= { iphcNotificationsPrefix 4 }

iphcNotification5 NOTIFICATION-TYPE
    OBJECTS { 
              iphc5_interface, 
              iphc5_cid,
              iphc5_flags,
              iphc5_sequence_number,
              iphc5_ack_number,
              iphc5_window_size,
              iphc5_checksum,
              iphc5_ip_id,
              iphc5_pkt_counter 
            }
    STATUS current
    DESCRIPTION
        "Notification of Event IPHC.5

        Message: '[$1] Encoded COMP_TCP cid $2 ($3) SEQ=$4 ACK=$5 W=$6 CHK=0x$7 ID=0x$8, #$9'

        Parameters list:
              $1: iphc5_interface
              $2: iphc5_cid
              $3: iphc5_flags
              $4: iphc5_sequence_number
              $5: iphc5_ack_number
              $6: iphc5_window_size
              $7: iphc5_checksum
              $8: iphc5_ip_id
              $9: iphc5_pkt_counter

        ."
    ::= { iphcNotificationsPrefix 5 }

iphcNotification6 NOTIFICATION-TYPE
    OBJECTS { 
              iphc6_interface, 
              iphc6_cid,
              iphc6_flags,
              iphc6_sequence_number,
              iphc6_ack_number,
              iphc6_window_size,
              iphc6_checksum,
              iphc6_ip_id,
              iphc6_pkt_counter 
            }
    STATUS current
    DESCRIPTION
        "Notification of Event IPHC.6

        Message: '[$1] Decoded COMP_TCP cid $2 ($3) SEQ=$4 ACK=$5 W=$6 CHK=0x$7 ID=0x$8, #$9'

        Parameters list:
              $1: iphc6_interface
              $2: iphc6_cid
              $3: iphc6_flags
              $4: iphc6_sequence_number
              $5: iphc6_ack_number
              $6: iphc6_window_size
              $7: iphc6_checksum
              $8: iphc6_ip_id
              $9: iphc6_pkt_counter

        ."
    ::= { iphcNotificationsPrefix 6 }

iphcNotification7 NOTIFICATION-TYPE
    OBJECTS { 
              iphc7_interface, 
              iphc7_cid 
            }
    STATUS current
    DESCRIPTION
        "Notification of Event IPHC.7

        Message: '[$1] Encoded COMP_TCP_NO_DELTA cid $2'

        Parameters list:
              $1: iphc7_interface
              $2: iphc7_cid

        ."
    ::= { iphcNotificationsPrefix 7 }

iphcNotification8 NOTIFICATION-TYPE
    OBJECTS { 
              iphc8_interface, 
              iphc8_cid 
            }
    STATUS current
    DESCRIPTION
        "Notification of Event IPHC.8

        Message: '[$1] Decoded COMP_TCP_NO_DELTA cid $2'

        Parameters list:
              $1: iphc8_interface
              $2: iphc8_cid

        ."
    ::= { iphcNotificationsPrefix 8 }

iphcNotification9 NOTIFICATION-TYPE
    OBJECTS { 
              iphc9_interface, 
              iphc9_cid,
              iphc9_flags,
              iphc9_link_sequence,
              iphc9_ip_id,
              iphc9_pkt_counter 
            }
    STATUS current
    DESCRIPTION
        "Notification of Event IPHC.9

        Message: '[$1] Encoded COMP_RTP8 cid $2 ($3), link_seq 0x$4, ip_id 0x$5, #$6'

        Parameters list:
              $1: iphc9_interface
              $2: iphc9_cid
              $3: iphc9_flags
              $4: iphc9_link_sequence
              $5: iphc9_ip_id
              $6: iphc9_pkt_counter

        ."
    ::= { iphcNotificationsPrefix 9 }

iphcNotification10 NOTIFICATION-TYPE
    OBJECTS { 
              iphc10_interface, 
              iphc10_cid,
              iphc10_flags,
              iphc10_link_sequence,
              iphc10_ip_id,
              iphc10_pkt_counter 
            }
    STATUS current
    DESCRIPTION
        "Notification of Event IPHC.10

        Message: '[$1] Decoded COMP_RTP8 cid $2 ($3), link_seq 0x$4, ip_id 0x$5, #$6'

        Parameters list:
              $1: iphc10_interface
              $2: iphc10_cid
              $3: iphc10_flags
              $4: iphc10_link_sequence
              $5: iphc10_ip_id
              $6: iphc10_pkt_counter

        ."
    ::= { iphcNotificationsPrefix 10 }

iphcNotification11 NOTIFICATION-TYPE
    OBJECTS { 
              iphc11_interface, 
              iphc11_cid,
              iphc11_flags,
              iphc11_link_sequence,
              iphc11_pkt_counter 
            }
    STATUS current
    DESCRIPTION
        "Notification of Event IPHC.11

        Message: '[$1] Encoded COMP_RTP16 cid $2 ($3), link_seq 0x$4, #$5'

        Parameters list:
              $1: iphc11_interface
              $2: iphc11_cid
              $3: iphc11_flags
              $4: iphc11_link_sequence
              $5: iphc11_pkt_counter

        ."
    ::= { iphcNotificationsPrefix 11 }

iphcNotification12 NOTIFICATION-TYPE
    OBJECTS { 
              iphc12_interface, 
              iphc12_cid,
              iphc12_flags,
              iphc12_link_sequence,
              iphc12_ip_id,
              iphc12_pkt_counter 
            }
    STATUS current
    DESCRIPTION
        "Notification of Event IPHC.12

        Message: '[$1] Decoded COMP_RTP16 cid $2 ($3), link_seq 0x$4, ip_id 0x$5, #$6'

        Parameters list:
              $1: iphc12_interface
              $2: iphc12_cid
              $3: iphc12_flags
              $4: iphc12_link_sequence
              $5: iphc12_ip_id
              $6: iphc12_pkt_counter

        ."
    ::= { iphcNotificationsPrefix 12 }

iphcNotification13 NOTIFICATION-TYPE
    OBJECTS { 
              iphc13_interface, 
              iphc13_cid 
            }
    STATUS current
    DESCRIPTION
        "Notification of Event IPHC.13

        Message: '[$1] Encoded COMP_UDP8 cid $2'

        Parameters list:
              $1: iphc13_interface
              $2: iphc13_cid

        ."
    ::= { iphcNotificationsPrefix 13 }

iphcNotification14 NOTIFICATION-TYPE
    OBJECTS { 
              iphc14_interface, 
              iphc14_cid,
              iphc14_flags,
              iphc14_link_sequence,
              iphc14_ip_id,
              iphc14_pkt_counter 
            }
    STATUS current
    DESCRIPTION
        "Notification of Event IPHC.14

        Message: '[$1] Decoded COMP_UDP8 cid $2 ($3), link_seq 0x$4, ip_id 0x$5, #$6'

        Parameters list:
              $1: iphc14_interface
              $2: iphc14_cid
              $3: iphc14_flags
              $4: iphc14_link_sequence
              $5: iphc14_ip_id
              $6: iphc14_pkt_counter

        ."
    ::= { iphcNotificationsPrefix 14 }

iphcNotification15 NOTIFICATION-TYPE
    OBJECTS { 
              iphc15_interface, 
              iphc15_cid 
            }
    STATUS current
    DESCRIPTION
        "Notification of Event IPHC.15

        Message: '[$1] Encoded COMP_UDP16 cid $2'

        Parameters list:
              $1: iphc15_interface
              $2: iphc15_cid

        ."
    ::= { iphcNotificationsPrefix 15 }

iphcNotification16 NOTIFICATION-TYPE
    OBJECTS { 
              iphc16_interface, 
              iphc16_cid,
              iphc16_flags,
              iphc16_link_sequence,
              iphc16_ip_id,
              iphc16_pkt_counter 
            }
    STATUS current
    DESCRIPTION
        "Notification of Event IPHC.16

        Message: '[$1] Decoded COMP_UDP16 cid $2 ($3), link_seq 0x$4, ip_id 0x$5, #$6'

        Parameters list:
              $1: iphc16_interface
              $2: iphc16_cid
              $3: iphc16_flags
              $4: iphc16_link_sequence
              $5: iphc16_ip_id
              $6: iphc16_pkt_counter

        ."
    ::= { iphcNotificationsPrefix 16 }

iphcNotification17 NOTIFICATION-TYPE
    OBJECTS { 
              iphc17_interface, 
              iphc17_cid 
            }
    STATUS current
    DESCRIPTION
        "Notification of Event IPHC.17

        Message: '[$1] Decoded COMP_RTP with CSRC list changes not allowed, cid $2'

        Parameters list:
              $1: iphc17_interface
              $2: iphc17_cid

        ."
    ::= { iphcNotificationsPrefix 17 }

iphcNotification18 NOTIFICATION-TYPE
    OBJECTS { 
              iphc18_interface, 
              iphc18_cid,
              iphc18_generation,
              iphc18_current_generation,
              iphc18_flag_I,
              iphc18_link_sequence,
              iphc18_current_link_sequence,
              iphc18_pkt_counter 
            }
    STATUS current
    DESCRIPTION
        "Notification of Event IPHC.18

        Message: '[$1] Decoded CONTEXT_STATE prot NON_TCP cid $2, generation $3 (curr $4), ($5), lnk_seq $6 (curr $7), #$8'

        Parameters list:
              $1: iphc18_interface
              $2: iphc18_cid
              $3: iphc18_generation
              $4: iphc18_current_generation
              $5: iphc18_flag_I
              $6: iphc18_link_sequence
              $7: iphc18_current_link_sequence
              $8: iphc18_pkt_counter

        ."
    ::= { iphcNotificationsPrefix 18 }

iphcNotification19 NOTIFICATION-TYPE
    OBJECTS { 
              iphc19_interface, 
              iphc19_checksum,
              iphc19_expected_checksum,
              iphc19_cid 
            }
    STATUS current
    DESCRIPTION
        "Notification of Event IPHC.19

        Message: '[$1] Decoded bad header cksum 0x$2 (exp 0x$3), cid $4'

        Parameters list:
              $1: iphc19_interface
              $2: iphc19_checksum
              $3: iphc19_expected_checksum
              $4: iphc19_cid

        ."
    ::= { iphcNotificationsPrefix 19 }

iphcNotification20 NOTIFICATION-TYPE
    OBJECTS { 
              iphc20_interface, 
              iphc20_cid,
              iphc20_max_cid 
            }
    STATUS current
    DESCRIPTION
        "Notification of Event IPHC.20

        Message: '[$1] Received context id $2 greated than maximum configured $3'

        Parameters list:
              $1: iphc20_interface
              $2: iphc20_cid
              $3: iphc20_max_cid

        ."
    ::= { iphcNotificationsPrefix 20 }

iphcNotification21 NOTIFICATION-TYPE
    OBJECTS { 
              iphc21_interface, 
              iphc21_cid 
            }
    STATUS current
    DESCRIPTION
        "Notification of Event IPHC.21

        Message: '[$1] Received TCP invalid context id $2'

        Parameters list:
              $1: iphc21_interface
              $2: iphc21_cid

        ."
    ::= { iphcNotificationsPrefix 21 }

iphcNotification22 NOTIFICATION-TYPE
    OBJECTS { 
              iphc22_interface, 
              iphc22_cid,
              iphc22_ip_id,
              iphc22_src_ipaddr,
              iphc22_src_port,
              iphc22_dst_ipaddr,
              iphc22_dst_port,
              iphc22_generation,
              iphc22_cksum,
              iphc22_flag,
              iphc22_link_sequence 
            }
    STATUS current
    DESCRIPTION
        "Notification of Event IPHC.22

        Message: '[$1] Decoded cid $2, prot NON_TCP, ip_id 0x$3, $4/$5 -> $6/$7, generation $8, cksum 0x$9, ($10) link_seq 0x$11'

        Parameters list:
              $1: iphc22_interface
              $2: iphc22_cid
              $3: iphc22_ip_id
              $4: iphc22_src_ipaddr
              $5: iphc22_src_port
              $6: iphc22_dst_ipaddr
              $7: iphc22_dst_port
              $8: iphc22_generation
              $9: iphc22_cksum
              $10: iphc22_flag
              $11: iphc22_link_sequence

        ."
    ::= { iphcNotificationsPrefix 22 }

iphcNotification23 NOTIFICATION-TYPE
    OBJECTS { 
              iphc23_interface, 
              iphc23_cid,
              iphc23_cause,
              iphc23_pkt_counter 
            }
    STATUS current
    DESCRIPTION
        "Notification of Event IPHC.23

        Message: '[$1] Encoded FULL_HEADER cid $2, prot TCP, Cause: $3, #$4'

        Parameters list:
              $1: iphc23_interface
              $2: iphc23_cid
              $3: iphc23_cause
              $4: iphc23_pkt_counter

        ."
    ::= { iphcNotificationsPrefix 23 }

iphcNotification24 NOTIFICATION-TYPE
    OBJECTS { 
              iphc24_interface, 
              iphc24_cid,
              iphc24_pkt_counter 
            }
    STATUS current
    DESCRIPTION
        "Notification of Event IPHC.24

        Message: '[$1] Decoded FULL_HEADER cid $2, prot TCP, #$3'

        Parameters list:
              $1: iphc24_interface
              $2: iphc24_cid
              $3: iphc24_pkt_counter

        ."
    ::= { iphcNotificationsPrefix 24 }

iphcNotification25 NOTIFICATION-TYPE
    OBJECTS { 
              iphc25_interface, 
              iphc25_cid,
              iphc25_ip_id,
              iphc25_src_ipaddr,
              iphc25_src_port,
              iphc25_dst_ipaddr,
              iphc25_dst_port,
              iphc25_cksum 
            }
    STATUS current
    DESCRIPTION
        "Notification of Event IPHC.25

        Message: '[$1] Decoded cid $2, prot TCP, id 0x$3,  $4/$5 -> $6/$7, cksum 0x$8'

        Parameters list:
              $1: iphc25_interface
              $2: iphc25_cid
              $3: iphc25_ip_id
              $4: iphc25_src_ipaddr
              $5: iphc25_src_port
              $6: iphc25_dst_ipaddr
              $7: iphc25_dst_port
              $8: iphc25_cksum

        ."
    ::= { iphcNotificationsPrefix 25 }

iphcNotification26 NOTIFICATION-TYPE
    OBJECTS { 
              iphc26_interface, 
              iphc26_cid,
              iphc26_hlen,
              iphc26_max_hlen 
            }
    STATUS current
    DESCRIPTION
        "Notification of Event IPHC.26

        Message: '[$1] Decoded cid $2, prot TCP, header length too large $3 (max $4)'

        Parameters list:
              $1: iphc26_interface
              $2: iphc26_cid
              $3: iphc26_hlen
              $4: iphc26_max_hlen

        ."
    ::= { iphcNotificationsPrefix 26 }

iphcNotification27 NOTIFICATION-TYPE
    OBJECTS { 
              iphc27_interface, 
              iphc27_cid,
              iphc27_generation,
              iphc27_expected_generation 
            }
    STATUS current
    DESCRIPTION
        "Notification of Event IPHC.27

        Message: '[$1] Decoded cid $2, prot NON_TCP, invalid generation $3 (exp $4)'

        Parameters list:
              $1: iphc27_interface
              $2: iphc27_cid
              $3: iphc27_generation
              $4: iphc27_expected_generation

        ."
    ::= { iphcNotificationsPrefix 27 }

iphcNotification28 NOTIFICATION-TYPE
    STATUS current
    DESCRIPTION
        "Notification of Event IPHC.28

        Message: 'Disable this event to disable event sample mode'

        ."
    ::= { iphcNotificationsPrefix 28 }

iphcNotification29 NOTIFICATION-TYPE
    OBJECTS { 
              iphc29_interface, 
              iphc29_link_sequence,
              iphc29_expected_link_sequence,
              iphc29_cid 
            }
    STATUS current
    DESCRIPTION
        "Notification of Event IPHC.29

        Message: '[$1] Decoded bad link_seq 0x$2 (exp 0x$3), cid $4'

        Parameters list:
              $1: iphc29_interface
              $2: iphc29_link_sequence
              $3: iphc29_expected_link_sequence
              $4: iphc29_cid

        This message is generated when an packet has an invalid sequence.
        The received sequence, together with the correct sequence,
        are displayed."
    ::= { iphcNotificationsPrefix 29 }

iphcNotification30 NOTIFICATION-TYPE
    OBJECTS { 
              iphc30_interface, 
              iphc30_cid,
              iphc30_ip_id,
              iphc30_src_ipaddr,
              iphc30_src_port,
              iphc30_dst_ipaddr,
              iphc30_dst_port,
              iphc30_generation,
              iphc30_cksum,
              iphc30_flag,
              iphc30_link_sequence 
            }
    STATUS current
    DESCRIPTION
        "Notification of Event IPHC.30

        Message: '[$1] Encoded cid $2, prot NON_TCP, id 0x$3, $4/$5 -> $6/$7, generation $8, cksum 0x$9, ($10) link_seq 0x$11'

        Parameters list:
              $1: iphc30_interface
              $2: iphc30_cid
              $3: iphc30_ip_id
              $4: iphc30_src_ipaddr
              $5: iphc30_src_port
              $6: iphc30_dst_ipaddr
              $7: iphc30_dst_port
              $8: iphc30_generation
              $9: iphc30_cksum
              $10: iphc30_flag
              $11: iphc30_link_sequence

        ."
    ::= { iphcNotificationsPrefix 30 }

iphcNotification31 NOTIFICATION-TYPE
    OBJECTS { 
              iphc31_interface, 
              iphc31_cid,
              iphc31_chksum,
              iphc31_chksumexp 
            }
    STATUS current
    DESCRIPTION
        "Notification of Event IPHC.31

        Message: '[$1] Encoded cid $2, prot NON_TCP, detected unexpected checksum change 0x$3 (exp 0x$4)'

        Parameters list:
              $1: iphc31_interface
              $2: iphc31_cid
              $3: iphc31_chksum
              $4: iphc31_chksumexp

        ."
    ::= { iphcNotificationsPrefix 31 }

iphcNotification32 NOTIFICATION-TYPE
    OBJECTS { 
              iphc32_interface, 
              iphc32_cid,
              iphc32_pkt_counter 
            }
    STATUS current
    DESCRIPTION
        "Notification of Event IPHC.32

        Message: '[$1] Decoded CONTEXT_STATE prot TCP cid $2, #$3'

        Parameters list:
              $1: iphc32_interface
              $2: iphc32_cid
              $3: iphc32_pkt_counter

        ."
    ::= { iphcNotificationsPrefix 32 }

iphcNotification33 NOTIFICATION-TYPE
    OBJECTS { 
              iphc33_interface, 
              iphc33_cid,
              iphc33_pkt_counter 
            }
    STATUS current
    DESCRIPTION
        "Notification of Event IPHC.33

        Message: '[$1] Encoded CONTEXT_STATE prot NON_TCP cid $2, #$3'

        Parameters list:
              $1: iphc33_interface
              $2: iphc33_cid
              $3: iphc33_pkt_counter

        ."
    ::= { iphcNotificationsPrefix 33 }

iphcNotification34 NOTIFICATION-TYPE
    OBJECTS { 
              iphc34_interface, 
              iphc34_cid,
              iphc34_pkt_counter 
            }
    STATUS current
    DESCRIPTION
        "Notification of Event IPHC.34

        Message: '[$1] Encoded CONTEXT_STATE prot TCP cid $2, #$3'

        Parameters list:
              $1: iphc34_interface
              $2: iphc34_cid
              $3: iphc34_pkt_counter

        ."
    ::= { iphcNotificationsPrefix 34 }

iphcNotification35 NOTIFICATION-TYPE
    OBJECTS { 
              iphc35_interface, 
              iphc35_rx_tx,
              iphc35_ietf_compat,
              iphc35_tcp_space,
              iphc35_nontcp_space,
              iphc35_maxheader,
              iphc35_maxperiod,
              iphc35_maxtime 
            }
    STATUS current
    DESCRIPTION
        "Notification of Event IPHC.35

        Message: '[$1] Init, $2, $3 format, tcp_space $4, nontcp_space $5, maxheader $6, maxperiod $7, maxtime $8'

        Parameters list:
              $1: iphc35_interface
              $2: iphc35_rx_tx
              $3: iphc35_ietf_compat
              $4: iphc35_tcp_space
              $5: iphc35_nontcp_space
              $6: iphc35_maxheader
              $7: iphc35_maxperiod
              $8: iphc35_maxtime

        ."
    ::= { iphcNotificationsPrefix 35 }

iphcNotification36 NOTIFICATION-TYPE
    OBJECTS { 
              iphc36_interface 
            }
    STATUS current
    DESCRIPTION
        "Notification of Event IPHC.36

        Message: '[$1] Destroy'

        Parameters list:
              $1: iphc36_interface

        ."
    ::= { iphcNotificationsPrefix 36 }

iphcNotification37 NOTIFICATION-TYPE
    OBJECTS { 
              iphc37_interface, 
              iphc37_protocol,
              iphc37_cid 
            }
    STATUS current
    DESCRIPTION
        "Notification of Event IPHC.37

        Message: '[$1] Freeing context state, prot $2, cid $3, due to inactivity'

        Parameters list:
              $1: iphc37_interface
              $2: iphc37_protocol
              $3: iphc37_cid

        ."
    ::= { iphcNotificationsPrefix 37 }

iphcNotification38 NOTIFICATION-TYPE
    OBJECTS { 
              iphc38_interface, 
              iphc38_cid,
              iphc38_ip_id,
              iphc38_src_ipaddr,
              iphc38_src_port,
              iphc38_dst_ipaddr,
              iphc38_dst_port,
              iphc38_cksum 
            }
    STATUS current
    DESCRIPTION
        "Notification of Event IPHC.38

        Message: '[$1] Encoded cid $2, prot TCP, id 0x$3, $4/$5 -> $6/$7, cksum 0x$8'

        Parameters list:
              $1: iphc38_interface
              $2: iphc38_cid
              $3: iphc38_ip_id
              $4: iphc38_src_ipaddr
              $5: iphc38_src_port
              $6: iphc38_dst_ipaddr
              $7: iphc38_dst_port
              $8: iphc38_cksum

        ."
    ::= { iphcNotificationsPrefix 38 }

iphcNotification39 NOTIFICATION-TYPE
    OBJECTS { 
              iphc39_interface, 
              iphc39_cid,
              iphc39_chksum,
              iphc39_chksumexp 
            }
    STATUS current
    DESCRIPTION
        "Notification of Event IPHC.39

        Message: '[$1] Encoded cid $2, prot TCP, detected unexpected checksum change 0x$3 (exp 0x$4)'

        Parameters list:
              $1: iphc39_interface
              $2: iphc39_cid
              $3: iphc39_chksum
              $4: iphc39_chksumexp

        ."
    ::= { iphcNotificationsPrefix 39 }

iphcNotification40 NOTIFICATION-TYPE
    OBJECTS { 
              iphc40_interface, 
              iphc40_cid,
              iphc40_chksum,
              iphc40_chksumexp 
            }
    STATUS current
    DESCRIPTION
        "Notification of Event IPHC.40

        Message: '[$1] Decoded cid $2, prot NON_TCP, detected unexpected checksum change 0x$3 (exp 0x$4)'

        Parameters list:
              $1: iphc40_interface
              $2: iphc40_cid
              $3: iphc40_chksum
              $4: iphc40_chksumexp

        ."
    ::= { iphcNotificationsPrefix 40 }

iphcNotification41 NOTIFICATION-TYPE
    OBJECTS { 
              iphc41_interface, 
              iphc41_cid,
              iphc41_chksum,
              iphc41_chksumexp 
            }
    STATUS current
    DESCRIPTION
        "Notification of Event IPHC.41

        Message: '[$1] Decoded cid $2, prot TCP, detected unexpected checksum change 0x$3 (exp 0x$4)'

        Parameters list:
              $1: iphc41_interface
              $2: iphc41_cid
              $3: iphc41_chksum
              $4: iphc41_chksumexp

        ."
    ::= { iphcNotificationsPrefix 41 }

iphcNotification42 NOTIFICATION-TYPE
    OBJECTS { 
              iphc42_interface, 
              iphc42_cause 
            }
    STATUS current
    DESCRIPTION
        "Notification of Event IPHC.42

        Message: '[$1] UNCOMPRESS, Cause: $2'

        Parameters list:
              $1: iphc42_interface
              $2: iphc42_cause

        ."
    ::= { iphcNotificationsPrefix 42 }

iphcNotification43 NOTIFICATION-TYPE
    OBJECTS { 
              iphc43_interface, 
              iphc43_cid,
              iphc43_pps 
            }
    STATUS current
    DESCRIPTION
        "Notification of Event IPHC.43

        Message: '[$1] Decoded RTP per second stats cid $2, PPS: $3'

        Parameters list:
              $1: iphc43_interface
              $2: iphc43_cid
              $3: iphc43_pps

        ."
    ::= { iphcNotificationsPrefix 43 }

iphcNotification44 NOTIFICATION-TYPE
    OBJECTS { 
              iphc44_interface, 
              iphc44_cid,
              iphc44_pps 
            }
    STATUS current
    DESCRIPTION
        "Notification of Event IPHC.44

        Message: '[$1] Encoded RTP per second stats cid $2, PPS: $3'

        Parameters list:
              $1: iphc44_interface
              $2: iphc44_cid
              $3: iphc44_pps

        ."
    ::= { iphcNotificationsPrefix 44 }

iphcNotification45 NOTIFICATION-TYPE
    OBJECTS { 
              iphc45_interface, 
              iphc45_cause 
            }
    STATUS current
    DESCRIPTION
        "Notification of Event IPHC.45

        Message: '[$1] Decoded DROP PACKET, Cause: $2'

        Parameters list:
              $1: iphc45_interface
              $2: iphc45_cause

        ."
    ::= { iphcNotificationsPrefix 45 }

iphcNotification46 NOTIFICATION-TYPE
    OBJECTS { 
              iphc46_interface, 
              iphc46_cid,
              iphc46_link_sequence 
            }
    STATUS current
    DESCRIPTION
        "Notification of Event IPHC.46

        Message: '[$1] Received NON_TCP invalid context id $2, link_seq 0x$3'

        Parameters list:
              $1: iphc46_interface
              $2: iphc46_cid
              $3: iphc46_link_sequence

        ."
    ::= { iphcNotificationsPrefix 46 }


END
