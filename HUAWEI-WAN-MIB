-- ==================================================================
-- Copyright (C) 2007 by HUAWEI TECHNOLOGIES. All rights reserved.
-- 
-- Description:  This MIB module defines MIB objects of hwIBTable, hw3GTable and hwSPRTrap.
-- Reference:
-- Version: V1.0
-- History:
-- V1.0 2007-10-21 publish
-- ==================================================================
          
    HUAWEI-WAN-MIB DEFINITIONS ::= BEGIN
 
    IMPORTS
            hwDatacomm            
                FROM HUAWEI-MIB            
            OBJECT-GROUP, MODULE-COMPLIANCE, NOTIFICATION-GROUP            
                FROM SNMPv2-CONF            
            InterfaceIndex
                FROM IF-MIB              
            Integer32, OBJECT-TYPE, MODULE-IDENTITY, Counter64, NOTIFICATION-TYPE           
  --           FROM SNMPv2-SMI;
  --       DisplayString,TruthValue,RowStatus   
  --           FROM SNMPv2-TC;
  --       EnabledStatus
                FROM SNMPv2-SMI;
                      
          hwWANMIB MODULE-IDENTITY 
          LAST-UPDATED "201401091451Z"
          ORGANIZATION 
              "Huawei Technologies Co.,Ltd."
          CONTACT-INFO 
              "Huawei Industrial Base                
              Bantian, Longgang                     
              Shenzhen 518129                       
              People's Republic of China            
              Website: http://www.huawei.com        
              Email: support@huawei.com             
              "  
          DESCRIPTION 
              "The private mib file includes the general extent 
              information of the device.hwDatacomm(241).hwWANMIB" 

          REVISION   "201401091451Z"
          
          DESCRIPTION    "V1.06, update version"

          REVISION   "201310162047Z"
          
          DESCRIPTION    "V1.05, update version"
                    
          REVISION   "201309111647Z"
          
          DESCRIPTION    "V1.04, update version"

          REVISION   "201308261942Z"
          
          DESCRIPTION    "V1.03, update version"

          REVISION   "201306242018Z"
          
          DESCRIPTION    "V1.02, update version"

          REVISION   "201304261142Z"
          
          DESCRIPTION    "V1.01, update version"

          ::= { hwDatacomm 241 }
          
                            
      hwWANMIBObjects OBJECT IDENTIFIER ::= { hwWANMIB 1 }
      
      hwIB OBJECT IDENTIFIER ::= { hwWANMIBObjects 1 }
--
-- hwIBTable Table 
--           
      hwIBTable OBJECT-TYPE
          SYNTAX      SEQUENCE OF HwIBEntry
          MAX-ACCESS  not-accessible
          STATUS      current
          DESCRIPTION
              "Indicates the attribute of the IB interface formed by timeslots.
              This table lists the physical attributes of the IB interface."
          ::= { hwIB 1 }
            
      hwIBEntry OBJECT-TYPE
          SYNTAX HwIBEntry
          MAX-ACCESS not-accessible
          STATUS current
          DESCRIPTION
                "Indicates the attribute of the IB interface formed by timeslots.
                This table lists the physical attributes of the IB interface."
          INDEX  { hwIBMainIfIndex }    
          ::= { hwIBTable 1 }           
    
      HwIBEntry  ::= 
          SEQUENCE{
              hwIBMainIfIndex
                  InterfaceIndex,   
              hwIBStandbyIf1     
                  Integer32,  
			  hwIBPri1     
                  Integer32,
              hwIBStandbyIf2     
                  Integer32,  
			  hwIBPri2     
                  Integer32,
              hwIBStandbyIf3     
                  Integer32,  
			  hwIBPri3     
                  Integer32,
              hwIBStandbyType
                  INTEGER,               
              hwIBStandbyBandWidth 
                  Integer32,                                  
              hwIBEnableThreshold     
                  Integer32,  
			  hwIBDisableThreshold     
                  Integer32,
              hwIBActiveTimer
                  Integer32,               
              hwIBInactiveTimer 
                  Integer32           
                  }
          
      hwIBMainIfIndex OBJECT-TYPE
         SYNTAX InterfaceIndex
          MAX-ACCESS not-accessible
          STATUS current
          DESCRIPTION
              "Interface index(es) of IB(s) present on the device ."
          ::= { hwIBEntry 1 }

      hwIBStandbyIf1 OBJECT-TYPE
          SYNTAX Integer32(0..32767)
          MAX-ACCESS read-only
          STATUS current
          DESCRIPTION
              "IB Standby Interface1."
          ::= { hwIBEntry 11 } 
          
      hwIBPri1 OBJECT-TYPE
          SYNTAX Integer32(0..255)
          MAX-ACCESS read-only
          STATUS current
          DESCRIPTION
              "IB Pri1."
          ::= { hwIBEntry 12 }
    
     hwIBStandbyIf2 OBJECT-TYPE
          SYNTAX Integer32(0..32767)
          MAX-ACCESS read-only
          STATUS current
          DESCRIPTION
              "IB Standby Interface2."
          ::= { hwIBEntry 13 } 
          
      hwIBPri2 OBJECT-TYPE
          SYNTAX Integer32(0..255)
          MAX-ACCESS read-only
          STATUS current
          DESCRIPTION
              "IB Pri2."
          ::= { hwIBEntry 14 }
    
      hwIBStandbyIf3 OBJECT-TYPE
          SYNTAX Integer32(0..32767)
          MAX-ACCESS read-only
          STATUS current
          DESCRIPTION
              "IB Standby Interface3."
          ::= { hwIBEntry 15 } 
          
      hwIBPri3 OBJECT-TYPE
          SYNTAX Integer32(0..255)
          MAX-ACCESS read-only
          STATUS current
          DESCRIPTION
              "IB Pri3."
          ::= { hwIBEntry 16 }    
    
      hwIBStandbyType OBJECT-TYPE
          SYNTAX INTEGER{ 
                masterslave(0),
         		loadbalance(1)
     			}
          MAX-ACCESS read-only
          STATUS current
          DESCRIPTION
              "IB Standby Type."
          ::= { hwIBEntry 17 } 
     
      hwIBStandbyBandWidth OBJECT-TYPE
          SYNTAX Integer32(0..32767)
          MAX-ACCESS read-only
          STATUS current
          DESCRIPTION
              "IB Standby BandWidth."
          ::= { hwIBEntry 18 }          
       
      hwIBEnableThreshold OBJECT-TYPE
          SYNTAX Integer32(0..99)
          MAX-ACCESS read-only
          STATUS current
          DESCRIPTION
              "IB Enable Threshold."
          ::= { hwIBEntry 19 } 
     
      hwIBDisableThreshold OBJECT-TYPE
          SYNTAX Integer32(0..99)
          MAX-ACCESS read-only
          STATUS current
          DESCRIPTION
              "IB Disable Threshold."
          ::= { hwIBEntry 20 } 
     
      hwIBActiveTimer OBJECT-TYPE
          SYNTAX Integer32(0..65535)
          MAX-ACCESS read-only
          STATUS current
          DESCRIPTION
              "IB Active Timer."
          ::= { hwIBEntry 21 } 
     
      hwIBInactiveTimer OBJECT-TYPE
          SYNTAX Integer32(0..65535)
          MAX-ACCESS read-only
          STATUS current
          DESCRIPTION
              "IB Inactive Timer"
          ::= { hwIBEntry 22 }  
          
   hw3G OBJECT IDENTIFIER ::= { hwWANMIBObjects 2 }
--
-- hw3GTable Table 
--           
      hw3GTable OBJECT-TYPE
          SYNTAX      SEQUENCE OF Hw3GEntry
          MAX-ACCESS  not-accessible
          STATUS      current
          DESCRIPTION
              "Indicates the attribute of the 3G interface ."
          ::= { hw3G 1 }
            
      hw3GEntry OBJECT-TYPE
          SYNTAX Hw3GEntry
          MAX-ACCESS not-accessible
          STATUS current
          DESCRIPTION
                "Indicates the attribute of the 3G interface ."
          INDEX  { hw3GIfIndex }    
          ::= { hw3GTable 1 }           
    
      Hw3GEntry  ::= 
          SEQUENCE{
              hw3GIfIndex
                  InterfaceIndex,   
              hw3GModemStatus     
                  INTEGER,  
              hw3GDeviceNumber     
                  OCTET STRING,
              hw3GManufaceturer     
                  OCTET STRING,  
			  hw3GLicense     
                  OCTET STRING,
              hw3GDeviceSerialNumber     
                  OCTET STRING,  
			  hw3GUIMStatus     
                  INTEGER,
              hw3GIMSI
                  OCTET STRING,               
              hw3GMV 
                  Integer32,                                  
              hw3GOper     
                  OCTET STRING,  
			  hw3GCSQ     
                  Integer32,
              hw3GAPNName
                  OCTET STRING,               
              hw3GNetworkConnectionType 
                  INTEGER, 
              hw3GTotalConnectionTime 
                  Integer32,
              hw3GTxRate
                  Integer32,
              hw3GRxRate
                  Integer32,  
              hw3GBytesSent
                  Integer32,       
              hw3GBytesReceived
                  Integer32,
              hw3GBytesRateSent
                  Integer32, 
              hw3GBytesRateReceived
                  Integer32,
              hw3GUpBand
                  Integer32, 
              hw3GDownBand
                  Integer32,
              hw3GPacketSessionStatus
                  INTEGER,
              hw3GIccId     
                  OCTET STRING                   
                  }
    
     hw3GIfIndex OBJECT-TYPE
          SYNTAX InterfaceIndex
          MAX-ACCESS not-accessible
          STATUS current
          DESCRIPTION
              "3G index(es) of port(s) present on the device ."
          ::= { hw3GEntry 1 }
          
      hw3GModemStatus OBJECT-TYPE
          SYNTAX INTEGER{ 
           		online(1),
        		offline(4)
        		}
          MAX-ACCESS read-only
          STATUS current
          DESCRIPTION
            "The ModemState of 3G interface is used to test 3G whether online or not"  
         ::= { hw3GEntry 11 }
    
      hw3GDeviceNumber OBJECT-TYPE
          SYNTAX OCTET STRING(SIZE (0..64))
          MAX-ACCESS read-only
          STATUS current
          DESCRIPTION
              "Device Number"
          ::= { hw3GEntry 12 }    
    
      hw3GManufaceturer OBJECT-TYPE
          SYNTAX OCTET STRING(SIZE (0..32))
          MAX-ACCESS read-only
          STATUS current
          DESCRIPTION
              "Device Manufaceturer"
          ::= { hw3GEntry 13 }
          
      hw3GLicense OBJECT-TYPE
          SYNTAX OCTET STRING(SIZE (0..1023))
          MAX-ACCESS read-only
          STATUS current
          DESCRIPTION
              "3G License"
          ::= { hw3GEntry 14 }         
          
      hw3GDeviceSerialNumber OBJECT-TYPE
          SYNTAX OCTET STRING(SIZE (0..64))
          MAX-ACCESS read-only
          STATUS current
          DESCRIPTION
              "3G Device Serial Number"
          ::= { hw3GEntry 15 }
          
      hw3GUIMStatus OBJECT-TYPE
          SYNTAX INTEGER{
                     nocard(0),
                     sim(1),  
                     uim(2)
                    }
          MAX-ACCESS read-only
          STATUS current
          DESCRIPTION
            "The Status of 3G UIM"  
         ::= { hw3GEntry 16 }

       hw3GIMSI OBJECT-TYPE
          SYNTAX OCTET STRING(SIZE (0..15))
          MAX-ACCESS read-only
          STATUS current
          DESCRIPTION
              "3G IMSI"
          ::= { hw3GEntry 17 }
      
       hw3GMV OBJECT-TYPE
          SYNTAX Integer32
          MAX-ACCESS read-only
          STATUS current
          DESCRIPTION
              "3G MV "
          ::= { hw3GEntry 18 } 
      
      hw3GOper OBJECT-TYPE
          SYNTAX OCTET STRING(SIZE (0..64))
          MAX-ACCESS read-only
          STATUS current
          DESCRIPTION
              "3G Oper"
          ::= { hw3GEntry 19 } 
          
      hw3GCSQ OBJECT-TYPE
         SYNTAX Integer32(0..200)
          MAX-ACCESS read-only
          STATUS current
          DESCRIPTION
              "3G Signal Intensity"
          ::= { hw3GEntry 20 }  
          
       hw3GAPNName OBJECT-TYPE
           SYNTAX OCTET STRING(SIZE (0..256))
           MAX-ACCESS read-only
           STATUS current
           DESCRIPTION
              "3G APN Name"
           ::= { hw3GEntry 21 } 
           
        hw3GNetworkConnectionType OBJECT-TYPE
           SYNTAX INTEGER{
                     gsmOnly(0),
                     gsmPrecedence(1),
                     wcdmaOnly(2),
                     wcdmaPrecedence(3),
                     evdoOnly(4),
                     cdma1xrttOnly(5),   
                     hybrid(8),   
                     auto(17),
                     lteOnly(18)  
                     }
           MAX-ACCESS read-only
           STATUS current
           DESCRIPTION
              "3G Network Connection Type"
           ::= { hw3GEntry 22 }  
            
        hw3GTotalConnectionTime  OBJECT-TYPE
           SYNTAX Integer32
           MAX-ACCESS read-only
           STATUS current
           DESCRIPTION
              "3G Total Connection Time"
           ::= { hw3GEntry 23 }   
              
       hw3GTxRate  OBJECT-TYPE
           SYNTAX Integer32
           MAX-ACCESS read-only
           STATUS current
           DESCRIPTION
              "3G sent Rate"
           ::= { hw3GEntry 24 }   

        hw3GRxRate  OBJECT-TYPE
           SYNTAX Integer32
           MAX-ACCESS read-only
           STATUS current
           DESCRIPTION
              "3G Receive Rate"
           ::= { hw3GEntry 25 }   
             
      hw3GBytesSent OBJECT-TYPE
          SYNTAX Integer32
          MAX-ACCESS read-only
          STATUS current
          DESCRIPTION
              "3G Bytes Sent"
          ::= { hw3GEntry 26 } 
              
      hw3GBytesReceived OBJECT-TYPE
          SYNTAX Integer32
          MAX-ACCESS read-only
          STATUS current
          DESCRIPTION
              "3G Bytes Received"
          ::= { hw3GEntry 27 }                              
 
      hw3GBytesRateSent OBJECT-TYPE
          SYNTAX Integer32
          MAX-ACCESS read-only
          STATUS current
          DESCRIPTION
              "3G Sent Bytes Rate"
          ::= { hw3GEntry 28 } 
              
      hw3GBytesRateReceived OBJECT-TYPE
          SYNTAX Integer32
          MAX-ACCESS read-only
          STATUS current
          DESCRIPTION
              "3G Receive Bytes Rate"
          ::= { hw3GEntry 29 }   
          
      hw3GUpBand OBJECT-TYPE
          SYNTAX Integer32
          MAX-ACCESS read-only
          STATUS current
          DESCRIPTION
              "3G Up Band"
          ::= { hw3GEntry 30 } 
              
      hw3GDownBand OBJECT-TYPE
          SYNTAX Integer32
          MAX-ACCESS read-only
          STATUS current
          DESCRIPTION
              "3G Down Band"
          ::= { hw3GEntry 31 }  
          
      hw3GPacketSessionStatus OBJECT-TYPE
          SYNTAX INTEGER{ 
           		active(1),
        		inactive(0)
        		}
          MAX-ACCESS read-only
          STATUS current
          DESCRIPTION
              "Packet Session Status"
          ::= { hw3GEntry 32 } 
          
      hw3GIccId  OBJECT-TYPE
          SYNTAX OCTET STRING(SIZE (0..32))
          MAX-ACCESS read-only
          STATUS current
          DESCRIPTION
              "Integrate Circuit Card Identity "
          ::= { hw3GEntry 33 }     
          
          
                              
          
      hwSPRMIBTrap OBJECT IDENTIFIER ::= { hwWANMIB 2 }
      hwSPRTrapOid OBJECT IDENTIFIER ::= { hwSPRMIBTrap 1 }
      
        hwSPRLinkStateIndex  OBJECT-TYPE
            SYNTAX Integer32 (0..1023)
            MAX-ACCESS read-only
            STATUS current
            DESCRIPTION
                "Link Index"
            ::= { hwSPRTrapOid 1 }     
            
        hwSPRLinkStateName OBJECT-TYPE
            SYNTAX OCTET STRING(SIZE (0..64))
            MAX-ACCESS read-only
            STATUS current
            DESCRIPTION
                "Link Name"
            ::= { hwSPRTrapOid 2 }         
            
        hwSPRLinkStateEligibility OBJECT-TYPE
            SYNTAX Integer32 
            MAX-ACCESS read-only
            STATUS current
            DESCRIPTION
                "Link State.0 is eligible;1 is not eligible"
            ::= { hwSPRTrapOid 3 }    
            
      hwSPRTrapDefine OBJECT IDENTIFIER ::= { hwSPRMIBTrap 2 }
      hwSPRTrap OBJECT IDENTIFIER ::= { hwSPRTrapDefine 1 }
      
          hwSPRLinkReport NOTIFICATION-TYPE
            OBJECTS {hwSPRLinkStateIndex, hwSPRLinkStateName, hwSPRLinkStateEligibility}
            STATUS current
            DESCRIPTION
                "
                1 Notice/Trap name:  Link not eligible 
                2 Notice/Trap generation cause:  Link not eligible 
                3 Repair suggestions:
                    Check the links according to not eligible reasons.
                "
            ::= { hwSPRTrap 1 }
      
      hwSPR OBJECT IDENTIFIER ::= { hwSPRMIBTrap 3 }
 
      hwSPRServiceTable OBJECT-TYPE
          SYNTAX      SEQUENCE OF HwSPRServiceEntry
          MAX-ACCESS  not-accessible
          STATUS      current
          DESCRIPTION
              "Indicates the attribute of the SPR service map."
          ::= { hwSPR 1 }
            
      hwSPRServiceEntry OBJECT-TYPE
          SYNTAX HwSPRServiceEntry
          MAX-ACCESS not-accessible
          STATUS current
          DESCRIPTION
                "Indicates the attribute of the SPR service map."
          INDEX  { hwSPRServiceIndex }    
          ::= { hwSPRServiceTable 1 }           
    
      HwSPRServiceEntry  ::= 
          SEQUENCE{
              hwSPRServiceIndex
                  Integer32,   
              hwSPRServiceName
                  OCTET STRING,
              hwSPRServiceCurLinkName
                  OCTET STRING     
                  }
                
      hwSPRServiceIndex  OBJECT-TYPE
            SYNTAX Integer32 (1..65535)
            MAX-ACCESS accessible-for-notify
            STATUS current
            DESCRIPTION
                "Service Index"
            ::= { hwSPRServiceEntry 1 }     
            
      hwSPRServiceName OBJECT-TYPE
            SYNTAX OCTET STRING(SIZE (0..32))
            MAX-ACCESS read-only
            STATUS current
            DESCRIPTION
                "Service Name"
            ::= { hwSPRServiceEntry 2 }         
            
      hwSPRServiceCurLinkName OBJECT-TYPE
            SYNTAX OCTET STRING(SIZE (0..64))
            MAX-ACCESS read-only
            STATUS current
            DESCRIPTION
                "Service Current Link Name"
            ::= { hwSPRServiceEntry 3 }    
                                                  
      hwSPRTraps OBJECT IDENTIFIER ::= { hwSPRMIBTrap 4 }
      
         hwSPRServiceReport NOTIFICATION-TYPE
            OBJECTS {hwSPRServiceIndex, hwSPRServiceName, hwSPRServiceCurLinkName}
            STATUS current
            DESCRIPTION
                "
                The notification indicates that the current link of SPR service map was changed.
                "
            ::= { hwSPRTraps 1 }
            
            
--  ============== conformance information ==============
        hwWANConformance OBJECT IDENTIFIER ::= { hwWANMIB 3 }
        
        
        hwWANCompliances OBJECT IDENTIFIER ::= { hwWANConformance 1 }
        hwWANCompliance MODULE-COMPLIANCE
               STATUS      current
               DESCRIPTION
                   "The compliance statement for systems supporting 
                the this module."

               MODULE      -- this module
               MANDATORY-GROUPS    {hwIBGroup, hw3GGroup, hwSPRMIBTrapObjectGroup, hwSPRMIBTrapsDefineGroup, hwSPRServiceGroup, hwSPRTrapsGroup}  
                                               
              ::= { hwWANCompliances 1 }  
              
       
        --  ============== groups ==============  
        hwWANGroups OBJECT IDENTIFIER ::= { hwWANConformance 2 } 
        
        hwIBGroup OBJECT-GROUP
            OBJECTS {
                hwIBMainIfIndex,
                hwIBStandbyIf1,
                hwIBPri1,
                hwIBStandbyIf2,
                hwIBPri2,     
                hwIBStandbyIf3,
                hwIBPri3,
                hwIBStandbyType,
                hwIBStandbyBandWidth,
                hwIBEnableThreshold,  
                hwIBDisableThreshold,
                hwIBActiveTimer,
                hwIBInactiveTimer
             }       
            STATUS current
            DESCRIPTION 
                "The IB group."
            ::= { hwWANGroups 1 }


        hw3GGroup OBJECT-GROUP
            OBJECTS {    
                hw3GIfIndex,  
                hw3GModemStatus,
                hw3GDeviceNumber,
                hw3GManufaceturer,  
                hw3GLicense,  
                hw3GDeviceSerialNumber ,   
                hw3GUIMStatus,
                hw3GIMSI,
                hw3GMV,                        
                hw3GOper,            
                hw3GCSQ,
                hw3GAPNName,   
                hw3GNetworkConnectionType,
                hw3GTotalConnectionTime,
                hw3GTxRate,
                hw3GRxRate,
                hw3GBytesSent,
                hw3GBytesReceived,
                hw3GBytesRateSent, 
                hw3GBytesRateReceived,
                hw3GUpBand, 
                hw3GDownBand,
                hw3GPacketSessionStatus,
                hw3GIccId 
            }          
            STATUS current
            DESCRIPTION 
                "The 3G group."
            ::= { hwWANGroups 2 }
            
        hwSPRMIBTrapObjectGroup OBJECT-GROUP
            OBJECTS { 
                hwSPRLinkStateIndex,
                hwSPRLinkStateName,
                hwSPRLinkStateEligibility
                    }            
            STATUS current
            DESCRIPTION 
                "The SPR Link group."
            ::= { hwWANGroups 3 }
                    
        hwSPRMIBTrapsDefineGroup NOTIFICATION-GROUP
            NOTIFICATIONS { hwSPRLinkReport}           
            STATUS current
            DESCRIPTION 
                "The SPR Link Trap Define group."
            ::= { hwWANGroups 4 }            

        hwSPRServiceGroup OBJECT-GROUP
            OBJECTS { 
                hwSPRServiceIndex,
                hwSPRServiceName,
                hwSPRServiceCurLinkName
                    }            
            STATUS current
            DESCRIPTION 
                "The SPR Service group."
            ::= { hwWANGroups 5 }

                    
        hwSPRTrapsGroup NOTIFICATION-GROUP
            NOTIFICATIONS {
                hwSPRServiceReport
                    }            
            STATUS current
            DESCRIPTION 
                "The SPR Traps group."
            ::= { hwWANGroups 6 }            
            
             
                    
        --  ============== conformance information define end ==============

END
