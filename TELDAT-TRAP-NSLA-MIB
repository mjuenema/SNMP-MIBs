-- file automatically created


TELDAT-TRAP-NSLA-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


nslaTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the NSLA event subsystem."
    REVISION "201401200930Z"
    DESCRIPTION "Initial implementation"
        ::= { telEventTraps 173 }


nslaEventsGroup	OBJECT IDENTIFIER	::= { nslaTrapsMIB 1 }

nslaNotifications	OBJECT IDENTIFIER	::= { nslaTrapsMIB 2 }
nslaNotificationsPrefix	OBJECT IDENTIFIER	::= { nslaNotifications 0 }

nslaEventObjects1 OBJECT-IDENTITY
    STATUS current
    DESCRIPTION
        "Event NSLA.1
        Event at global level.
        \par The 'event_detail' arg will take one of the following values:
        \par 	- ioctl failed rsn = out of tasker
        \par 	- ioctl MUTE failed rsn = already MUTED
        \par 	- ioctl MUTE
        \par 	- ioctl UNMUTE failed rsn = not MUTED
        \par 	- ioctl UNMUTE
        \par 	- ioctl DISABLE failed rsn = already DISABLED
        \par 	- ioctl DISABLE
        \par 	- ioctl ENABLE failed rsn = already ENABLED
        \par 	- ioctl ENABLE"
    ::= { nslaEventsGroup 1 }

nsla1_event_detail OBJECT-TYPE
    SYNTAX DisplayString
    MAX-ACCESS accessible-for-notify
    STATUS current
    DESCRIPTION
        "Parameter 'event_detail' in event NSLA.1"
    ::= { nslaEventObjects1 1 }

nslaEventObjects2 OBJECT-IDENTITY
    STATUS current
    DESCRIPTION
        "Event NSLA.2
        Event at filter level.
        \par The 'event_detail' arg will take one of the following values:
        \par 	- creation failed rsn = NSLA disabled
        \par 	- creation failed rsn = ID duplicated
        \par 	- creation bypassed rsn = disabled
        \par 	- creation failed rsn = memory exhaustion
        \par 	- creation failed rsn = unknown filter type
        \par 	- creation failed rsn = unknown NSM parameter
        \par 	- creation failed rsn = NSM registration failed
        \par 	- creation ok
        \par    - client (<upcall> <arg 1> <arg 2>) mutated to zombie		
        \par 	- removal phase <1|2> ok
        \par 	- removal ok
        \par 	- client (<upcall> <arg 1> <arg 2>) registration failed rsn = NULL upcall
        \par 	- client (<upcall> <arg 1> <arg 2>) registration failed rsn = memory exhaustion
        \par 	- client (<upcall> <arg 1> <arg 2>) registration ok
        \par 	- client (<upcall> <arg 1> <arg 2>) zombie reanimation ok		
        \par 	- client (<upcall> <arg 1> <arg 2>) deregistration failed rsn = NULL upcall
        \par 	- client (<upcall> <arg 1> <arg 2>) deregistration ok		
        \par 	- client (<upcall> <arg 1> <arg 2>) deregistration failed rsn = no matching client found
        \par 	- ioctl failed rsn = out of tasker
        \par 	- ioctl failed rsn = not active ID
        \par 	- ioctl ACT failed rsn = already ACT
        \par 	- ioctl ACTIVATE
        \par 	- ioctl DEACT failed rsn = already DEACT
        \par 	- ioctl DEACTIVATE
        \par 	- ioctl REST failed rsn = neither ACT nor DEACT
        \par 	- ioctl RESTORE
        \par 	- ioctl MUTE failed rsn = already MUTED
        \par 	- ioctl MUTE
        \par 	- ioctl UNMUTE failed rsn = not MUTED
        \par 	- ioctl UNMUTE
        \par 	- ioctl DISABLE failed rsn = already DISABLED
        \par 	- ioctl DISABLE
        \par 	- ioctl ENABLE failed rsn = already ENABLED
        \par 	- ioctl ENABLE
        \par 	- ioctl UNKNOWN
        \par 	- client notification bypassed
        \par 	- client notification <TRUE | FALSE>
        \par 	- client (<upcall> <arg 1> <arg 2>) notification overwritten		
        \par 	- act cond detected
        \par 	- act cond removed
        \par 	- deact cond detected
        \par 	- deact cond removed 
        \par 	- act/deact overlap detected
        \par 	- act cond detected
        \par 	- act cond removed"
    ::= { nslaEventsGroup 2 }

nsla2_filter_id OBJECT-TYPE
    SYNTAX Integer32
    MAX-ACCESS accessible-for-notify
    STATUS current
    DESCRIPTION
        "Parameter 'filter_id' in event NSLA.2"
    ::= { nslaEventObjects2 1 }

nsla2_event_detail OBJECT-TYPE
    SYNTAX DisplayString
    MAX-ACCESS accessible-for-notify
    STATUS current
    DESCRIPTION
        "Parameter 'event_detail' in event NSLA.2"
    ::= { nslaEventObjects2 2 }

nslaEventObjects3 OBJECT-IDENTITY
    STATUS current
    DESCRIPTION
        "Event NSLA.3
        Sample reported to filter.
        \par The 'event_detail' arg will take one of the following values:
        \par 	- sample = <value>
        \par 	- sample = <value> -> ACTIVE
        \par 	- sample = <valor> -> DEACTIVE
        \par 	- sample = timeout
        \par 	- sample = timeout -> ACTIVE"
    ::= { nslaEventsGroup 3 }

nsla3_filter_id OBJECT-TYPE
    SYNTAX Integer32
    MAX-ACCESS accessible-for-notify
    STATUS current
    DESCRIPTION
        "Parameter 'filter_id' in event NSLA.3"
    ::= { nslaEventObjects3 1 }

nsla3_event_detail OBJECT-TYPE
    SYNTAX DisplayString
    MAX-ACCESS accessible-for-notify
    STATUS current
    DESCRIPTION
        "Parameter 'event_detail' in event NSLA.3"
    ::= { nslaEventObjects3 2 }

nslaEventObjects4 OBJECT-IDENTITY
    STATUS current
    DESCRIPTION
        "Event NSLA.4
        Event at alarm level.
        \par The 'event_detail' arg will take one of the following values:
        \par 	- creation failed rsn = NSLA disabled
        \par 	- creation failed rsn = ID duplicated
        \par 	- creation bypassed rsn = disabled
        \par 	- creation failed rsn = memory exhaustion
        \par 	- creation failed rsn = registration in filter <id> failed
        \par 	- registration in filter <id> ok
        \par 	- creation ok
        \par    - client (<upcall> <arg 1> <arg 2>) mutated to zombie		
        \par 	- removal successful		
        \par 	- client (<upcall> <arg 1> <arg 2>) registration failed rsn = NULL upcall
        \par 	- client (<upcall> <arg 1> <arg 2>) registration failed rsn = memory exhaustion
        \par 	- client (<upcall> <arg 1> <arg 2>) registration ok
        \par 	- client (<upcall> <arg 1> <arg 2>) zombie reanimation ok		
        \par 	- client (<upcall> <arg 1> <arg 2>) deregistration failed rsn = NULL upcall
        \par 	- client (<upcall> <arg 1> <arg 2>) deregistration ok
        \par 	- client (<upcall> <arg 1> <arg 2>) deregistration failed rsn = no matching client found
        \par 	- ioctl failed rsn = out of tasker
        \par 	- ioctl failed rsn = not active ID
        \par 	- ioctl ACT failed rsn = already ACT
        \par 	- ioctl ACTIVATE
        \par 	- ioctl DEACT failed rsn = already DEACT
        \par 	- ioctl DEACTIVATE
        \par 	- ioctl REST failed rsn = neither ACT nor DEACT
        \par 	- ioctl RESTORE
        \par 	- ioctl MUTE failed rsn = already MUTED
        \par 	- ioctl MUTE
        \par 	- ioctl UNMUTE failed rsn = not MUTED
        \par 	- ioctl UNMUTE
        \par 	- ioctl DISABLE failed rsn = already DISABLED
        \par 	- ioctl DISABLE
        \par 	- ioctl ENABLE failed rsn = already ENABLED
        \par 	- ioctl ENABLE
        \par 	- ioctl MNEMONICAL EXP
        \par 	- ioctl ioctl NUMERICAL EXP
        \par 	- ioctl UNKNOWN
        \par 	- notification from filter <id>: <TRUE|FALSE>
        \par 	- filter map change (0x%04x --> 0x%04x)
        \par 	- client notification bypassed
        \par 	- client notification <TRUE|FALSE>
        \par 	- client (<upcall> <arg 1> <arg 2>) notification overwritten"
    ::= { nslaEventsGroup 4 }

nsla4_alarm_id OBJECT-TYPE
    SYNTAX Integer32
    MAX-ACCESS accessible-for-notify
    STATUS current
    DESCRIPTION
        "Parameter 'alarm_id' in event NSLA.4"
    ::= { nslaEventObjects4 1 }

nsla4_event_detail OBJECT-TYPE
    SYNTAX DisplayString
    MAX-ACCESS accessible-for-notify
    STATUS current
    DESCRIPTION
        "Parameter 'event_detail' in event NSLA.4"
    ::= { nslaEventObjects4 2 }

nslaEventObjects5 OBJECT-IDENTITY
    STATUS current
    DESCRIPTION
        "Event NSLA.5
        Event at advisor level.
        \par The 'event_detail' arg will take one of the following values:
        \par 	- creation failed rsn = NSLA disabled
        \par 	- creation failed rsn = ID duplicated
        \par 	- creation bypassed rsn = disabled
        \par 	- creation failed rsn = memory exhaustion
        \par 	- creation failed rsn = registration in alarm <id> failed
        \par 	- registration in alarm <id> ok
        \par 	- creation ok
        \par    - client (<upcall> <arg>) mutated to zombie		
        \par 	- removal successful		
        \par 	- client (<upcall> <arg>) registration failed rsn = NULL upcall
        \par 	- client (<upcall> <arg>) registration failed rsn = memory exhaustion
        \par    - client (<upcall> <arg>) registration ok
        \par    - client (<upcall> <arg>) zombie reanimation ok
        \par 	- client (<upcall> <arg>) deregistration failed rsn = NULL upcall
        \par 	- client (<upcall> <arg>) deregistration ok
        \par 	- client (<upcall> <arg>) deregistration failed rsn = no matching client found
        \par 	- ioctl failed rsn = out of tasker
        \par 	- ioctl failed rsn = not active ID
        \par 	- ioctl ACT failed rsn = already ACT
        \par 	- ioctl ACTIVATE
        \par 	- ioctl DEACT failed rsn = already DEACT
        \par 	- ioctl DEACTIVATE
        \par 	- ioctl REST failed rsn = neither ACT nor DEACT
        \par 	- ioctl RESTORE
        \par 	- ioctl MUTE failed rsn = already MUTED
        \par 	- ioctl MUTE
        \par 	- ioctl UNMUTE failed rsn = not MUTED
        \par 	- ioctl UNMUTE
        \par 	- ioctl DISABLE failed rsn = already DISABLED
        \par 	- ioctl DISABLE
        \par 	- ioctl ENABLE failed rsn = already ENABLED
        \par 	- ioctl ENABLE
        \par 	- ioctl MNEMONICAL EXP
        \par 	- ioctl ioctl NUMERICAL EXP
        \par 	- ioctl UNKNOWN
        \par 	- notification from alarm <id>: <TRUE|FALSE>
        \par 	- alarm map change (0x%04x --> 0x%04x)
        \par 	- client notification bypassed
        \par 	- client notification <TRUE|FALSE>
        \par 	- client (<upcall> <arg>) notification overwritten"
    ::= { nslaEventsGroup 5 }

nsla5_advisor_id OBJECT-TYPE
    SYNTAX Integer32
    MAX-ACCESS accessible-for-notify
    STATUS current
    DESCRIPTION
        "Parameter 'advisor_id' in event NSLA.5"
    ::= { nslaEventObjects5 1 }

nsla5_event_detail OBJECT-TYPE
    SYNTAX DisplayString
    MAX-ACCESS accessible-for-notify
    STATUS current
    DESCRIPTION
        "Parameter 'event_detail' in event NSLA.5"
    ::= { nslaEventObjects5 2 }

nslaEventObjects6 OBJECT-IDENTITY
    STATUS current
    DESCRIPTION
        "Event NSLA.6
        Filter output change.
        \par The 'output_detail' arg will take one of the following values:
        \par 	- output TRUE
        \par 	- output FALSE"
    ::= { nslaEventsGroup 6 }

nsla6_filter_id OBJECT-TYPE
    SYNTAX Integer32
    MAX-ACCESS accessible-for-notify
    STATUS current
    DESCRIPTION
        "Parameter 'filter_id' in event NSLA.6"
    ::= { nslaEventObjects6 1 }

nsla6_output_detail OBJECT-TYPE
    SYNTAX DisplayString
    MAX-ACCESS accessible-for-notify
    STATUS current
    DESCRIPTION
        "Parameter 'output_detail' in event NSLA.6"
    ::= { nslaEventObjects6 2 }

nslaEventObjects7 OBJECT-IDENTITY
    STATUS current
    DESCRIPTION
        "Event NSLA.7
        Alarm output change.
        \par The 'output_detail' arg will take one of the following values:
        \par 	- output TRUE
        \par 	- output FALSE"
    ::= { nslaEventsGroup 7 }

nsla7_alarm_id OBJECT-TYPE
    SYNTAX Integer32
    MAX-ACCESS accessible-for-notify
    STATUS current
    DESCRIPTION
        "Parameter 'alarm_id' in event NSLA.7"
    ::= { nslaEventObjects7 1 }

nsla7_output_detail OBJECT-TYPE
    SYNTAX DisplayString
    MAX-ACCESS accessible-for-notify
    STATUS current
    DESCRIPTION
        "Parameter 'output_detail' in event NSLA.7"
    ::= { nslaEventObjects7 2 }

nslaEventObjects8 OBJECT-IDENTITY
    STATUS current
    DESCRIPTION
        "Event NSLA.8
        Advisor output change.
        \par The 'output_detail' arg will take one of the following values:
        \par 	- output TRUE
        \par 	- output FALSE"
    ::= { nslaEventsGroup 8 }

nsla8_advisor_id OBJECT-TYPE
    SYNTAX Integer32
    MAX-ACCESS accessible-for-notify
    STATUS current
    DESCRIPTION
        "Parameter 'advisor_id' in event NSLA.8"
    ::= { nslaEventObjects8 1 }

nsla8_output_detail OBJECT-TYPE
    SYNTAX DisplayString
    MAX-ACCESS accessible-for-notify
    STATUS current
    DESCRIPTION
        "Parameter 'output_detail' in event NSLA.8"
    ::= { nslaEventObjects8 2 }


nslaNotification1 NOTIFICATION-TYPE
    OBJECTS { 
              nsla1_event_detail 
            }
    STATUS current
    DESCRIPTION
        "Notification of Event NSLA.1

        Message: 'global $1'

        Parameters list:
              $1: nsla1_event_detail

        Event at global level.
        \par The 'event_detail' arg will take one of the following values:
        \par 	- ioctl failed rsn = out of tasker
        \par 	- ioctl MUTE failed rsn = already MUTED
        \par 	- ioctl MUTE
        \par 	- ioctl UNMUTE failed rsn = not MUTED
        \par 	- ioctl UNMUTE
        \par 	- ioctl DISABLE failed rsn = already DISABLED
        \par 	- ioctl DISABLE
        \par 	- ioctl ENABLE failed rsn = already ENABLED
        \par 	- ioctl ENABLE"
    ::= { nslaNotificationsPrefix 1 }

nslaNotification2 NOTIFICATION-TYPE
    OBJECTS { 
              nsla2_filter_id, 
              nsla2_event_detail 
            }
    STATUS current
    DESCRIPTION
        "Notification of Event NSLA.2

        Message: 'filter/$1 $2'

        Parameters list:
              $1: nsla2_filter_id
              $2: nsla2_event_detail

        Event at filter level.
        \par The 'event_detail' arg will take one of the following values:
        \par 	- creation failed rsn = NSLA disabled
        \par 	- creation failed rsn = ID duplicated
        \par 	- creation bypassed rsn = disabled
        \par 	- creation failed rsn = memory exhaustion
        \par 	- creation failed rsn = unknown filter type
        \par 	- creation failed rsn = unknown NSM parameter
        \par 	- creation failed rsn = NSM registration failed
        \par 	- creation ok
        \par    - client (<upcall> <arg 1> <arg 2>) mutated to zombie		
        \par 	- removal phase <1|2> ok
        \par 	- removal ok
        \par 	- client (<upcall> <arg 1> <arg 2>) registration failed rsn = NULL upcall
        \par 	- client (<upcall> <arg 1> <arg 2>) registration failed rsn = memory exhaustion
        \par 	- client (<upcall> <arg 1> <arg 2>) registration ok
        \par 	- client (<upcall> <arg 1> <arg 2>) zombie reanimation ok		
        \par 	- client (<upcall> <arg 1> <arg 2>) deregistration failed rsn = NULL upcall
        \par 	- client (<upcall> <arg 1> <arg 2>) deregistration ok		
        \par 	- client (<upcall> <arg 1> <arg 2>) deregistration failed rsn = no matching client found
        \par 	- ioctl failed rsn = out of tasker
        \par 	- ioctl failed rsn = not active ID
        \par 	- ioctl ACT failed rsn = already ACT
        \par 	- ioctl ACTIVATE
        \par 	- ioctl DEACT failed rsn = already DEACT
        \par 	- ioctl DEACTIVATE
        \par 	- ioctl REST failed rsn = neither ACT nor DEACT
        \par 	- ioctl RESTORE
        \par 	- ioctl MUTE failed rsn = already MUTED
        \par 	- ioctl MUTE
        \par 	- ioctl UNMUTE failed rsn = not MUTED
        \par 	- ioctl UNMUTE
        \par 	- ioctl DISABLE failed rsn = already DISABLED
        \par 	- ioctl DISABLE
        \par 	- ioctl ENABLE failed rsn = already ENABLED
        \par 	- ioctl ENABLE
        \par 	- ioctl UNKNOWN
        \par 	- client notification bypassed
        \par 	- client notification <TRUE | FALSE>
        \par 	- client (<upcall> <arg 1> <arg 2>) notification overwritten		
        \par 	- act cond detected
        \par 	- act cond removed
        \par 	- deact cond detected
        \par 	- deact cond removed 
        \par 	- act/deact overlap detected
        \par 	- act cond detected
        \par 	- act cond removed"
    ::= { nslaNotificationsPrefix 2 }

nslaNotification3 NOTIFICATION-TYPE
    OBJECTS { 
              nsla3_filter_id, 
              nsla3_event_detail 
            }
    STATUS current
    DESCRIPTION
        "Notification of Event NSLA.3

        Message: 'filter/$1 $2'

        Parameters list:
              $1: nsla3_filter_id
              $2: nsla3_event_detail

        Sample reported to filter.
        \par The 'event_detail' arg will take one of the following values:
        \par 	- sample = <value>
        \par 	- sample = <value> -> ACTIVE
        \par 	- sample = <valor> -> DEACTIVE
        \par 	- sample = timeout
        \par 	- sample = timeout -> ACTIVE"
    ::= { nslaNotificationsPrefix 3 }

nslaNotification4 NOTIFICATION-TYPE
    OBJECTS { 
              nsla4_alarm_id, 
              nsla4_event_detail 
            }
    STATUS current
    DESCRIPTION
        "Notification of Event NSLA.4

        Message: 'alarm/$1 $2'

        Parameters list:
              $1: nsla4_alarm_id
              $2: nsla4_event_detail

        Event at alarm level.
        \par The 'event_detail' arg will take one of the following values:
        \par 	- creation failed rsn = NSLA disabled
        \par 	- creation failed rsn = ID duplicated
        \par 	- creation bypassed rsn = disabled
        \par 	- creation failed rsn = memory exhaustion
        \par 	- creation failed rsn = registration in filter <id> failed
        \par 	- registration in filter <id> ok
        \par 	- creation ok
        \par    - client (<upcall> <arg 1> <arg 2>) mutated to zombie		
        \par 	- removal successful		
        \par 	- client (<upcall> <arg 1> <arg 2>) registration failed rsn = NULL upcall
        \par 	- client (<upcall> <arg 1> <arg 2>) registration failed rsn = memory exhaustion
        \par 	- client (<upcall> <arg 1> <arg 2>) registration ok
        \par 	- client (<upcall> <arg 1> <arg 2>) zombie reanimation ok		
        \par 	- client (<upcall> <arg 1> <arg 2>) deregistration failed rsn = NULL upcall
        \par 	- client (<upcall> <arg 1> <arg 2>) deregistration ok
        \par 	- client (<upcall> <arg 1> <arg 2>) deregistration failed rsn = no matching client found
        \par 	- ioctl failed rsn = out of tasker
        \par 	- ioctl failed rsn = not active ID
        \par 	- ioctl ACT failed rsn = already ACT
        \par 	- ioctl ACTIVATE
        \par 	- ioctl DEACT failed rsn = already DEACT
        \par 	- ioctl DEACTIVATE
        \par 	- ioctl REST failed rsn = neither ACT nor DEACT
        \par 	- ioctl RESTORE
        \par 	- ioctl MUTE failed rsn = already MUTED
        \par 	- ioctl MUTE
        \par 	- ioctl UNMUTE failed rsn = not MUTED
        \par 	- ioctl UNMUTE
        \par 	- ioctl DISABLE failed rsn = already DISABLED
        \par 	- ioctl DISABLE
        \par 	- ioctl ENABLE failed rsn = already ENABLED
        \par 	- ioctl ENABLE
        \par 	- ioctl MNEMONICAL EXP
        \par 	- ioctl ioctl NUMERICAL EXP
        \par 	- ioctl UNKNOWN
        \par 	- notification from filter <id>: <TRUE|FALSE>
        \par 	- filter map change (0x%04x --> 0x%04x)
        \par 	- client notification bypassed
        \par 	- client notification <TRUE|FALSE>
        \par 	- client (<upcall> <arg 1> <arg 2>) notification overwritten"
    ::= { nslaNotificationsPrefix 4 }

nslaNotification5 NOTIFICATION-TYPE
    OBJECTS { 
              nsla5_advisor_id, 
              nsla5_event_detail 
            }
    STATUS current
    DESCRIPTION
        "Notification of Event NSLA.5

        Message: 'advisor/$1 $2'

        Parameters list:
              $1: nsla5_advisor_id
              $2: nsla5_event_detail

        Event at advisor level.
        \par The 'event_detail' arg will take one of the following values:
        \par 	- creation failed rsn = NSLA disabled
        \par 	- creation failed rsn = ID duplicated
        \par 	- creation bypassed rsn = disabled
        \par 	- creation failed rsn = memory exhaustion
        \par 	- creation failed rsn = registration in alarm <id> failed
        \par 	- registration in alarm <id> ok
        \par 	- creation ok
        \par    - client (<upcall> <arg>) mutated to zombie		
        \par 	- removal successful		
        \par 	- client (<upcall> <arg>) registration failed rsn = NULL upcall
        \par 	- client (<upcall> <arg>) registration failed rsn = memory exhaustion
        \par    - client (<upcall> <arg>) registration ok
        \par    - client (<upcall> <arg>) zombie reanimation ok
        \par 	- client (<upcall> <arg>) deregistration failed rsn = NULL upcall
        \par 	- client (<upcall> <arg>) deregistration ok
        \par 	- client (<upcall> <arg>) deregistration failed rsn = no matching client found
        \par 	- ioctl failed rsn = out of tasker
        \par 	- ioctl failed rsn = not active ID
        \par 	- ioctl ACT failed rsn = already ACT
        \par 	- ioctl ACTIVATE
        \par 	- ioctl DEACT failed rsn = already DEACT
        \par 	- ioctl DEACTIVATE
        \par 	- ioctl REST failed rsn = neither ACT nor DEACT
        \par 	- ioctl RESTORE
        \par 	- ioctl MUTE failed rsn = already MUTED
        \par 	- ioctl MUTE
        \par 	- ioctl UNMUTE failed rsn = not MUTED
        \par 	- ioctl UNMUTE
        \par 	- ioctl DISABLE failed rsn = already DISABLED
        \par 	- ioctl DISABLE
        \par 	- ioctl ENABLE failed rsn = already ENABLED
        \par 	- ioctl ENABLE
        \par 	- ioctl MNEMONICAL EXP
        \par 	- ioctl ioctl NUMERICAL EXP
        \par 	- ioctl UNKNOWN
        \par 	- notification from alarm <id>: <TRUE|FALSE>
        \par 	- alarm map change (0x%04x --> 0x%04x)
        \par 	- client notification bypassed
        \par 	- client notification <TRUE|FALSE>
        \par 	- client (<upcall> <arg>) notification overwritten"
    ::= { nslaNotificationsPrefix 5 }

nslaNotification6 NOTIFICATION-TYPE
    OBJECTS { 
              nsla6_filter_id, 
              nsla6_output_detail 
            }
    STATUS current
    DESCRIPTION
        "Notification of Event NSLA.6

        Message: 'filter/$1 $2'

        Parameters list:
              $1: nsla6_filter_id
              $2: nsla6_output_detail

        Filter output change.
        \par The 'output_detail' arg will take one of the following values:
        \par 	- output TRUE
        \par 	- output FALSE"
    ::= { nslaNotificationsPrefix 6 }

nslaNotification7 NOTIFICATION-TYPE
    OBJECTS { 
              nsla7_alarm_id, 
              nsla7_output_detail 
            }
    STATUS current
    DESCRIPTION
        "Notification of Event NSLA.7

        Message: 'alarm/$1 $2'

        Parameters list:
              $1: nsla7_alarm_id
              $2: nsla7_output_detail

        Alarm output change.
        \par The 'output_detail' arg will take one of the following values:
        \par 	- output TRUE
        \par 	- output FALSE"
    ::= { nslaNotificationsPrefix 7 }

nslaNotification8 NOTIFICATION-TYPE
    OBJECTS { 
              nsla8_advisor_id, 
              nsla8_output_detail 
            }
    STATUS current
    DESCRIPTION
        "Notification of Event NSLA.8

        Message: 'advisor/$1 $2'

        Parameters list:
              $1: nsla8_advisor_id
              $2: nsla8_output_detail

        Advisor output change.
        \par The 'output_detail' arg will take one of the following values:
        \par 	- output TRUE
        \par 	- output FALSE"
    ::= { nslaNotificationsPrefix 8 }


END
