--MibName=rcLldpPrivate
RAISECOM-LLDP-PRI-MIB DEFINITIONS ::= BEGIN 
   
IMPORTS         
      MODULE-IDENTITY, OBJECT-TYPE, NOTIFICATION-TYPE
        									FROM SNMPv2-SMI
      	TruthValue				FROM SNMPv2-TC 
        InterfaceIndex   	  FROM IF-MIB
        iscomSwitch       FROM RAISECOM-BASE-MIB   
        MacAddress     FROM SNMPv2-TC;     -- [RFC2579]

rcLldp 			 OBJECT IDENTIFIER ::= { iscomSwitch 57 }

rcLldpPrivate MODULE-IDENTITY 
        LAST-UPDATED "201001040000Z"  -- Jan 4,2010"
        ORGANIZATION 
          "raisecom"
        CONTACT-INFO 
          "          "
        DESCRIPTION
          "The MIB module for private canfiguration of lldp."
   
        REVISION    "201001040000Z"  -- Jan 4, 2010"
        DESCRIPTION ""
     
         ::= { rcLldp 2 }
      
      -- 
      -- Sections of the raisecom LLDP MIB
      --

rcLldpConfig 			   OBJECT IDENTIFIER ::= { rcLldpPrivate 1 }
rcLldpPortConfig		 OBJECT IDENTIFIER ::= { rcLldpPrivate 2 }

        
-- ***************************************************************
--
-- private LLDP objectes group
--


rcLldpEnable OBJECT-TYPE
    SYNTAX      TruthValue
    MAX-ACCESS  read-write
    STATUS      current
    DESCRIPTION
            "The vlalue indicats that LLDP is valid when it is set TRUE.
            The default value is FALSE."
    DEFVAL     { FALSE }
    ::= { rcLldpConfig 1 }

rcLldpNotificationEnable OBJECT-TYPE
    SYNTAX      TruthValue
    MAX-ACCESS  read-write
    STATUS      current
    DESCRIPTION
            "The vlalue indicats whether LLDP trap can be sent to SNMP when 
            some events occurs.The 'TRUE'value indicats trap 
            can execute,or cannot execute."
    DEFVAL     { TRUE }
    ::= { rcLldpConfig 2 }

rcLldpClearGlobalStatistic OBJECT-TYPE
    SYNTAX      TruthValue
    MAX-ACCESS  read-write
    STATUS      current
    DESCRIPTION
            "Clear global statistic information."
    DEFVAL     { FALSE }
    ::= { rcLldpConfig 3 }
             
rcLldpPortConfigTable OBJECT-TYPE
	SYNTAX      SEQUENCE OF rcLldpPortConfigEntry
	MAX-ACCESS  not-accessible
	STATUS      current
	DESCRIPTION 
	  "A table of LLDP port configuration. "   
	::= { rcLldpPortConfig 1 }

rcLldpPortConfigEntry OBJECT-TYPE
	SYNTAX     rcLldpPortConfigEntry
	MAX-ACCESS not-accessible
	STATUS     current
	DESCRIPTION 
	  "Table entry for LLDP port configuration."
	INDEX       { rcLldpPortIndex }
	::= { rcLldpPortConfigTable 1 }

rcLldpPortConfigEntry ::=
	SEQUENCE { 
	  rcLldpPortIndex	        InterfaceIndex,
	  rcLldpPortEnable			TruthValue,
	  rcLldpPortClearStatistic TruthValue,
	  rcLldpPortClearRemTablesEntries TruthValue,
	  rcLldpPortDestAddress MacAddress
}
rcLldpPortIndex        OBJECT-TYPE
	SYNTAX      InterfaceIndex
    MAX-ACCESS  not-accessible
    STATUS      current
    DESCRIPTION
            "This object represents the  Bridge Port" 
	::= { rcLldpPortConfigEntry 1 }
      
rcLldpPortEnable OBJECT-TYPE
	SYNTAX      TruthValue
	MAX-ACCESS  read-write
	STATUS      current
	DESCRIPTION 
	  "Enable or disable port lldp function." 
	DEFVAL     { TRUE }
	 ::= { rcLldpPortConfigEntry 2 }

rcLldpPortClearStatistic OBJECT-TYPE
	SYNTAX      TruthValue
	MAX-ACCESS  read-write
	STATUS      current
	DESCRIPTION 
	  "Clear port statistic information." 
	DEFVAL     { FALSE }
	 ::= { rcLldpPortConfigEntry 3 }
	 
rcLldpPortClearRemTablesEntries OBJECT-TYPE
	SYNTAX      TruthValue
	MAX-ACCESS  read-write
	STATUS      current
	DESCRIPTION 
	  "Clear port remote information."
	DEFVAL     { FALSE }
	 ::= { rcLldpPortConfigEntry 4 }
	 
rcLldpPortDestAddress OBJECT-TYPE
	SYNTAX      MacAddress
	MAX-ACCESS  read-write
	STATUS      current
	DESCRIPTION 
	  "Dest mac address of LLDPDU."
	 ::= { rcLldpPortConfigEntry 5 }	
END
