IBM-SYSTEM-NETWORK-MIB DEFINITIONS ::= BEGIN

IMPORTS
   OBJECT-TYPE
        FROM RFC-1212

   TRAP-TYPE
        FROM RFC-1215

   ibmSystemNetwork,
   Boolean, Uint8, Sint8, Uint16, Sint16, Uint32,
   Sint32, Uint64, Sint64, Real32, Real64, String, Datetime
      FROM IBM-SYSTEM-MIB;
      

--
-- Primitive types
--
Boolean  ::= INTEGER (0..1)
Uint8    ::= INTEGER (0..255)
Sint8    ::= INTEGER (-128..127)
Uint16   ::= INTEGER (0..65535)
Sint16   ::= INTEGER (-32767..32766)
Uint32   ::= INTEGER (0..4294967295)
Sint32   ::= INTEGER (-2147483647..2147483646)
Uint64   ::= OCTET STRING
Sint64   ::= OCTET STRING
Real32   ::= INTEGER (-1..1)
Real64   ::= INTEGER (-1..1)
String   ::= OCTET STRING
Datetime ::= OCTET STRING

ibmSystemLogicalNetworkAdapterTable OBJECT-TYPE
   SYNTAX          SEQUENCE OF IbmSystemLogicalNetworkAdapterEntry
   ACCESS          not-accessible
   STATUS          mandatory
   DESCRIPTION     "A table of logical network adapter entries."
   REFERENCE       "IBMPSG_LogicalNetworkAdapter"
::= { ibmSystemNetwork 1 }

ibmSystemLogicalNetworkAdapterEntry OBJECT-TYPE
   SYNTAX          IbmSystemLogicalNetworkAdapterEntry
   ACCESS          not-accessible
   STATUS          mandatory
   DESCRIPTION     "This class defines an entry for each IBMPSG_LogicalNetworkAdapter
                    instance. Each instance of the IBMPSG_LogicalNetworkAdapter class 
                    contains status and descriptive information for each logical network 
                    adapter recognized by the operating system."
   INDEX           { ibmSystemLogicalNetworkAdapterKeyIndex }
::= { ibmSystemLogicalNetworkAdapterTable 1 }

IbmSystemLogicalNetworkAdapterEntry ::= SEQUENCE
{
   ibmSystemLogicalNetworkAdapterKeyIndex String,
   ibmSystemLogicalNetworkAdapterName String,
   ibmSystemLogicalNetworkAdapterDescription String,
   ibmSystemLogicalNetworkAdapterDeviceID String,
   ibmSystemLogicalNetworkAdapterOctetsReceived Uint64,
   ibmSystemLogicalNetworkAdapterOctetsTransmitted Uint64,
   ibmSystemLogicalNetworkAdapterPermanentAddress String,
   ibmSystemLogicalNetworkAdapterSpeed Uint64,
   ibmSystemLogicalNetworkAdapterStatus String
}

ibmSystemLogicalNetworkAdapterKeyIndex OBJECT-TYPE
   SYNTAX          String
   ACCESS          read-write
   STATUS          mandatory
   DESCRIPTION     "Index of specific Logical Network Adapter instance in table of instances."
   REFERENCE       "IBMPSG_LogicalNetworkAdapter.KeyIndex"
::= { ibmSystemLogicalNetworkAdapterEntry 1 }
      
ibmSystemLogicalNetworkAdapterName OBJECT-TYPE
   SYNTAX          String
   ACCESS          read-write
   STATUS          mandatory
   DESCRIPTION     "Label for this device."
   REFERENCE       "IBMPSG_LogicalNetworkAdapter.Name"
::= { ibmSystemLogicalNetworkAdapterEntry 2 }

ibmSystemLogicalNetworkAdapterDescription OBJECT-TYPE
   SYNTAX          String
   ACCESS          read-write
   STATUS          mandatory
   DESCRIPTION     "Product name of adapter."
   REFERENCE       "IBMPSG_LogicalNetworkAdapter.Description"
::= { ibmSystemLogicalNetworkAdapterEntry 3 }

ibmSystemLogicalNetworkAdapterDeviceID OBJECT-TYPE
   SYNTAX          String
   ACCESS          read-write
   STATUS          mandatory
   DESCRIPTION     "ID used by management agent to discern different instances of Networks."
   REFERENCE       "IBMPSG_LogicalNetworkAdapter.DeviceID"
::= { ibmSystemLogicalNetworkAdapterEntry 4 }

ibmSystemLogicalNetworkAdapterOctetsReceived OBJECT-TYPE
   SYNTAX          Uint64
   ACCESS          read-write
   STATUS          mandatory
   DESCRIPTION     "Number of octets received by adapter in current session."
   REFERENCE       "IBMPSG_LogicalNetworkAdapter.OctetsReceived"
::= { ibmSystemLogicalNetworkAdapterEntry 5 }

ibmSystemLogicalNetworkAdapterOctetsTransmitted OBJECT-TYPE
   SYNTAX          Uint64
   ACCESS          read-write
   STATUS          mandatory
   DESCRIPTION     "Number of octets transmitted by adapter in current session."
   REFERENCE       "IBMPSG_LogicalNetworkAdapter.OctetsTransmitted"
::= { ibmSystemLogicalNetworkAdapterEntry 6 }

ibmSystemLogicalNetworkAdapterPermanentAddress OBJECT-TYPE
   SYNTAX          String
   ACCESS          read-write
   STATUS          mandatory
   DESCRIPTION     "The permanent address of the network adapter."
   REFERENCE       "IBMPSG_LogicalNetworkAdapter.PermanentAddress"
::= { ibmSystemLogicalNetworkAdapterEntry 7 }

ibmSystemLogicalNetworkAdapterSpeed OBJECT-TYPE
   SYNTAX          Uint64
   ACCESS          read-write
   STATUS          mandatory
   DESCRIPTION     "The speed of the adapter in megabytes per second."
   REFERENCE       "IBMPSG_LogicalNetworkAdapter.Speed"
::= { ibmSystemLogicalNetworkAdapterEntry 8 }

ibmSystemLogicalNetworkAdapterStatus OBJECT-TYPE
   SYNTAX          String
   ACCESS          read-write
   STATUS          mandatory
   DESCRIPTION     "The online status of the adapter."
   REFERENCE       "IBMPSG_LogicalNetworkAdapter.Status"
::= { ibmSystemLogicalNetworkAdapterEntry 9 }

ibmSystemPhysicalNetworkAdapterTable OBJECT-TYPE
   SYNTAX          SEQUENCE OF IbmSystemPhysicalNetworkAdapterEntry
   ACCESS          not-accessible
   STATUS          mandatory
   DESCRIPTION     "A table of physical network adapter entries."
   REFERENCE       "IBMPSG_PhysicalNetworkAdapter"
::= { ibmSystemNetwork 2 }

ibmSystemPhysicalNetworkAdapterEntry OBJECT-TYPE
   SYNTAX          IbmSystemPhysicalNetworkAdapterEntry
   ACCESS          not-accessible
   STATUS          mandatory
   DESCRIPTION     "This class defines an entry for each IBMPSG_PhysicalNetworkAdapter
                    instance. Each instance of the IBMPSG_PhysicalNetworkAdapter class 
                    contains status and descriptive information for each physical network 
                    adapter recognized by the operating system."
   INDEX           { ibmSystemPhysicalNetworkAdapterKeyIndex }
::= { ibmSystemPhysicalNetworkAdapterTable 1 }

IbmSystemPhysicalNetworkAdapterEntry ::= SEQUENCE
{
   ibmSystemPhysicalNetworkAdapterKeyIndex String,
   ibmSystemPhysicalNetworkAdapterName String,
   ibmSystemPhysicalNetworkAdapterDescription String,
   ibmSystemPhysicalNetworkAdapterVersion String,
   ibmSystemPhysicalNetworkAdapterRemovable Boolean,
   ibmSystemPhysicalNetworkAdapterReplaceable Boolean,
   ibmSystemPhysicalNetworkAdapterHotSwappable Boolean,
   ibmSystemPhysicalNetworkAdapterHostingBoard Boolean,
   ibmSystemPhysicalNetworkAdapterRequiresDaughterBoard Boolean,
   ibmSystemPhysicalNetworkAdapterStatus String
}

ibmSystemPhysicalNetworkAdapterKeyIndex OBJECT-TYPE
   SYNTAX          String
   ACCESS          read-write
   STATUS          mandatory
   DESCRIPTION     "Index of specific Physical Network Adapter instance in table of instances."
   REFERENCE       "IBMPSG_PhysicalNetworkAdapter.KeyIndex"
::= { ibmSystemPhysicalNetworkAdapterEntry 1 }
      
ibmSystemPhysicalNetworkAdapterName OBJECT-TYPE
   SYNTAX          String
   ACCESS          read-write
   STATUS          mandatory
   DESCRIPTION     "Label for this device."
   REFERENCE       "IBMPSG_PhysicalNetworkAdapter.Name"
::= { ibmSystemPhysicalNetworkAdapterEntry 2 }

ibmSystemPhysicalNetworkAdapterDescription OBJECT-TYPE
   SYNTAX          String
   ACCESS          read-write
   STATUS          mandatory
   DESCRIPTION     "Product name of adapter."
   REFERENCE       "IBMPSG_PhysicalNetworkAdapter.Description"
::= { ibmSystemPhysicalNetworkAdapterEntry 3 }

ibmSystemPhysicalNetworkAdapterVersion OBJECT-TYPE
   SYNTAX          String
   ACCESS          read-write
   STATUS          mandatory
   DESCRIPTION     "Version of Network."
   REFERENCE       "IBMPSG_PhysicalNetworkAdapter.Version"
::= { ibmSystemPhysicalNetworkAdapterEntry 4 }

ibmSystemPhysicalNetworkAdapterRemovable OBJECT-TYPE
   SYNTAX          Boolean
   ACCESS          read-write
   STATUS          mandatory
   DESCRIPTION     "Value indicates whether or not adapter is removable from system."
   REFERENCE       "IBMPSG_PhysicalNetworkAdapter.Removable"
::= { ibmSystemPhysicalNetworkAdapterEntry 5 }

ibmSystemPhysicalNetworkAdapterReplaceable OBJECT-TYPE
   SYNTAX          Boolean
   ACCESS          read-write
   STATUS          mandatory
   DESCRIPTION     "Value indicates whether or not adapter is replaceable in system."
   REFERENCE       "IBMPSG_PhysicalNetworkAdapter.OctetsTransmitted"
::= { ibmSystemPhysicalNetworkAdapterEntry 6 }

ibmSystemPhysicalNetworkAdapterHotSwappable OBJECT-TYPE
   SYNTAX          Boolean
   ACCESS          read-write
   STATUS          mandatory
   DESCRIPTION     "Value indicates whether or not adapter is hot-swappable."
   REFERENCE       "IBMPSG_PhysicalNetworkAdapter.HotSwappable"
::= { ibmSystemPhysicalNetworkAdapterEntry 7 }

ibmSystemPhysicalNetworkAdapterHostingBoard OBJECT-TYPE
   SYNTAX          Boolean
   ACCESS          read-write
   STATUS          mandatory
   DESCRIPTION     "Value indicates whether or not adapter requires a hosting board."
   REFERENCE       "IBMPSG_PhysicalNetworkAdapter.HostingBoard"
::= { ibmSystemPhysicalNetworkAdapterEntry 8 }

ibmSystemPhysicalNetworkAdapterRequiresDaughterBoard OBJECT-TYPE
   SYNTAX          Boolean
   ACCESS          read-write
   STATUS          mandatory
   DESCRIPTION     "Value indicates whether or not adapter resides on a daughterboard."
   REFERENCE       "IBMPSG_PhysicalNetworkAdapter.RequiresDaughterBoard"
::= { ibmSystemPhysicalNetworkAdapterEntry 9 }

ibmSystemPhysicalNetworkAdapterStatus OBJECT-TYPE
   SYNTAX          String
   ACCESS          read-write
   STATUS          mandatory
   DESCRIPTION     "The online status of the adapter."
   REFERENCE       "IBMPSG_PhysicalNetworkAdapter.Status"
::= { ibmSystemPhysicalNetworkAdapterEntry 10 }

END
