-- Teldat, S.A.

                -- Parque Tecnolgico de Madrid

                -- 28760, Tres Cantos (Madrid)

                -- Tlf: +34-918076565

                -- Fax: +34-918076521

                -- e-mail: id@teldat.com


            -- MIB privada de Teldat

            -- Monitorizacin de GW IEC104/101.


    -- Historial:
    --      07/02/14    M.A. Pastor     XH 3523. Errors with HP Openview 9.20
    -- 1.2  11-01-13    E. Amorena      XH 2610. MIBs compilation.
    -- 1.1  03/01/13  F. Hernandez     XH 2610. Compilation error
    -- 1.0  09/04/11  Benjamin G.      Implementacin inicial
    --------------------------------------------------------------------------

TELDAT-MON-PROTOCOL-GW104-MIB DEFINITIONS ::= BEGIN

    IMPORTS
            IpAddress
        FROM RFC1155-SMI
            OBJECT-TYPE
        FROM RFC-1212
            DisplayString
        FROM RFC1213-MIB
            telProdNpMonProtocols
        FROM TELDAT-SW-STRUCTURE-MIB;


    telProdNpMonProtGW104   OBJECT IDENTIFIER ::= { telProdNpMonProtocols 14 }


--  = = = = = = = = = = = = = = = = = = = = = = = = = = = = = = = = = = = = = =
--  Global Info GW104 monitoring variables
--  = = = = = = = = = = = = = = = = = = = = = = = = = = = = = = = = = = = = = =

telProdNpMonProtGW104Global OBJECT IDENTIFIER ::= { telProdNpMonProtGW104 1 }

telProdNpMonProtGW104GlobalStatus OBJECT-TYPE
    SYNTAX INTEGER{
        disabled(0),
        enabled(1)
        }
    ACCESS read-only
    STATUS mandatory
    DESCRIPTION
    "It indicates if Gateway IEC-104 to IEC-101 is running."
    ::= { telProdNpMonProtGW104Global 1 }

telProdNpMonProtGW104GlobalOpenSes OBJECT-TYPE
    SYNTAX INTEGER
    ACCESS read-only
    STATUS mandatory
    DESCRIPTION
    "Current number of open TCP sessions ."
    ::= { telProdNpMonProtGW104Global 2 }

telProdNpMonProtGW104GlobalRemClose OBJECT-TYPE
    SYNTAX INTEGER
    ACCESS read-only
    STATUS mandatory
    DESCRIPTION
    "Number of TCP sessions closed by remote end (Control Center), for all IEC104 agents."
    ::= { telProdNpMonProtGW104Global 3 }

telProdNpMonProtGW104GlobalLocClose OBJECT-TYPE
    SYNTAX INTEGER
    ACCESS read-only
    STATUS mandatory
    DESCRIPTION
    "Number of TCP sessions closed by local end (GW104/101)."
    ::= { telProdNpMonProtGW104Global 4 }

telProdNpMonProtGW104GlobalRxBytes OBJECT-TYPE
    SYNTAX INTEGER
    ACCESS read-only
    STATUS mandatory
    DESCRIPTION
    "Number of data bytes received from all Control Centers."
    ::= { telProdNpMonProtGW104Global 5 }

telProdNpMonProtGW104GlobalRxPkts OBJECT-TYPE
    SYNTAX INTEGER
    ACCESS read-only
    STATUS mandatory
    DESCRIPTION
    "Number of valid data packets IEC-104 received from all Control Centers."
    ::= { telProdNpMonProtGW104Global 6 }

telProdNpMonProtGW104GlobalTxBytes OBJECT-TYPE
    SYNTAX INTEGER
    ACCESS read-only
    STATUS mandatory
    DESCRIPTION
    "Number of data bytes sent to all Control Centers."
    ::= { telProdNpMonProtGW104Global 7 }

telProdNpMonProtGW104GlobalTxPkts OBJECT-TYPE
    SYNTAX INTEGER
    ACCESS read-only
    STATUS mandatory
    DESCRIPTION
    "Number of data packets IEC-104 sent to all Control Centers."
    ::= { telProdNpMonProtGW104Global 8 }


--  = = = = = = = = = = = = = = = = = = = = = = = = = = = = = = = = = = = = = =
--  Agents IEC-104 monitoring variables
--  = = = = = = = = = = = = = = = = = = = = = = = = = = = = = = = = = = = = = =

telProdNpMonProtGW104AgentObject   OBJECT IDENTIFIER ::= { telProdNpMonProtGW104 2 }

--  - - - - - - - - - - - - - - - - - - - - - - - - - - - - - - - - - - - - - -
--  Agents IEC-104 monitoring global variables
--  - - - - - - - - - - - - - - - - - - - - - - - - - - - - - - - - - - - - - -

telProdNpMonProtGW104AgentInfoTable OBJECT-TYPE
    SYNTAX  SEQUENCE OF TelProdNpMonProtGW104AgentInfoEntry
    ACCESS  not-accessible
    STATUS  mandatory
    DESCRIPTION
        "Table of information available for IEC-104 Agents involved in GW.
         Each row represents an agent"
    ::= { telProdNpMonProtGW104AgentObject 1 }

telProdNpMonProtGW104AgentInfoEntry OBJECT-TYPE
    SYNTAX  TelProdNpMonProtGW104AgentInfoEntry
    ACCESS  not-accessible
    STATUS  mandatory
    DESCRIPTION
        "A base list of objects that are information about an IEC-104 agent."
    INDEX   { telProdNpMonProtGW104AgentInfoIndex }
    ::= { telProdNpMonProtGW104AgentInfoTable 1 }

TelProdNpMonProtGW104AgentInfoEntry ::= SEQUENCE
{
    telProdNpMonProtGW104AgentInfoIndex             INTEGER,
    telProdNpMonProtGW104AgentInfoName              DisplayString,
    telProdNpMonProtGW104AgentInfoRxBytes           INTEGER,
    telProdNpMonProtGW104AgentInfoRxPkts            INTEGER,
    telProdNpMonProtGW104AgentInfoTxBytes           INTEGER,
    telProdNpMonProtGW104AgentInfoTxPkts            INTEGER,
    telProdNpMonProtGW104AgentInfoTxCongestion      INTEGER,
    telProdNpMonProtGW104AgentInfoTxQueue           INTEGER,
    telProdNpMonProtGW104AgentInfoQueueDiscart      INTEGER,
    telProdNpMonProtGW104AgentInfoOpenSes           INTEGER,
    telProdNpMonProtGW104AgentInfoMaxOpenSes        INTEGER,
    telProdNpMonProtGW104AgentInfoOpenedSes         INTEGER,
    telProdNpMonProtGW104AgentInfoRemClose          INTEGER,
    telProdNpMonProtGW104AgentInfoLocalClose        INTEGER
}

telProdNpMonProtGW104AgentInfoIndex OBJECT-TYPE
    SYNTAX  INTEGER
    ACCESS  read-only
    STATUS  mandatory
    DESCRIPTION
        "IEC104 Agent index."
    ::= { telProdNpMonProtGW104AgentInfoEntry 1 }

telProdNpMonProtGW104AgentInfoName OBJECT-TYPE
    SYNTAX  DisplayString
    ACCESS  read-only
    STATUS  mandatory
    DESCRIPTION
        "IEC104 Agent name."
    ::= { telProdNpMonProtGW104AgentInfoEntry 2 }

telProdNpMonProtGW104AgentInfoRxBytes OBJECT-TYPE
    SYNTAX INTEGER
    ACCESS read-only
    STATUS mandatory
    DESCRIPTION
        "Number of data bytes received on IEC-104 agent."
    ::= { telProdNpMonProtGW104AgentInfoEntry 3 }

telProdNpMonProtGW104AgentInfoRxPkts OBJECT-TYPE
    SYNTAX INTEGER
    ACCESS read-only
    STATUS mandatory
    DESCRIPTION
        "Number of valid pakets received on IEC-104 agent."
    ::= { telProdNpMonProtGW104AgentInfoEntry 4 }

telProdNpMonProtGW104AgentInfoTxBytes OBJECT-TYPE
    SYNTAX INTEGER
    ACCESS read-only
    STATUS mandatory
    DESCRIPTION
        "Number of data bytes sent to associated Control Center."
    ::= { telProdNpMonProtGW104AgentInfoEntry 5 }

telProdNpMonProtGW104AgentInfoTxPkts OBJECT-TYPE
    SYNTAX INTEGER
    ACCESS read-only
    STATUS mandatory
    DESCRIPTION
        "Number of pakets sent to associated Control Center."
    ::= { telProdNpMonProtGW104AgentInfoEntry 6 }

telProdNpMonProtGW104AgentInfoTxCongestion OBJECT-TYPE
    SYNTAX INTEGER
    ACCESS read-only
    STATUS mandatory
    DESCRIPTION
        "Number of packets discarded due to transmission congestion to
         associated Control Center."
    ::= { telProdNpMonProtGW104AgentInfoEntry 7 }

telProdNpMonProtGW104AgentInfoTxQueue OBJECT-TYPE
    SYNTAX INTEGER
    ACCESS read-only
    STATUS mandatory
    DESCRIPTION
        "Number of messages queued, received from RTU's, pending to send to
         associated Control Center."
    ::= { telProdNpMonProtGW104AgentInfoEntry 8 }

telProdNpMonProtGW104AgentInfoQueueDiscart OBJECT-TYPE
    SYNTAX INTEGER
    ACCESS read-only
    STATUS mandatory
    DESCRIPTION
        "Number of messages, received from RTU's, discarted due messages's
         queue overflow."
    ::= { telProdNpMonProtGW104AgentInfoEntry 9 }

telProdNpMonProtGW104AgentInfoOpenSes OBJECT-TYPE
    SYNTAX INTEGER
    ACCESS read-only
    STATUS mandatory
    DESCRIPTION
    "Current number of open TCP sessions for IEC-104 agent."
    ::= { telProdNpMonProtGW104AgentInfoEntry 10 }

telProdNpMonProtGW104AgentInfoMaxOpenSes OBJECT-TYPE
    SYNTAX INTEGER
    ACCESS read-only
    STATUS mandatory
    DESCRIPTION
    "Number of max simultaneous open TCP sessions for IEC-104 agent."
    ::= { telProdNpMonProtGW104AgentInfoEntry 11 }

telProdNpMonProtGW104AgentInfoOpenedSes OBJECT-TYPE
    SYNTAX INTEGER
    ACCESS read-only
    STATUS mandatory
    DESCRIPTION
    "Number of opened TCP sessions for IEC-104 agent."
    ::= { telProdNpMonProtGW104AgentInfoEntry 12 }

telProdNpMonProtGW104AgentInfoRemClose OBJECT-TYPE
    SYNTAX INTEGER
    ACCESS read-only
    STATUS mandatory
    DESCRIPTION
    "Number of TCP sessions closed by remote end (Control Center),
     for IEC-104 agent."
    ::= { telProdNpMonProtGW104AgentInfoEntry 13 }

telProdNpMonProtGW104AgentInfoLocalClose OBJECT-TYPE
    SYNTAX INTEGER
    ACCESS read-only
    STATUS mandatory
    DESCRIPTION
    "Number of TCP sessions closed by local end (IEC-104 agent)."
    ::= { telProdNpMonProtGW104AgentInfoEntry 14 }


--  - - - - - - - - - - - - - - - - - - - - - - - - - - - - - - - - - - - - - -
--  TCP session for Agents IEC-104 monitoring variables
--  - - - - - - - - - - - - - - - - - - - - - - - - - - - - - - - - - - - - - -

telProdNpMonProtGW104AgentTcpTable OBJECT-TYPE
    SYNTAX  SEQUENCE OF TelProdNpMonProtGW104AgentTcpEntry
    ACCESS  not-accessible
    STATUS  mandatory
    DESCRIPTION
        "Table of TCP sessions monitoring information for IEC104 agent."
    ::= { telProdNpMonProtGW104AgentObject 2 }

telProdNpMonProtGW104AgentTcpEntry OBJECT-TYPE
    SYNTAX  TelProdNpMonProtGW104AgentTcpEntry
    ACCESS  not-accessible
    STATUS  mandatory
    DESCRIPTION
        "Each entry contains TCP session info for IEC104 agent, which value is
        the first table index, and it contains all possible TCP sessions info
        for that IEC-104 agent. The second table index indicates the order
        number of that TCP session inside that IEC-104 agent."
    INDEX   { telProdNpMonProtGW104AgentTcpAgentIndex, telProdNpMonProtGW104AgentTcpSessIndex}
    ::= { telProdNpMonProtGW104AgentTcpTable 1 }

TelProdNpMonProtGW104AgentTcpEntry ::= SEQUENCE
{
    telProdNpMonProtGW104AgentTcpAgentIndex     INTEGER,
    telProdNpMonProtGW104AgentTcpSessIndex      INTEGER,
    telProdNpMonProtGW104AgentTcpAgentName      DisplayString,
    telProdNpMonProtGW104AgentTcpState          DisplayString,
    telProdNpMonProtGW104AgentTcpRemIpAddr      IpAddress,
    telProdNpMonProtGW104AgentTcpRemPort        INTEGER,
    telProdNpMonProtGW104AgentTcpOpenTime       DisplayString,
    telProdNpMonProtGW104AgentTcp104Level       INTEGER,
    telProdNpMonProtGW104AgentTcpRxBytes        INTEGER,
    telProdNpMonProtGW104AgentTcpRxPkts         INTEGER,
    telProdNpMonProtGW104AgentTcpTxBytes        INTEGER,
    telProdNpMonProtGW104AgentTcpTxPkts         INTEGER,
    telProdNpMonProtGW104AgentTcpTxCongestion   INTEGER
}

telProdNpMonProtGW104AgentTcpAgentIndex OBJECT-TYPE
    SYNTAX  INTEGER
    ACCESS  read-only
    STATUS  mandatory
    DESCRIPTION
        "First table index: Index of IEC-104 agent that owns that entry TCP session."
    ::={ telProdNpMonProtGW104AgentTcpEntry 1 }

telProdNpMonProtGW104AgentTcpSessIndex OBJECT-TYPE
    SYNTAX  INTEGER
    ACCESS  read-only
    STATUS  mandatory
    DESCRIPTION
        "Second table index: order number of the RTU inside the list of
        configured interfaces for that interfa determined by the first index."
    ::={ telProdNpMonProtGW104AgentTcpEntry 2 }

telProdNpMonProtGW104AgentTcpAgentName OBJECT-TYPE
    SYNTAX  DisplayString
    ACCESS  read-only
    STATUS  mandatory
    DESCRIPTION
        "IEC-104 Agent name."
    ::={ telProdNpMonProtGW104AgentTcpEntry 3 }

telProdNpMonProtGW104AgentTcpState OBJECT-TYPE
    SYNTAX  DisplayString
    ACCESS  read-only
    STATUS  mandatory
    DESCRIPTION
        "TCP session state"
    ::={ telProdNpMonProtGW104AgentTcpEntry 4 }

telProdNpMonProtGW104AgentTcpRemIpAddr OBJECT-TYPE
    SYNTAX  IpAddress
    ACCESS  read-only
    STATUS  mandatory
    DESCRIPTION
        "TCP session remote IP address (Control Center)"
    ::={ telProdNpMonProtGW104AgentTcpEntry 5 }

telProdNpMonProtGW104AgentTcpRemPort OBJECT-TYPE
    SYNTAX  INTEGER
    ACCESS  read-only
    STATUS  mandatory
    DESCRIPTION
        "TCP Session remote port(Control Center)"
    ::={ telProdNpMonProtGW104AgentTcpEntry 6 }

telProdNpMonProtGW104AgentTcpOpenTime OBJECT-TYPE
    SYNTAX  DisplayString
    ACCESS  read-only
    STATUS  mandatory
    DESCRIPTION
        "Time it opens the TCP session"
    ::={ telProdNpMonProtGW104AgentTcpEntry 7 }

telProdNpMonProtGW104AgentTcp104Level OBJECT-TYPE
    SYNTAX  INTEGER{
        stopped(0),
        started(1)
        }
    ACCESS  read-only
    STATUS  mandatory
    DESCRIPTION
        "Status of IEC-104 protocol for TCP session"
    ::={ telProdNpMonProtGW104AgentTcpEntry 8 }

telProdNpMonProtGW104AgentTcpRxBytes OBJECT-TYPE
    SYNTAX INTEGER
    ACCESS read-only
    STATUS mandatory
    DESCRIPTION
        "Number of data bytes received on TCP session."
    ::= { telProdNpMonProtGW104AgentTcpEntry 9 }

telProdNpMonProtGW104AgentTcpRxPkts OBJECT-TYPE
    SYNTAX INTEGER
    ACCESS read-only
    STATUS mandatory
    DESCRIPTION
        "Number of valid pakets received on TCP session."
    ::= { telProdNpMonProtGW104AgentTcpEntry 10 }

telProdNpMonProtGW104AgentTcpTxBytes OBJECT-TYPE
    SYNTAX INTEGER
    ACCESS read-only
    STATUS mandatory
    DESCRIPTION
        "Number of data bytes sent by TCP session to
         associated Control Center."
    ::= { telProdNpMonProtGW104AgentTcpEntry 11 }

telProdNpMonProtGW104AgentTcpTxPkts OBJECT-TYPE
    SYNTAX INTEGER
    ACCESS read-only
    STATUS mandatory
    DESCRIPTION
        "Number of pakets sent by TCP session to
         associated Control Center."
    ::= { telProdNpMonProtGW104AgentTcpEntry 12 }

telProdNpMonProtGW104AgentTcpTxCongestion OBJECT-TYPE
    SYNTAX INTEGER
    ACCESS read-only
    STATUS mandatory
    DESCRIPTION
        "Number of packets discarded due to transmission congestion by TCP
        session to associated Control Center."
    ::= { telProdNpMonProtGW104AgentTcpEntry 13 }

END
