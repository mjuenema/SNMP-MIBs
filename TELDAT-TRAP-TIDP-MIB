-- file automatically created


TELDAT-TRAP-TIDP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


tidpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the TIDP event subsystem."
    REVISION "201401200930Z"
    DESCRIPTION "Initial implementation"
        ::= { telEventTraps 197 }


tidpEventsGroup	OBJECT IDENTIFIER	::= { tidpTrapsMIB 1 }

tidpNotifications	OBJECT IDENTIFIER	::= { tidpTrapsMIB 2 }
tidpNotificationsPrefix	OBJECT IDENTIFIER	::= { tidpNotifications 0 }

tidpEventObjects1 OBJECT-IDENTITY
    STATUS current
    DESCRIPTION
        "Event TIDP.1
        Sending Notification Message"
    ::= { tidpEventsGroup 1 }

tidp1_ipdestination OBJECT-TYPE
    SYNTAX IpAddress
    MAX-ACCESS accessible-for-notify
    STATUS current
    DESCRIPTION
        "Parameter 'ipdestination' in event TIDP.1"
    ::= { tidpEventObjects1 1 }

tidp1_hostname OBJECT-TYPE
    SYNTAX DisplayString
    MAX-ACCESS accessible-for-notify
    STATUS current
    DESCRIPTION
        "Parameter 'hostname' in event TIDP.1"
    ::= { tidpEventObjects1 2 }

tidp1_serialnumber OBJECT-TYPE
    SYNTAX DisplayString
    MAX-ACCESS accessible-for-notify
    STATUS current
    DESCRIPTION
        "Parameter 'serialnumber' in event TIDP.1"
    ::= { tidpEventObjects1 3 }

tidp1_code OBJECT-TYPE
    SYNTAX Integer32
    MAX-ACCESS accessible-for-notify
    STATUS current
    DESCRIPTION
        "Parameter 'code' in event TIDP.1"
    ::= { tidpEventObjects1 4 }

tidp1_sequencenumber OBJECT-TYPE
    SYNTAX Integer32
    MAX-ACCESS accessible-for-notify
    STATUS current
    DESCRIPTION
        "Parameter 'sequencenumber' in event TIDP.1"
    ::= { tidpEventObjects1 5 }

tidp1_ack_rvd OBJECT-TYPE
    SYNTAX DisplayString
    MAX-ACCESS accessible-for-notify
    STATUS current
    DESCRIPTION
        "Parameter 'ack_rvd' in event TIDP.1"
    ::= { tidpEventObjects1 6 }

tidpEventObjects2 OBJECT-IDENTITY
    STATUS current
    DESCRIPTION
        "Event TIDP.2
        Sending Management Message"
    ::= { tidpEventsGroup 2 }

tidp2_ipdestination OBJECT-TYPE
    SYNTAX IpAddress
    MAX-ACCESS accessible-for-notify
    STATUS current
    DESCRIPTION
        "Parameter 'ipdestination' in event TIDP.2"
    ::= { tidpEventObjects2 1 }

tidp2_hostname OBJECT-TYPE
    SYNTAX DisplayString
    MAX-ACCESS accessible-for-notify
    STATUS current
    DESCRIPTION
        "Parameter 'hostname' in event TIDP.2"
    ::= { tidpEventObjects2 2 }

tidp2_serialnumber OBJECT-TYPE
    SYNTAX DisplayString
    MAX-ACCESS accessible-for-notify
    STATUS current
    DESCRIPTION
        "Parameter 'serialnumber' in event TIDP.2"
    ::= { tidpEventObjects2 3 }

tidp2_code OBJECT-TYPE
    SYNTAX Integer32
    MAX-ACCESS accessible-for-notify
    STATUS current
    DESCRIPTION
        "Parameter 'code' in event TIDP.2"
    ::= { tidpEventObjects2 4 }

tidp2_sequencenumber OBJECT-TYPE
    SYNTAX Integer32
    MAX-ACCESS accessible-for-notify
    STATUS current
    DESCRIPTION
        "Parameter 'sequencenumber' in event TIDP.2"
    ::= { tidpEventObjects2 5 }

tidpEventObjects3 OBJECT-IDENTITY
    STATUS current
    DESCRIPTION
        "Event TIDP.3
        Sending Management Request Message"
    ::= { tidpEventsGroup 3 }

tidp3_hostname OBJECT-TYPE
    SYNTAX DisplayString
    MAX-ACCESS accessible-for-notify
    STATUS current
    DESCRIPTION
        "Parameter 'hostname' in event TIDP.3"
    ::= { tidpEventObjects3 1 }

tidp3_ipdestination OBJECT-TYPE
    SYNTAX IpAddress
    MAX-ACCESS accessible-for-notify
    STATUS current
    DESCRIPTION
        "Parameter 'ipdestination' in event TIDP.3"
    ::= { tidpEventObjects3 2 }

tidp3_port OBJECT-TYPE
    SYNTAX Integer32
    MAX-ACCESS accessible-for-notify
    STATUS current
    DESCRIPTION
        "Parameter 'port' in event TIDP.3"
    ::= { tidpEventObjects3 3 }

tidpEventObjects4 OBJECT-IDENTITY
    STATUS current
    DESCRIPTION
        "Event TIDP.4
        A packet has been received with wrong HMAC checksum"
    ::= { tidpEventsGroup 4 }

tidp4_ipdestination OBJECT-TYPE
    SYNTAX IpAddress
    MAX-ACCESS accessible-for-notify
    STATUS current
    DESCRIPTION
        "Parameter 'ipdestination' in event TIDP.4"
    ::= { tidpEventObjects4 1 }

tidpEventObjects5 OBJECT-IDENTITY
    STATUS current
    DESCRIPTION
        "Event TIDP.5
        A packet has been received with wrong protocol version"
    ::= { tidpEventsGroup 5 }

tidp5_ipdestination OBJECT-TYPE
    SYNTAX IpAddress
    MAX-ACCESS accessible-for-notify
    STATUS current
    DESCRIPTION
        "Parameter 'ipdestination' in event TIDP.5"
    ::= { tidpEventObjects5 1 }

tidpEventObjects6 OBJECT-IDENTITY
    STATUS current
    DESCRIPTION
        "Event TIDP.6
        A packet has been received with wrong packet type"
    ::= { tidpEventsGroup 6 }

tidp6_ipdestination OBJECT-TYPE
    SYNTAX IpAddress
    MAX-ACCESS accessible-for-notify
    STATUS current
    DESCRIPTION
        "Parameter 'ipdestination' in event TIDP.6"
    ::= { tidpEventObjects6 1 }

tidpEventObjects7 OBJECT-IDENTITY
    STATUS current
    DESCRIPTION
        "Event TIDP.7
        Notify Request Received"
    ::= { tidpEventsGroup 7 }

tidp7_ipdestination OBJECT-TYPE
    SYNTAX IpAddress
    MAX-ACCESS accessible-for-notify
    STATUS current
    DESCRIPTION
        "Parameter 'ipdestination' in event TIDP.7"
    ::= { tidpEventObjects7 1 }

tidpEventObjects8 OBJECT-IDENTITY
    STATUS current
    DESCRIPTION
        "Event TIDP.8
        Management Request Received"
    ::= { tidpEventsGroup 8 }

tidp8_ipdestination OBJECT-TYPE
    SYNTAX IpAddress
    MAX-ACCESS accessible-for-notify
    STATUS current
    DESCRIPTION
        "Parameter 'ipdestination' in event TIDP.8"
    ::= { tidpEventObjects8 1 }

tidpEventObjects9 OBJECT-IDENTITY
    STATUS current
    DESCRIPTION
        "Event TIDP.9
        Unknown Type Message Received"
    ::= { tidpEventsGroup 9 }

tidp9_ipdestination OBJECT-TYPE
    SYNTAX IpAddress
    MAX-ACCESS accessible-for-notify
    STATUS current
    DESCRIPTION
        "Parameter 'ipdestination' in event TIDP.9"
    ::= { tidpEventObjects9 1 }

tidpEventObjects10 OBJECT-IDENTITY
    STATUS current
    DESCRIPTION
        "Event TIDP.10
        Notification Messege Received, might be Filtered by in Management"
    ::= { tidpEventsGroup 10 }

tidp10_ipsource OBJECT-TYPE
    SYNTAX IpAddress
    MAX-ACCESS accessible-for-notify
    STATUS current
    DESCRIPTION
        "Parameter 'ipsource' in event TIDP.10"
    ::= { tidpEventObjects10 1 }

tidp10_hostname OBJECT-TYPE
    SYNTAX DisplayString
    MAX-ACCESS accessible-for-notify
    STATUS current
    DESCRIPTION
        "Parameter 'hostname' in event TIDP.10"
    ::= { tidpEventObjects10 2 }

tidp10_serialnumber OBJECT-TYPE
    SYNTAX DisplayString
    MAX-ACCESS accessible-for-notify
    STATUS current
    DESCRIPTION
        "Parameter 'serialnumber' in event TIDP.10"
    ::= { tidpEventObjects10 3 }

tidp10_code OBJECT-TYPE
    SYNTAX Integer32
    MAX-ACCESS accessible-for-notify
    STATUS current
    DESCRIPTION
        "Parameter 'code' in event TIDP.10"
    ::= { tidpEventObjects10 4 }

tidp10_sequencenumber OBJECT-TYPE
    SYNTAX Integer32
    MAX-ACCESS accessible-for-notify
    STATUS current
    DESCRIPTION
        "Parameter 'sequencenumber' in event TIDP.10"
    ::= { tidpEventObjects10 5 }

tidp10_ack_rvd OBJECT-TYPE
    SYNTAX DisplayString
    MAX-ACCESS accessible-for-notify
    STATUS current
    DESCRIPTION
        "Parameter 'ack_rvd' in event TIDP.10"
    ::= { tidpEventObjects10 6 }

tidp10_payloadip OBJECT-TYPE
    SYNTAX IpAddress
    MAX-ACCESS accessible-for-notify
    STATUS current
    DESCRIPTION
        "Parameter 'payloadip' in event TIDP.10"
    ::= { tidpEventObjects10 7 }

tidp10_status OBJECT-TYPE
    SYNTAX DisplayString
    MAX-ACCESS accessible-for-notify
    STATUS current
    DESCRIPTION
        "Parameter 'status' in event TIDP.10"
    ::= { tidpEventObjects10 8 }

tidpEventObjects11 OBJECT-IDENTITY
    STATUS current
    DESCRIPTION
        "Event TIDP.11
        Management Messege Received might be Filtered by in Management"
    ::= { tidpEventsGroup 11 }

tidp11_ipsource OBJECT-TYPE
    SYNTAX IpAddress
    MAX-ACCESS accessible-for-notify
    STATUS current
    DESCRIPTION
        "Parameter 'ipsource' in event TIDP.11"
    ::= { tidpEventObjects11 1 }

tidp11_hostname OBJECT-TYPE
    SYNTAX DisplayString
    MAX-ACCESS accessible-for-notify
    STATUS current
    DESCRIPTION
        "Parameter 'hostname' in event TIDP.11"
    ::= { tidpEventObjects11 2 }

tidp11_serialnumber OBJECT-TYPE
    SYNTAX DisplayString
    MAX-ACCESS accessible-for-notify
    STATUS current
    DESCRIPTION
        "Parameter 'serialnumber' in event TIDP.11"
    ::= { tidpEventObjects11 3 }

tidp11_code OBJECT-TYPE
    SYNTAX Integer32
    MAX-ACCESS accessible-for-notify
    STATUS current
    DESCRIPTION
        "Parameter 'code' in event TIDP.11"
    ::= { tidpEventObjects11 4 }

tidp11_sequencenumber OBJECT-TYPE
    SYNTAX Integer32
    MAX-ACCESS accessible-for-notify
    STATUS current
    DESCRIPTION
        "Parameter 'sequencenumber' in event TIDP.11"
    ::= { tidpEventObjects11 5 }

tidp11_payloadip OBJECT-TYPE
    SYNTAX IpAddress
    MAX-ACCESS accessible-for-notify
    STATUS current
    DESCRIPTION
        "Parameter 'payloadip' in event TIDP.11"
    ::= { tidpEventObjects11 6 }

tidp11_status OBJECT-TYPE
    SYNTAX DisplayString
    MAX-ACCESS accessible-for-notify
    STATUS current
    DESCRIPTION
        "Parameter 'status' in event TIDP.11"
    ::= { tidpEventObjects11 7 }

tidpEventObjects14 OBJECT-IDENTITY
    STATUS current
    DESCRIPTION
        "Event TIDP.14
        Management lost from remote client. No management received in the expected time
        but client can hear master"
    ::= { tidpEventsGroup 14 }

tidp14_hostname OBJECT-TYPE
    SYNTAX DisplayString
    MAX-ACCESS accessible-for-notify
    STATUS current
    DESCRIPTION
        "Parameter 'hostname' in event TIDP.14"
    ::= { tidpEventObjects14 1 }

tidp14_serialnumber OBJECT-TYPE
    SYNTAX DisplayString
    MAX-ACCESS accessible-for-notify
    STATUS current
    DESCRIPTION
        "Parameter 'serialnumber' in event TIDP.14"
    ::= { tidpEventObjects14 2 }

tidpEventObjects15 OBJECT-IDENTITY
    STATUS current
    DESCRIPTION
        "Event TIDP.15
        Management lost from remote client. No management received in the expected time
        and client can not hear master"
    ::= { tidpEventsGroup 15 }

tidp15_hostname OBJECT-TYPE
    SYNTAX DisplayString
    MAX-ACCESS accessible-for-notify
    STATUS current
    DESCRIPTION
        "Parameter 'hostname' in event TIDP.15"
    ::= { tidpEventObjects15 1 }

tidp15_serialnumber OBJECT-TYPE
    SYNTAX DisplayString
    MAX-ACCESS accessible-for-notify
    STATUS current
    DESCRIPTION
        "Parameter 'serialnumber' in event TIDP.15"
    ::= { tidpEventObjects15 2 }

tidpEventObjects16 OBJECT-IDENTITY
    STATUS current
    DESCRIPTION
        "Event TIDP.16
        Notification lost from remote client. No notification received in the expected time."
    ::= { tidpEventsGroup 16 }

tidp16_hostname OBJECT-TYPE
    SYNTAX DisplayString
    MAX-ACCESS accessible-for-notify
    STATUS current
    DESCRIPTION
        "Parameter 'hostname' in event TIDP.16"
    ::= { tidpEventObjects16 1 }

tidp16_serialnumber OBJECT-TYPE
    SYNTAX DisplayString
    MAX-ACCESS accessible-for-notify
    STATUS current
    DESCRIPTION
        "Parameter 'serialnumber' in event TIDP.16"
    ::= { tidpEventObjects16 2 }

tidpEventObjects17 OBJECT-IDENTITY
    STATUS current
    DESCRIPTION
        "Event TIDP.17
        Sending Reset Request Message"
    ::= { tidpEventsGroup 17 }

tidp17_hostname OBJECT-TYPE
    SYNTAX DisplayString
    MAX-ACCESS accessible-for-notify
    STATUS current
    DESCRIPTION
        "Parameter 'hostname' in event TIDP.17"
    ::= { tidpEventObjects17 1 }

tidp17_ipdestination OBJECT-TYPE
    SYNTAX IpAddress
    MAX-ACCESS accessible-for-notify
    STATUS current
    DESCRIPTION
        "Parameter 'ipdestination' in event TIDP.17"
    ::= { tidpEventObjects17 2 }

tidp17_port OBJECT-TYPE
    SYNTAX Integer32
    MAX-ACCESS accessible-for-notify
    STATUS current
    DESCRIPTION
        "Parameter 'port' in event TIDP.17"
    ::= { tidpEventObjects17 3 }

tidpEventObjects18 OBJECT-IDENTITY
    STATUS current
    DESCRIPTION
        "Event TIDP.18
        Management Reset Received"
    ::= { tidpEventsGroup 18 }

tidp18_ipdestination OBJECT-TYPE
    SYNTAX IpAddress
    MAX-ACCESS accessible-for-notify
    STATUS current
    DESCRIPTION
        "Parameter 'ipdestination' in event TIDP.18"
    ::= { tidpEventObjects18 1 }


tidpNotification1 NOTIFICATION-TYPE
    OBJECTS { 
              tidp1_ipdestination, 
              tidp1_hostname,
              tidp1_serialnumber,
              tidp1_code,
              tidp1_sequencenumber,
              tidp1_ack_rvd 
            }
    STATUS current
    DESCRIPTION
        "Notification of Event TIDP.1

        Message: 'Sending Notify to $1->host $2, serial $3, code $4, seq $5, mng_rcv_ack $6'

        Parameters list:
              $1: tidp1_ipdestination
              $2: tidp1_hostname
              $3: tidp1_serialnumber
              $4: tidp1_code
              $5: tidp1_sequencenumber
              $6: tidp1_ack_rvd

        Sending Notification Message"
    ::= { tidpNotificationsPrefix 1 }

tidpNotification2 NOTIFICATION-TYPE
    OBJECTS { 
              tidp2_ipdestination, 
              tidp2_hostname,
              tidp2_serialnumber,
              tidp2_code,
              tidp2_sequencenumber 
            }
    STATUS current
    DESCRIPTION
        "Notification of Event TIDP.2

        Message: 'Sending Management to $1->host $2, serial $3, code $4, seq $5'

        Parameters list:
              $1: tidp2_ipdestination
              $2: tidp2_hostname
              $3: tidp2_serialnumber
              $4: tidp2_code
              $5: tidp2_sequencenumber

        Sending Management Message"
    ::= { tidpNotificationsPrefix 2 }

tidpNotification3 NOTIFICATION-TYPE
    OBJECTS { 
              tidp3_hostname, 
              tidp3_ipdestination,
              tidp3_port 
            }
    STATUS current
    DESCRIPTION
        "Notification of Event TIDP.3

        Message: 'Sending Management Request to hostname $1, $2, port $3'

        Parameters list:
              $1: tidp3_hostname
              $2: tidp3_ipdestination
              $3: tidp3_port

        Sending Management Request Message"
    ::= { tidpNotificationsPrefix 3 }

tidpNotification4 NOTIFICATION-TYPE
    OBJECTS { 
              tidp4_ipdestination 
            }
    STATUS current
    DESCRIPTION
        "Notification of Event TIDP.4

        Message: 'Bad HMAC from $1'

        Parameters list:
              $1: tidp4_ipdestination

        A packet has been received with wrong HMAC checksum"
    ::= { tidpNotificationsPrefix 4 }

tidpNotification5 NOTIFICATION-TYPE
    OBJECTS { 
              tidp5_ipdestination 
            }
    STATUS current
    DESCRIPTION
        "Notification of Event TIDP.5

        Message: 'Bad protocol version from $1'

        Parameters list:
              $1: tidp5_ipdestination

        A packet has been received with wrong protocol version"
    ::= { tidpNotificationsPrefix 5 }

tidpNotification6 NOTIFICATION-TYPE
    OBJECTS { 
              tidp6_ipdestination 
            }
    STATUS current
    DESCRIPTION
        "Notification of Event TIDP.6

        Message: 'Bad packet type from $1'

        Parameters list:
              $1: tidp6_ipdestination

        A packet has been received with wrong packet type"
    ::= { tidpNotificationsPrefix 6 }

tidpNotification7 NOTIFICATION-TYPE
    OBJECTS { 
              tidp7_ipdestination 
            }
    STATUS current
    DESCRIPTION
        "Notification of Event TIDP.7

        Message: 'Notify Request Received from $1'

        Parameters list:
              $1: tidp7_ipdestination

        Notify Request Received"
    ::= { tidpNotificationsPrefix 7 }

tidpNotification8 NOTIFICATION-TYPE
    OBJECTS { 
              tidp8_ipdestination 
            }
    STATUS current
    DESCRIPTION
        "Notification of Event TIDP.8

        Message: 'Management Request Received from $1'

        Parameters list:
              $1: tidp8_ipdestination

        Management Request Received"
    ::= { tidpNotificationsPrefix 8 }

tidpNotification9 NOTIFICATION-TYPE
    OBJECTS { 
              tidp9_ipdestination 
            }
    STATUS current
    DESCRIPTION
        "Notification of Event TIDP.9

        Message: 'Unknown Type Message Received from $1'

        Parameters list:
              $1: tidp9_ipdestination

        Unknown Type Message Received"
    ::= { tidpNotificationsPrefix 9 }

tidpNotification10 NOTIFICATION-TYPE
    OBJECTS { 
              tidp10_ipsource, 
              tidp10_hostname,
              tidp10_serialnumber,
              tidp10_code,
              tidp10_sequencenumber,
              tidp10_ack_rvd,
              tidp10_payloadip,
              tidp10_status 
            }
    STATUS current
    DESCRIPTION
        "Notification of Event TIDP.10

        Message: 'Notify Received from $1, hostname $2, serial $3, code $4, seq $5, mng_rcv_ack $6, payload IP $7, status $8'

        Parameters list:
              $1: tidp10_ipsource
              $2: tidp10_hostname
              $3: tidp10_serialnumber
              $4: tidp10_code
              $5: tidp10_sequencenumber
              $6: tidp10_ack_rvd
              $7: tidp10_payloadip
              $8: tidp10_status

        Notification Messege Received, might be Filtered by in Management"
    ::= { tidpNotificationsPrefix 10 }

tidpNotification11 NOTIFICATION-TYPE
    OBJECTS { 
              tidp11_ipsource, 
              tidp11_hostname,
              tidp11_serialnumber,
              tidp11_code,
              tidp11_sequencenumber,
              tidp11_payloadip,
              tidp11_status 
            }
    STATUS current
    DESCRIPTION
        "Notification of Event TIDP.11

        Message: 'Management Received from $1, hostname $2, serial $3, code $4, seq $5, payload IP $6, status $7'

        Parameters list:
              $1: tidp11_ipsource
              $2: tidp11_hostname
              $3: tidp11_serialnumber
              $4: tidp11_code
              $5: tidp11_sequencenumber
              $6: tidp11_payloadip
              $7: tidp11_status

        Management Messege Received might be Filtered by in Management"
    ::= { tidpNotificationsPrefix 11 }

tidpNotification12 NOTIFICATION-TYPE
    STATUS current
    DESCRIPTION
        "Notification of Event TIDP.12

        Message: 'Disable Filter of Notify Received Messages'

        Disables Filter of Notify Received Messages"
    ::= { tidpNotificationsPrefix 12 }

tidpNotification13 NOTIFICATION-TYPE
    STATUS current
    DESCRIPTION
        "Notification of Event TIDP.13

        Message: 'Disable Filter of Management Received Messages'

        Disables Filter of Management Received Messages"
    ::= { tidpNotificationsPrefix 13 }

tidpNotification14 NOTIFICATION-TYPE
    OBJECTS { 
              tidp14_hostname, 
              tidp14_serialnumber 
            }
    STATUS current
    DESCRIPTION
        "Notification of Event TIDP.14

        Message: 'Management lost from hostname $1, serial $2, though client can hear master'

        Parameters list:
              $1: tidp14_hostname
              $2: tidp14_serialnumber

        Management lost from remote client. No management received in the expected time
        but client can hear master"
    ::= { tidpNotificationsPrefix 14 }

tidpNotification15 NOTIFICATION-TYPE
    OBJECTS { 
              tidp15_hostname, 
              tidp15_serialnumber 
            }
    STATUS current
    DESCRIPTION
        "Notification of Event TIDP.15

        Message: 'Management lost from hostname $1, serial $2, and client can not hear master'

        Parameters list:
              $1: tidp15_hostname
              $2: tidp15_serialnumber

        Management lost from remote client. No management received in the expected time
        and client can not hear master"
    ::= { tidpNotificationsPrefix 15 }

tidpNotification16 NOTIFICATION-TYPE
    OBJECTS { 
              tidp16_hostname, 
              tidp16_serialnumber 
            }
    STATUS current
    DESCRIPTION
        "Notification of Event TIDP.16

        Message: 'Notify lost from hostname $1, serial $2'

        Parameters list:
              $1: tidp16_hostname
              $2: tidp16_serialnumber

        Notification lost from remote client. No notification received in the expected time."
    ::= { tidpNotificationsPrefix 16 }

tidpNotification17 NOTIFICATION-TYPE
    OBJECTS { 
              tidp17_hostname, 
              tidp17_ipdestination,
              tidp17_port 
            }
    STATUS current
    DESCRIPTION
        "Notification of Event TIDP.17

        Message: 'Sending Reset Request to hostname $1, $2, port $3'

        Parameters list:
              $1: tidp17_hostname
              $2: tidp17_ipdestination
              $3: tidp17_port

        Sending Reset Request Message"
    ::= { tidpNotificationsPrefix 17 }

tidpNotification18 NOTIFICATION-TYPE
    OBJECTS { 
              tidp18_ipdestination 
            }
    STATUS current
    DESCRIPTION
        "Notification of Event TIDP.18

        Message: 'Management Reset Received from $1'

        Parameters list:
              $1: tidp18_ipdestination

        Management Reset Received"
    ::= { tidpNotificationsPrefix 18 }


END
