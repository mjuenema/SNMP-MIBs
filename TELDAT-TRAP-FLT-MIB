-- file automatically created


TELDAT-TRAP-FLT-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


fltTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the FLT event subsystem."
    REVISION "201401200930Z"
    DESCRIPTION "Initial implementation"
        ::= { telEventTraps 2 }


fltEventsGroup	OBJECT IDENTIFIER	::= { fltTrapsMIB 1 }

fltNotifications	OBJECT IDENTIFIER	::= { fltTrapsMIB 2 }
fltNotificationsPrefix	OBJECT IDENTIFIER	::= { fltNotifications 0 }

fltEventObjects1 OBJECT-IDENTITY
    STATUS current
    DESCRIPTION
        "Event FLT.1
        This message is generated when the filtering subsystem cannot allocate
        the memory to hold a data structure to hold filtering information.
        This results in a filter not being built."
    ::= { fltEventsGroup 1 }

flt1_structure_type OBJECT-TYPE
    SYNTAX DisplayString
    MAX-ACCESS accessible-for-notify
    STATUS current
    DESCRIPTION
        "Parameter 'structure_type' in event FLT.1"
    ::= { fltEventObjects1 1 }

fltEventObjects2 OBJECT-IDENTITY
    STATUS current
    DESCRIPTION
        "Event FLT.2
        This message is generated when the maximum offset in a filter is larger
        than the length of a packet. The filter is not applied to the packet."
    ::= { fltEventsGroup 2 }

flt2_filter_offset OBJECT-TYPE
    SYNTAX Integer32
    MAX-ACCESS accessible-for-notify
    STATUS current
    DESCRIPTION
        "Parameter 'filter_offset' in event FLT.2"
    ::= { fltEventObjects2 1 }

flt2_packet_offset OBJECT-TYPE
    SYNTAX Integer32
    MAX-ACCESS accessible-for-notify
    STATUS current
    DESCRIPTION
        "Parameter 'packet_offset' in event FLT.2"
    ::= { fltEventObjects2 2 }

fltEventObjects3 OBJECT-IDENTITY
    STATUS current
    DESCRIPTION
        "Event FLT.3
        This message is generated if a filter is attempting to create a
        cache entry but cannot do so because there is no available memory
        on the heap. Instead, an existing entry is reused from the filter."
    ::= { fltEventsGroup 3 }

flt3_cache_entries_allocated OBJECT-TYPE
    SYNTAX Integer32
    MAX-ACCESS accessible-for-notify
    STATUS current
    DESCRIPTION
        "Parameter 'cache_entries_allocated' in event FLT.3"
    ::= { fltEventObjects3 1 }

fltEventObjects4 OBJECT-IDENTITY
    STATUS current
    DESCRIPTION
        "Event FLT.4
        A filter is being created for the router system identified by
        system_name."
    ::= { fltEventsGroup 4 }

flt4_system_name OBJECT-TYPE
    SYNTAX DisplayString
    MAX-ACCESS accessible-for-notify
    STATUS current
    DESCRIPTION
        "Parameter 'system_name' in event FLT.4"
    ::= { fltEventObjects4 1 }

fltEventObjects5 OBJECT-IDENTITY
    STATUS current
    DESCRIPTION
        "Event FLT.5
        A filter produced a cache hit. System_name is the system name of
        a filter that was previously created."
    ::= { fltEventsGroup 5 }

flt5_system_name OBJECT-TYPE
    SYNTAX DisplayString
    MAX-ACCESS accessible-for-notify
    STATUS current
    DESCRIPTION
        "Parameter 'system_name' in event FLT.5"
    ::= { fltEventObjects5 1 }

fltEventObjects6 OBJECT-IDENTITY
    STATUS current
    DESCRIPTION
        "Event FLT.6
        A filter produced a match, but with no cache hit. System_name is the
        system name of a filter that was previously created."
    ::= { fltEventsGroup 6 }

flt6_system_name OBJECT-TYPE
    SYNTAX DisplayString
    MAX-ACCESS accessible-for-notify
    STATUS current
    DESCRIPTION
        "Parameter 'system_name' in event FLT.6"
    ::= { fltEventObjects6 1 }

fltEventObjects7 OBJECT-IDENTITY
    STATUS current
    DESCRIPTION
        "Event FLT.7
        A filter was applied to a block a data, but not match was found.
        System_name is the system name of a filter that was previously created."
    ::= { fltEventsGroup 7 }

flt7_system_name OBJECT-TYPE
    SYNTAX DisplayString
    MAX-ACCESS accessible-for-notify
    STATUS current
    DESCRIPTION
        "Parameter 'system_name' in event FLT.7"
    ::= { fltEventObjects7 1 }


fltNotification1 NOTIFICATION-TYPE
    OBJECTS { 
              flt1_structure_type 
            }
    STATUS current
    DESCRIPTION
        "Notification of Event FLT.1

        Message: 'No free memory to create a $1'

        Parameters list:
              $1: flt1_structure_type

        This message is generated when the filtering subsystem cannot allocate
        the memory to hold a data structure to hold filtering information.
        This results in a filter not being built."
    ::= { fltNotificationsPrefix 1 }

fltNotification2 NOTIFICATION-TYPE
    OBJECTS { 
              flt2_filter_offset, 
              flt2_packet_offset 
            }
    STATUS current
    DESCRIPTION
        "Notification of Event FLT.2

        Message: 'Cannot apply filter (offset $1), to packet of length $2'

        Parameters list:
              $1: flt2_filter_offset
              $2: flt2_packet_offset

        This message is generated when the maximum offset in a filter is larger
        than the length of a packet. The filter is not applied to the packet."
    ::= { fltNotificationsPrefix 2 }

fltNotification3 NOTIFICATION-TYPE
    OBJECTS { 
              flt3_cache_entries_allocated 
            }
    STATUS current
    DESCRIPTION
        "Notification of Event FLT.3

        Message: 'No memory to cache packet (maximum $1)'

        Parameters list:
              $1: flt3_cache_entries_allocated

        This message is generated if a filter is attempting to create a
        cache entry but cannot do so because there is no available memory
        on the heap. Instead, an existing entry is reused from the filter."
    ::= { fltNotificationsPrefix 3 }

fltNotification4 NOTIFICATION-TYPE
    OBJECTS { 
              flt4_system_name 
            }
    STATUS current
    DESCRIPTION
        "Notification of Event FLT.4

        Message: 'Creating filter for system $1'

        Parameters list:
              $1: flt4_system_name

        A filter is being created for the router system identified by
        system_name."
    ::= { fltNotificationsPrefix 4 }

fltNotification5 NOTIFICATION-TYPE
    OBJECTS { 
              flt5_system_name 
            }
    STATUS current
    DESCRIPTION
        "Notification of Event FLT.5

        Message: 'Filter cache hit, system $1'

        Parameters list:
              $1: flt5_system_name

        A filter produced a cache hit. System_name is the system name of
        a filter that was previously created."
    ::= { fltNotificationsPrefix 5 }

fltNotification6 NOTIFICATION-TYPE
    OBJECTS { 
              flt6_system_name 
            }
    STATUS current
    DESCRIPTION
        "Notification of Event FLT.6

        Message: 'Filter match, system $1'

        Parameters list:
              $1: flt6_system_name

        A filter produced a match, but with no cache hit. System_name is the
        system name of a filter that was previously created."
    ::= { fltNotificationsPrefix 6 }

fltNotification7 NOTIFICATION-TYPE
    OBJECTS { 
              flt7_system_name 
            }
    STATUS current
    DESCRIPTION
        "Notification of Event FLT.7

        Message: 'Filter miss, system $1'

        Parameters list:
              $1: flt7_system_name

        A filter was applied to a block a data, but not match was found.
        System_name is the system name of a filter that was previously created."
    ::= { fltNotificationsPrefix 7 }


END
