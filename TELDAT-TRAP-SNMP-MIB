-- file automatically created


TELDAT-TRAP-SNMP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


snmpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the SNMP event subsystem."
    REVISION "201401200930Z"
    DESCRIPTION "Initial implementation"
        ::= { telEventTraps 21 }


snmpEventsGroup	OBJECT IDENTIFIER	::= { snmpTrapsMIB 1 }

snmpNotifications	OBJECT IDENTIFIER	::= { snmpTrapsMIB 2 }
snmpNotificationsPrefix	OBJECT IDENTIFIER	::= { snmpNotifications 0 }

snmpEventObjects1 OBJECT-IDENTITY
    STATUS current
    DESCRIPTION
        "Event SNMP.1
        This message is generated dor each SNMP packet received from a
        remote host."
    ::= { snmpEventsGroup 1 }

snmp1_source_snmp_address OBJECT-TYPE
    SYNTAX IpAddress
    MAX-ACCESS accessible-for-notify
    STATUS current
    DESCRIPTION
        "Parameter 'source_snmp_address' in event SNMP.1"
    ::= { snmpEventObjects1 1 }

snmpEventObjects2 OBJECT-IDENTITY
    STATUS current
    DESCRIPTION
        "Event SNMP.2
        This message is generated for each SNMP packet sent to a remote host."
    ::= { snmpEventsGroup 2 }

snmp2_destination_snmp_address OBJECT-TYPE
    SYNTAX IpAddress
    MAX-ACCESS accessible-for-notify
    STATUS current
    DESCRIPTION
        "Parameter 'destination_snmp_address' in event SNMP.2"
    ::= { snmpEventObjects2 1 }

snmpEventObjects3 OBJECT-IDENTITY
    STATUS current
    DESCRIPTION
        "Event SNMP.3
        This message is generated by a first-level reasonableness check of
        an incomming SNMP packet. The error codes have the following meanings:
        1 - packet does not begin with SEQUENCE (0x30) 2 - packet sequence
        length too small 3 - packet sequence length improperly encoded
        (in one byte) 4 - first packet field not an ASN.1 INTEGER 5 - packet
        sequence length improperly encoded (in two bytes) 6 - first packet
        field not an ASN.1 INTEGER 7 - some other error was detected"
    ::= { snmpEventsGroup 3 }

snmp3_source_snmp_address OBJECT-TYPE
    SYNTAX IpAddress
    MAX-ACCESS accessible-for-notify
    STATUS current
    DESCRIPTION
        "Parameter 'source_snmp_address' in event SNMP.3"
    ::= { snmpEventObjects3 1 }

snmp3_error_code OBJECT-TYPE
    SYNTAX Integer32
    MAX-ACCESS accessible-for-notify
    STATUS current
    DESCRIPTION
        "Parameter 'error_code' in event SNMP.3"
    ::= { snmpEventObjects3 2 }

snmpEventObjects4 OBJECT-IDENTITY
    STATUS current
    DESCRIPTION
        "Event SNMP.4
        This message indicates that an SNMP packet contained an incorrect
        version."
    ::= { snmpEventsGroup 4 }

snmp4_version_number OBJECT-TYPE
    SYNTAX Integer32
    MAX-ACCESS accessible-for-notify
    STATUS current
    DESCRIPTION
        "Parameter 'version_number' in event SNMP.4"
    ::= { snmpEventObjects4 1 }

snmp4_source_snmp_address OBJECT-TYPE
    SYNTAX IpAddress
    MAX-ACCESS accessible-for-notify
    STATUS current
    DESCRIPTION
        "Parameter 'source_snmp_address' in event SNMP.4"
    ::= { snmpEventObjects4 2 }

snmpEventObjects5 OBJECT-IDENTITY
    STATUS current
    DESCRIPTION
        "Event SNMP.5
        This message indicates that an SNMP request from a remote host
        specified a community which did not list that host's IP sddress
        as acceptable."
    ::= { snmpEventsGroup 5 }

snmp5_community OBJECT-TYPE
    SYNTAX DisplayString
    MAX-ACCESS accessible-for-notify
    STATUS current
    DESCRIPTION
        "Parameter 'community' in event SNMP.5"
    ::= { snmpEventObjects5 1 }

snmp5_source_snmp_address OBJECT-TYPE
    SYNTAX IpAddress
    MAX-ACCESS accessible-for-notify
    STATUS current
    DESCRIPTION
        "Parameter 'source_snmp_address' in event SNMP.5"
    ::= { snmpEventObjects5 2 }

snmpEventObjects6 OBJECT-IDENTITY
    STATUS current
    DESCRIPTION
        "Event SNMP.6
        This message indicates that an SNMP packet had a bad application type.
        That is, it was not a GET, GETNEXT, GETBULK or SET request."
    ::= { snmpEventsGroup 6 }

snmp6_appl_type OBJECT-TYPE
    SYNTAX Integer32
    MAX-ACCESS accessible-for-notify
    STATUS current
    DESCRIPTION
        "Parameter 'appl_type' in event SNMP.6"
    ::= { snmpEventObjects6 1 }

snmp6_source_snmp_address OBJECT-TYPE
    SYNTAX IpAddress
    MAX-ACCESS accessible-for-notify
    STATUS current
    DESCRIPTION
        "Parameter 'source_snmp_address' in event SNMP.6"
    ::= { snmpEventObjects6 2 }

snmpEventObjects8 OBJECT-IDENTITY
    STATUS current
    DESCRIPTION
        "Event SNMP.8
        This message indicates that a SET request came in on a community or
        userName which only provides read-only access to the MIB."
    ::= { snmpEventsGroup 8 }

snmp8_source_snmp_address OBJECT-TYPE
    SYNTAX IpAddress
    MAX-ACCESS accessible-for-notify
    STATUS current
    DESCRIPTION
        "Parameter 'source_snmp_address' in event SNMP.8"
    ::= { snmpEventObjects8 1 }

snmp8_userName OBJECT-TYPE
    SYNTAX DisplayString
    MAX-ACCESS accessible-for-notify
    STATUS current
    DESCRIPTION
        "Parameter 'userName' in event SNMP.8"
    ::= { snmpEventObjects8 2 }

snmpEventObjects10 OBJECT-IDENTITY
    STATUS current
    DESCRIPTION
        "Event SNMP.10
        This message is generated by the SNMP fake-oute routine."
    ::= { snmpEventsGroup 10 }

snmp10_source_snmp_address OBJECT-TYPE
    SYNTAX IpAddress
    MAX-ACCESS accessible-for-notify
    STATUS current
    DESCRIPTION
        "Parameter 'source_snmp_address' in event SNMP.10"
    ::= { snmpEventObjects10 1 }

snmpEventObjects11 OBJECT-IDENTITY
    STATUS current
    DESCRIPTION
        "Event SNMP.11
        This message is generated by a length check on the variable to be sent
        out."
    ::= { snmpEventsGroup 11 }

snmp11_ovarlen OBJECT-TYPE
    SYNTAX Integer32
    MAX-ACCESS accessible-for-notify
    STATUS current
    DESCRIPTION
        "Parameter 'ovarlen' in event SNMP.11"
    ::= { snmpEventObjects11 1 }

snmp11_source_snmp_address OBJECT-TYPE
    SYNTAX IpAddress
    MAX-ACCESS accessible-for-notify
    STATUS current
    DESCRIPTION
        "Parameter 'source_snmp_address' in event SNMP.11"
    ::= { snmpEventObjects11 2 }

snmpEventObjects12 OBJECT-IDENTITY
    STATUS current
    DESCRIPTION
        "Event SNMP.12
        This message is generated for each SNMP packet received from a remote
        host of the type get-request."
    ::= { snmpEventsGroup 12 }

snmp12_source_snmp_address OBJECT-TYPE
    SYNTAX IpAddress
    MAX-ACCESS accessible-for-notify
    STATUS current
    DESCRIPTION
        "Parameter 'source_snmp_address' in event SNMP.12"
    ::= { snmpEventObjects12 1 }

snmpEventObjects13 OBJECT-IDENTITY
    STATUS current
    DESCRIPTION
        "Event SNMP.13
        This message is generated for each SNMP packet received from a remote
        host of the type get-next."
    ::= { snmpEventsGroup 13 }

snmp13_source_snmp_address OBJECT-TYPE
    SYNTAX IpAddress
    MAX-ACCESS accessible-for-notify
    STATUS current
    DESCRIPTION
        "Parameter 'source_snmp_address' in event SNMP.13"
    ::= { snmpEventObjects13 1 }

snmpEventObjects14 OBJECT-IDENTITY
    STATUS current
    DESCRIPTION
        "Event SNMP.14
        This message is generated for each SNMP packet received from a remote
        host of the type set-request."
    ::= { snmpEventsGroup 14 }

snmp14_source_snmp_address OBJECT-TYPE
    SYNTAX IpAddress
    MAX-ACCESS accessible-for-notify
    STATUS current
    DESCRIPTION
        "Parameter 'source_snmp_address' in event SNMP.14"
    ::= { snmpEventObjects14 1 }

snmpEventObjects15 OBJECT-IDENTITY
    STATUS current
    DESCRIPTION
        "Event SNMP.15
        This message indicate that a packet was sent out with  the error status
        as too big as a result of the SNMP variable in question not fitting
        the packet size."
    ::= { snmpEventsGroup 15 }

snmp15_source_snmp_address OBJECT-TYPE
    SYNTAX IpAddress
    MAX-ACCESS accessible-for-notify
    STATUS current
    DESCRIPTION
        "Parameter 'source_snmp_address' in event SNMP.15"
    ::= { snmpEventObjects15 1 }

snmpEventObjects16 OBJECT-IDENTITY
    STATUS current
    DESCRIPTION
        "Event SNMP.16
        This message indicate that a packet was sent out with  the error status
        as noSuchName as a result of the SNMP variable in question not existing
        in the gateway or not in the view associated with the specified
        community or the operation is a set on a read-only variable."
    ::= { snmpEventsGroup 16 }

snmp16_source_snmp_address OBJECT-TYPE
    SYNTAX IpAddress
    MAX-ACCESS accessible-for-notify
    STATUS current
    DESCRIPTION
        "Parameter 'source_snmp_address' in event SNMP.16"
    ::= { snmpEventObjects16 1 }

snmpEventObjects17 OBJECT-IDENTITY
    STATUS current
    DESCRIPTION
        "Event SNMP.17
        This message indicate that a packet was sent out with  the error status
        as badvalue as a result of trying to set a variable with a wrong value
        specified in the SET request."
    ::= { snmpEventsGroup 17 }

snmp17_source_snmp_address OBJECT-TYPE
    SYNTAX IpAddress
    MAX-ACCESS accessible-for-notify
    STATUS current
    DESCRIPTION
        "Parameter 'source_snmp_address' in event SNMP.17"
    ::= { snmpEventObjects17 1 }

snmpEventObjects22 OBJECT-IDENTITY
    STATUS current
    DESCRIPTION
        "Event SNMP.22
        One trap will not be sent because it could not be built for some reason."
    ::= { snmpEventsGroup 22 }

snmp22_type OBJECT-TYPE
    SYNTAX Integer32
    MAX-ACCESS accessible-for-notify
    STATUS current
    DESCRIPTION
        "Parameter 'type' in event SNMP.22"
    ::= { snmpEventObjects22 1 }

snmp22_subtype OBJECT-TYPE
    SYNTAX Integer32
    MAX-ACCESS accessible-for-notify
    STATUS current
    DESCRIPTION
        "Parameter 'subtype' in event SNMP.22"
    ::= { snmpEventObjects22 2 }

snmp22_event OBJECT-TYPE
    SYNTAX DisplayString
    MAX-ACCESS accessible-for-notify
    STATUS current
    DESCRIPTION
        "Parameter 'event' in event SNMP.22"
    ::= { snmpEventObjects22 3 }

snmpEventObjects23 OBJECT-IDENTITY
    STATUS current
    DESCRIPTION
        "Event SNMP.23
        One trap could not be built because its total length in ASN.1 is greater
        than the maximun value allowed."
    ::= { snmpEventsGroup 23 }

snmp23_type OBJECT-TYPE
    SYNTAX Integer32
    MAX-ACCESS accessible-for-notify
    STATUS current
    DESCRIPTION
        "Parameter 'type' in event SNMP.23"
    ::= { snmpEventObjects23 1 }

snmp23_subtype OBJECT-TYPE
    SYNTAX Integer32
    MAX-ACCESS accessible-for-notify
    STATUS current
    DESCRIPTION
        "Parameter 'subtype' in event SNMP.23"
    ::= { snmpEventObjects23 2 }

snmp23_event OBJECT-TYPE
    SYNTAX DisplayString
    MAX-ACCESS accessible-for-notify
    STATUS current
    DESCRIPTION
        "Parameter 'event' in event SNMP.23"
    ::= { snmpEventObjects23 3 }

snmp23_length OBJECT-TYPE
    SYNTAX Integer32
    MAX-ACCESS accessible-for-notify
    STATUS current
    DESCRIPTION
        "Parameter 'length' in event SNMP.23"
    ::= { snmpEventObjects23 4 }

snmp23_max_lengh OBJECT-TYPE
    SYNTAX Integer32
    MAX-ACCESS accessible-for-notify
    STATUS current
    DESCRIPTION
        "Parameter 'max_lengh' in event SNMP.23"
    ::= { snmpEventObjects23 5 }

snmpEventObjects24 OBJECT-IDENTITY
    STATUS current
    DESCRIPTION
        "Event SNMP.24
        One trap could not be built because the length in ASN.1 of one of its
        parameters (at least) is greater than the maximum value allowed."
    ::= { snmpEventsGroup 24 }

snmp24_parameter_number OBJECT-TYPE
    SYNTAX Integer32
    MAX-ACCESS accessible-for-notify
    STATUS current
    DESCRIPTION
        "Parameter 'parameter_number' in event SNMP.24"
    ::= { snmpEventObjects24 1 }

snmp24_length OBJECT-TYPE
    SYNTAX Integer32
    MAX-ACCESS accessible-for-notify
    STATUS current
    DESCRIPTION
        "Parameter 'length' in event SNMP.24"
    ::= { snmpEventObjects24 2 }

snmp24_max_length OBJECT-TYPE
    SYNTAX Integer32
    MAX-ACCESS accessible-for-notify
    STATUS current
    DESCRIPTION
        "Parameter 'max_length' in event SNMP.24"
    ::= { snmpEventObjects24 3 }

snmpEventObjects25 OBJECT-IDENTITY
    STATUS current
    DESCRIPTION
        "Event SNMP.25
        One trap could not be built because the number of parameters is greater
        than the maximum allowed."
    ::= { snmpEventsGroup 25 }

snmp25_max_parameters OBJECT-TYPE
    SYNTAX Integer32
    MAX-ACCESS accessible-for-notify
    STATUS current
    DESCRIPTION
        "Parameter 'max_parameters' in event SNMP.25"
    ::= { snmpEventObjects25 1 }

snmpEventObjects26 OBJECT-IDENTITY
    STATUS current
    DESCRIPTION
        "Event SNMP.26
        This message is generated for each OID included in a get-request,
        get-next-request, get-bulk or set-request PDU."
    ::= { snmpEventsGroup 26 }

snmp26_operation OBJECT-TYPE
    SYNTAX DisplayString
    MAX-ACCESS accessible-for-notify
    STATUS current
    DESCRIPTION
        "Parameter 'operation' in event SNMP.26"
    ::= { snmpEventObjects26 1 }

snmp26_oid OBJECT-TYPE
    SYNTAX DisplayString
    MAX-ACCESS accessible-for-notify
    STATUS current
    DESCRIPTION
        "Parameter 'oid' in event SNMP.26"
    ::= { snmpEventObjects26 2 }

snmpEventObjects27 OBJECT-IDENTITY
    STATUS current
    DESCRIPTION
        "Event SNMP.27
        An authenticationFailure trap signifies that the sending protocol
        entity is the addressee of a protocol message that is not properly
        authenticated."
    ::= { snmpEventsGroup 27 }

snmp27_secName OBJECT-TYPE
    SYNTAX DisplayString
    MAX-ACCESS accessible-for-notify
    STATUS current
    DESCRIPTION
        "Parameter 'secName' in event SNMP.27"
    ::= { snmpEventObjects27 1 }

snmp27_version OBJECT-TYPE
    SYNTAX Integer32
    MAX-ACCESS accessible-for-notify
    STATUS current
    DESCRIPTION
        "Parameter 'version' in event SNMP.27"
    ::= { snmpEventObjects27 2 }

snmp27_source_snmp_address OBJECT-TYPE
    SYNTAX IpAddress
    MAX-ACCESS accessible-for-notify
    STATUS current
    DESCRIPTION
        "Parameter 'source_snmp_address' in event SNMP.27"
    ::= { snmpEventObjects27 3 }

snmpEventObjects28 OBJECT-IDENTITY
    STATUS current
    DESCRIPTION
        "Event SNMP.28
        Generic informational event."
    ::= { snmpEventsGroup 28 }

snmp28_string OBJECT-TYPE
    SYNTAX DisplayString
    MAX-ACCESS accessible-for-notify
    STATUS current
    DESCRIPTION
        "Parameter 'string' in event SNMP.28"
    ::= { snmpEventObjects28 1 }

snmpEventObjects29 OBJECT-IDENTITY
    STATUS current
    DESCRIPTION
        "Event SNMP.29
        This message is generated for each SNMP packet received from a remote
        host of the type get-bulk."
    ::= { snmpEventsGroup 29 }

snmp29_source_snmp_address OBJECT-TYPE
    SYNTAX IpAddress
    MAX-ACCESS accessible-for-notify
    STATUS current
    DESCRIPTION
        "Parameter 'source_snmp_address' in event SNMP.29"
    ::= { snmpEventObjects29 1 }


snmpNotification1 NOTIFICATION-TYPE
    OBJECTS { 
              snmp1_source_snmp_address 
            }
    STATUS current
    DESCRIPTION
        "Notification of Event SNMP.1

        Message: 'received packet from host $1'

        Parameters list:
              $1: snmp1_source_snmp_address

        This message is generated dor each SNMP packet received from a
        remote host."
    ::= { snmpNotificationsPrefix 1 }

snmpNotification2 NOTIFICATION-TYPE
    OBJECTS { 
              snmp2_destination_snmp_address 
            }
    STATUS current
    DESCRIPTION
        "Notification of Event SNMP.2

        Message: 'sent packet to host $1'

        Parameters list:
              $1: snmp2_destination_snmp_address

        This message is generated for each SNMP packet sent to a remote host."
    ::= { snmpNotificationsPrefix 2 }

snmpNotification3 NOTIFICATION-TYPE
    OBJECTS { 
              snmp3_source_snmp_address, 
              snmp3_error_code 
            }
    STATUS current
    DESCRIPTION
        "Notification of Event SNMP.3

        Message: 'received bad SNMP pcket from host $1 (error code = $2)'

        Parameters list:
              $1: snmp3_source_snmp_address
              $2: snmp3_error_code

        This message is generated by a first-level reasonableness check of
        an incomming SNMP packet. The error codes have the following meanings:
        1 - packet does not begin with SEQUENCE (0x30) 2 - packet sequence
        length too small 3 - packet sequence length improperly encoded
        (in one byte) 4 - first packet field not an ASN.1 INTEGER 5 - packet
        sequence length improperly encoded (in two bytes) 6 - first packet
        field not an ASN.1 INTEGER 7 - some other error was detected"
    ::= { snmpNotificationsPrefix 3 }

snmpNotification4 NOTIFICATION-TYPE
    OBJECTS { 
              snmp4_version_number, 
              snmp4_source_snmp_address 
            }
    STATUS current
    DESCRIPTION
        "Notification of Event SNMP.4

        Message: 'bad version number $1 from host $2'

        Parameters list:
              $1: snmp4_version_number
              $2: snmp4_source_snmp_address

        This message indicates that an SNMP packet contained an incorrect
        version."
    ::= { snmpNotificationsPrefix 4 }

snmpNotification5 NOTIFICATION-TYPE
    OBJECTS { 
              snmp5_community, 
              snmp5_source_snmp_address 
            }
    STATUS current
    DESCRIPTION
        "Notification of Event SNMP.5

        Message: 'no access to community $1 from host $2'

        Parameters list:
              $1: snmp5_community
              $2: snmp5_source_snmp_address

        This message indicates that an SNMP request from a remote host
        specified a community which did not list that host's IP sddress
        as acceptable."
    ::= { snmpNotificationsPrefix 5 }

snmpNotification6 NOTIFICATION-TYPE
    OBJECTS { 
              snmp6_appl_type, 
              snmp6_source_snmp_address 
            }
    STATUS current
    DESCRIPTION
        "Notification of Event SNMP.6

        Message: 'bad application type $1 from host $2'

        Parameters list:
              $1: snmp6_appl_type
              $2: snmp6_source_snmp_address

        This message indicates that an SNMP packet had a bad application type.
        That is, it was not a GET, GETNEXT, GETBULK or SET request."
    ::= { snmpNotificationsPrefix 6 }

snmpNotification7 NOTIFICATION-TYPE
    STATUS current
    DESCRIPTION
        "Notification of Event SNMP.7

        Message: 'no free packet buffer available'

        This message is generated when SNMP cannot allocate a packet in which
        to construct an SNMP response."
    ::= { snmpNotificationsPrefix 7 }

snmpNotification8 NOTIFICATION-TYPE
    OBJECTS { 
              snmp8_source_snmp_address, 
              snmp8_userName 
            }
    STATUS current
    DESCRIPTION
        "Notification of Event SNMP.8

        Message: 'SET request from host $1 has read-only access in userName $2'

        Parameters list:
              $1: snmp8_source_snmp_address
              $2: snmp8_userName

        This message indicates that a SET request came in on a community or
        userName which only provides read-only access to the MIB."
    ::= { snmpNotificationsPrefix 8 }

snmpNotification9 NOTIFICATION-TYPE
    STATUS current
    DESCRIPTION
        "Notification of Event SNMP.9

        Message: 'TRAP: no free packet buffer available'

        This message is generated whenever SNMP cannot send an event because
        it cannot allocate storage."
    ::= { snmpNotificationsPrefix 9 }

snmpNotification10 NOTIFICATION-TYPE
    OBJECTS { 
              snmp10_source_snmp_address 
            }
    STATUS current
    DESCRIPTION
        "Notification of Event SNMP.10

        Message: 'SNMP disabled packet discarded from host $1'

        Parameters list:
              $1: snmp10_source_snmp_address

        This message is generated by the SNMP fake-oute routine."
    ::= { snmpNotificationsPrefix 10 }

snmpNotification11 NOTIFICATION-TYPE
    OBJECTS { 
              snmp11_ovarlen, 
              snmp11_source_snmp_address 
            }
    STATUS current
    DESCRIPTION
        "Notification of Event SNMP.11

        Message: 'length of variable to be sent out exceeds max length $1 from host $2'

        Parameters list:
              $1: snmp11_ovarlen
              $2: snmp11_source_snmp_address

        This message is generated by a length check on the variable to be sent
        out."
    ::= { snmpNotificationsPrefix 11 }

snmpNotification12 NOTIFICATION-TYPE
    OBJECTS { 
              snmp12_source_snmp_address 
            }
    STATUS current
    DESCRIPTION
        "Notification of Event SNMP.12

        Message: 'received a get-request packet from host $1'

        Parameters list:
              $1: snmp12_source_snmp_address

        This message is generated for each SNMP packet received from a remote
        host of the type get-request."
    ::= { snmpNotificationsPrefix 12 }

snmpNotification13 NOTIFICATION-TYPE
    OBJECTS { 
              snmp13_source_snmp_address 
            }
    STATUS current
    DESCRIPTION
        "Notification of Event SNMP.13

        Message: 'received a get-next packet from host $1'

        Parameters list:
              $1: snmp13_source_snmp_address

        This message is generated for each SNMP packet received from a remote
        host of the type get-next."
    ::= { snmpNotificationsPrefix 13 }

snmpNotification14 NOTIFICATION-TYPE
    OBJECTS { 
              snmp14_source_snmp_address 
            }
    STATUS current
    DESCRIPTION
        "Notification of Event SNMP.14

        Message: 'received a set-request packet from host $1'

        Parameters list:
              $1: snmp14_source_snmp_address

        This message is generated for each SNMP packet received from a remote
        host of the type set-request."
    ::= { snmpNotificationsPrefix 14 }

snmpNotification15 NOTIFICATION-TYPE
    OBJECTS { 
              snmp15_source_snmp_address 
            }
    STATUS current
    DESCRIPTION
        "Notification of Event SNMP.15

        Message: 'packet from host $1 resulted in a pakt with error status: toobig'

        Parameters list:
              $1: snmp15_source_snmp_address

        This message indicate that a packet was sent out with  the error status
        as too big as a result of the SNMP variable in question not fitting
        the packet size."
    ::= { snmpNotificationsPrefix 15 }

snmpNotification16 NOTIFICATION-TYPE
    OBJECTS { 
              snmp16_source_snmp_address 
            }
    STATUS current
    DESCRIPTION
        "Notification of Event SNMP.16

        Message: 'packet from host $1 resulted in a packet with error status: nosuchnam'

        Parameters list:
              $1: snmp16_source_snmp_address

        This message indicate that a packet was sent out with  the error status
        as noSuchName as a result of the SNMP variable in question not existing
        in the gateway or not in the view associated with the specified
        community or the operation is a set on a read-only variable."
    ::= { snmpNotificationsPrefix 16 }

snmpNotification17 NOTIFICATION-TYPE
    OBJECTS { 
              snmp17_source_snmp_address 
            }
    STATUS current
    DESCRIPTION
        "Notification of Event SNMP.17

        Message: 'packet from host $1 resulted in a packet with error status: badvalue'

        Parameters list:
              $1: snmp17_source_snmp_address

        This message indicate that a packet was sent out with  the error status
        as badvalue as a result of trying to set a variable with a wrong value
        specified in the SET request."
    ::= { snmpNotificationsPrefix 17 }

snmpNotification18 NOTIFICATION-TYPE
    STATUS current
    DESCRIPTION
        "Notification of Event SNMP.18

        Message: 'Snmp traps buffer full'

        Snmp traps buffer is full."
    ::= { snmpNotificationsPrefix 18 }

snmpNotification19 NOTIFICATION-TYPE
    STATUS current
    DESCRIPTION
        "Notification of Event SNMP.19

        Message: 'Previous trap not transmitted'

        It isn't allowed to allocate more memory if the previous trap wasn't
        transmitted successfully."
    ::= { snmpNotificationsPrefix 19 }

snmpNotification20 NOTIFICATION-TYPE
    STATUS current
    DESCRIPTION
        "Notification of Event SNMP.20

        Message: 'There are no parameters stored to be sent inside the trap'

        The trap is empty, without parameters."
    ::= { snmpNotificationsPrefix 20 }

snmpNotification21 NOTIFICATION-TYPE
    STATUS current
    DESCRIPTION
        "Notification of Event SNMP.21

        Message: 'No memory was allocated to store the value pointed by use'

        The trap is empty, without parameters."
    ::= { snmpNotificationsPrefix 21 }

snmpNotification22 NOTIFICATION-TYPE
    OBJECTS { 
              snmp22_type, 
              snmp22_subtype,
              snmp22_event 
            }
    STATUS current
    DESCRIPTION
        "Notification of Event SNMP.22

        Message: 'Snmp trap type $1 subtype $2 $3 could not be built'

        Parameters list:
              $1: snmp22_type
              $2: snmp22_subtype
              $3: snmp22_event

        One trap will not be sent because it could not be built for some reason."
    ::= { snmpNotificationsPrefix 22 }

snmpNotification23 NOTIFICATION-TYPE
    OBJECTS { 
              snmp23_type, 
              snmp23_subtype,
              snmp23_event,
              snmp23_length,
              snmp23_max_lengh 
            }
    STATUS current
    DESCRIPTION
        "Notification of Event SNMP.23

        Message: 'The lenght of the snmp trap type $1 subtype $2 $3 (in ASN.1) is greater than the maximum allowed (length: $4, max: $5)'

        Parameters list:
              $1: snmp23_type
              $2: snmp23_subtype
              $3: snmp23_event
              $4: snmp23_length
              $5: snmp23_max_lengh

        One trap could not be built because its total length in ASN.1 is greater
        than the maximun value allowed."
    ::= { snmpNotificationsPrefix 23 }

snmpNotification24 NOTIFICATION-TYPE
    OBJECTS { 
              snmp24_parameter_number, 
              snmp24_length,
              snmp24_max_length 
            }
    STATUS current
    DESCRIPTION
        "Notification of Event SNMP.24

        Message: 'Parameter $1 in Snmp trap too long (length: $2, max: $3)'

        Parameters list:
              $1: snmp24_parameter_number
              $2: snmp24_length
              $3: snmp24_max_length

        One trap could not be built because the length in ASN.1 of one of its
        parameters (at least) is greater than the maximum value allowed."
    ::= { snmpNotificationsPrefix 24 }

snmpNotification25 NOTIFICATION-TYPE
    OBJECTS { 
              snmp25_max_parameters 
            }
    STATUS current
    DESCRIPTION
        "Notification of Event SNMP.25

        Message: 'Snmp trap has too many parameters (max: $1)'

        Parameters list:
              $1: snmp25_max_parameters

        One trap could not be built because the number of parameters is greater
        than the maximum allowed."
    ::= { snmpNotificationsPrefix 25 }

snmpNotification26 NOTIFICATION-TYPE
    OBJECTS { 
              snmp26_operation, 
              snmp26_oid 
            }
    STATUS current
    DESCRIPTION
        "Notification of Event SNMP.26

        Message: '$1: OID = $2'

        Parameters list:
              $1: snmp26_operation
              $2: snmp26_oid

        This message is generated for each OID included in a get-request,
        get-next-request, get-bulk or set-request PDU."
    ::= { snmpNotificationsPrefix 26 }

snmpNotification27 NOTIFICATION-TYPE
    OBJECTS { 
              snmp27_secName, 
              snmp27_version,
              snmp27_source_snmp_address 
            }
    STATUS current
    DESCRIPTION
        "Notification of Event SNMP.27

        Message: 'authentication failure for secName $1, version $2 from host $3'

        Parameters list:
              $1: snmp27_secName
              $2: snmp27_version
              $3: snmp27_source_snmp_address

        An authenticationFailure trap signifies that the sending protocol
        entity is the addressee of a protocol message that is not properly
        authenticated."
    ::= { snmpNotificationsPrefix 27 }

snmpNotification28 NOTIFICATION-TYPE
    OBJECTS { 
              snmp28_string 
            }
    STATUS current
    DESCRIPTION
        "Notification of Event SNMP.28

        Message: '$1'

        Parameters list:
              $1: snmp28_string

        Generic informational event."
    ::= { snmpNotificationsPrefix 28 }

snmpNotification29 NOTIFICATION-TYPE
    OBJECTS { 
              snmp29_source_snmp_address 
            }
    STATUS current
    DESCRIPTION
        "Notification of Event SNMP.29

        Message: 'received a get-bulk packet from host $1'

        Parameters list:
              $1: snmp29_source_snmp_address

        This message is generated for each SNMP packet received from a remote
        host of the type get-bulk."
    ::= { snmpNotificationsPrefix 29 }


END
