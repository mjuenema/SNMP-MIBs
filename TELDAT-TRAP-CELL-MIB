-- file automatically created


TELDAT-TRAP-CELL-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


cellTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the CELL event subsystem."
    REVISION "201401200930Z"
    DESCRIPTION "Initial implementation"
        ::= { telEventTraps 208 }


cellEventsGroup	OBJECT IDENTIFIER	::= { cellTrapsMIB 1 }

cellNotifications	OBJECT IDENTIFIER	::= { cellTrapsMIB 2 }
cellNotificationsPrefix	OBJECT IDENTIFIER	::= { cellNotifications 0 }

cellEventObjects1 OBJECT-IDENTITY
    STATUS current
    DESCRIPTION
        "Event CELL.1
        Generic informational event."
    ::= { cellEventsGroup 1 }

cell1_info_string OBJECT-TYPE
    SYNTAX DisplayString
    MAX-ACCESS accessible-for-notify
    STATUS current
    DESCRIPTION
        "Parameter 'info_string' in event CELL.1"
    ::= { cellEventObjects1 1 }

cell1_ifcname OBJECT-TYPE
    SYNTAX DisplayString
    MAX-ACCESS accessible-for-notify
    STATUS current
    DESCRIPTION
        "Parameter 'ifcname' in event CELL.1"
    ::= { cellEventObjects1 2 }

cellEventObjects2 OBJECT-IDENTITY
    STATUS current
    DESCRIPTION
        "Event CELL.2
        Generic error report."
    ::= { cellEventsGroup 2 }

cell2_error_string OBJECT-TYPE
    SYNTAX DisplayString
    MAX-ACCESS accessible-for-notify
    STATUS current
    DESCRIPTION
        "Parameter 'error_string' in event CELL.2"
    ::= { cellEventObjects2 1 }

cell2_ifcname OBJECT-TYPE
    SYNTAX DisplayString
    MAX-ACCESS accessible-for-notify
    STATUS current
    DESCRIPTION
        "Parameter 'ifcname' in event CELL.2"
    ::= { cellEventObjects2 2 }

cellEventObjects3 OBJECT-IDENTITY
    STATUS current
    DESCRIPTION
        "Event CELL.3
        Registration state has changed."
    ::= { cellEventsGroup 3 }

cell3_state OBJECT-TYPE
    SYNTAX DisplayString
    MAX-ACCESS accessible-for-notify
    STATUS current
    DESCRIPTION
        "Parameter 'state' in event CELL.3"
    ::= { cellEventObjects3 1 }

cell3_ifcname OBJECT-TYPE
    SYNTAX DisplayString
    MAX-ACCESS accessible-for-notify
    STATUS current
    DESCRIPTION
        "Parameter 'ifcname' in event CELL.3"
    ::= { cellEventObjects3 2 }

cellEventObjects4 OBJECT-IDENTITY
    STATUS current
    DESCRIPTION
        "Event CELL.4
        The cellular interface now uses a different Public Land Mobile Network,
        (Mobile Operator) identified by the number displayed."
    ::= { cellEventsGroup 4 }

cell4_operator OBJECT-TYPE
    SYNTAX Integer32
    MAX-ACCESS accessible-for-notify
    STATUS current
    DESCRIPTION
        "Parameter 'operator' in event CELL.4"
    ::= { cellEventObjects4 1 }

cell4_ifcname OBJECT-TYPE
    SYNTAX DisplayString
    MAX-ACCESS accessible-for-notify
    STATUS current
    DESCRIPTION
        "Parameter 'ifcname' in event CELL.4"
    ::= { cellEventObjects4 2 }

cellEventObjects5 OBJECT-IDENTITY
    STATUS current
    DESCRIPTION
        "Event CELL.5
        The cellular interface is connected to a different base station,
        identified by the Location Area Code (LAC) and the Cell Identifier code
        (CiD)."
    ::= { cellEventsGroup 5 }

cell5_location_area_code OBJECT-TYPE
    SYNTAX Integer32
    MAX-ACCESS accessible-for-notify
    STATUS current
    DESCRIPTION
        "Parameter 'location_area_code' in event CELL.5"
    ::= { cellEventObjects5 1 }

cell5_cell_id OBJECT-TYPE
    SYNTAX Integer32
    MAX-ACCESS accessible-for-notify
    STATUS current
    DESCRIPTION
        "Parameter 'cell_id' in event CELL.5"
    ::= { cellEventObjects5 2 }

cell5_ifcname OBJECT-TYPE
    SYNTAX DisplayString
    MAX-ACCESS accessible-for-notify
    STATUS current
    DESCRIPTION
        "Parameter 'ifcname' in event CELL.5"
    ::= { cellEventObjects5 3 }

cellEventObjects6 OBJECT-IDENTITY
    STATUS current
    DESCRIPTION
        "Event CELL.6
        Notify a change of the used cellular technology, which implies different
        radio bands, coding methods and therefore different data rates."
    ::= { cellEventsGroup 6 }

cell6_technology OBJECT-TYPE
    SYNTAX DisplayString
    MAX-ACCESS accessible-for-notify
    STATUS current
    DESCRIPTION
        "Parameter 'technology' in event CELL.6"
    ::= { cellEventObjects6 1 }

cell6_ifcname OBJECT-TYPE
    SYNTAX DisplayString
    MAX-ACCESS accessible-for-notify
    STATUS current
    DESCRIPTION
        "Parameter 'ifcname' in event CELL.6"
    ::= { cellEventObjects6 2 }

cellEventObjects7 OBJECT-IDENTITY
    STATUS current
    DESCRIPTION
        "Event CELL.7
        Received Signal Strength Indication (RSSI) changed to the level
        displayed. This event depends of user's configuration thresholds and
        appears only if the used technology is GSM or GPRS."
    ::= { cellEventsGroup 7 }

cell7_rssi_level OBJECT-TYPE
    SYNTAX Integer32
    MAX-ACCESS accessible-for-notify
    STATUS current
    DESCRIPTION
        "Parameter 'rssi_level' in event CELL.7"
    ::= { cellEventObjects7 1 }

cell7_ifcname OBJECT-TYPE
    SYNTAX DisplayString
    MAX-ACCESS accessible-for-notify
    STATUS current
    DESCRIPTION
        "Parameter 'ifcname' in event CELL.7"
    ::= { cellEventObjects7 2 }

cellEventObjects8 OBJECT-IDENTITY
    STATUS current
    DESCRIPTION
        "Event CELL.8
        Received Signal Code Power (RSCP) has changed to the level displayed or
        the EcNo ratio (received energy per chip divided by the power density in
        the band) has changed to the value displayed. This event depends of
        user's configuration thresholds and appears only if the used technology
        is UMTS, HSDPA or CDMA."
    ::= { cellEventsGroup 8 }

cell8_rscp_level OBJECT-TYPE
    SYNTAX Integer32
    MAX-ACCESS accessible-for-notify
    STATUS current
    DESCRIPTION
        "Parameter 'rscp_level' in event CELL.8"
    ::= { cellEventObjects8 1 }

cell8_ecno_level OBJECT-TYPE
    SYNTAX Integer32
    MAX-ACCESS accessible-for-notify
    STATUS current
    DESCRIPTION
        "Parameter 'ecno_level' in event CELL.8"
    ::= { cellEventObjects8 2 }

cell8_ifcname OBJECT-TYPE
    SYNTAX DisplayString
    MAX-ACCESS accessible-for-notify
    STATUS current
    DESCRIPTION
        "Parameter 'ifcname' in event CELL.8"
    ::= { cellEventObjects8 3 }

cellEventObjects9 OBJECT-IDENTITY
    STATUS current
    DESCRIPTION
        "Event CELL.9
        Active SIM is placed in the displayed socked."
    ::= { cellEventsGroup 9 }

cell9_sim_socket OBJECT-TYPE
    SYNTAX DisplayString
    MAX-ACCESS accessible-for-notify
    STATUS current
    DESCRIPTION
        "Parameter 'sim_socket' in event CELL.9"
    ::= { cellEventObjects9 1 }

cell9_ifcname OBJECT-TYPE
    SYNTAX DisplayString
    MAX-ACCESS accessible-for-notify
    STATUS current
    DESCRIPTION
        "Parameter 'ifcname' in event CELL.9"
    ::= { cellEventObjects9 2 }

cellEventObjects10 OBJECT-IDENTITY
    STATUS current
    DESCRIPTION
        "Event CELL.10
        Interface call stated changed to the state displayed"
    ::= { cellEventsGroup 10 }

cell10_call_state_string OBJECT-TYPE
    SYNTAX DisplayString
    MAX-ACCESS accessible-for-notify
    STATUS current
    DESCRIPTION
        "Parameter 'call_state_string' in event CELL.10"
    ::= { cellEventObjects10 1 }

cell10_call_state_num OBJECT-TYPE
    SYNTAX Integer32
    MAX-ACCESS accessible-for-notify
    STATUS current
    DESCRIPTION
        "Parameter 'call_state_num' in event CELL.10"
    ::= { cellEventObjects10 2 }

cell10_ifcname OBJECT-TYPE
    SYNTAX DisplayString
    MAX-ACCESS accessible-for-notify
    STATUS current
    DESCRIPTION
        "Parameter 'ifcname' in event CELL.10"
    ::= { cellEventObjects10 3 }

cellEventObjects11 OBJECT-IDENTITY
    STATUS current
    DESCRIPTION
        "Event CELL.11
        A successful upgrade has been done to the displayed release"
    ::= { cellEventsGroup 11 }

cell11_frmwr_release OBJECT-TYPE
    SYNTAX DisplayString
    MAX-ACCESS accessible-for-notify
    STATUS current
    DESCRIPTION
        "Parameter 'frmwr_release' in event CELL.11"
    ::= { cellEventObjects11 1 }

cell11_ifcname OBJECT-TYPE
    SYNTAX DisplayString
    MAX-ACCESS accessible-for-notify
    STATUS current
    DESCRIPTION
        "Parameter 'ifcname' in event CELL.11"
    ::= { cellEventObjects11 2 }

cellEventObjects12 OBJECT-IDENTITY
    STATUS current
    DESCRIPTION
        "Event CELL.12
        Voice-call supervision has disabled voice-calls because of the reported
        reason. These are registration problems o low coverage."
    ::= { cellEventsGroup 12 }

cell12_cause OBJECT-TYPE
    SYNTAX DisplayString
    MAX-ACCESS accessible-for-notify
    STATUS current
    DESCRIPTION
        "Parameter 'cause' in event CELL.12"
    ::= { cellEventObjects12 1 }

cell12_ifcname OBJECT-TYPE
    SYNTAX DisplayString
    MAX-ACCESS accessible-for-notify
    STATUS current
    DESCRIPTION
        "Parameter 'ifcname' in event CELL.12"
    ::= { cellEventObjects12 2 }

cellEventObjects13 OBJECT-IDENTITY
    STATUS current
    DESCRIPTION
        "Event CELL.13
        Voice-call supervision allows voice-calls"
    ::= { cellEventsGroup 13 }

cell13_ifcname OBJECT-TYPE
    SYNTAX DisplayString
    MAX-ACCESS accessible-for-notify
    STATUS current
    DESCRIPTION
        "Parameter 'ifcname' in event CELL.13"
    ::= { cellEventObjects13 1 }

cellEventObjects14 OBJECT-IDENTITY
    STATUS current
    DESCRIPTION
        "Event CELL.14
        Module upgrade process has finish, FAILURE result."
    ::= { cellEventsGroup 14 }

cell14_ifcname OBJECT-TYPE
    SYNTAX DisplayString
    MAX-ACCESS accessible-for-notify
    STATUS current
    DESCRIPTION
        "Parameter 'ifcname' in event CELL.14"
    ::= { cellEventObjects14 1 }

cellEventObjects15 OBJECT-IDENTITY
    STATUS current
    DESCRIPTION
        "Event CELL.15
        Module upgrade process has finish, OK result."
    ::= { cellEventsGroup 15 }

cell15_ifcname OBJECT-TYPE
    SYNTAX DisplayString
    MAX-ACCESS accessible-for-notify
    STATUS current
    DESCRIPTION
        "Parameter 'ifcname' in event CELL.15"
    ::= { cellEventObjects15 1 }

cellEventObjects16 OBJECT-IDENTITY
    STATUS current
    DESCRIPTION
        "Event CELL.16
        SIM-LOCK process has finish, failure result."
    ::= { cellEventsGroup 16 }

cell16_cause OBJECT-TYPE
    SYNTAX DisplayString
    MAX-ACCESS accessible-for-notify
    STATUS current
    DESCRIPTION
        "Parameter 'cause' in event CELL.16"
    ::= { cellEventObjects16 1 }

cell16_ifcname OBJECT-TYPE
    SYNTAX DisplayString
    MAX-ACCESS accessible-for-notify
    STATUS current
    DESCRIPTION
        "Parameter 'ifcname' in event CELL.16"
    ::= { cellEventObjects16 2 }

cellEventObjects17 OBJECT-IDENTITY
    STATUS current
    DESCRIPTION
        "Event CELL.17
        SIM-LOCK process has finish, OK result."
    ::= { cellEventsGroup 17 }

cell17_ifcname OBJECT-TYPE
    SYNTAX DisplayString
    MAX-ACCESS accessible-for-notify
    STATUS current
    DESCRIPTION
        "Parameter 'ifcname' in event CELL.17"
    ::= { cellEventObjects17 1 }

cellEventObjects18 OBJECT-IDENTITY
    STATUS current
    DESCRIPTION
        "Event CELL.18
        GPS process has finish, OK result."
    ::= { cellEventsGroup 18 }

cell18_hour OBJECT-TYPE
    SYNTAX Integer32
    MAX-ACCESS accessible-for-notify
    STATUS current
    DESCRIPTION
        "Parameter 'hour' in event CELL.18"
    ::= { cellEventObjects18 1 }

cell18_min OBJECT-TYPE
    SYNTAX Integer32
    MAX-ACCESS accessible-for-notify
    STATUS current
    DESCRIPTION
        "Parameter 'min' in event CELL.18"
    ::= { cellEventObjects18 2 }

cell18_sec OBJECT-TYPE
    SYNTAX Integer32
    MAX-ACCESS accessible-for-notify
    STATUS current
    DESCRIPTION
        "Parameter 'sec' in event CELL.18"
    ::= { cellEventObjects18 3 }

cell18_latg OBJECT-TYPE
    SYNTAX Integer32
    MAX-ACCESS accessible-for-notify
    STATUS current
    DESCRIPTION
        "Parameter 'latg' in event CELL.18"
    ::= { cellEventObjects18 4 }

cell18_latm OBJECT-TYPE
    SYNTAX Integer32
    MAX-ACCESS accessible-for-notify
    STATUS current
    DESCRIPTION
        "Parameter 'latm' in event CELL.18"
    ::= { cellEventObjects18 5 }

cell18_latdm OBJECT-TYPE
    SYNTAX Integer32
    MAX-ACCESS accessible-for-notify
    STATUS current
    DESCRIPTION
        "Parameter 'latdm' in event CELL.18"
    ::= { cellEventObjects18 6 }

cell18_latc OBJECT-TYPE
    SYNTAX DisplayString
    MAX-ACCESS accessible-for-notify
    STATUS current
    DESCRIPTION
        "Parameter 'latc' in event CELL.18"
    ::= { cellEventObjects18 7 }

cell18_long OBJECT-TYPE
    SYNTAX Integer32
    MAX-ACCESS accessible-for-notify
    STATUS current
    DESCRIPTION
        "Parameter 'long' in event CELL.18"
    ::= { cellEventObjects18 8 }

cell18_lonm OBJECT-TYPE
    SYNTAX Integer32
    MAX-ACCESS accessible-for-notify
    STATUS current
    DESCRIPTION
        "Parameter 'lonm' in event CELL.18"
    ::= { cellEventObjects18 9 }

cell18_londm OBJECT-TYPE
    SYNTAX Integer32
    MAX-ACCESS accessible-for-notify
    STATUS current
    DESCRIPTION
        "Parameter 'londm' in event CELL.18"
    ::= { cellEventObjects18 10 }

cell18_lonc OBJECT-TYPE
    SYNTAX DisplayString
    MAX-ACCESS accessible-for-notify
    STATUS current
    DESCRIPTION
        "Parameter 'lonc' in event CELL.18"
    ::= { cellEventObjects18 11 }

cell18_altm OBJECT-TYPE
    SYNTAX Integer32
    MAX-ACCESS accessible-for-notify
    STATUS current
    DESCRIPTION
        "Parameter 'altm' in event CELL.18"
    ::= { cellEventObjects18 12 }

cell18_altdm OBJECT-TYPE
    SYNTAX Integer32
    MAX-ACCESS accessible-for-notify
    STATUS current
    DESCRIPTION
        "Parameter 'altdm' in event CELL.18"
    ::= { cellEventObjects18 13 }

cell18_nsat OBJECT-TYPE
    SYNTAX Integer32
    MAX-ACCESS accessible-for-notify
    STATUS current
    DESCRIPTION
        "Parameter 'nsat' in event CELL.18"
    ::= { cellEventObjects18 14 }

cellEventObjects19 OBJECT-IDENTITY
    STATUS current
    DESCRIPTION
        "Event CELL.19
        GPS synchronization, OK result."
    ::= { cellEventsGroup 19 }

cell19_month OBJECT-TYPE
    SYNTAX Integer32
    MAX-ACCESS accessible-for-notify
    STATUS current
    DESCRIPTION
        "Parameter 'month' in event CELL.19"
    ::= { cellEventObjects19 1 }

cell19_day OBJECT-TYPE
    SYNTAX Integer32
    MAX-ACCESS accessible-for-notify
    STATUS current
    DESCRIPTION
        "Parameter 'day' in event CELL.19"
    ::= { cellEventObjects19 2 }

cell19_year OBJECT-TYPE
    SYNTAX Integer32
    MAX-ACCESS accessible-for-notify
    STATUS current
    DESCRIPTION
        "Parameter 'year' in event CELL.19"
    ::= { cellEventObjects19 3 }

cell19_hour OBJECT-TYPE
    SYNTAX Integer32
    MAX-ACCESS accessible-for-notify
    STATUS current
    DESCRIPTION
        "Parameter 'hour' in event CELL.19"
    ::= { cellEventObjects19 4 }

cell19_min OBJECT-TYPE
    SYNTAX Integer32
    MAX-ACCESS accessible-for-notify
    STATUS current
    DESCRIPTION
        "Parameter 'min' in event CELL.19"
    ::= { cellEventObjects19 5 }

cell19_sec OBJECT-TYPE
    SYNTAX Integer32
    MAX-ACCESS accessible-for-notify
    STATUS current
    DESCRIPTION
        "Parameter 'sec' in event CELL.19"
    ::= { cellEventObjects19 6 }

cellEventObjects20 OBJECT-IDENTITY
    STATUS current
    DESCRIPTION
        "Event CELL.20
        GPS process has finish, OK result."
    ::= { cellEventsGroup 20 }

cell20_hdop OBJECT-TYPE
    SYNTAX Integer32
    MAX-ACCESS accessible-for-notify
    STATUS current
    DESCRIPTION
        "Parameter 'hdop' in event CELL.20"
    ::= { cellEventObjects20 1 }

cell20_latg OBJECT-TYPE
    SYNTAX Integer32
    MAX-ACCESS accessible-for-notify
    STATUS current
    DESCRIPTION
        "Parameter 'latg' in event CELL.20"
    ::= { cellEventObjects20 2 }

cell20_latm OBJECT-TYPE
    SYNTAX Integer32
    MAX-ACCESS accessible-for-notify
    STATUS current
    DESCRIPTION
        "Parameter 'latm' in event CELL.20"
    ::= { cellEventObjects20 3 }

cell20_latdm OBJECT-TYPE
    SYNTAX Integer32
    MAX-ACCESS accessible-for-notify
    STATUS current
    DESCRIPTION
        "Parameter 'latdm' in event CELL.20"
    ::= { cellEventObjects20 4 }

cell20_latc OBJECT-TYPE
    SYNTAX DisplayString
    MAX-ACCESS accessible-for-notify
    STATUS current
    DESCRIPTION
        "Parameter 'latc' in event CELL.20"
    ::= { cellEventObjects20 5 }

cell20_long OBJECT-TYPE
    SYNTAX Integer32
    MAX-ACCESS accessible-for-notify
    STATUS current
    DESCRIPTION
        "Parameter 'long' in event CELL.20"
    ::= { cellEventObjects20 6 }

cell20_lonm OBJECT-TYPE
    SYNTAX Integer32
    MAX-ACCESS accessible-for-notify
    STATUS current
    DESCRIPTION
        "Parameter 'lonm' in event CELL.20"
    ::= { cellEventObjects20 7 }

cell20_londm OBJECT-TYPE
    SYNTAX Integer32
    MAX-ACCESS accessible-for-notify
    STATUS current
    DESCRIPTION
        "Parameter 'londm' in event CELL.20"
    ::= { cellEventObjects20 8 }

cell20_lonc OBJECT-TYPE
    SYNTAX DisplayString
    MAX-ACCESS accessible-for-notify
    STATUS current
    DESCRIPTION
        "Parameter 'lonc' in event CELL.20"
    ::= { cellEventObjects20 9 }

cell20_altm OBJECT-TYPE
    SYNTAX Integer32
    MAX-ACCESS accessible-for-notify
    STATUS current
    DESCRIPTION
        "Parameter 'altm' in event CELL.20"
    ::= { cellEventObjects20 10 }

cell20_altdm OBJECT-TYPE
    SYNTAX Integer32
    MAX-ACCESS accessible-for-notify
    STATUS current
    DESCRIPTION
        "Parameter 'altdm' in event CELL.20"
    ::= { cellEventObjects20 11 }

cell20_nsat OBJECT-TYPE
    SYNTAX Integer32
    MAX-ACCESS accessible-for-notify
    STATUS current
    DESCRIPTION
        "Parameter 'nsat' in event CELL.20"
    ::= { cellEventObjects20 12 }

cellEventObjects22 OBJECT-IDENTITY
    STATUS current
    DESCRIPTION
        "Event CELL.22
        GPS Zone filter status change has occur."
    ::= { cellEventsGroup 22 }

cell22_zone OBJECT-TYPE
    SYNTAX Integer32
    MAX-ACCESS accessible-for-notify
    STATUS current
    DESCRIPTION
        "Parameter 'zone' in event CELL.22"
    ::= { cellEventObjects22 1 }

cell22_status OBJECT-TYPE
    SYNTAX Integer32
    MAX-ACCESS accessible-for-notify
    STATUS current
    DESCRIPTION
        "Parameter 'status' in event CELL.22"
    ::= { cellEventObjects22 2 }

cell22_state OBJECT-TYPE
    SYNTAX Integer32
    MAX-ACCESS accessible-for-notify
    STATUS current
    DESCRIPTION
        "Parameter 'state' in event CELL.22"
    ::= { cellEventObjects22 3 }

cellEventObjects23 OBJECT-IDENTITY
    STATUS current
    DESCRIPTION
        "Event CELL.23
        GPS Advisor status change has occur."
    ::= { cellEventsGroup 23 }

cell23_adv OBJECT-TYPE
    SYNTAX Integer32
    MAX-ACCESS accessible-for-notify
    STATUS current
    DESCRIPTION
        "Parameter 'adv' in event CELL.23"
    ::= { cellEventObjects23 1 }

cell23_status OBJECT-TYPE
    SYNTAX Integer32
    MAX-ACCESS accessible-for-notify
    STATUS current
    DESCRIPTION
        "Parameter 'status' in event CELL.23"
    ::= { cellEventObjects23 2 }


cellNotification1 NOTIFICATION-TYPE
    OBJECTS { 
              cell1_info_string, 
              cell1_ifcname 
            }
    STATUS current
    DESCRIPTION
        "Notification of Event CELL.1

        Message: '$1 intf $2'

        Parameters list:
              $1: cell1_info_string
              $2: cell1_ifcname

        Generic informational event."
    ::= { cellNotificationsPrefix 1 }

cellNotification2 NOTIFICATION-TYPE
    OBJECTS { 
              cell2_error_string, 
              cell2_ifcname 
            }
    STATUS current
    DESCRIPTION
        "Notification of Event CELL.2

        Message: '$1 intf $2'

        Parameters list:
              $1: cell2_error_string
              $2: cell2_ifcname

        Generic error report."
    ::= { cellNotificationsPrefix 2 }

cellNotification3 NOTIFICATION-TYPE
    OBJECTS { 
              cell3_state, 
              cell3_ifcname 
            }
    STATUS current
    DESCRIPTION
        "Notification of Event CELL.3

        Message: 'CHANGED Registration state to $1, on interface $2'

        Parameters list:
              $1: cell3_state
              $2: cell3_ifcname

        Registration state has changed."
    ::= { cellNotificationsPrefix 3 }

cellNotification4 NOTIFICATION-TYPE
    OBJECTS { 
              cell4_operator, 
              cell4_ifcname 
            }
    STATUS current
    DESCRIPTION
        "Notification of Event CELL.4

        Message: 'CHANGED PLMN to $1, on interface $2'

        Parameters list:
              $1: cell4_operator
              $2: cell4_ifcname

        The cellular interface now uses a different Public Land Mobile Network,
        (Mobile Operator) identified by the number displayed."
    ::= { cellNotificationsPrefix 4 }

cellNotification5 NOTIFICATION-TYPE
    OBJECTS { 
              cell5_location_area_code, 
              cell5_cell_id,
              cell5_ifcname 
            }
    STATUS current
    DESCRIPTION
        "Notification of Event CELL.5

        Message: 'CHANGE Connected cell LAC $1 CELL ID $2, on interface $3'

        Parameters list:
              $1: cell5_location_area_code
              $2: cell5_cell_id
              $3: cell5_ifcname

        The cellular interface is connected to a different base station,
        identified by the Location Area Code (LAC) and the Cell Identifier code
        (CiD)."
    ::= { cellNotificationsPrefix 5 }

cellNotification6 NOTIFICATION-TYPE
    OBJECTS { 
              cell6_technology, 
              cell6_ifcname 
            }
    STATUS current
    DESCRIPTION
        "Notification of Event CELL.6

        Message: 'CHANGED cellular technology to $1, on interface $2'

        Parameters list:
              $1: cell6_technology
              $2: cell6_ifcname

        Notify a change of the used cellular technology, which implies different
        radio bands, coding methods and therefore different data rates."
    ::= { cellNotificationsPrefix 6 }

cellNotification7 NOTIFICATION-TYPE
    OBJECTS { 
              cell7_rssi_level, 
              cell7_ifcname 
            }
    STATUS current
    DESCRIPTION
        "Notification of Event CELL.7

        Message: 'CHANGED GSM/GPRS Coverage, RSSI $1 dBm, on interface $2'

        Parameters list:
              $1: cell7_rssi_level
              $2: cell7_ifcname

        Received Signal Strength Indication (RSSI) changed to the level
        displayed. This event depends of user's configuration thresholds and
        appears only if the used technology is GSM or GPRS."
    ::= { cellNotificationsPrefix 7 }

cellNotification8 NOTIFICATION-TYPE
    OBJECTS { 
              cell8_rscp_level, 
              cell8_ecno_level,
              cell8_ifcname 
            }
    STATUS current
    DESCRIPTION
        "Notification of Event CELL.8

        Message: 'CHANGED 3GPP Coverage, RSCP to $1 dBm and EcNo to $2 dB, on interface $3'

        Parameters list:
              $1: cell8_rscp_level
              $2: cell8_ecno_level
              $3: cell8_ifcname

        Received Signal Code Power (RSCP) has changed to the level displayed or
        the EcNo ratio (received energy per chip divided by the power density in
        the band) has changed to the value displayed. This event depends of
        user's configuration thresholds and appears only if the used technology
        is UMTS, HSDPA or CDMA."
    ::= { cellNotificationsPrefix 8 }

cellNotification9 NOTIFICATION-TYPE
    OBJECTS { 
              cell9_sim_socket, 
              cell9_ifcname 
            }
    STATUS current
    DESCRIPTION
        "Notification of Event CELL.9

        Message: 'CHANGED Used SIM. Used SIM is located in the $1 socket, on interface $2'

        Parameters list:
              $1: cell9_sim_socket
              $2: cell9_ifcname

        Active SIM is placed in the displayed socked."
    ::= { cellNotificationsPrefix 9 }

cellNotification10 NOTIFICATION-TYPE
    OBJECTS { 
              cell10_call_state_string, 
              cell10_call_state_num,
              cell10_ifcname 
            }
    STATUS current
    DESCRIPTION
        "Notification of Event CELL.10

        Message: 'CHANGED Call state to $1 ($2), on interface $3'

        Parameters list:
              $1: cell10_call_state_string
              $2: cell10_call_state_num
              $3: cell10_ifcname

        Interface call stated changed to the state displayed"
    ::= { cellNotificationsPrefix 10 }

cellNotification11 NOTIFICATION-TYPE
    OBJECTS { 
              cell11_frmwr_release, 
              cell11_ifcname 
            }
    STATUS current
    DESCRIPTION
        "Notification of Event CELL.11

        Message: 'CHANGED cellular module firmware to release $1, on interface $2'

        Parameters list:
              $1: cell11_frmwr_release
              $2: cell11_ifcname

        A successful upgrade has been done to the displayed release"
    ::= { cellNotificationsPrefix 11 }

cellNotification12 NOTIFICATION-TYPE
    OBJECTS { 
              cell12_cause, 
              cell12_ifcname 
            }
    STATUS current
    DESCRIPTION
        "Notification of Event CELL.12

        Message: 'Voice calls disabled due to $1, on interface $2'

        Parameters list:
              $1: cell12_cause
              $2: cell12_ifcname

        Voice-call supervision has disabled voice-calls because of the reported
        reason. These are registration problems o low coverage."
    ::= { cellNotificationsPrefix 12 }

cellNotification13 NOTIFICATION-TYPE
    OBJECTS { 
              cell13_ifcname 
            }
    STATUS current
    DESCRIPTION
        "Notification of Event CELL.13

        Message: 'Voice calls enabled, on interface $1'

        Parameters list:
              $1: cell13_ifcname

        Voice-call supervision allows voice-calls"
    ::= { cellNotificationsPrefix 13 }

cellNotification14 NOTIFICATION-TYPE
    OBJECTS { 
              cell14_ifcname 
            }
    STATUS current
    DESCRIPTION
        "Notification of Event CELL.14

        Message: 'Module upgrade FAILURE, on interface $1'

        Parameters list:
              $1: cell14_ifcname

        Module upgrade process has finish, FAILURE result."
    ::= { cellNotificationsPrefix 14 }

cellNotification15 NOTIFICATION-TYPE
    OBJECTS { 
              cell15_ifcname 
            }
    STATUS current
    DESCRIPTION
        "Notification of Event CELL.15

        Message: 'Module upgrade OK, on interface $1'

        Parameters list:
              $1: cell15_ifcname

        Module upgrade process has finish, OK result."
    ::= { cellNotificationsPrefix 15 }

cellNotification16 NOTIFICATION-TYPE
    OBJECTS { 
              cell16_cause, 
              cell16_ifcname 
            }
    STATUS current
    DESCRIPTION
        "Notification of Event CELL.16

        Message: 'SIM-LOCK process failure($1), on interface $2'

        Parameters list:
              $1: cell16_cause
              $2: cell16_ifcname

        SIM-LOCK process has finish, failure result."
    ::= { cellNotificationsPrefix 16 }

cellNotification17 NOTIFICATION-TYPE
    OBJECTS { 
              cell17_ifcname 
            }
    STATUS current
    DESCRIPTION
        "Notification of Event CELL.17

        Message: 'SIM-LOCK process finish OK, on interface $1'

        Parameters list:
              $1: cell17_ifcname

        SIM-LOCK process has finish, OK result."
    ::= { cellNotificationsPrefix 17 }

cellNotification18 NOTIFICATION-TYPE
    OBJECTS { 
              cell18_hour, 
              cell18_min,
              cell18_sec,
              cell18_latg,
              cell18_latm,
              cell18_latdm,
              cell18_latc,
              cell18_long,
              cell18_lonm,
              cell18_londm,
              cell18_lonc,
              cell18_altm,
              cell18_altdm,
              cell18_nsat 
            }
    STATUS current
    DESCRIPTION
        "Notification of Event CELL.18

        Message: 'GPS process finish OK, information printed: T: $1:$2:$3 Lat: $4— $5.$6' $7 Lon: $8— $9.$10' $11 Alt: $12.$13 m N—sat: $14'

        Parameters list:
              $1: cell18_hour
              $2: cell18_min
              $3: cell18_sec
              $4: cell18_latg
              $5: cell18_latm
              $6: cell18_latdm
              $7: cell18_latc
              $8: cell18_long
              $9: cell18_lonm
              $10: cell18_londm
              $11: cell18_lonc
              $12: cell18_altm
              $13: cell18_altdm
              $14: cell18_nsat

        GPS process has finish, OK result."
    ::= { cellNotificationsPrefix 18 }

cellNotification19 NOTIFICATION-TYPE
    OBJECTS { 
              cell19_month, 
              cell19_day,
              cell19_year,
              cell19_hour,
              cell19_min,
              cell19_sec 
            }
    STATUS current
    DESCRIPTION
        "Notification of Event CELL.19

        Message: 'GPS synchronization OK, information printed: Date: $1/$2/$3 Time: $4:$5:$6'

        Parameters list:
              $1: cell19_month
              $2: cell19_day
              $3: cell19_year
              $4: cell19_hour
              $5: cell19_min
              $6: cell19_sec

        GPS synchronization, OK result."
    ::= { cellNotificationsPrefix 19 }

cellNotification20 NOTIFICATION-TYPE
    OBJECTS { 
              cell20_hdop, 
              cell20_latg,
              cell20_latm,
              cell20_latdm,
              cell20_latc,
              cell20_long,
              cell20_lonm,
              cell20_londm,
              cell20_lonc,
              cell20_altm,
              cell20_altdm,
              cell20_nsat 
            }
    STATUS current
    DESCRIPTION
        "Notification of Event CELL.20

        Message: 'GPS ADVISOR location OK, information: HDOP: $1, Lat: $2— $3.$4' $5 Lon: $6— $7.$8' $9 Alt: $10.$11 m N—sat: $12'

        Parameters list:
              $1: cell20_hdop
              $2: cell20_latg
              $3: cell20_latm
              $4: cell20_latdm
              $5: cell20_latc
              $6: cell20_long
              $7: cell20_lonm
              $8: cell20_londm
              $9: cell20_lonc
              $10: cell20_altm
              $11: cell20_altdm
              $12: cell20_nsat

        GPS process has finish, OK result."
    ::= { cellNotificationsPrefix 20 }

cellNotification21 NOTIFICATION-TYPE
    STATUS current
    DESCRIPTION
        "Notification of Event CELL.21

        Message: 'GPS Location failure due GPS don't detect signal'

        GPS don't get satellites signals."
    ::= { cellNotificationsPrefix 21 }

cellNotification22 NOTIFICATION-TYPE
    OBJECTS { 
              cell22_zone, 
              cell22_status,
              cell22_state 
            }
    STATUS current
    DESCRIPTION
        "Notification of Event CELL.22

        Message: 'GPS ZONE filter $1 status change to $2, zone state $3'

        Parameters list:
              $1: cell22_zone
              $2: cell22_status
              $3: cell22_state

        GPS Zone filter status change has occur."
    ::= { cellNotificationsPrefix 22 }

cellNotification23 NOTIFICATION-TYPE
    OBJECTS { 
              cell23_adv, 
              cell23_status 
            }
    STATUS current
    DESCRIPTION
        "Notification of Event CELL.23

        Message: 'GPS ADVISOR $1 status change to $2'

        Parameters list:
              $1: cell23_adv
              $2: cell23_status

        GPS Advisor status change has occur."
    ::= { cellNotificationsPrefix 23 }

cellNotification24 NOTIFICATION-TYPE
    STATUS current
    DESCRIPTION
        "Notification of Event CELL.24

        Message: 'GPS ADVISOR timeout waiting position'

        Timeout waiting GPS position."
    ::= { cellNotificationsPrefix 24 }


END
