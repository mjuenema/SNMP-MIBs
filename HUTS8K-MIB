HUTS8K-MIB DEFINITIONS ::= BEGIN

IMPORTS

	enterprises
			FROM RFC1155-SMI

  	OBJECT-TYPE
			FROM RFC-1212;

	HCL            			OBJECT IDENTIFIER ::= { enterprises 1694 }	
	HUTS         			OBJECT IDENTIFIER ::= { HCL 9 }

-- HUTS PRIMARY DEFINITIONS

	NETWORK				OBJECT IDENTIFIER ::= { HUTS 1 }
	NETWORK_DNS			OBJECT IDENTIFIER ::= { HUTS 2 }
	NETWORK_GATEWAY		  	OBJECT IDENTIFIER ::= { HUTS 3 }
	NETWORK_HOST		  	OBJECT IDENTIFIER ::= { HUTS 4 }

	COM_PORT			OBJECT IDENTIFIER ::= { HUTS 5 }
	SERVICE_CONFIG			OBJECT IDENTIFIER ::= { HUTS 7 }
	ASSET_INFORMATION		OBJECT IDENTIFIER ::= { HUTS 10 }
	CPU_UTILIZATION			OBJECT IDENTIFIER ::= { HUTS 13 }

-- HUTS SECONDARY SUB LEVEL DEFINITIONS


-- NETWORK SUB LEVEL DEFINITIONS

	CLIENTNAME OBJECT-TYPE
        SYNTAX  DisplayString
        ACCESS  read-write
        STATUS  mandatory
        DESCRIPTION
            "Client Name of thin Client"
		::= { NETWORK 1 }

	GRP_NAME OBJECT-TYPE
        SYNTAX  DisplayString
        ACCESS  read-write
        STATUS  mandatory
        DESCRIPTION
            "Group Name of thin Client"
		::= { NETWORK 2 }

	DHCPSET OBJECT-TYPE
        SYNTAX INTEGER
        ACCESS read-write
        STATUS mandatory
        DESCRIPTION
            "Option for DHCP Enable"
		::= { NETWORK 3 }

	STATICIP OBJECT-TYPE
        SYNTAX  DisplayString
        ACCESS  read-write
        STATUS  mandatory
        DESCRIPTION
            "Static IP Address of Thin Client"
		::= { NETWORK 4 }

	SUBNETMASK OBJECT-TYPE
        SYNTAX  DisplayString
        ACCESS  read-write
        STATUS  mandatory
        DESCRIPTION
            "Sub-Net-Mask Address of Thin Client"
		::= { NETWORK 5 }
	
-- NETWORK_GATEWAY SUB LEVEL DEFINITIONS

	NGATEWAYS OBJECT-TYPE
        SYNTAX INTEGER
        ACCESS read-write
        STATUS mandatory
        DESCRIPTION
            "Number of Gateways"
		::= { NETWORK_GATEWAY 1 }

	GATEWAYIP OBJECT-TYPE
        SYNTAX  DisplayString
        ACCESS  read-write
        STATUS  mandatory
        DESCRIPTION
            "Gateway IP address of Thin Client"
		::= { NETWORK_GATEWAY 2 }

	DELGATEWAY OBJECT-TYPE
        SYNTAX  DisplayString
        ACCESS  read-write
        STATUS  mandatory
        DESCRIPTION
            "Option for Gateway addition"
		::= { NETWORK_GATEWAY 3 }

	
	GATEWAYTABLE OBJECT-TYPE
	SYNTAX     SEQUENCE OF GatewayEntry
        ACCESS  read-write
        STATUS  mandatory
    	DESCRIPTION
            "The Gateway Table."
	    	::= { NETWORK_GATEWAY 4 }


	GATEWAYENTRY OBJECT-TYPE
 	SYNTAX	GatewayEntry   
 	ACCESS  read-write
       	STATUS  mandatory
    	DESCRIPTION
            "Each Gateway address"
    	INDEX      { IP }
	    	::= { GATEWAYTABLE 1 }

	GatewayEntry ::= SEQUENCE {
    		IP     	DisplayString
    	}

	IP 	OBJECT-TYPE
	SYNTAX  DisplayString
        ACCESS  read-write
       	STATUS  mandatory
       	DESCRIPTION
       	    "IP of the Gateway."
        ::= { GATEWAYENTRY 1 }

-- NETWORK_DNS SUB LEVEL DEFINITIONS

	DOMAINNAME OBJECT-TYPE
        SYNTAX INTEGER
        ACCESS read-write
        STATUS mandatory
        DESCRIPTION
            "Domain Name of Thin Client"
		::= { NETWORK_DNS 1 }

	NDNS OBJECT-TYPE
        SYNTAX INTEGER
        ACCESS read-write
        STATUS mandatory
        DESCRIPTION
            "Number of DNS Server's"
		::= { NETWORK_DNS 2 }

	DNSIP OBJECT-TYPE
        SYNTAX  DisplayString
        ACCESS  read-write
        STATUS  mandatory
        DESCRIPTION
            "IP Address of Domain Name of server"
		::= { NETWORK_DNS 3 }


	DELDNS OBJECT-TYPE
        SYNTAX  DisplayString
        ACCESS  read-write
        STATUS  mandatory
        DESCRIPTION
            "Option for DNS Configuration"
		::= { NETWORK_DNS 4 }


-- NETWORK_HOST SUB LEVEL DEFINITIONS

	NO_OF_HOSTS OBJECT-TYPE
        SYNTAX INTEGER
        ACCESS read-write
        STATUS mandatory
        DESCRIPTION
            "Number of Host table Entries"
		::= { NETWORK_HOST 1 }

	HOST_N OBJECT-TYPE
        SYNTAX  DisplayString
        ACCESS  read-write
        STATUS  mandatory
        DESCRIPTION
            "Name of Host in Host tables"
		::= { NETWORK_HOST 2 }

	HOST_IP OBJECT-TYPE
        SYNTAX  DisplayString
        ACCESS  read-write
        STATUS  mandatory
        DESCRIPTION
            "IP address of Corresponding Host name in the host table"
		::= { NETWORK_HOST 3 }


	DELHOST OBJECT-TYPE
        SYNTAX  DisplayString
        ACCESS  read-write
        STATUS  mandatory
        DESCRIPTION
            "Option for Host table"
		::= { NETWORK_HOST 4 }


-- COM_PORT SUB LEVEL DEFINITIONS

	BAUDRATE1 OBJECT-TYPE
        SYNTAX INTEGER
        ACCESS read-write
        STATUS mandatory
        DESCRIPTION
            "Baud Rate for Serial Port 1"
		::= { COM_PORT 1 }

	DATASIZE1 OBJECT-TYPE
        SYNTAX INTEGER
        ACCESS read-write
        STATUS mandatory
        DESCRIPTION
            "Data size for Serial port 1"
		::= { COM_PORT 2 }

	STOPBIT1 OBJECT-TYPE
        SYNTAX INTEGER
        ACCESS read-write
        STATUS mandatory
        DESCRIPTION
            "Stop bits for Serial port 1"
		::= { COM_PORT 3 }

	PARITYBIT1 OBJECT-TYPE
        SYNTAX INTEGER
        ACCESS read-write
        STATUS mandatory
        DESCRIPTION
            "Parity bits for serial port 1"
		::= { COM_PORT 4 }

	FLOWCONTROL1 OBJECT-TYPE
        SYNTAX INTEGER
        ACCESS read-write
        STATUS mandatory
        DESCRIPTION
            "Flow Controll for serial port 1"
		::= { COM_PORT 5 }

	BAUDRATE2 OBJECT-TYPE
        SYNTAX INTEGER
        ACCESS read-write
        STATUS mandatory
        DESCRIPTION
            "Baud Rate for Serial Port 2"
	
		::= { COM_PORT 6 }

	DATASIZE2 OBJECT-TYPE
        SYNTAX INTEGER
        ACCESS read-write
        STATUS mandatory
        DESCRIPTION
            "Data size for Serial port 2"
		::= { COM_PORT 7 }

	STOPBIT2 OBJECT-TYPE
        SYNTAX INTEGER
        ACCESS read-write
        STATUS mandatory
        DESCRIPTION
            "Stop bits for Serial port 2"
		::= { COM_PORT 8 }

	PARITYBIT2 OBJECT-TYPE
        SYNTAX INTEGER
        ACCESS read-write
        STATUS mandatory
        DESCRIPTION
            "Parity bits for serial port 2"
		::= { COM_PORT 9 }

	FLOWCONTROL2 OBJECT-TYPE
        SYNTAX INTEGER
        ACCESS read-write
        STATUS mandatory
        DESCRIPTION
            "Flow Controll for serial port 1"
		::= { COM_PORT 10 }

-- SERVICE_CONFIG SUB LEVEL DEFINITIONS

	Telnet OBJECT-TYPE
        SYNTAX INTEGER
        ACCESS read-write
        STATUS mandatory
        DESCRIPTION
            "Option for Telnet Service"
		::= { SERVICE_CONFIG 1 }

	 FTP OBJECT-TYPE
        SYNTAX INTEGER
        ACCESS read-write
        STATUS mandatory
        DESCRIPTION
            "Option for FTP Service"
		::= { SERVICE_CONFIG 2 }

	CRON OBJECT-TYPE
        SYNTAX  DisplayString
        ACCESS  read-write
        STATUS  mandatory
        DESCRIPTION
            "Option for CROND Service"
		::= { SERVICE_CONFIG 3 }
	
	LPD OBJECT-TYPE
        SYNTAX INTEGER
        ACCESS read-write
        STATUS mandatory
        DESCRIPTION
            "Option for Printer Service"
		::= { SERVICE_CONFIG 4 }
	
	RSH OBJECT-TYPE
        SYNTAX INTEGER
        ACCESS read-write
        STATUS mandatory
        DESCRIPTION
            "Option for RSH  Service"
		::= { SERVICE_CONFIG 5 }
	
	RLOGIN OBJECT-TYPE
        SYNTAX  DisplayString
        ACCESS  read-write
        STATUS  mandatory
        DESCRIPTION
            "Option for RLOGIN  Service"
		::= { SERVICE_CONFIG 6 }

	REXEC OBJECT-TYPE
        SYNTAX  DisplayString
        ACCESS  read-write
        STATUS  mandatory
        DESCRIPTION
            "Option for REXEC  Service"
		::= { SERVICE_CONFIG 7 }

	SSH OBJECT-TYPE
	SYNTAX INTEGER
        ACCESS read-write
        STATUS mandatory
        DESCRIPTION
            "Option for SSH  Service"
		::= { SERVICE_CONFIG 8 }

	HUTCONTROL OBJECT-TYPE
        SYNTAX  DisplayString
        ACCESS  read-write
        STATUS  mandatory
        DESCRIPTION
            "Option for HUTSCONTROLL  Service"
		::= { SERVICE_CONFIG 9 }



-- ASSET_INFORMATIONSUB LEVEL DEFINITIONS

	MACID OBJECT-TYPE
        SYNTAX DisplayString
        ACCESS read-only
        STATUS mandatory
        DESCRIPTION
            "Machine ID of the device"
		::= { ASSET_INFORMATION 1 }

	Serial_Number OBJECT-TYPE
        SYNTAX DisplayString
        ACCESS read-only
        STATUS mandatory
        DESCRIPTION
            "Serial Number of the Device"
		::= { ASSET_INFORMATION 2 }

	CLIENTVER OBJECT-TYPE
        SYNTAX  DisplayString
        ACCESS  read-only
        STATUS  mandatory
        DESCRIPTION
            "Version of Thin Client"
		::= { ASSET_INFORMATION 3 }
	
	CLIENTMODEL OBJECT-TYPE
        SYNTAX  DisplayString
        ACCESS  read-only
        STATUS  mandatory
        DESCRIPTION
            "Model Number of Thin Client"
		::= { ASSET_INFORMATION 4 }

	CLIENTOS OBJECT-TYPE
        SYNTAX  DisplayString
        ACCESS  read-only
        STATUS  mandatory
        DESCRIPTION
            "Operating System of Thin Client"
		::= { ASSET_INFORMATION 5 }

	CLIENTKERNEL OBJECT-TYPE
        SYNTAX  DisplayString
        ACCESS  read-only
        STATUS  mandatory
        DESCRIPTION
            "Kernel Version of Thin Client"
		::= { ASSET_INFORMATION 6 }
	
	RAMSIZE OBJECT-TYPE
        SYNTAX  DisplayString
        ACCESS  read-only
        STATUS  mandatory
        DESCRIPTION
            "Total RAM Size of Thin Client"
		::= { ASSET_INFORMATION 7 }

   	RAMAVAIL OBJECT-TYPE
        SYNTAX  DisplayString
        ACCESS  read-only
        STATUS  mandatory
        DESCRIPTION
            "Available RAM Size of Thin Client"
		::= { ASSET_INFORMATION 8 }

	DOMSIZE OBJECT-TYPE
        SYNTAX  DisplayString
        ACCESS  read-only
        STATUS  mandatory
        DESCRIPTION
            "Available DOM Size of the Thin Client"
		::= { ASSET_INFORMATION 9 }

	PRCRMODEL OBJECT-TYPE
        SYNTAX  DisplayString
        ACCESS  read-only
        STATUS  mandatory
        DESCRIPTION
            "Processor model of Thin Client"
		::= { ASSET_INFORMATION 11 }


	Manufacturer OBJECT-TYPE
        SYNTAX  DisplayString
        ACCESS  read-only
        STATUS  mandatory
        DESCRIPTION
            "Manufaturer of Thin Client"
		::= { ASSET_INFORMATION 13 }


-- CPU_UTILIZATION SUB LEVEL DEFINITIONS

	USER_UTILIZATION OBJECT-TYPE
        SYNTAX DisplayString
        ACCESS read-write
        STATUS mandatory
        DESCRIPTION
            "CPU Utilization for User space"
		::= { CPU_UTILIZATION 1 }
	
	SYSTEM_UTILIZATION OBJECT-TYPE
        SYNTAX INTEGER
        ACCESS read-write
        STATUS mandatory
        DESCRIPTION
            "CPU Utilization for System Space"
		::= { CPU_UTILIZATION 2 }
  
END
