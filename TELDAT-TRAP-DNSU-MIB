-- file automatically created


TELDAT-TRAP-DNSU-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


dnsuTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the DNSU event subsystem."
    REVISION "201401200930Z"
    DESCRIPTION "Initial implementation"
        ::= { telEventTraps 204 }


dnsuEventsGroup	OBJECT IDENTIFIER	::= { dnsuTrapsMIB 1 }

dnsuNotifications	OBJECT IDENTIFIER	::= { dnsuTrapsMIB 2 }
dnsuNotificationsPrefix	OBJECT IDENTIFIER	::= { dnsuNotifications 0 }

dnsuEventObjects1 OBJECT-IDENTITY
    STATUS current
    DESCRIPTION
        "Event DNSU.1
        There was an error during initialize"
    ::= { dnsuEventsGroup 1 }

dnsu1_error OBJECT-TYPE
    SYNTAX DisplayString
    MAX-ACCESS accessible-for-notify
    STATUS current
    DESCRIPTION
        "Parameter 'error' in event DNSU.1"
    ::= { dnsuEventObjects1 1 }

dnsuEventObjects3 OBJECT-IDENTITY
    STATUS current
    DESCRIPTION
        "Event DNSU.3
        IP address has changed for an entry."
    ::= { dnsuEventsGroup 3 }

dnsu3_entry_id OBJECT-TYPE
    SYNTAX Integer32
    MAX-ACCESS accessible-for-notify
    STATUS current
    DESCRIPTION
        "Parameter 'entry_id' in event DNSU.3"
    ::= { dnsuEventObjects3 1 }

dnsu3_last_ip_address OBJECT-TYPE
    SYNTAX IpAddress
    MAX-ACCESS accessible-for-notify
    STATUS current
    DESCRIPTION
        "Parameter 'last_ip_address' in event DNSU.3"
    ::= { dnsuEventObjects3 2 }

dnsu3_new_ip_address OBJECT-TYPE
    SYNTAX IpAddress
    MAX-ACCESS accessible-for-notify
    STATUS current
    DESCRIPTION
        "Parameter 'new_ip_address' in event DNSU.3"
    ::= { dnsuEventObjects3 3 }

dnsuEventObjects4 OBJECT-IDENTITY
    STATUS current
    DESCRIPTION
        "Event DNSU.4
        IP addres has to be updated because of timer expiration."
    ::= { dnsuEventsGroup 4 }

dnsu4_entry_id OBJECT-TYPE
    SYNTAX Integer32
    MAX-ACCESS accessible-for-notify
    STATUS current
    DESCRIPTION
        "Parameter 'entry_id' in event DNSU.4"
    ::= { dnsuEventObjects4 1 }

dnsu4_last_ip OBJECT-TYPE
    SYNTAX IpAddress
    MAX-ACCESS accessible-for-notify
    STATUS current
    DESCRIPTION
        "Parameter 'last_ip' in event DNSU.4"
    ::= { dnsuEventObjects4 2 }

dnsuEventObjects5 OBJECT-IDENTITY
    STATUS current
    DESCRIPTION
        "Event DNSU.5
        An http request will be created."
    ::= { dnsuEventsGroup 5 }

dnsu5_entry_id OBJECT-TYPE
    SYNTAX Integer32
    MAX-ACCESS accessible-for-notify
    STATUS current
    DESCRIPTION
        "Parameter 'entry_id' in event DNSU.5"
    ::= { dnsuEventObjects5 1 }

dnsu5_protocol OBJECT-TYPE
    SYNTAX DisplayString
    MAX-ACCESS accessible-for-notify
    STATUS current
    DESCRIPTION
        "Parameter 'protocol' in event DNSU.5"
    ::= { dnsuEventObjects5 2 }

dnsuEventObjects6 OBJECT-IDENTITY
    STATUS current
    DESCRIPTION
        "Event DNSU.6
        A strange response has been received, perharps we are trying to connect
        to the wrong server"
    ::= { dnsuEventsGroup 6 }

dnsu6_entry_id OBJECT-TYPE
    SYNTAX Integer32
    MAX-ACCESS accessible-for-notify
    STATUS current
    DESCRIPTION
        "Parameter 'entry_id' in event DNSU.6"
    ::= { dnsuEventObjects6 1 }

dnsuEventObjects7 OBJECT-IDENTITY
    STATUS current
    DESCRIPTION
        "Event DNSU.7
        A correct response has been received from the server"
    ::= { dnsuEventsGroup 7 }

dnsu7_entry_id OBJECT-TYPE
    SYNTAX Integer32
    MAX-ACCESS accessible-for-notify
    STATUS current
    DESCRIPTION
        "Parameter 'entry_id' in event DNSU.7"
    ::= { dnsuEventObjects7 1 }

dnsu7_message_identifier OBJECT-TYPE
    SYNTAX DisplayString
    MAX-ACCESS accessible-for-notify
    STATUS current
    DESCRIPTION
        "Parameter 'message_identifier' in event DNSU.7"
    ::= { dnsuEventObjects7 2 }

dnsuEventObjects8 OBJECT-IDENTITY
    STATUS current
    DESCRIPTION
        "Event DNSU.8
        A response has an answer field that does not match the query."
    ::= { dnsuEventsGroup 8 }

dnsu8_entry_id OBJECT-TYPE
    SYNTAX Integer32
    MAX-ACCESS accessible-for-notify
    STATUS current
    DESCRIPTION
        "Parameter 'entry_id' in event DNSU.8"
    ::= { dnsuEventObjects8 1 }

dnsuEventObjects9 OBJECT-IDENTITY
    STATUS current
    DESCRIPTION
        "Event DNSU.9
        IP update fihished succesfully for an entry"
    ::= { dnsuEventsGroup 9 }

dnsu9_identifier OBJECT-TYPE
    SYNTAX Integer32
    MAX-ACCESS accessible-for-notify
    STATUS current
    DESCRIPTION
        "Parameter 'identifier' in event DNSU.9"
    ::= { dnsuEventObjects9 1 }

dnsuEventObjects10 OBJECT-IDENTITY
    STATUS current
    DESCRIPTION
        "Event DNSU.10
        Report an error during socket handling"
    ::= { dnsuEventsGroup 10 }

dnsu10_entry_id OBJECT-TYPE
    SYNTAX Integer32
    MAX-ACCESS accessible-for-notify
    STATUS current
    DESCRIPTION
        "Parameter 'entry_id' in event DNSU.10"
    ::= { dnsuEventObjects10 1 }

dnsu10_operation OBJECT-TYPE
    SYNTAX DisplayString
    MAX-ACCESS accessible-for-notify
    STATUS current
    DESCRIPTION
        "Parameter 'operation' in event DNSU.10"
    ::= { dnsuEventObjects10 2 }

dnsuEventObjects11 OBJECT-IDENTITY
    STATUS current
    DESCRIPTION
        "Event DNSU.11
        External IP address can not be get"
    ::= { dnsuEventsGroup 11 }

dnsu11_entry_id OBJECT-TYPE
    SYNTAX Integer32
    MAX-ACCESS accessible-for-notify
    STATUS current
    DESCRIPTION
        "Parameter 'entry_id' in event DNSU.11"
    ::= { dnsuEventObjects11 1 }

dnsuEventObjects12 OBJECT-IDENTITY
    STATUS current
    DESCRIPTION
        "Event DNSU.12
        Erroneous received message"
    ::= { dnsuEventsGroup 12 }

dnsu12_entry_id OBJECT-TYPE
    SYNTAX Integer32
    MAX-ACCESS accessible-for-notify
    STATUS current
    DESCRIPTION
        "Parameter 'entry_id' in event DNSU.12"
    ::= { dnsuEventObjects12 1 }

dnsuEventObjects13 OBJECT-IDENTITY
    STATUS current
    DESCRIPTION
        "Event DNSU.13
        Server IP founded succesfuly"
    ::= { dnsuEventsGroup 13 }

dnsu13_entry_id OBJECT-TYPE
    SYNTAX Integer32
    MAX-ACCESS accessible-for-notify
    STATUS current
    DESCRIPTION
        "Parameter 'entry_id' in event DNSU.13"
    ::= { dnsuEventObjects13 1 }

dnsu13_server_ip OBJECT-TYPE
    SYNTAX IpAddress
    MAX-ACCESS accessible-for-notify
    STATUS current
    DESCRIPTION
        "Parameter 'server_ip' in event DNSU.13"
    ::= { dnsuEventObjects13 2 }

dnsuEventObjects14 OBJECT-IDENTITY
    STATUS current
    DESCRIPTION
        "Event DNSU.14
        DNS query failed"
    ::= { dnsuEventsGroup 14 }

dnsu14_entry_id OBJECT-TYPE
    SYNTAX Integer32
    MAX-ACCESS accessible-for-notify
    STATUS current
    DESCRIPTION
        "Parameter 'entry_id' in event DNSU.14"
    ::= { dnsuEventObjects14 1 }

dnsu14_dns_query_error OBJECT-TYPE
    SYNTAX DisplayString
    MAX-ACCESS accessible-for-notify
    STATUS current
    DESCRIPTION
        "Parameter 'dns_query_error' in event DNSU.14"
    ::= { dnsuEventObjects14 2 }

dnsuEventObjects15 OBJECT-IDENTITY
    STATUS current
    DESCRIPTION
        "Event DNSU.15
        Configured server not found, a default server will be used."
    ::= { dnsuEventsGroup 15 }

dnsu15_server_ip OBJECT-TYPE
    SYNTAX IpAddress
    MAX-ACCESS accessible-for-notify
    STATUS current
    DESCRIPTION
        "Parameter 'server_ip' in event DNSU.15"
    ::= { dnsuEventObjects15 1 }

dnsuEventObjects16 OBJECT-IDENTITY
    STATUS current
    DESCRIPTION
        "Event DNSU.16
        We are using an invalid IP address as server IP"
    ::= { dnsuEventsGroup 16 }

dnsu16_entry_id OBJECT-TYPE
    SYNTAX Integer32
    MAX-ACCESS accessible-for-notify
    STATUS current
    DESCRIPTION
        "Parameter 'entry_id' in event DNSU.16"
    ::= { dnsuEventObjects16 1 }

dnsuEventObjects17 OBJECT-IDENTITY
    STATUS current
    DESCRIPTION
        "Event DNSU.17
        Updated process finished succesfuly but updated IP
        is not a local address"
    ::= { dnsuEventsGroup 17 }

dnsu17_entry_id OBJECT-TYPE
    SYNTAX Integer32
    MAX-ACCESS accessible-for-notify
    STATUS current
    DESCRIPTION
        "Parameter 'entry_id' in event DNSU.17"
    ::= { dnsuEventObjects17 1 }

dnsu17_external_IP OBJECT-TYPE
    SYNTAX IpAddress
    MAX-ACCESS accessible-for-notify
    STATUS current
    DESCRIPTION
        "Parameter 'external_IP' in event DNSU.17"
    ::= { dnsuEventObjects17 2 }

dnsuEventObjects19 OBJECT-IDENTITY
    STATUS current
    DESCRIPTION
        "Event DNSU.19
        There is another entry with the same identifier"
    ::= { dnsuEventsGroup 19 }

dnsu19_entry_id OBJECT-TYPE
    SYNTAX Integer32
    MAX-ACCESS accessible-for-notify
    STATUS current
    DESCRIPTION
        "Parameter 'entry_id' in event DNSU.19"
    ::= { dnsuEventObjects19 1 }

dnsuEventObjects20 OBJECT-IDENTITY
    STATUS current
    DESCRIPTION
        "Event DNSU.20
        An entry has been added succesfuly"
    ::= { dnsuEventsGroup 20 }

dnsu20_entry_id OBJECT-TYPE
    SYNTAX Integer32
    MAX-ACCESS accessible-for-notify
    STATUS current
    DESCRIPTION
        "Parameter 'entry_id' in event DNSU.20"
    ::= { dnsuEventObjects20 1 }

dnsuEventObjects21 OBJECT-IDENTITY
    STATUS current
    DESCRIPTION
        "Event DNSU.21
        IP address has changed for an entry."
    ::= { dnsuEventsGroup 21 }

dnsu21_entry_id OBJECT-TYPE
    SYNTAX Integer32
    MAX-ACCESS accessible-for-notify
    STATUS current
    DESCRIPTION
        "Parameter 'entry_id' in event DNSU.21"
    ::= { dnsuEventObjects21 1 }

dnsuEventObjects22 OBJECT-IDENTITY
    STATUS current
    DESCRIPTION
        "Event DNSU.22
        We are using DynDNS protocol and IP is external. We need
        to ckeck if there is any change in that IP, but process failed"
    ::= { dnsuEventsGroup 22 }

dnsu22_entry_id OBJECT-TYPE
    SYNTAX Integer32
    MAX-ACCESS accessible-for-notify
    STATUS current
    DESCRIPTION
        "Parameter 'entry_id' in event DNSU.22"
    ::= { dnsuEventObjects22 1 }

dnsuEventObjects23 OBJECT-IDENTITY
    STATUS current
    DESCRIPTION
        "Event DNSU.23
        We are using DynDNS protocol and we have to check if our external
        IP is the same as IP loaded in server."
    ::= { dnsuEventsGroup 23 }

dnsu23_entry_id OBJECT-TYPE
    SYNTAX Integer32
    MAX-ACCESS accessible-for-notify
    STATUS current
    DESCRIPTION
        "Parameter 'entry_id' in event DNSU.23"
    ::= { dnsuEventObjects23 1 }

dnsuEventObjects24 OBJECT-IDENTITY
    STATUS current
    DESCRIPTION
        "Event DNSU.24
        We are using DynDNS protocol and we have to check if our external IP
        changes through a server. Server can not be resolved so process is
        aborted"
    ::= { dnsuEventsGroup 24 }

dnsu24_entry_id OBJECT-TYPE
    SYNTAX Integer32
    MAX-ACCESS accessible-for-notify
    STATUS current
    DESCRIPTION
        "Parameter 'entry_id' in event DNSU.24"
    ::= { dnsuEventObjects24 1 }

dnsuEventObjects25 OBJECT-IDENTITY
    STATUS current
    DESCRIPTION
        "Event DNSU.25
        Trace text is reported"
    ::= { dnsuEventsGroup 25 }

dnsu25_entry_id OBJECT-TYPE
    SYNTAX Integer32
    MAX-ACCESS accessible-for-notify
    STATUS current
    DESCRIPTION
        "Parameter 'entry_id' in event DNSU.25"
    ::= { dnsuEventObjects25 1 }

dnsu25_trace_text OBJECT-TYPE
    SYNTAX DisplayString
    MAX-ACCESS accessible-for-notify
    STATUS current
    DESCRIPTION
        "Parameter 'trace_text' in event DNSU.25"
    ::= { dnsuEventObjects25 2 }

dnsuEventObjects26 OBJECT-IDENTITY
    STATUS current
    DESCRIPTION
        "Event DNSU.26
        There was an error in the task"
    ::= { dnsuEventsGroup 26 }

dnsu26_reason OBJECT-TYPE
    SYNTAX DisplayString
    MAX-ACCESS accessible-for-notify
    STATUS current
    DESCRIPTION
        "Parameter 'reason' in event DNSU.26"
    ::= { dnsuEventObjects26 1 }

dnsuEventObjects27 OBJECT-IDENTITY
    STATUS current
    DESCRIPTION
        "Event DNSU.27
        External-ip server IP found successfully"
    ::= { dnsuEventsGroup 27 }

dnsu27_entry_id OBJECT-TYPE
    SYNTAX Integer32
    MAX-ACCESS accessible-for-notify
    STATUS current
    DESCRIPTION
        "Parameter 'entry_id' in event DNSU.27"
    ::= { dnsuEventObjects27 1 }

dnsu27_external_ip_server_ip OBJECT-TYPE
    SYNTAX IpAddress
    MAX-ACCESS accessible-for-notify
    STATUS current
    DESCRIPTION
        "Parameter 'external_ip_server_ip' in event DNSU.27"
    ::= { dnsuEventObjects27 2 }


dnsuNotification1 NOTIFICATION-TYPE
    OBJECTS { 
              dnsu1_error 
            }
    STATUS current
    DESCRIPTION
        "Notification of Event DNSU.1

        Message: 'Initialize error: $1'

        Parameters list:
              $1: dnsu1_error

        There was an error during initialize"
    ::= { dnsuNotificationsPrefix 1 }

dnsuNotification2 NOTIFICATION-TYPE
    STATUS current
    DESCRIPTION
        "Notification of Event DNSU.2

        Message: 'DNS UPDATER disabled'

        Dns Updater feature is disabled"
    ::= { dnsuNotificationsPrefix 2 }

dnsuNotification3 NOTIFICATION-TYPE
    OBJECTS { 
              dnsu3_entry_id, 
              dnsu3_last_ip_address,
              dnsu3_new_ip_address 
            }
    STATUS current
    DESCRIPTION
        "Notification of Event DNSU.3

        Message: 'Entry $1 IP address change detected $2 -> $3'

        Parameters list:
              $1: dnsu3_entry_id
              $2: dnsu3_last_ip_address
              $3: dnsu3_new_ip_address

        IP address has changed for an entry."
    ::= { dnsuNotificationsPrefix 3 }

dnsuNotification4 NOTIFICATION-TYPE
    OBJECTS { 
              dnsu4_entry_id, 
              dnsu4_last_ip 
            }
    STATUS current
    DESCRIPTION
        "Notification of Event DNSU.4

        Message: 'Time to update entry $1 has been expired. Last IP $2'

        Parameters list:
              $1: dnsu4_entry_id
              $2: dnsu4_last_ip

        IP addres has to be updated because of timer expiration."
    ::= { dnsuNotificationsPrefix 4 }

dnsuNotification5 NOTIFICATION-TYPE
    OBJECTS { 
              dnsu5_entry_id, 
              dnsu5_protocol 
            }
    STATUS current
    DESCRIPTION
        "Notification of Event DNSU.5

        Message: 'Entry $1 Creating message for $2 protocol'

        Parameters list:
              $1: dnsu5_entry_id
              $2: dnsu5_protocol

        An http request will be created."
    ::= { dnsuNotificationsPrefix 5 }

dnsuNotification6 NOTIFICATION-TYPE
    OBJECTS { 
              dnsu6_entry_id 
            }
    STATUS current
    DESCRIPTION
        "Notification of Event DNSU.6

        Message: 'Entry $1 Strange server response.'

        Parameters list:
              $1: dnsu6_entry_id

        A strange response has been received, perharps we are trying to connect
        to the wrong server"
    ::= { dnsuNotificationsPrefix 6 }

dnsuNotification7 NOTIFICATION-TYPE
    OBJECTS { 
              dnsu7_entry_id, 
              dnsu7_message_identifier 
            }
    STATUS current
    DESCRIPTION
        "Notification of Event DNSU.7

        Message: 'Entry $1 received response with identifier $2.'

        Parameters list:
              $1: dnsu7_entry_id
              $2: dnsu7_message_identifier

        A correct response has been received from the server"
    ::= { dnsuNotificationsPrefix 7 }

dnsuNotification8 NOTIFICATION-TYPE
    OBJECTS { 
              dnsu8_entry_id 
            }
    STATUS current
    DESCRIPTION
        "Notification of Event DNSU.8

        Message: 'Entry $1 Unknown server response'

        Parameters list:
              $1: dnsu8_entry_id

        A response has an answer field that does not match the query."
    ::= { dnsuNotificationsPrefix 8 }

dnsuNotification9 NOTIFICATION-TYPE
    OBJECTS { 
              dnsu9_identifier 
            }
    STATUS current
    DESCRIPTION
        "Notification of Event DNSU.9

        Message: 'Entry $1 IP updated succesfully'

        Parameters list:
              $1: dnsu9_identifier

        IP update fihished succesfully for an entry"
    ::= { dnsuNotificationsPrefix 9 }

dnsuNotification10 NOTIFICATION-TYPE
    OBJECTS { 
              dnsu10_entry_id, 
              dnsu10_operation 
            }
    STATUS current
    DESCRIPTION
        "Notification of Event DNSU.10

        Message: 'Entry $1 Socket $2 error'

        Parameters list:
              $1: dnsu10_entry_id
              $2: dnsu10_operation

        Report an error during socket handling"
    ::= { dnsuNotificationsPrefix 10 }

dnsuNotification11 NOTIFICATION-TYPE
    OBJECTS { 
              dnsu11_entry_id 
            }
    STATUS current
    DESCRIPTION
        "Notification of Event DNSU.11

        Message: 'Entry $1 Error checking external IP address'

        Parameters list:
              $1: dnsu11_entry_id

        External IP address can not be get"
    ::= { dnsuNotificationsPrefix 11 }

dnsuNotification12 NOTIFICATION-TYPE
    OBJECTS { 
              dnsu12_entry_id 
            }
    STATUS current
    DESCRIPTION
        "Notification of Event DNSU.12

        Message: 'Entry $1 Bad message received'

        Parameters list:
              $1: dnsu12_entry_id

        Erroneous received message"
    ::= { dnsuNotificationsPrefix 12 }

dnsuNotification13 NOTIFICATION-TYPE
    OBJECTS { 
              dnsu13_entry_id, 
              dnsu13_server_ip 
            }
    STATUS current
    DESCRIPTION
        "Notification of Event DNSU.13

        Message: 'Entry $1 server IP founded $2'

        Parameters list:
              $1: dnsu13_entry_id
              $2: dnsu13_server_ip

        Server IP founded succesfuly"
    ::= { dnsuNotificationsPrefix 13 }

dnsuNotification14 NOTIFICATION-TYPE
    OBJECTS { 
              dnsu14_entry_id, 
              dnsu14_dns_query_error 
            }
    STATUS current
    DESCRIPTION
        "Notification of Event DNSU.14

        Message: 'Entry $1 DNS query error $2'

        Parameters list:
              $1: dnsu14_entry_id
              $2: dnsu14_dns_query_error

        DNS query failed"
    ::= { dnsuNotificationsPrefix 14 }

dnsuNotification15 NOTIFICATION-TYPE
    OBJECTS { 
              dnsu15_server_ip 
            }
    STATUS current
    DESCRIPTION
        "Notification of Event DNSU.15

        Message: 'Using default server, IP $1'

        Parameters list:
              $1: dnsu15_server_ip

        Configured server not found, a default server will be used."
    ::= { dnsuNotificationsPrefix 15 }

dnsuNotification16 NOTIFICATION-TYPE
    OBJECTS { 
              dnsu16_entry_id 
            }
    STATUS current
    DESCRIPTION
        "Notification of Event DNSU.16

        Message: 'Entry $1 error with server address'

        Parameters list:
              $1: dnsu16_entry_id

        We are using an invalid IP address as server IP"
    ::= { dnsuNotificationsPrefix 16 }

dnsuNotification17 NOTIFICATION-TYPE
    OBJECTS { 
              dnsu17_entry_id, 
              dnsu17_external_IP 
            }
    STATUS current
    DESCRIPTION
        "Notification of Event DNSU.17

        Message: 'Entry $1 IP updated is not internal $2'

        Parameters list:
              $1: dnsu17_entry_id
              $2: dnsu17_external_IP

        Updated process finished succesfuly but updated IP
        is not a local address"
    ::= { dnsuNotificationsPrefix 17 }

dnsuNotification18 NOTIFICATION-TYPE
    STATUS current
    DESCRIPTION
        "Notification of Event DNSU.18

        Message: 'DNS UPDATER Initialized'

        Failure initializating the feature"
    ::= { dnsuNotificationsPrefix 18 }

dnsuNotification19 NOTIFICATION-TYPE
    OBJECTS { 
              dnsu19_entry_id 
            }
    STATUS current
    DESCRIPTION
        "Notification of Event DNSU.19

        Message: 'An entry just exists with id $1'

        Parameters list:
              $1: dnsu19_entry_id

        There is another entry with the same identifier"
    ::= { dnsuNotificationsPrefix 19 }

dnsuNotification20 NOTIFICATION-TYPE
    OBJECTS { 
              dnsu20_entry_id 
            }
    STATUS current
    DESCRIPTION
        "Notification of Event DNSU.20

        Message: 'Entry $1 added succesfuly'

        Parameters list:
              $1: dnsu20_entry_id

        An entry has been added succesfuly"
    ::= { dnsuNotificationsPrefix 20 }

dnsuNotification21 NOTIFICATION-TYPE
    OBJECTS { 
              dnsu21_entry_id 
            }
    STATUS current
    DESCRIPTION
        "Notification of Event DNSU.21

        Message: 'Entry $1 needs to be updated'

        Parameters list:
              $1: dnsu21_entry_id

        IP address has changed for an entry."
    ::= { dnsuNotificationsPrefix 21 }

dnsuNotification22 NOTIFICATION-TYPE
    OBJECTS { 
              dnsu22_entry_id 
            }
    STATUS current
    DESCRIPTION
        "Notification of Event DNSU.22

        Message: 'Error $1 checking external IP in DynDNS protocol.'

        Parameters list:
              $1: dnsu22_entry_id

        We are using DynDNS protocol and IP is external. We need
        to ckeck if there is any change in that IP, but process failed"
    ::= { dnsuNotificationsPrefix 22 }

dnsuNotification23 NOTIFICATION-TYPE
    OBJECTS { 
              dnsu23_entry_id 
            }
    STATUS current
    DESCRIPTION
        "Notification of Event DNSU.23

        Message: 'Entry $1 Dyndns check_ip updated IP finished successfuly'

        Parameters list:
              $1: dnsu23_entry_id

        We are using DynDNS protocol and we have to check if our external
        IP is the same as IP loaded in server."
    ::= { dnsuNotificationsPrefix 23 }

dnsuNotification24 NOTIFICATION-TYPE
    OBJECTS { 
              dnsu24_entry_id 
            }
    STATUS current
    DESCRIPTION
        "Notification of Event DNSU.24

        Message: 'Entry $1 Dyndns check_ip server can not be resolved'

        Parameters list:
              $1: dnsu24_entry_id

        We are using DynDNS protocol and we have to check if our external IP
        changes through a server. Server can not be resolved so process is
        aborted"
    ::= { dnsuNotificationsPrefix 24 }

dnsuNotification25 NOTIFICATION-TYPE
    OBJECTS { 
              dnsu25_entry_id, 
              dnsu25_trace_text 
            }
    STATUS current
    DESCRIPTION
        "Notification of Event DNSU.25

        Message: 'Entry $1 $2'

        Parameters list:
              $1: dnsu25_entry_id
              $2: dnsu25_trace_text

        Trace text is reported"
    ::= { dnsuNotificationsPrefix 25 }

dnsuNotification26 NOTIFICATION-TYPE
    OBJECTS { 
              dnsu26_reason 
            }
    STATUS current
    DESCRIPTION
        "Notification of Event DNSU.26

        Message: 'Error in DNS UPDATER task: $1'

        Parameters list:
              $1: dnsu26_reason

        There was an error in the task"
    ::= { dnsuNotificationsPrefix 26 }

dnsuNotification27 NOTIFICATION-TYPE
    OBJECTS { 
              dnsu27_entry_id, 
              dnsu27_external_ip_server_ip 
            }
    STATUS current
    DESCRIPTION
        "Notification of Event DNSU.27

        Message: 'Entry $1 external-ip server IP found $2'

        Parameters list:
              $1: dnsu27_entry_id
              $2: dnsu27_external_ip_server_ip

        External-ip server IP found successfully"
    ::= { dnsuNotificationsPrefix 27 }


END
