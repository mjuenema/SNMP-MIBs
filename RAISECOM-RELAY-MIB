--MibName=rcRelay
-- *****************************************************************
-- RAISECOM-RELAY-MIB.my
--
-- Mar 2008, longyang
--
-- Copyright(c) 2003-2005 by RAISECOM TECH, Ltd. 
-- All rights reserved.
-- *****************************************************************

RAISECOM-RELAY-MIB DEFINITIONS ::= BEGIN

IMPORTS
    MODULE-IDENTITY,
    OBJECT-TYPE,
    Unsigned32,
    Counter32
        FROM SNMPv2-SMI
	MacAddress        
		FROM SNMPv2-TC
    rcPortIndex
        FROM SWITCH-SYSTEM-MIB
    iscomSwitch
    	FROM RAISECOM-BASE-MIB
    EnableVar
      FROM SWITCH-TC;

rcRelay MODULE-IDENTITY
    LAST-UPDATED   "200803110000Z"
    ORGANIZATION   "Raisecom, Inc."
    CONTACT-INFO  
                "Raisecom Systems
                        
                Postal: Beijing,
                        China

                Tel: 86-010-82884499"
    DESCRIPTION
        "This MIB module defines objects to RELAY
            1. wangjian add stp_prv to rcRelayProtocolType"
        REVISION   "201203010000Z"
        DESCRIPTION
            "The initial revision of this MIB."
        ::={ iscomSwitch 35 }


--------------------------------------------------------------------------
--rcRelayGrobal
--------------------------------------------------------------------------   
rcRelayGrobal  OBJECT IDENTIFIER
    ::= { rcRelay 1 }

rcRelayMacAddress OBJECT-TYPE
    SYNTAX          MacAddress
    MAX-ACCESS      read-write
    STATUS          current
    DESCRIPTION
            "Specifies the destination MAC address of the tunneled PDUs 
            and applies to all ingress tunneling interfaces." 
    ::= { rcRelayGrobal 1 }

rcRelayCos OBJECT-TYPE
    SYNTAX          Unsigned32(0..8)
    MAX-ACCESS      read-write
    STATUS          current
    DESCRIPTION
            "Specifies the user priority of the tunneled PDUs and applies
            to all ingress tunneling interfaces." 
    DEFVAL          { 8 }
    ::= { rcRelayGrobal 2 }
    
rcRelayTransparentEnable OBJECT-TYPE
    SYNTAX          EnableVar
    MAX-ACCESS      read-write
    STATUS          current
    DESCRIPTION
            "Specifies the status of BPDU relay transparent.1:enable,2:disable" 
    ::= { rcRelayGrobal 3 }    
 
 
-------------------------------------------------------------------------------------- 
-- rcRelayProtocolTable
--------------------------------------------------------------------------------------

rcRelayProtocolTable OBJECT-TYPE
    SYNTAX          SEQUENCE OF RcRelayProtocolEntry
    MAX-ACCESS      not-accessible
    STATUS          current
    DESCRIPTION
            "This table contains information about the protocols being
            tunneled. "
    ::= { rcRelay 2 }                          

rcRelayProtocolEntry OBJECT-TYPE
    SYNTAX          RcRelayProtocolEntry
    MAX-ACCESS      not-accessible
    STATUS          current
    DESCRIPTION
            "Information about the protocols being tunneled. "
    INDEX           { rcPortIndex } 
    ::= { rcRelayProtocolTable 1 }

RcRelayProtocolEntry ::= SEQUENCE {
        rcRelayProtocolType        BITS,
        rcRelayProtocolVlan        Unsigned32,
        rcRelayProtocolEgressPort  Unsigned32,
        rcRelayProtocolPortStatus  INTEGER,
        rcRelayProtocolTunnelType  INTEGER,
        rcRelayProtocolMplsVlan    Unsigned32,
        rcRelayProtocolMplsStatus  INTEGER
}

rcRelayProtocolType OBJECT-TYPE
    SYNTAX          BITS {
                        stp(0),
                        dot1x(1),
                        lacp(2),
                        gmrp(3), 
                        gvrp(4),
                        cdp(5),
                        vtp(6),
                        pvst(7),
                        lldp(8)    
                    }
    MAX-ACCESS      read-write
    STATUS          current
    DESCRIPTION
            "Indicates tunneled protocol of the interface. 

            If a BIT is set, then the value of the corresponding
            protocol is tunneled." 
    ::= { rcRelayProtocolEntry 1 }
 
rcRelayProtocolVlan OBJECT-TYPE
    SYNTAX          Unsigned32(0..4094)
    MAX-ACCESS      read-write
    STATUS          current
    DESCRIPTION
            "Specifies vlan ID of tunneled protocol PDUs of the interface." 
    ::= { rcRelayProtocolEntry 2 }

rcRelayProtocolEgressPort OBJECT-TYPE
    SYNTAX          Unsigned32
    MAX-ACCESS      read-write
    STATUS          current
    DESCRIPTION
            "Specifies egress port of tunneled protocol PDUs of the interface." 
    ::= { rcRelayProtocolEntry 3 }

rcRelayProtocolPortStatus OBJECT-TYPE
    SYNTAX          INTEGER  {
                        up(1),
                        down(2) 
                    }
    MAX-ACCESS      read-write
    STATUS          current
    DESCRIPTION
            "The desired state of the interface by RELAY." 
    ::= { rcRelayProtocolEntry 4 }
rcRelayProtocolTunnelType OBJECT-TYPE
    SYNTAX          INTEGER  {  
    					none(0),
                        mac(1),
                        mpls(2) 
                    }
    MAX-ACCESS      read-write
    STATUS          current
    DESCRIPTION
            "The tunnel type used by RELAY." 
    ::= { rcRelayProtocolEntry 5 }

rcRelayProtocolMplsVlan OBJECT-TYPE
    SYNTAX          Unsigned32(1..4095)
    MAX-ACCESS      read-write
    STATUS          current
    DESCRIPTION
            "Specifies MPLS vlan ID of tunneled protocol PDUs of the interface."  
    DEFVAL          { 4095 }
    ::= { rcRelayProtocolEntry 6 }

rcRelayProtocolMplsStatus OBJECT-TYPE
    SYNTAX          INTEGER  {
                        up(1),
                        down(2) 
                    }
    MAX-ACCESS      read-only
    STATUS          current
    DESCRIPTION
            "The actual operational status of MPLS Relay."
    DEFVAL          { down } 
    ::= { rcRelayProtocolEntry 7 }

-------------------------------------------------------------------------------------- 
-- rcRelayThresholdTable
--------------------------------------------------------------------------------------

rcRelayThresholdTable OBJECT-TYPE
    SYNTAX          SEQUENCE OF RcRelayThresholdEntry 
    MAX-ACCESS      not-accessible
    STATUS          current
    DESCRIPTION
            "This table contains information about the thresholds for
            protocol tunneling. Only tunneled protocol filtering capable
            interfaces are shown. The objects will be on a per interface,
            per protocol basis."
    ::= { rcRelay 3 }

rcRelayThresholdEntry OBJECT-TYPE
    SYNTAX          RcRelayThresholdEntry
    MAX-ACCESS      not-accessible
    STATUS          current
    DESCRIPTION
            "Information about the thresholds for protocol tunneling. Only
            tunneled protocol filtering capable interfaces are shown. The
            entries will be on a per interface, per protocol basis"
    INDEX           {
                        rcPortIndex,
                        rcRelayThresholdProtocolIndex
                    } 
    ::= { rcRelayThresholdTable 1 }

RcRelayThresholdEntry ::= SEQUENCE {
        rcRelayThresholdProtocolIndex INTEGER ,
        rcRelayDropThreshold          Unsigned32,
        rcRelayShutdownThreshold      Unsigned32
}

rcRelayThresholdProtocolIndex OBJECT-TYPE
    SYNTAX          INTEGER  {
                        stp(1),
                        dot1x(2),
                        lacp(3),
                        gmrp(4),      
                        gvrp(5),
                        cdp(6),
                        vtp(7),
                        pvst(8),
                        lldp(9) 
                    }
    MAX-ACCESS      not-accessible
    STATUS          current
    DESCRIPTION
            "Supported protocol for devices which allow the setting of 
            thresholds on a per interface, per protocol basis." 
    ::= { rcRelayThresholdEntry 1 }

rcRelayDropThreshold OBJECT-TYPE
    SYNTAX          Unsigned32(0..4096)
    UNITS           "PDUs/sec"
    MAX-ACCESS      read-write
    STATUS          current
    DESCRIPTION
            "The drop threshold on an interface for a given protocol. After
            reaching this drop threshold, the interface will start dropping
            PDUs for the given protocol. This value cannot be greater than
            the value of rcRelayShutdownThreshold.  A value of 0
            indicates that no limit is set."
    DEFVAL          { 0 } 
    ::= { rcRelayThresholdEntry 2 }

rcRelayShutdownThreshold OBJECT-TYPE
    SYNTAX          Unsigned32(0..4096)
    UNITS           "PDUs/sec"
    MAX-ACCESS      read-write
    STATUS          current
    DESCRIPTION
            "The shutdown threshold on an interface for a given protocol.
            After reaching the shutdown threshold, the interface will
            shutdown for the given protocol.  This value cannot be less
            than the value of rcRelayDropThreshold. A value of 0
            indicates that no limit is set."
    DEFVAL          { 0 } 
    ::= { rcRelayThresholdEntry 3 }
 
-------------------------------------------------------------------------------------- 
-- rcRelayStatisticsTable
--------------------------------------------------------------------------------------

rcRelayStatisticsTable OBJECT-TYPE
    SYNTAX          SEQUENCE OF RcRelayStatisticsEntry 
    MAX-ACCESS      not-accessible
    STATUS          current
    DESCRIPTION
            "This table contains protocol tunneling statistics on the
            interface."
    ::= { rcRelay 4 }

rcRelayStatisticsEntry OBJECT-TYPE
    SYNTAX          RcRelayStatisticsEntry
    MAX-ACCESS      not-accessible
    STATUS          current
    DESCRIPTION     "Protocol tunneling statistics on the interface."
    INDEX           {
                        rcPortIndex,
                        rcRelayStatsProtocolIndex
                    } 
    ::= { rcRelayStatisticsTable 1 }

RcRelayStatisticsEntry ::= SEQUENCE {
        rcRelayStatsProtocolIndex INTEGER ,
        rcRelayEncapStats      	  Counter32,
        rcRelayDeEncapStats       Counter32,
        rcRelayDropStats          Counter32
}

rcRelayStatsProtocolIndex OBJECT-TYPE
    SYNTAX          INTEGER  {
                        stp(1),
                        dot1x(2),
                        lacp(3),
                        gmrp(4),      
                        gvrp(5),
                        cdp(6),
                        vtp(7),
                        pvst(8),
                        lldp(9)  
                    }
    MAX-ACCESS      not-accessible
    STATUS          current
    DESCRIPTION     "A tunneled protocol of an interface." 
    ::= { rcRelayStatisticsEntry 1 }

rcRelayEncapStats OBJECT-TYPE
    SYNTAX          Counter32
    UNITS           "encapsulated PDUs"
    MAX-ACCESS      read-only
    STATUS          current
    DESCRIPTION
            "The tunneled PDU encapsulation statistics of an interface.
            These statistics cover the number of tunneled ingress
            PDUs." 
    ::= { rcRelayStatisticsEntry 2 }

rcRelayDeEncapStats OBJECT-TYPE
    SYNTAX          Counter32
    UNITS           "de-encapsulated PDUs"
    MAX-ACCESS      read-only
    STATUS          current
    DESCRIPTION
            "The tunneled PDU de-encapsulation statistics of an interface.
            These statistics cover the number of tunneled egress PDUs." 
    ::= { rcRelayStatisticsEntry 3 }

rcRelayDropStats OBJECT-TYPE
    SYNTAX          Counter32
    UNITS           "PDUs"
    MAX-ACCESS      read-only
    STATUS          current
    DESCRIPTION
            "The number of PDUs dropped on an interface for a given
            protocol. The PDUs will be dropped when the
            rcRelayDropThreshold is reached." 
    ::= { rcRelayStatisticsEntry 4 }
 

END
