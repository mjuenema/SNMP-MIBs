BROCADE-QOS-MIB DEFINITIONS ::= BEGIN

IMPORTS
    MODULE-IDENTITY, OBJECT-TYPE, Unsigned32, Counter64, Counter32
      FROM SNMPv2-SMI                  -- [RFC2578]
    InterfaceIndex
      FROM IF-MIB                      -- [RFC2863]
    DisplayString
      FROM SNMPv2-TC                   -- [RFC2579]
    brcdQos
      FROM FOUNDRY-SN-ROOT-MIB                           -- [snrootu]
    PortPriorityTC
      FROM FOUNDRY-SN-SWITCH-GROUP-MIB;

brcdQosMIB MODULE-IDENTITY
   LAST-UPDATED "201207180000Z"  -- July 18, 2012
   ORGANIZATION "Brocade Communications Systems, Inc."
   CONTACT-INFO
             "Technical Support Center
              130 Holger Way,
              San Jose, CA  95134
              Email:  ipsupport@brocade.com
              Phone: 1-800-752-8061
              URL:  www.brocade.com"
   DESCRIPTION
             "The MIB module contains the managed object definition for
              Brocade Quality of Service.

              Supported Platforms:
                   - supported on NetIron XMR/MLX latforms.

              Copyright 1996-2012 Brocade Communications Systems, Inc.
              All rights reserved.
              This Brocade Communications Systems SNMP Management Information
              Base Specification embodies Brocade Communications Systems
              confidential and proprietary intellectual property.
              Brocade Communications Systems retains all title and ownership
              in the Specification, including any revisions.

              This Specification is supplied AS IS, and Brocade Communications
              Systems makes no warranty, either express or implied, as to the
              use, operation, condition, or performance of the specification,
              and any unintended consequence it may on the user environment."

   REVISION      "201207180000Z"  -- July 18, 2012
   DESCRIPTION
            "Initial version"

   ::= { brcdQos 1 }

-- Top level components of this MIB module.

brcdHqosObjects       OBJECT IDENTIFIER ::= { brcdQosMIB 1 }

---
--- HQoS Statistics Table
---
brcdHqosStatsTable OBJECT-TYPE
   SYNTAX        SEQUENCE OF BrcdHqosStatsEntry
   MAX-ACCESS    not-accessible
   STATUS        current
   DESCRIPTION
       "A list of brcHqosStats entries. This table contains information
        of various HQoS counters. The HQoS is supported on NI-MLX-10Gx8-M/D
        LP modules."
  ::= { brcdHqosObjects 1 }

brcdHqosStatsEntry OBJECT-TYPE
   SYNTAX        BrcdHqosStatsEntry
   MAX-ACCESS    not-accessible
   STATUS        current
   DESCRIPTION
       "An entry containing Hqos statistics counter information applicable
        for 10Gx8 interface if the module is physically present."
   INDEX   {   brcdHqosIfIndex,
               brcdHqosEndpointType,
               brcdHqosEndpointTag,
               brcdHqosEndpointInnerTag,
               brcdHqosStatsPriority }
   ::= { brcdHqosStatsTable 1 }

BrcdHqosStatsEntry ::= SEQUENCE {
   brcdHqosIfIndex                      InterfaceIndex,
   brcdHqosEndpointType                 INTEGER,
   brcdHqosEndpointTag                  Unsigned32,
   brcdHqosEndpointInnerTag             Unsigned32,
   brcdHqosStatsPriority                PortPriorityTC,
   brcdHqosStatsDescription             DisplayString,
   brcdHqosStatsEnquePkts               Counter64,
   brcdHqosStatsEnqueBytes              Counter64,
   brcdHqosStatsDequePkts               Counter64,
   brcdHqosStatsDequeBytes              Counter64,
   brcdHqosStatsTotalDiscardPkts        Counter64,
   brcdHqosStatsTotalDiscardBytes       Counter64,
   brcdHqosStatsOldestDiscardPkts       Counter64,
   brcdHqosStatsOldestDiscardBytes      Counter64,
   brcdHqosStatsWREDDroppedPkts         Counter64,
   brcdHqosStatsWREDDroppedBytes        Counter64,
   brcdHqosStatsCurrentQDepth           Counter64,
   brcdHqosStatsMaxQDepthSinceLastRead  Counter64
  }

brcdHqosIfIndex OBJECT-TYPE
    SYNTAX      InterfaceIndex
    MAX-ACCESS  not-accessible
    STATUS      current
    DESCRIPTION
            "The index of the interface index where the HQoS is configured.
             The LP module must be physically present and operationally up."
    ::= { brcdHqosStatsEntry 1 }

brcdHqosEndpointType OBJECT-TYPE
    SYNTAX      INTEGER {
                    other(1),
                    singleTaggedVlan(2),
                    doubleTaggedVlan(3),
                    bVlanIsid(4)
                }
    MAX-ACCESS  not-accessible
    STATUS      current
    DESCRIPTION
            "This object specifies the End point type for HQoS scheduler."
    ::= { brcdHqosStatsEntry 2 }

brcdHqosEndpointTag OBJECT-TYPE
    SYNTAX      Unsigned32
    MAX-ACCESS  not-accessible
    STATUS      current
    DESCRIPTION
           "This object specifies the HQoS end point tag.
            If the brcdHqosEndpointType is other(1), then this object
            has zero value.
            If the brcdHqosEndpointType is singleTaggedVlan(2),
            dougleTaggedVlan(3) or bVlanIsid(4), then this object has
            VLAN id. The valid VLAN ids are 1 to 4094."
    ::= { brcdHqosStatsEntry 3 }

brcdHqosEndpointInnerTag OBJECT-TYPE
    SYNTAX      Unsigned32
    MAX-ACCESS  not-accessible
    STATUS      current
    DESCRIPTION
           "This object specifies the HQoS end point inner tag.
            If the brcdHqosEndpointType is other(1) or singleTaggedVlan(2)
            then this object has zero value.
            If the brcdHqosEndpointType is dougleTaggedVlan(3) then this
            object has VLAN id. The valid VLAN ids are 1 to 4094
            If the index brcdHqosEndpointType is bVlanIsid(4), then this object
            has ISID value. The valid ISID are 256 to 16777214."
    ::= { brcdHqosStatsEntry 4 }

brcdHqosStatsPriority OBJECT-TYPE
    SYNTAX      PortPriorityTC
    MAX-ACCESS  not-accessible
    STATUS      current
    DESCRIPTION
            "The priority of the packets that will be stored in this queue.
             This is 1-based index.
             The HQoS queue with brcdHqosEndpointType as other(1) have
             8 priorities. All other HQoS queues have 4 priorities, two
             consecutive priorities are stored in one queue. In this case,
             the valid values for this index are 1, 3, 5 and 7. The queue
             with priority 1 has the packets with priority 1 and 2.
             Same applies for priority 3, 5 and 7"
    ::= { brcdHqosStatsEntry 5 }

brcdHqosStatsDescription OBJECT-TYPE
    SYNTAX      DisplayString
    MAX-ACCESS  read-only
    STATUS      current
    DESCRIPTION
            "This object gives the HQoS scheduler node name in full path
             format with each node separated by dot."
    ::= { brcdHqosStatsEntry 6 }

brcdHqosStatsEnquePkts OBJECT-TYPE
    SYNTAX      Counter64
    MAX-ACCESS  read-only
    STATUS      current
    DESCRIPTION
            "A count of all packets entering ingress queues on this queue."
    ::= { brcdHqosStatsEntry 7 }

brcdHqosStatsEnqueBytes OBJECT-TYPE
    SYNTAX      Counter64
    MAX-ACCESS  read-only
    STATUS      current
    DESCRIPTION
            "A count of all bytes entering ingress queues on this queue."
    ::= { brcdHqosStatsEntry 8 }

brcdHqosStatsDequePkts OBJECT-TYPE
    SYNTAX      Counter64
    MAX-ACCESS  read-only
    STATUS      current
    DESCRIPTION
            "A count of all packets dequeued from ingress queues and forwarded
             on this queue."
    ::= { brcdHqosStatsEntry 9 }

brcdHqosStatsDequeBytes OBJECT-TYPE
    SYNTAX      Counter64
    MAX-ACCESS  read-only
    STATUS      current
    DESCRIPTION
            "A count of all bytes dequeued from ingress queues and forwarded on
             this queue."
    ::= { brcdHqosStatsEntry 10 }

brcdHqosStatsTotalDiscardPkts OBJECT-TYPE
    SYNTAX      Counter64
    MAX-ACCESS  read-only
    STATUS      current
    DESCRIPTION
            "A count of all packets failing to enter ingress queues on this
             queue. This may be due to:
             * The queue reaching its maximum depth, WRED, or other reasons.
             * The network processor deciding to drop packets for reasons
               including: an unknown Layer-3 route, RPF, or segment filtering."
    ::= { brcdHqosStatsEntry 11 }

brcdHqosStatsTotalDiscardBytes OBJECT-TYPE
    SYNTAX      Counter64
    MAX-ACCESS  read-only
    STATUS      current
    DESCRIPTION
            "A count of all bytes failing to enter ingress queues on this
             queue. This may be due to:
             * The queue reaching its maximum depth, WRED, or other reasons.
             * The network processor deciding to drop packets for reasons
               including: an unknown Layer-3 route, RPF, or segment filtering"
    ::= { brcdHqosStatsEntry 12 }

brcdHqosStatsOldestDiscardPkts OBJECT-TYPE
    SYNTAX      Counter64
    MAX-ACCESS  read-only
    STATUS      current
    DESCRIPTION
            "A count of all packets entering ingress queues on this queue,
             but deleted afterwards due to buffer full."
    ::= { brcdHqosStatsEntry 13 }

brcdHqosStatsOldestDiscardBytes OBJECT-TYPE
    SYNTAX      Counter64
    MAX-ACCESS  read-only
    STATUS      current
    DESCRIPTION
            "A count of all bytes entering ingress queues on this queue,
             but deleted afterwards due to buffer full"
    ::= { brcdHqosStatsEntry 14 }

brcdHqosStatsWREDDroppedPkts OBJECT-TYPE
    SYNTAX      Counter64
    MAX-ACCESS  read-only
    STATUS      current
    DESCRIPTION
            "A count of all bytes entering ingress queues on this queue,
             but deleted afterwards due to buffer full"
    ::= { brcdHqosStatsEntry 15 }

brcdHqosStatsWREDDroppedBytes OBJECT-TYPE
    SYNTAX      Counter64
    MAX-ACCESS  read-only
    STATUS      current
    DESCRIPTION
            "A count of all bytes entering ingress queues on this queue,
             but deleted afterwards due to buffer full"
    ::= { brcdHqosStatsEntry 16 }

brcdHqosStatsCurrentQDepth OBJECT-TYPE
    SYNTAX      Counter64
    MAX-ACCESS  read-only
    STATUS      current
    DESCRIPTION
            "The current queue depth."
    ::= { brcdHqosStatsEntry 17 }

brcdHqosStatsMaxQDepthSinceLastRead OBJECT-TYPE
    SYNTAX      Counter64
    MAX-ACCESS  read-only
    STATUS      current
    DESCRIPTION
            "The maximum queue depth since last access to read."
    ::= { brcdHqosStatsEntry 18 }

--- End of HQoS Statistics Table
END
