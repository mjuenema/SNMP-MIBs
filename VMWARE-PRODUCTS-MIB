-- **********************************************************
-- Copyright 2007 VMware, Inc.  All rights reserved. 
-- 
--  This MIB Module provides product sysObjectId assignments
--  for agents in VMware Managed products
--
-- **********************************************************
-- Version 1.0

VMWARE-PRODUCTS-MIB DEFINITIONS ::= BEGIN

IMPORTS
   OBJECT-TYPE
      FROM RFC-1212
   DisplayString 
      FROM RFC1213-MIB
   vmwOID, vmwProductSpecific
      FROM VMWARE-ROOT-MIB;

-- 1.3.6.1.2.1.6786.60.1
oidESX OBJECT IDENTIFIER ::= { vmwOID 1 }

-- 1.3.6.1.4.1.6876.4.1
vmwESX OBJECT IDENTIFIER ::= { vmwProductSpecific 1 }

-- 1.3.6.1.2.1.6786.4.2
vmwEmbeddedESX OBJECT IDENTIFIER ::= { vmwProductSpecific 2 }

-- 1.3.6.1.4.1.6876.4.3
vmwVC OBJECT IDENTIFIER ::= { vmwProductSpecific 3 }

-- 1.3.6.1.4.1.6876.4.4
vmwServer OBJECT IDENTIFIER ::= { vmwProductSpecific 4 }


END
