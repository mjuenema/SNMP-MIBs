-- file automatically created


TELDAT-TRAP-ICMP-MIB DEFINITIONS ::= BEGIN


IMPORTS
	MODULE-IDENTITY,OBJECT-TYPE,OBJECT-IDENTITY,NOTIFICATION-TYPE,Integer32,IpAddress
		FROM SNMPv2-SMI
	DisplayString
		FROM SNMPv2-TC
	telEventTraps
		FROM TELDAT-MIB;


icmpTrapsMIB MODULE-IDENTITY
    LAST-UPDATED "201401200930Z"
    ORGANIZATION "Teldat, S.A."
    CONTACT-INFO 
        "Teldat, S.A.
        Customer Service

        Postal: Parque Tecnologico de Madrid
                Tres Cantos 28760
                Madrid, SPAIN

        Tel.: +34 918 076 565

        http://www.teldat.com"
    DESCRIPTION
        "This Module Information Base file is defined for managing received
        SNMP notifications generated by the ICMP event subsystem."
    REVISION "201401200930Z"
    DESCRIPTION "Initial implementation"
        ::= { telEventTraps 11 }


icmpEventsGroup	OBJECT IDENTIFIER	::= { icmpTrapsMIB 1 }

icmpNotifications	OBJECT IDENTIFIER	::= { icmpTrapsMIB 2 }
icmpNotificationsPrefix	OBJECT IDENTIFIER	::= { icmpNotifications 0 }

icmpEventObjects1 OBJECT-IDENTITY
    STATUS current
    DESCRIPTION
        "Event ICMP.1
        A bad ICMP checksum was detected in an incoming ICMP message. The
        received checksum is displayed, together with the value that the checkum
        should have had. The received packet is discarded."
    ::= { icmpEventsGroup 1 }

icmp1_received_checksum OBJECT-TYPE
    SYNTAX Integer32
    MAX-ACCESS accessible-for-notify
    STATUS current
    DESCRIPTION
        "Parameter 'received_checksum' in event ICMP.1"
    ::= { icmpEventObjects1 1 }

icmp1_good_checksum OBJECT-TYPE
    SYNTAX Integer32
    MAX-ACCESS accessible-for-notify
    STATUS current
    DESCRIPTION
        "Parameter 'good_checksum' in event ICMP.1"
    ::= { icmpEventObjects1 2 }

icmp1_source_IP_address OBJECT-TYPE
    SYNTAX IpAddress
    MAX-ACCESS accessible-for-notify
    STATUS current
    DESCRIPTION
        "Parameter 'source_IP_address' in event ICMP.1"
    ::= { icmpEventObjects1 3 }

icmp1_destination_IP_address OBJECT-TYPE
    SYNTAX IpAddress
    MAX-ACCESS accessible-for-notify
    STATUS current
    DESCRIPTION
        "Parameter 'destination_IP_address' in event ICMP.1"
    ::= { icmpEventObjects1 4 }

icmpEventObjects2 OBJECT-IDENTITY
    STATUS current
    DESCRIPTION
        "Event ICMP.2
        An ICMP Echo Request was received from the source host by the router.
        Note that an ICMP Echo Request is only recognized when it comes in
        over the interface with the address the packet is addressed to."
    ::= { icmpEventsGroup 2 }

icmp2_source_IP_address OBJECT-TYPE
    SYNTAX IpAddress
    MAX-ACCESS accessible-for-notify
    STATUS current
    DESCRIPTION
        "Parameter 'source_IP_address' in event ICMP.2"
    ::= { icmpEventObjects2 1 }

icmp2_destination_IP_address OBJECT-TYPE
    SYNTAX IpAddress
    MAX-ACCESS accessible-for-notify
    STATUS current
    DESCRIPTION
        "Parameter 'destination_IP_address' in event ICMP.2"
    ::= { icmpEventObjects2 2 }

icmpEventObjects3 OBJECT-IDENTITY
    STATUS current
    DESCRIPTION
        "Event ICMP.3
        An ICMP Echo Reply was received from the source host by the router.
        This is a slightly suspicious event, since the router does not
        normally send ICMP Echo Requests."
    ::= { icmpEventsGroup 3 }

icmp3_source_IP_address OBJECT-TYPE
    SYNTAX IpAddress
    MAX-ACCESS accessible-for-notify
    STATUS current
    DESCRIPTION
        "Parameter 'source_IP_address' in event ICMP.3"
    ::= { icmpEventObjects3 1 }

icmp3_destination_IP_address OBJECT-TYPE
    SYNTAX IpAddress
    MAX-ACCESS accessible-for-notify
    STATUS current
    DESCRIPTION
        "Parameter 'destination_IP_address' in event ICMP.3"
    ::= { icmpEventObjects3 2 }

icmpEventObjects4 OBJECT-IDENTITY
    STATUS current
    DESCRIPTION
        "Event ICMP.4
        An ICMP message came in with a type that the router software does
        not handle."
    ::= { icmpEventsGroup 4 }

icmp4_ICMP_type OBJECT-TYPE
    SYNTAX Integer32
    MAX-ACCESS accessible-for-notify
    STATUS current
    DESCRIPTION
        "Parameter 'ICMP_type' in event ICMP.4"
    ::= { icmpEventObjects4 1 }

icmp4_ICMP_code OBJECT-TYPE
    SYNTAX Integer32
    MAX-ACCESS accessible-for-notify
    STATUS current
    DESCRIPTION
        "Parameter 'ICMP_code' in event ICMP.4"
    ::= { icmpEventObjects4 2 }

icmp4_source_IP_address OBJECT-TYPE
    SYNTAX IpAddress
    MAX-ACCESS accessible-for-notify
    STATUS current
    DESCRIPTION
        "Parameter 'source_IP_address' in event ICMP.4"
    ::= { icmpEventObjects4 3 }

icmp4_destination_IP_address OBJECT-TYPE
    SYNTAX IpAddress
    MAX-ACCESS accessible-for-notify
    STATUS current
    DESCRIPTION
        "Parameter 'destination_IP_address' in event ICMP.4"
    ::= { icmpEventObjects4 4 }

icmpEventObjects5 OBJECT-IDENTITY
    STATUS current
    DESCRIPTION
        "Event ICMP.5
        A broadcast ICMP message came in with a type that the router software
        does not handle."
    ::= { icmpEventsGroup 5 }

icmp5_ICMP_type OBJECT-TYPE
    SYNTAX Integer32
    MAX-ACCESS accessible-for-notify
    STATUS current
    DESCRIPTION
        "Parameter 'ICMP_type' in event ICMP.5"
    ::= { icmpEventObjects5 1 }

icmp5_ICMP_code OBJECT-TYPE
    SYNTAX Integer32
    MAX-ACCESS accessible-for-notify
    STATUS current
    DESCRIPTION
        "Parameter 'ICMP_code' in event ICMP.5"
    ::= { icmpEventObjects5 2 }

icmp5_source_IP_address OBJECT-TYPE
    SYNTAX IpAddress
    MAX-ACCESS accessible-for-notify
    STATUS current
    DESCRIPTION
        "Parameter 'source_IP_address' in event ICMP.5"
    ::= { icmpEventObjects5 3 }

icmp5_destination_IP_address OBJECT-TYPE
    SYNTAX IpAddress
    MAX-ACCESS accessible-for-notify
    STATUS current
    DESCRIPTION
        "Parameter 'destination_IP_address' in event ICMP.5"
    ::= { icmpEventObjects5 4 }

icmpEventObjects6 OBJECT-IDENTITY
    STATUS current
    DESCRIPTION
        "Event ICMP.6
        An ICMP message came in with a type that is not legal."
    ::= { icmpEventsGroup 6 }

icmp6_ICMP_type OBJECT-TYPE
    SYNTAX Integer32
    MAX-ACCESS accessible-for-notify
    STATUS current
    DESCRIPTION
        "Parameter 'ICMP_type' in event ICMP.6"
    ::= { icmpEventObjects6 1 }

icmp6_ICMP_code OBJECT-TYPE
    SYNTAX Integer32
    MAX-ACCESS accessible-for-notify
    STATUS current
    DESCRIPTION
        "Parameter 'ICMP_code' in event ICMP.6"
    ::= { icmpEventObjects6 2 }

icmp6_source_IP_address OBJECT-TYPE
    SYNTAX IpAddress
    MAX-ACCESS accessible-for-notify
    STATUS current
    DESCRIPTION
        "Parameter 'source_IP_address' in event ICMP.6"
    ::= { icmpEventObjects6 3 }

icmp6_destination_IP_address OBJECT-TYPE
    SYNTAX IpAddress
    MAX-ACCESS accessible-for-notify
    STATUS current
    DESCRIPTION
        "Parameter 'destination_IP_address' in event ICMP.6"
    ::= { icmpEventObjects6 4 }

icmpEventObjects7 OBJECT-IDENTITY
    STATUS current
    DESCRIPTION
        "Event ICMP.7
        An ICMP Address Mask Request was received from the source host by
        the router."
    ::= { icmpEventsGroup 7 }

icmp7_source_IP_address OBJECT-TYPE
    SYNTAX IpAddress
    MAX-ACCESS accessible-for-notify
    STATUS current
    DESCRIPTION
        "Parameter 'source_IP_address' in event ICMP.7"
    ::= { icmpEventObjects7 1 }

icmp7_destination_IP_address OBJECT-TYPE
    SYNTAX IpAddress
    MAX-ACCESS accessible-for-notify
    STATUS current
    DESCRIPTION
        "Parameter 'destination_IP_address' in event ICMP.7"
    ::= { icmpEventObjects7 2 }

icmpEventObjects8 OBJECT-IDENTITY
    STATUS current
    DESCRIPTION
        "Event ICMP.8
        An ICMP Address Mask Reply was received from the source host by
        the router."
    ::= { icmpEventsGroup 8 }

icmp8_source_IP_address OBJECT-TYPE
    SYNTAX IpAddress
    MAX-ACCESS accessible-for-notify
    STATUS current
    DESCRIPTION
        "Parameter 'source_IP_address' in event ICMP.8"
    ::= { icmpEventObjects8 1 }

icmp8_destination_IP_address OBJECT-TYPE
    SYNTAX IpAddress
    MAX-ACCESS accessible-for-notify
    STATUS current
    DESCRIPTION
        "Parameter 'destination_IP_address' in event ICMP.8"
    ::= { icmpEventObjects8 2 }

icmpEventObjects10 OBJECT-IDENTITY
    STATUS current
    DESCRIPTION
        "Event ICMP.10
        An incoming address mask request on an interface which contained more
        than one IP source address contained a destination address which could
        not be localized to one of the addresses, so no reply could be
        generated."
    ::= { icmpEventsGroup 10 }

icmp10_source_IP_address OBJECT-TYPE
    SYNTAX IpAddress
    MAX-ACCESS accessible-for-notify
    STATUS current
    DESCRIPTION
        "Parameter 'source_IP_address' in event ICMP.10"
    ::= { icmpEventObjects10 1 }

icmp10_destination_IP_address OBJECT-TYPE
    SYNTAX IpAddress
    MAX-ACCESS accessible-for-notify
    STATUS current
    DESCRIPTION
        "Parameter 'destination_IP_address' in event ICMP.10"
    ::= { icmpEventObjects10 2 }

icmpEventObjects11 OBJECT-IDENTITY
    STATUS current
    DESCRIPTION
        "Event ICMP.11
        An outgoing reply packet was dropped as the result of some
        problem in the router."
    ::= { icmpEventsGroup 11 }

icmp11_code OBJECT-TYPE
    SYNTAX Integer32
    MAX-ACCESS accessible-for-notify
    STATUS current
    DESCRIPTION
        "Parameter 'code' in event ICMP.11"
    ::= { icmpEventObjects11 1 }

icmp11_interface OBJECT-TYPE
    SYNTAX DisplayString
    MAX-ACCESS accessible-for-notify
    STATUS current
    DESCRIPTION
        "Parameter 'interface' in event ICMP.11"
    ::= { icmpEventObjects11 2 }

icmpEventObjects12 OBJECT-IDENTITY
    STATUS current
    DESCRIPTION
        "Event ICMP.12
        The router is sending an ICMP Redirect, advising a source host on
        a directly connected network that there is a better first hop router
        for this traffic."
    ::= { icmpEventsGroup 12 }

icmp12_source_IP_address OBJECT-TYPE
    SYNTAX IpAddress
    MAX-ACCESS accessible-for-notify
    STATUS current
    DESCRIPTION
        "Parameter 'source_IP_address' in event ICMP.12"
    ::= { icmpEventObjects12 1 }

icmp12_destination_IP_address OBJECT-TYPE
    SYNTAX IpAddress
    MAX-ACCESS accessible-for-notify
    STATUS current
    DESCRIPTION
        "Parameter 'destination_IP_address' in event ICMP.12"
    ::= { icmpEventObjects12 2 }

icmp12_new_next_hop_IP_address OBJECT-TYPE
    SYNTAX IpAddress
    MAX-ACCESS accessible-for-notify
    STATUS current
    DESCRIPTION
        "Parameter 'new_next_hop_IP_address' in event ICMP.12"
    ::= { icmpEventObjects12 3 }

icmpEventObjects13 OBJECT-IDENTITY
    STATUS current
    DESCRIPTION
        "Event ICMP.13
        The router is sending an ICMP Parameter Problem message, for an
        unspecified problem at the given offset."
    ::= { icmpEventsGroup 13 }

icmp13_problem_offset OBJECT-TYPE
    SYNTAX Integer32
    MAX-ACCESS accessible-for-notify
    STATUS current
    DESCRIPTION
        "Parameter 'problem_offset' in event ICMP.13"
    ::= { icmpEventObjects13 1 }

icmp13_source_IP_address OBJECT-TYPE
    SYNTAX IpAddress
    MAX-ACCESS accessible-for-notify
    STATUS current
    DESCRIPTION
        "Parameter 'source_IP_address' in event ICMP.13"
    ::= { icmpEventObjects13 2 }

icmp13_destination_IP_address OBJECT-TYPE
    SYNTAX IpAddress
    MAX-ACCESS accessible-for-notify
    STATUS current
    DESCRIPTION
        "Parameter 'destination_IP_address' in event ICMP.13"
    ::= { icmpEventObjects13 3 }

icmpEventObjects14 OBJECT-IDENTITY
    STATUS current
    DESCRIPTION
        "Event ICMP.14
        The router is sending an ICMP packet of the specified type about
        a packet from the source host to the destination."
    ::= { icmpEventsGroup 14 }

icmp14_ICMP_type OBJECT-TYPE
    SYNTAX Integer32
    MAX-ACCESS accessible-for-notify
    STATUS current
    DESCRIPTION
        "Parameter 'ICMP_type' in event ICMP.14"
    ::= { icmpEventObjects14 1 }

icmp14_ICMP_code OBJECT-TYPE
    SYNTAX Integer32
    MAX-ACCESS accessible-for-notify
    STATUS current
    DESCRIPTION
        "Parameter 'ICMP_code' in event ICMP.14"
    ::= { icmpEventObjects14 2 }

icmp14_source_IP_address OBJECT-TYPE
    SYNTAX IpAddress
    MAX-ACCESS accessible-for-notify
    STATUS current
    DESCRIPTION
        "Parameter 'source_IP_address' in event ICMP.14"
    ::= { icmpEventObjects14 3 }

icmp14_destination_IP_address OBJECT-TYPE
    SYNTAX IpAddress
    MAX-ACCESS accessible-for-notify
    STATUS current
    DESCRIPTION
        "Parameter 'destination_IP_address' in event ICMP.14"
    ::= { icmpEventObjects14 4 }

icmpEventObjects15 OBJECT-IDENTITY
    STATUS current
    DESCRIPTION
        "Event ICMP.15
        This message is generated when an ICMP packet's indicated header length
        is below the minimum possible length for an ICMP packet."
    ::= { icmpEventsGroup 15 }

icmp15_header_length OBJECT-TYPE
    SYNTAX Integer32
    MAX-ACCESS accessible-for-notify
    STATUS current
    DESCRIPTION
        "Parameter 'header_length' in event ICMP.15"
    ::= { icmpEventObjects15 1 }

icmp15_source_ip_address OBJECT-TYPE
    SYNTAX IpAddress
    MAX-ACCESS accessible-for-notify
    STATUS current
    DESCRIPTION
        "Parameter 'source_ip_address' in event ICMP.15"
    ::= { icmpEventObjects15 2 }

icmpEventObjects16 OBJECT-IDENTITY
    STATUS current
    DESCRIPTION
        "Event ICMP.16
        A redirect has been received, changing the next hop for the given
        destination. Redirects are only processed when running in host mode."
    ::= { icmpEventsGroup 16 }

icmp16_current_next_hop OBJECT-TYPE
    SYNTAX IpAddress
    MAX-ACCESS accessible-for-notify
    STATUS current
    DESCRIPTION
        "Parameter 'current_next_hop' in event ICMP.16"
    ::= { icmpEventObjects16 1 }

icmp16_IP_destination OBJECT-TYPE
    SYNTAX IpAddress
    MAX-ACCESS accessible-for-notify
    STATUS current
    DESCRIPTION
        "Parameter 'IP_destination' in event ICMP.16"
    ::= { icmpEventObjects16 2 }

icmp16_better_next_hop OBJECT-TYPE
    SYNTAX IpAddress
    MAX-ACCESS accessible-for-notify
    STATUS current
    DESCRIPTION
        "Parameter 'better_next_hop' in event ICMP.16"
    ::= { icmpEventObjects16 3 }

icmpEventObjects17 OBJECT-IDENTITY
    STATUS current
    DESCRIPTION
        "Event ICMP.17
        A redirect was received from a router, but rejected for the
        specified reason."
    ::= { icmpEventsGroup 17 }

icmp17_gateway_address OBJECT-TYPE
    SYNTAX IpAddress
    MAX-ACCESS accessible-for-notify
    STATUS current
    DESCRIPTION
        "Parameter 'gateway_address' in event ICMP.17"
    ::= { icmpEventObjects17 1 }

icmp17_reason OBJECT-TYPE
    SYNTAX DisplayString
    MAX-ACCESS accessible-for-notify
    STATUS current
    DESCRIPTION
        "Parameter 'reason' in event ICMP.17"
    ::= { icmpEventObjects17 2 }

icmpEventObjects18 OBJECT-IDENTITY
    STATUS current
    DESCRIPTION
        "Event ICMP.18
        An ICMP Router Advertisement (Gateway Discovery) message has
        been received from the specified router."
    ::= { icmpEventsGroup 18 }

icmp18_router_address OBJECT-TYPE
    SYNTAX IpAddress
    MAX-ACCESS accessible-for-notify
    STATUS current
    DESCRIPTION
        "Parameter 'router_address' in event ICMP.18"
    ::= { icmpEventObjects18 1 }

icmpEventObjects19 OBJECT-IDENTITY
    STATUS current
    DESCRIPTION
        "Event ICMP.19
        An ICMP Router Advertisement (Gateway Discovery) message has been
        received from the specified router, but was rejected for
        the specified reason."
    ::= { icmpEventsGroup 19 }

icmp19_gateway_address OBJECT-TYPE
    SYNTAX IpAddress
    MAX-ACCESS accessible-for-notify
    STATUS current
    DESCRIPTION
        "Parameter 'gateway_address' in event ICMP.19"
    ::= { icmpEventObjects19 1 }

icmp19_reason OBJECT-TYPE
    SYNTAX DisplayString
    MAX-ACCESS accessible-for-notify
    STATUS current
    DESCRIPTION
        "Parameter 'reason' in event ICMP.19"
    ::= { icmpEventObjects19 2 }

icmpEventObjects20 OBJECT-IDENTITY
    STATUS current
    DESCRIPTION
        "Event ICMP.20
        The router has received an ICMP message of the specified type from
        the source host."
    ::= { icmpEventsGroup 20 }

icmp20_ICMP_type OBJECT-TYPE
    SYNTAX Integer32
    MAX-ACCESS accessible-for-notify
    STATUS current
    DESCRIPTION
        "Parameter 'ICMP_type' in event ICMP.20"
    ::= { icmpEventObjects20 1 }

icmp20_ICMP_code OBJECT-TYPE
    SYNTAX Integer32
    MAX-ACCESS accessible-for-notify
    STATUS current
    DESCRIPTION
        "Parameter 'ICMP_code' in event ICMP.20"
    ::= { icmpEventObjects20 2 }

icmp20_source_IP_address OBJECT-TYPE
    SYNTAX IpAddress
    MAX-ACCESS accessible-for-notify
    STATUS current
    DESCRIPTION
        "Parameter 'source_IP_address' in event ICMP.20"
    ::= { icmpEventObjects20 3 }

icmp20_destination_IP_address OBJECT-TYPE
    SYNTAX IpAddress
    MAX-ACCESS accessible-for-notify
    STATUS current
    DESCRIPTION
        "Parameter 'destination_IP_address' in event ICMP.20"
    ::= { icmpEventObjects20 4 }

icmpEventObjects21 OBJECT-IDENTITY
    STATUS current
    DESCRIPTION
        "Event ICMP.21
        A redirect message has been filtered at specified interface."
    ::= { icmpEventsGroup 21 }

icmp21_interface OBJECT-TYPE
    SYNTAX DisplayString
    MAX-ACCESS accessible-for-notify
    STATUS current
    DESCRIPTION
        "Parameter 'interface' in event ICMP.21"
    ::= { icmpEventObjects21 1 }

icmpEventObjects22 OBJECT-IDENTITY
    STATUS current
    DESCRIPTION
        "Event ICMP.22
        An unreachable message has been filtered at specified interface."
    ::= { icmpEventsGroup 22 }

icmp22_interface OBJECT-TYPE
    SYNTAX DisplayString
    MAX-ACCESS accessible-for-notify
    STATUS current
    DESCRIPTION
        "Parameter 'interface' in event ICMP.22"
    ::= { icmpEventObjects22 1 }


icmpNotification1 NOTIFICATION-TYPE
    OBJECTS { 
              icmp1_received_checksum, 
              icmp1_good_checksum,
              icmp1_source_IP_address,
              icmp1_destination_IP_address 
            }
    STATUS current
    DESCRIPTION
        "Notification of Event ICMP.1

        Message: 'bad ICMP checksum 0x$1 received (expected 0x$2) in packet from $3 to $4'

        Parameters list:
              $1: icmp1_received_checksum
              $2: icmp1_good_checksum
              $3: icmp1_source_IP_address
              $4: icmp1_destination_IP_address

        A bad ICMP checksum was detected in an incoming ICMP message. The
        received checksum is displayed, together with the value that the checkum
        should have had. The received packet is discarded."
    ::= { icmpNotificationsPrefix 1 }

icmpNotification2 NOTIFICATION-TYPE
    OBJECTS { 
              icmp2_source_IP_address, 
              icmp2_destination_IP_address 
            }
    STATUS current
    DESCRIPTION
        "Notification of Event ICMP.2

        Message: 'echo request packet received from $1 to $2'

        Parameters list:
              $1: icmp2_source_IP_address
              $2: icmp2_destination_IP_address

        An ICMP Echo Request was received from the source host by the router.
        Note that an ICMP Echo Request is only recognized when it comes in
        over the interface with the address the packet is addressed to."
    ::= { icmpNotificationsPrefix 2 }

icmpNotification3 NOTIFICATION-TYPE
    OBJECTS { 
              icmp3_source_IP_address, 
              icmp3_destination_IP_address 
            }
    STATUS current
    DESCRIPTION
        "Notification of Event ICMP.3

        Message: 'echo reply packet received from $1 to $2'

        Parameters list:
              $1: icmp3_source_IP_address
              $2: icmp3_destination_IP_address

        An ICMP Echo Reply was received from the source host by the router.
        This is a slightly suspicious event, since the router does not
        normally send ICMP Echo Requests."
    ::= { icmpNotificationsPrefix 3 }

icmpNotification4 NOTIFICATION-TYPE
    OBJECTS { 
              icmp4_ICMP_type, 
              icmp4_ICMP_code,
              icmp4_source_IP_address,
              icmp4_destination_IP_address 
            }
    STATUS current
    DESCRIPTION
        "Notification of Event ICMP.4

        Message: 'unhandled message type $1 $2 from $3 to $4'

        Parameters list:
              $1: icmp4_ICMP_type
              $2: icmp4_ICMP_code
              $3: icmp4_source_IP_address
              $4: icmp4_destination_IP_address

        An ICMP message came in with a type that the router software does
        not handle."
    ::= { icmpNotificationsPrefix 4 }

icmpNotification5 NOTIFICATION-TYPE
    OBJECTS { 
              icmp5_ICMP_type, 
              icmp5_ICMP_code,
              icmp5_source_IP_address,
              icmp5_destination_IP_address 
            }
    STATUS current
    DESCRIPTION
        "Notification of Event ICMP.5

        Message: 'unhandled broadcast message type $1 $2 from $3 to $4'

        Parameters list:
              $1: icmp5_ICMP_type
              $2: icmp5_ICMP_code
              $3: icmp5_source_IP_address
              $4: icmp5_destination_IP_address

        A broadcast ICMP message came in with a type that the router software
        does not handle."
    ::= { icmpNotificationsPrefix 5 }

icmpNotification6 NOTIFICATION-TYPE
    OBJECTS { 
              icmp6_ICMP_type, 
              icmp6_ICMP_code,
              icmp6_source_IP_address,
              icmp6_destination_IP_address 
            }
    STATUS current
    DESCRIPTION
        "Notification of Event ICMP.6

        Message: 'bad message type $1 $2 from $3 to $4'

        Parameters list:
              $1: icmp6_ICMP_type
              $2: icmp6_ICMP_code
              $3: icmp6_source_IP_address
              $4: icmp6_destination_IP_address

        An ICMP message came in with a type that is not legal."
    ::= { icmpNotificationsPrefix 6 }

icmpNotification7 NOTIFICATION-TYPE
    OBJECTS { 
              icmp7_source_IP_address, 
              icmp7_destination_IP_address 
            }
    STATUS current
    DESCRIPTION
        "Notification of Event ICMP.7

        Message: 'address mask request received from $1 to $2'

        Parameters list:
              $1: icmp7_source_IP_address
              $2: icmp7_destination_IP_address

        An ICMP Address Mask Request was received from the source host by
        the router."
    ::= { icmpNotificationsPrefix 7 }

icmpNotification8 NOTIFICATION-TYPE
    OBJECTS { 
              icmp8_source_IP_address, 
              icmp8_destination_IP_address 
            }
    STATUS current
    DESCRIPTION
        "Notification of Event ICMP.8

        Message: 'address mask reply received from $1 to $2'

        Parameters list:
              $1: icmp8_source_IP_address
              $2: icmp8_destination_IP_address

        An ICMP Address Mask Reply was received from the source host by
        the router."
    ::= { icmpNotificationsPrefix 8 }

icmpNotification9 NOTIFICATION-TYPE
    STATUS current
    DESCRIPTION
        "Notification of Event ICMP.9

        Message: 'heap memory or packet buffer not available'

        Internal resources in the router necessary to reply to the incoming
        message were unavailable."
    ::= { icmpNotificationsPrefix 9 }

icmpNotification10 NOTIFICATION-TYPE
    OBJECTS { 
              icmp10_source_IP_address, 
              icmp10_destination_IP_address 
            }
    STATUS current
    DESCRIPTION
        "Notification of Event ICMP.10

        Message: 'ambiguous address mask request received from $1 to $2'

        Parameters list:
              $1: icmp10_source_IP_address
              $2: icmp10_destination_IP_address

        An incoming address mask request on an interface which contained more
        than one IP source address contained a destination address which could
        not be localized to one of the addresses, so no reply could be
        generated."
    ::= { icmpNotificationsPrefix 10 }

icmpNotification11 NOTIFICATION-TYPE
    OBJECTS { 
              icmp11_code, 
              icmp11_interface 
            }
    STATUS current
    DESCRIPTION
        "Notification of Event ICMP.11

        Message: 'error $1 sending packet to interface $2'

        Parameters list:
              $1: icmp11_code
              $2: icmp11_interface

        An outgoing reply packet was dropped as the result of some
        problem in the router."
    ::= { icmpNotificationsPrefix 11 }

icmpNotification12 NOTIFICATION-TYPE
    OBJECTS { 
              icmp12_source_IP_address, 
              icmp12_destination_IP_address,
              icmp12_new_next_hop_IP_address 
            }
    STATUS current
    DESCRIPTION
        "Notification of Event ICMP.12

        Message: 'sending redirect for packet from $1 to $2 to use router $3'

        Parameters list:
              $1: icmp12_source_IP_address
              $2: icmp12_destination_IP_address
              $3: icmp12_new_next_hop_IP_address

        The router is sending an ICMP Redirect, advising a source host on
        a directly connected network that there is a better first hop router
        for this traffic."
    ::= { icmpNotificationsPrefix 12 }

icmpNotification13 NOTIFICATION-TYPE
    OBJECTS { 
              icmp13_problem_offset, 
              icmp13_source_IP_address,
              icmp13_destination_IP_address 
            }
    STATUS current
    DESCRIPTION
        "Notification of Event ICMP.13

        Message: 'sending parameter problem message problem offset $1 for packet from $2 to $3'

        Parameters list:
              $1: icmp13_problem_offset
              $2: icmp13_source_IP_address
              $3: icmp13_destination_IP_address

        The router is sending an ICMP Parameter Problem message, for an
        unspecified problem at the given offset."
    ::= { icmpNotificationsPrefix 13 }

icmpNotification14 NOTIFICATION-TYPE
    OBJECTS { 
              icmp14_ICMP_type, 
              icmp14_ICMP_code,
              icmp14_source_IP_address,
              icmp14_destination_IP_address 
            }
    STATUS current
    DESCRIPTION
        "Notification of Event ICMP.14

        Message: 'sending packet type $1 code $2 for packet from $3 to $4'

        Parameters list:
              $1: icmp14_ICMP_type
              $2: icmp14_ICMP_code
              $3: icmp14_source_IP_address
              $4: icmp14_destination_IP_address

        The router is sending an ICMP packet of the specified type about
        a packet from the source host to the destination."
    ::= { icmpNotificationsPrefix 14 }

icmpNotification15 NOTIFICATION-TYPE
    OBJECTS { 
              icmp15_header_length, 
              icmp15_source_ip_address 
            }
    STATUS current
    DESCRIPTION
        "Notification of Event ICMP.15

        Message: 'short ICMP packet $1 received in packet from $2'

        Parameters list:
              $1: icmp15_header_length
              $2: icmp15_source_ip_address

        This message is generated when an ICMP packet's indicated header length
        is below the minimum possible length for an ICMP packet."
    ::= { icmpNotificationsPrefix 15 }

icmpNotification16 NOTIFICATION-TYPE
    OBJECTS { 
              icmp16_current_next_hop, 
              icmp16_IP_destination,
              icmp16_better_next_hop 
            }
    STATUS current
    DESCRIPTION
        "Notification of Event ICMP.16

        Message: '$1 has redirected traffic for $2 to $3'

        Parameters list:
              $1: icmp16_current_next_hop
              $2: icmp16_IP_destination
              $3: icmp16_better_next_hop

        A redirect has been received, changing the next hop for the given
        destination. Redirects are only processed when running in host mode."
    ::= { icmpNotificationsPrefix 16 }

icmpNotification17 NOTIFICATION-TYPE
    OBJECTS { 
              icmp17_gateway_address, 
              icmp17_reason 
            }
    STATUS current
    DESCRIPTION
        "Notification of Event ICMP.17

        Message: 'Redirect received from $1 was bad for the reason: $2'

        Parameters list:
              $1: icmp17_gateway_address
              $2: icmp17_reason

        A redirect was received from a router, but rejected for the
        specified reason."
    ::= { icmpNotificationsPrefix 17 }

icmpNotification18 NOTIFICATION-TYPE
    OBJECTS { 
              icmp18_router_address 
            }
    STATUS current
    DESCRIPTION
        "Notification of Event ICMP.18

        Message: 'Router advertisement received from $1'

        Parameters list:
              $1: icmp18_router_address

        An ICMP Router Advertisement (Gateway Discovery) message has
        been received from the specified router."
    ::= { icmpNotificationsPrefix 18 }

icmpNotification19 NOTIFICATION-TYPE
    OBJECTS { 
              icmp19_gateway_address, 
              icmp19_reason 
            }
    STATUS current
    DESCRIPTION
        "Notification of Event ICMP.19

        Message: 'Router advertisement received from $1 was bad for the reason: $2'

        Parameters list:
              $1: icmp19_gateway_address
              $2: icmp19_reason

        An ICMP Router Advertisement (Gateway Discovery) message has been
        received from the specified router, but was rejected for
        the specified reason."
    ::= { icmpNotificationsPrefix 19 }

icmpNotification20 NOTIFICATION-TYPE
    OBJECTS { 
              icmp20_ICMP_type, 
              icmp20_ICMP_code,
              icmp20_source_IP_address,
              icmp20_destination_IP_address 
            }
    STATUS current
    DESCRIPTION
        "Notification of Event ICMP.20

        Message: 'received message type $1 $2 from $3 to $4'

        Parameters list:
              $1: icmp20_ICMP_type
              $2: icmp20_ICMP_code
              $3: icmp20_source_IP_address
              $4: icmp20_destination_IP_address

        The router has received an ICMP message of the specified type from
        the source host."
    ::= { icmpNotificationsPrefix 20 }

icmpNotification21 NOTIFICATION-TYPE
    OBJECTS { 
              icmp21_interface 
            }
    STATUS current
    DESCRIPTION
        "Notification of Event ICMP.21

        Message: 'redirect message filtered at interface $1'

        Parameters list:
              $1: icmp21_interface

        A redirect message has been filtered at specified interface."
    ::= { icmpNotificationsPrefix 21 }

icmpNotification22 NOTIFICATION-TYPE
    OBJECTS { 
              icmp22_interface 
            }
    STATUS current
    DESCRIPTION
        "Notification of Event ICMP.22

        Message: 'unreachable message filtered at interface $1'

        Parameters list:
              $1: icmp22_interface

        An unreachable message has been filtered at specified interface."
    ::= { icmpNotificationsPrefix 22 }


END
